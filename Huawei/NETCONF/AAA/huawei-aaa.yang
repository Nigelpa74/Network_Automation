/*
Copyright (C) 2020-2025 Huawei Technologies Co., Ltd. All rights reserved.
*/
module huawei-aaa {
  yang-version 1.1;
  namespace "urn:huawei:yang:huawei-aaa";
  prefix aaa;
  import huawei-hwtacacs {
    prefix hwtacacs;
  }
  import huawei-radius {
    prefix radius;
  }
  import huawei-acl {
    prefix acl;
  }
  import huawei-time-range {
    prefix timerange;
  }
  import huawei-extension {
    prefix ext;
  }
  import ietf-inet-types {
    prefix inet;
  }
  import ietf-yang-types {
    prefix yang;
  }
  import huawei-pub-type {
    prefix pub-type;
  }
  include huawei-aaa-type;
  include huawei-aaa-lam;
  organization
    "Huawei Technologies Co., Ltd.";
  contact
    "Huawei Industrial Base
    Bantian, Longgang
    Shenzhen 518129
    People's Republic of China
    Website: http://www.huawei.com
    Email: support@huawei.com";
  description
    "Security management, which includes the management on authentication, authorization, accounting, domains, and users.";
  revision 2025-08-28 {
    description
      "Add container of syslog-restrain.";
    reference
      "Huawei private.";
  }
  revision 2025-08-15 {
    description
      "Modify the maximum length of change-current-password node.";
    reference
      "Huawei private.";
 }
  revision 2025-06-24 {
    description
      "Modify yang-version 1.1.";
    reference
      "Huawei private.";
  }
  revision 2025-06-05 {
    description
      "Add leaf of password similar-to-name-check-type and modify spelling of words.";
    reference
      "Huawei private.";
  }
  revision 2025-05-12 {
    description
      "Add container of global-user-policy.";
    reference
      "Huawei private.";
  }
  revision 2025-03-28 {
    description
      "Modify the length of the access user name.";
    reference
      "Huawei private.";
  }
  revision 2025-03-10 {
    description
      "Add aaa-lam leaf of virtual-ip and container of bind-address.";
    reference
      "Huawei private.";
  }
  revision 2025-01-23 {
    description
      "Modify description in the leaf of index.";
    reference
      "Huawei private.";
  }
  revision 2024-12-07 {
    description
      "Modify the container access-codes.";
    reference
      "Huawei private.";
  }
  revision 2024-11-28 {
    description
      "Add leaf of private user.";
    reference
      "Huawei private.";
  }
  revision 2024-11-19 {
    description
      "Add leaf of ou UCL group.";
    reference
      "Huawei private.";
  }
  revision 2024-11-01 {
    description
      "Synchronize code.";
    reference
      "Huawei private.";
  }
  revision 2024-08-24 {
    description
      "Add access code configuration.";
    reference
      "Huawei private.";
  }
  revision 2024-07-24 {
    description
      "Modify pattern of authen-scheme-name/author-scheme-name/acct-scheme-name.";
    reference
      "Huawei private.";
  }
  revision 2024-06-26 {
    description
      "Add leaf as-mac.";
    reference
      "Huawei private.";
  }
  revision 2024-05-31 {
    description
      "Add must condition for end-life-date and time-range.";
    reference
      "Huawei private.";
  }
  revision 2024-05-28 {
    description
      "Add must condition for user/name. Modify the type of time-range.";
    reference
      "Huawei private.";
  }
  revision 2024-05-25 {
    description
      "Add must condition for complexity-check-four.";
    reference
      "Huawei private.";
  }
  revision 2024-05-24 {
    description
      "Add must condition for password. Modify the must condition of password-type.";
    reference
      "Huawei private.";
  }
  revision 2024-05-13 {
    description
      "Check the spelling of words.";
    reference
      "Huawei private.";
  }
  revision 2024-05-10 {
    description
      "Add two RPC nodes for re-authorization, and add a container node for querying authorization information.";
    reference
      "Huawei private.";
  }
  revision 2024-05-08 {
    description
      "Delete rpc cut-access-user mandatory.";
    reference
      "Huawei private.";
  }
  revision 2024-03-12 {
    description
      "Add a node for querying the user creation time.";
    reference
      "Huawei private.";
  }
  revision 2023-12-22 {
    description
      "Add several nodes for NAC AAA.";
    reference
      "Huawei private.";
  }
  revision 2023-08-31 {
    description
      "Modify recording-scheme-name.";
    reference
      "Huawei private.";
  }
  revision 2023-02-13 {
    description
      "Add leaf up-bytes-v6, down-bytes-v6. Modify leaf-list access-type.";
    reference
      "Huawei private.";
  }
  revision 2022-12-15 {
    description
      "Add leaf-list account-separate.";
    reference
      "Huawei private.";
  }    
  revision 2022-12-09 {
    description
      "Add leaf upward-bytes, leaf downward-bytes, leaf upward-speed, leaf downward-speed, leaf duration-auth to list access-user-qry.";
    reference
      "Huawei private.";
  }
  revision 2022-05-19 {
    description
      "Modify test-server-connectivity.";
    reference
      "Huawei private.";
  }
  revision 2022-04-02 {
    description
      "Add leaf-list IPv6 node.";
    reference
      "Huawei private.";
  }
  revision 2022-03-31 {
    description
      "Modify path of authen-mode and author-mode.";
    reference
      "Huawei private.";
  }
  revision 2022-01-05 {
    description
      "Add container remote-access-user-policy.";
    reference
      "Huawei private.";
  }
  revision 2021-12-10 {
    description
      "Modify radius-server-template type from string to leafref.";
    reference
      "Huawei private.";
  }
  revision 2021-09-09 {
    description
      "Add typedef authen-change, node authentication-change, node alive-user-statistics, node alive-user-qrys.";
    reference
      "Huawei private.";
  }
  revision 2021-07-15 {
    description
      "Delete typedef authen-change, node is-authen-change, node alive-user-statistics, node alive-user-qrys. Add node access-user-qrys, node access-user-records.";
    reference
      "Huawei private.";
  }
  revision 2021-06-23 {
    description
      "Modify path of include-user-group-name.";
    reference
      "Huawei private.";
  }
  revision 2021-03-17 {
    description
      "Add read|write|execute|debug node of list user-group-task-group-map.";
    reference
      "Huawei private.";
  }
  revision 2021-01-28 {
    description
      "Add read|write|execute|debug node of list user-group-task-group-map.";
    reference
      "Huawei private.";
  }
  revision 2021-01-20 {
    description
      "Add no-response-authorization node.";
    reference
      "Huawei private.";
  }
  revision 2020-07-01 {
    description
      "Add node constraint information.";
    reference
      "Huawei private.";
  }
  revision 2020-06-17 {
    description
      "Add management-user-qrys node.";
    reference
      "Huawei private.";
  }
  revision 2020-03-02 {
    description
      "Init revision.";
    reference
      "Huawei private.";
  }
  typedef authen-change {
    type enumeration {
      enum "none" {
        value 0;
        description
          "Change authen mode (none).";
      }
      enum "hwtacacs-local" {
        value 1;
        description
          "Tacs authentication fails, switch to local.";
      }
    }
    description
      "Authen change switch.";
  }
  container aaa {
    description
      "Security management, which includes the management on authentication, authorization, accounting, domains, and users.";
    container tasks {
      config false;
      description
        "List of tasks.";
      list task {
        key "name";
        config false;
        description
          "Statistics of minimum unit for dividing rights on an NE. Tasks can be determined when an NE is delivered. Tasks cannot be customized.";
        leaf name {
          type string {
            length "1..32";
          }
          config false;
          description
            "Name of a task, it is not case sensitive.";
        }
      }
    }
    container syslog-restrain {
      description
        "Configure access user syslog-restrain.";
      leaf enable {
          type boolean;
          default "false";
          description
            "Enable/disable syslog restrain function.";
        }
      leaf period {
        type int32 {
          range "60..604800";
        }
        units "s";
        default "300";
        description
          "Access user syslog-restrain period.";
      }
    }
    container access-codes {
      description
        "List of access code.";
      list access-code {
        key "index";
        max-elements "1024";
        description
          "Configure one access-code.";
        leaf index {
          type uint32 {
            range "1..4096";
          }
          mandatory true;
          description
            "One password is related to a unique index, ranging from 1 to 4096.";
        }
        leaf password {
          type pub-type:password-extend {
            length "4..148";
          }
          mandatory true;
          description
            "STRING<4-16>/<128-148> Unencrypted/Encrypted access code, The UNENCRYPTED access code should only be numbers, uppercase or lowercase letters.";
        }
        leaf expire-date {
          type pub-type:date;
          mandatory true;
          description
            "Select a date within the year 2000 to 2099 and later than the current time.";
        }
        leaf expire-hour {
          type uint8 {
            range "0..23";
          }
          default "12";
          description
            "Access-code expired hour.";
        }
        leaf code-description {
          type string {
            length "1..16";
            pattern "[A-Za-z0-9-]+";
          }
          description
            "Access-code description, it should only be numbers,uppercase or lowercase letters and '-'";
        }
      }
    }
    container task-groups {
      description
        "List of task groups.";
      list task-group {
        key "name";
        description
          "Configure a collection of certain tasks. The default task groups cannot be removed and are set in the system before the NE delivery.";
        leaf name {
          type string {
            length "1..32";
            pattern "[^A-Z/\\*\":?<>|]+";
          }
          ext:case-sensitivity lower-only;
          description
            "Name of a task group.";
        }
        container task-group-include-maps {
          description
            "List of the task groups included in a main task group.";
          list task-group-include-map {
            key "include-task-group-name";
            max-elements "1";
            description
              "Configure task group included in a main task group.";
            leaf include-task-group-name {
              type leafref {
                path "../../../name";
              }
              must "(../../../name!=../include-task-group-name)";
              description
                "Name of included task group, it is not case sensitive.";
            }
          }
        }
        container task-group-task-maps {
          description
            "List of the tasks included in a task group.";
          list task-group-task-map {
            key "task-name";
            description
              "Configure task in a task group. The default task group cannot be modified.";
            leaf task-name {
              type string {
                length "1..32";
                pattern "[^A-Z]+";
              }
              ext:case-sensitivity lower-only;
              must "(../write='enable' or ../execute='enable' or ../debug='enable' or ../read='enable')";
              description
                "Name of a task. It must be an existing task.";
            }
            leaf read {
              type aaa-enable-type;
              must "not(../write='disable' and ../execute='disable' and ../debug='disable') or (../write='disable' and ../execute='disable' and ../debug='disable' and ../read!=../write)";
              default "disable";
              description
                "To determine whether a task has the read right.";
            }
            leaf write {
              type aaa-enable-type;
              default "disable";
              description
                "To determine whether a task has the write right.";
            }
            leaf execute {
              type aaa-enable-type;
              default "disable";
              description
                "To determine whether a task has the operation right.";
            }
            leaf debug {
              type aaa-enable-type;
              default "disable";
              description
                "To determine whether a task has the debug right.";
            }
          }
        }
      }
    }
    container user-groups {
      description
        "List of user groups.";
      list user-group {
        key "name";
        ext:generated-by "system" {
          ext:filter "name='manage-ug' or name='system-ug' or name='monitor-ug' or name='visit-ug'";
          description
            "The default user-group is generated by system.";
        }
        ext:operation-exclude "delete" {
          ext:filter "name='manage-ug' or name='system-ug' or name='monitor-ug' or name='visit-ug'";
          description
            "The default user-group cannot be deleted.";
        }
        description
          "Configure a collection of certain users. Certain default user groups are set before an NE is delivered and cannot be deleted.";
        leaf name {
          type string {
            length "1..32";
            pattern "[^A-Z/\\*\":?<>|]+";
          }
          ext:case-sensitivity lower-only;
          description
            "Name of a user group.";
        }
        container user-group-task-group-maps {
          description
            "List of the task groups included in a user group.";
          list user-group-task-group-map {
            key "task-group-name";
            description
              "Configure task group in a user group.";
            leaf task-group-name {
              type leafref {
                path "../../../../../task-groups/task-group/name";
              }
              must "(../execute='enable' or ../debug='enable' or ../read='enable' or ../write='enable')";
              description
                "Name of a task group, it is not case sensitive.";
            }
            leaf read {
              type aaa-enable-type;
              must "not(../write='enable'  and ../read='disable')";
              default "disable";
              description
                "To determine whether a task has the read right.";
            }
            leaf write {
              type aaa-enable-type;
              default "disable";
              description
                "To determine whether a task has the write right.";
            }
            leaf execute {
              type aaa-enable-type;
              default "disable";
              description
                "To determine whether a task has the operation right.";
            }
            leaf debug {
            type aaa-enable-type;
            default "disable";
            description
              "To determine whether a task has the debug right.";
            }
          }
        }
        container user-group-include-maps {
          description
            "List of the user groups included in a main user group.";
          list user-group-include-map {
            key "include-user-group-name";
            max-elements 1;
            description
              "Configure user group included in a main user group.";
            leaf include-user-group-name {
              type leafref {
                path "/aaa:aaa/aaa:user-groups/aaa:user-group/aaa:name";
              }
              must "(../../../name!=../include-user-group-name)";
              description
                "Name of a task group, it is not case sensitive.";
            }
          }
        }
      }
    }
    container authentication-schemes {
      description
        "List of authentication scheme.";
      list authentication-scheme {
        key "authen-scheme-name";
        description
          "Configure authentication scheme. The default authentication scheme cannot be deleted.";
        leaf authen-scheme-name {
          type string {
            length "1..32";
            pattern "[^/\\*\":?<>|]+";
          }
          description
            "Name of an authentication scheme.";
        }
        leaf-list authen-mode {
          type aaa-authen-mode;
          ordered-by user;
          description
            "Configure an authentication mode for an authentication scheme.";
        }
        choice authen-mode-type {
          description
            "Sorting method of authentication mode.";
          case ordered-strictly {
            description 
              "Ordered strictly case.";
            leaf first-authen-mode {
              type aaa-authen-mode;
              must "(../first-authen-mode!='invalid' )";
              default "local";
              description
                "Preferred authentication mode. The second, third, or fourth authentication mode is used only when the first authentication mode does not respond. The first authentication mode cannot be set to unavailable.";
            }
            leaf second-authen-mode {
              type aaa-authen-mode;
              must "(../second-authen-mode!='radius-proxy' and (((../first-authen-mode='none' or ../first-authen-mode='radius-proxy') and (../second-authen-mode='invalid')) or ((../first-authen-mode!='none' and ../first-authen-mode!='radius-proxy') and ../first-authen-mode!=../second-authen-mode)))";
              default "invalid";
              description
                "Authentication mode with the preference lower than the first authentication mode. The second authentication mode is used when the first authentication mode does not respond. If the setting of the second authentication mode is unavailable, the third and fourth authentication modes fail to be set.";
            }
            leaf third-authen-mode {
              type aaa-authen-mode;
              must "(../third-authen-mode!='radius-proxy' and ((../second-authen-mode ='none' or ../second-authen-mode='invalid') and (../third-authen-mode='invalid') ) or ((../second-authen-mode !='none' and ../second-authen-mode!='invalid'  and ../first-authen-mode!='radius-proxy') and ../third-authen-mode!=../second-authen-mode and ../third-authen-mode!=../first-authen-mode ))";
              default "invalid";
              description
                "Authentication mode with the preference lower than the first and second authentication modes. The third authentication mode is used when the first and second authentication modes do not respond. If the setting of the third authentication mode is unavailable, the fourth authentication mode fails to be set.";
            }
            leaf fourth-authen-mode {
              type aaa-authen-mode;
              must "(../fourth-authen-mode='none' and ../first-authen-mode!='invalid' and ../first-authen-mode!='none' and ../first-authen-mode!='radius-proxy' and ../second-authen-mode!='invalid' and ../second-authen-mode!='none' and ../third-authen-mode!='invalid' and ../third-authen-mode!='none' ) or ../fourth-authen-mode='invalid' ";
              default "invalid";
              description
                "Authentication mode with the least preference. The fourth authentication mode is used when the first, second, and third authentication modes do not respond. If the setting of the fourth authentication mode is unavailable or the fourth authentication mode does not respond, the authentication fails.";
            }
          }
        }
        leaf authentication-change {
          type authen-change;
          default "none";
          description
            "Enable/disable auto change authen mode.";
        }
        leaf-list authentication-super-mode {
          type aaa-authen-mode;
          ordered-by user;
          description
            "Configure an authentication mode for upgrading user levels in an authentication scheme.";
        }
        leaf no-response-accounting {
          type boolean;
          default "false";
          description
            "Enable/disable a device to continue sending accounting packets when the accounting function is configured 
            and a user is authenticated using the local authentication mode after the server does not respond to the user's authentication request.";
        }
        leaf no-response-authorization {
          type boolean;
          default "false";
          description
            "Enable/disable a device to continue sending authorization packets when the authorization function is configured 
            and a user is authenticated using the local authentication mode after the server does not respond to the user's authentication request.";
        }
        container radius-chap {
          description
            "Configure authentication type of radius by chap access for admin users.";
          leaf-list access-type {
            type enumeration {
              enum "ftp" {
                value 0;
                description
                  "Configure replace PAP authentication with CHAP authentication when RADIUS authentication is performed on administrators who access the device using FTP.";
              }
              enum "ssh" {
                value 1;
                description
                  "Replaces PAP authentication with CHAP authentication when RADIUS authentication is performed on administrators who access the device using SSH.";
              }
              enum "telnet" {
                value 2;
                description
                  "Replaces PAP authentication with CHAP authentication when RADIUS authentication is performed on administrators who access the device using Telnet.";
              }
              enum "terminal" {
                value 3;
                description
                  "Replaces PAP authentication with CHAP authentication when RADIUS authentication is performed on administrators who access the device using a terminal.";
              }
              enum "http" {
                value 4;
                description
                  "Replaces PAP authentication with CHAP authentication when RADIUS authentication is performed on administrators who access the device using a web management system.";
              }
              enum "md-cli" {
                value 5;
                description 
                  "Replaces PAP authentication with CHAP authentication when RADIUS authentication is performed on administrators who access the device using MD-CLI.";
              }
              enum "snmp" {
                value 6;
                description 
                  "Replaces PAP authentication with CHAP authentication when RADIUS authentication is performed on administrators who access the device using SNMP.";
              }
            }
            description
              "Configure authentication type of radius by chap access for admin users.";
          }
        }
      }
    }
    container authorization-schemes {
      description
        "List of authorization scheme.";
      list authorization-scheme {
        key "author-scheme-name";
        ext:generated-by "system" {
          ext:filter "author-scheme-name = 'default'";
          description
            "The default author scheme name is generated by system.";
        }
        ext:operation-exclude "delete" {
          ext:filter "author-scheme-name = 'default'";
          description
            "The default author scheme name cannot be deleted.";
        }
        description
          "Configure authorization scheme. The default authorization scheme cannot be deleted.";
        leaf author-scheme-name {
          type string {
            length "1..32";
            pattern "[^/\\*\":?<>|]+";
          }
          description
            "Name of an authorization scheme. The name uniquely identifies the authorization scheme and can be used in the domain.";
        }
        leaf-list author-mode {
          type aaa-author-mode;
          ordered-by user;
          description
            "Configure an authorization mode for an authorization scheme.";
        }
        choice author-mode-type {
          description
            "Sorting method of authorization mode.";
          case ordered-strictly {
            description 
              "Ordered strictly case.";
            leaf first-author-mode {
              type aaa-author-mode;
              must "../first-author-mode='local' or ../first-author-mode='hwtacacs' or ../first-author-mode='if-authenticated' or ../first-author-mode='none'";
              default "local";
              description
                "Preferred authorization mode. The second, third, or fourth authorization mode can be used only when the first authorization mode does not respond. The first authorization mode must be available.";
            }
            leaf second-author-mode {
              type aaa-author-mode;
              must "(../first-author-mode='none' and (../second-author-mode='invalid') ) or (../first-author-mode!='invalid' and ../first-author-mode!='none' and ../second-author-mode!=../first-author-mode)";
              default "invalid";
              description
                "Authorization mode with the preference next to the first authorization mode. It is used when the first authorization mode does not respond. If the setting of the second authorization mode is unavailable, the third and fourth authorization modes fail to be set.";
            }
            leaf third-author-mode {
              type aaa-author-mode;
              must "((../second-author-mode='none' or ../second-author-mode='invalid') and ../third-author-mode='invalid' ) or (../second-author-mode !='none' and ../second-author-mode!='invalid'  and ../first-author-mode!='none' and ../third-author-mode!=../second-author-mode and ../third-author-mode!=../first-author-mode ) or (../first-author-mode='none' and (../third-author-mode='invalid') )";
              default "invalid";
              description
                "Authorization mode with the preference next to the first and second authorization modes. It is used when the first and second authorization modes do not respond. If the setting of the third authorization mode is unavailable, the fourth authorization mode fails to be set.";
            }
            leaf fourth-author-mode {
              type aaa-author-mode;
              must "(../fourth-author-mode='none' and ../first-author-mode!='invalid' and ../first-author-mode!='none' and ../second-author-mode!='invalid' and ../second-author-mode!='none' and ../third-author-mode!='invalid' and ../third-author-mode!='none' ) or ../fourth-author-mode='invalid' ";
              default "invalid";
              description
                "Authorization mode with the least preference. It is used when the first, second, and third authorization modes do not respond. If the setting of the fourth authorization mode is unavailable or the fourth authorization mode does not respond, the authorization fails.";
            }
          }
        }
        leaf no-lvl-first-cmd-author {
          type aaa-author-cmd-mode;
          must "../no-lvl-first-cmd-author='local' or ../no-lvl-first-cmd-author='hwtacacs'";
          default "local";
          description
            "Configures the first authorization mode for users of user group.";
        }
        leaf no-lvl-second-cmd-author {
          type aaa-author-cmd-mode;
          must "(../no-lvl-first-cmd-author='local' and (../no-lvl-second-cmd-author='invalid' or ../no-lvl-second-cmd-author='hwtacacs') ) or ((not(../no-lvl-first-cmd-author='local') and (../no-lvl-second-cmd-author='invalid' or ../no-lvl-second-cmd-author='local') ))";
          default "invalid";
          description
            "Configures the second authorization mode for users of user group.";
        }
        leaf no-response-policy {
          type author-no-res-policy-type;
          default "online";
          description
            "Configures a policy for a scenario where no responses are obtained during command line-based authorization.";
        }
        leaf no-response-times {
          when "../no-response-policy='offline'";
          type uint32 {
            range "1..10";
          }
          default "5";
          description
            "Configures the number of times of failed authorization.";
        }
        container authorization-cmds {
          description
            "List of authorization cmd.";
          list authorization-cmd {
            key "level";
            description
              "Configure authorization cmd.";
            leaf level {
              type uint32 {
                range "0..15";
              }
              description
                "The level of authorization cmd.";
            }
            leaf-list author-mode {
              type aaa-author-cmd-mode;
              ordered-by user;
              description
                "Configure the authorization mode of command. support hwtacacs or local or none.";
            }
            choice cmd-author-mode-type {
              description
                "Sorting method of cmd authorization mode.";
              case ordered-strictly {
                description 
                  "Ordered strictly case.";
                leaf first-cmd-author {
                  type aaa-author-cmd-mode;
                  must "../first-cmd-author='local' or ../first-cmd-author='hwtacacs'";
                  default "local";
                  description
                    "First cmd authorization mode.";
                }
                leaf second-cmd-author {
                  type aaa-author-cmd-mode;
                  must "(../first-cmd-author='local' and (../second-cmd-author='invalid' or ../second-cmd-author='hwtacacs') ) or ((not(../first-cmd-author='local') and (../second-cmd-author='invalid' or ../second-cmd-author='local') ))";
                  default "invalid";
                  description
                    "Second cmd authorization mode.";
                }
              }
            }
          }
        }
      }
    }
    container accounting-schemes {
      description
        "List of accounting scheme.";
      list accounting-scheme {
        key "acct-scheme-name";
        description
          "Configure accounting scheme. The default accounting scheme cannot be deleted.";
        leaf acct-scheme-name {
          type string {
            length "1..32";
            pattern "[^/\\*\":?<>|]+";
          }
          description
            "Accounting scheme name.";
        }
        leaf accounting-mode {
          type aaa-acct-mode;
          must "../accounting-mode='radius' or ../accounting-mode='hwtacacs' or ../accounting-mode='none'";
          default "none";
          description
            "Accounting Mode.";
        }
        container start-accounting-fail {
          description
            "Configure the start accounting fail.";
          leaf fail-policy {
            type enumeration {
              enum "offline" {
                value 0;
                description
                  "Value of offline.";
              }
              enum "online" {
                value 1;
                description
                  "Value of online.";
              }
            }
            default "offline";
            description
              "Configures a policy for accounting-start failures.";
          }
        }
        container realtime-accounting {
          description
            "Configure the realtime accounting.";
          leaf realtime-interval {
            type uint16 {
              range "0..65535";
            }
            units "min";
            description
              "Enable the real-time accounting function and sets the interval for real-time accounting in an accounting scheme.";
          }
          container realtime-fail {
            description
              "Configure the maximum number of real-time accounting failures and configures a policy used after the number of real-time accounting failures exceeds the maximum.";
            leaf fail-policy {
              type enumeration {
                enum "offline" {
                  value 0;
                  description
                    "Value of offline.";
                }
                enum "online" {
                  value 1;
                  description
                    "Value of online.";
                }
              }
              default "online";
              description
                "Offline or online when realtime accounting fail.";
            }
            leaf fail-max-times {
              type uint8 {
                range "1..255";
              }
              default "3";
              description
                "Permit max failure times.";
            }
          }
        }
      }
    }
    container domains {
      description
        "List of domain.";
      list domain {
        key "name";
        description
          "Configure in a domain, users apply the same authentication/authorization scheme or server. The default domain cannot be deleted.";
        leaf name {
          type string {
            length "1..64";
            pattern "([^A-Z*?\"']{3,})|[^A-Z*?\"'-]|([^A-Z*?\"'-][^A-Z*?\"'])|([^A-Z*?\"'][^A-Z*?\"'-])";
          }
          ext:case-sensitivity lower-only;
          description
            "Name of a domain.";
        }
        leaf admin-level {
          type uint32 {
            range "0..15";
          }
          description
            "The admin level of domain. If the command level adjustment function is disabled, the value of admin level ranges from 0 to 3. If the command level adjustment function is enabled, the value of admin level ranges from 0 to 15.";
        }
        leaf authen-scheme-name {
          type leafref {
            path "../../../authentication-schemes/authentication-scheme/authen-scheme-name";
          }
          description
            "Name of the authentication scheme used by the domain, it is not case sensitive. The default value varies according to domains. The default value is restored when the node is deleted.";
        }
        leaf author-scheme-name {
          type leafref {
            path "../../../authorization-schemes/authorization-scheme/author-scheme-name";
          }
          description
            "Name of the authorization scheme used by the domain, it is not case sensitive. The default value varies according to domains. The default value is restored when the node is deleted.";
        }
        leaf acct-scheme-name {
          type leafref {
            path "../../../accounting-schemes/accounting-scheme/acct-scheme-name";
          }
          description
            "Name of the accounting scheme used by the domain, it is not case sensitive. The default value varies according to domains. The default value is restored when the node is deleted.";
        }
        leaf access-limit {
          type int32 {
            range "0..2147483647";
          }
          description
            "Domain max access number. The default value is defined in the PAF file and is restored when the node is deleted.";
        }
        leaf radius-server-template {
          type leafref {
            path "/radius:radius/radius:radius-server-groups/radius:radius-server-group/radius:name";
          }
          description
            "Name of the RADIUS server used by the domain, it is not case sensitive.";
        }
        leaf radius-server-copy {
          type leafref {
            path "/radius:radius/radius:radius-server-groups/radius:radius-server-group/radius:name";
          }
          description
           "Name of the RADIUS server used by the domain for level-2 accounting, it is not case sensitive.";
        }
        leaf hwtacacs-server-template {
          type leafref {
            path "/hwtacacs:hwtacacs/hwtacacs:templates/hwtacacs:template/hwtacacs:name";
          }
          description
            "Name of the HWTACACS server used by the domain, it is not case sensitive.";
        }
        leaf state {
          type aaa-state-type;
          default "active";
          description
            "Activated state of the domain.";
        }
        leaf time-range-enable {
          type boolean;
          default "false";
          description
            "Enable/disable the time range function used by a domain.";
        }
        leaf-list time-range {
          type leafref {
            path "/timerange:time-range/timerange:time-range-instances/timerange:time-range-instance/timerange:name";
          }
          max-elements 4;
          description
            "Configure the block time range of the domain.";
        }
        leaf service-terminal {
          type boolean;
          default "true";
          description
            "Enable/disable users to log in Terminal mode.";
        }
        leaf service-telnet {
          type boolean;
          default "true";
          description
            "Enable/disable users to log in Telnet mode.";
        }
        leaf service-ftp {
          type boolean;
          default "true";
          description
            "Enable/disable users to log in FTP mode.";
        }
        leaf service-ppp {
          type boolean;
          default "true";
          description
            "Enable/disable users to log in PPP mode.";
        }
        leaf service-ssh {
          type boolean;
          default "true";
          description
            "Enable/disable users to log in SSH mode.";
        }
        leaf service-qx {
          type boolean;
          default "true";
          description
            "Enable/disable users to log in QX mode.";
        }
        leaf service-snmp {
          type boolean;
          default "true";
          description
            "Enable/disable users to log in SNMP mode.";
        }
        leaf service-mml {
          type boolean;
          default "true";
          description
            "Enable/disable users to log in MML mode.";
        }
        leaf service-http {
          type boolean;
          default "true";
          description
            "Enable/disable users to log in HTTP mode.";
        }
        leaf account-separate {
          type boolean;
          default "false";
          description
            "Enable/disable accounting dual-stack separate mode.";
        }        
        leaf online-num {
          type int32 {
            range "0..2147483647";
          }
          config false;
          description
            "Online number of the domain.";
        }
        leaf statistics-enable {
          type boolean;
          default "false";
          description
            "Enable/disable traffic statistics collection for domain users.";
        }
        leaf band-width {
          type boolean;
          default "false";
          description
            "Enable/disable the bandwidth share mode.";
        }
        container force-push-function {
          description
            "Configure push URL template or push UR function.";
          choice url-source {
            description
              "Force push url source choice.";
            case template {
              description
                "Template case.";
              leaf url-template {
                type string {
                  length "1..31";
                }
                description
                  "Specifies the name of a pushed URL template.";
              }
            }
            case url {
              description
                "Url case.";
              leaf url-address {
                type string {
                  length "1..247";
                }
                description
                  "Specifies a pushed URL.";
              }
            }
          }
        }
      }
    }
    container login-alarm-threshold {
      description
        "Configure alarm when manager login failed frequently.";
      leaf report-times {
        type uint16 {
          range "0..100";
        }
        units "min";
        must "../resume-times<=../report-times";
        default "30";
        description
          "Login Alarm report times.";
      }
      leaf resume-times {
        type uint16 {
          range "0..100";
        }
        must "../resume-times<=../report-times";
        default "20";
        description
          "Login Alarm resume times.";
      }
      leaf period {
        type uint16 {
          range "1..120";
        }
        units "min";
        default "5";
        description
          "Login Alarm period.";
      }
    }
    container alive-user-statistics {
      config false;
      description
        "Active user statistics.";
      leaf total-user-number {
        type uint16;
        config false;
        description
          "The total number of current active users.";
      }
    }
    container alive-user-qrys {
      config false;
      description
        "List of alive users.";
      list alive-user-qry {
        key "user-id";
        config false;
        description
          "Statistics of active users.";
        leaf user-id {
          type uint32;
          config false;
          description
            "User ID.";
        }
        leaf user-name {
          type string {
            length "1..253";
          }
          config false;
          description
            "Name of an access user, it is not case sensitive.";
        }
        leaf level {
          type uint32 {
            range "0..15";
          }
          config false;
          description
            "User level.";
        }
        leaf user-group-name {
          type string {
            length "1..32";
          }
          config false;
          description
            "Specifies the name of a user group, it is not case sensitive.";
        }
        leaf name {
          type string {
            length "1..64";
          }
          config false;
          description
            "Name of a domain, it is not case sensitive.";
        }
        leaf access-type {
          type aaa-user-access-type;
          config false;
          description
            "Access type.";
        }
        leaf access-interface {
          type string {
            length "1..63";
          }
          config false;
          description
            "Access interface of a user.";
        }
        leaf user-vlan {
          type string {
            length "1..8";
          }
          config false;
          description
            "VLAN that a user belongs to.";
        }
        leaf mac {
          type yang:mac-address;
          config false;
          description
            "MAC address of a user.";
        }
        leaf ip {
          type inet:ip-address-no-zone;
          config false;
          description
            "IP address of a user.";
        }
        leaf access-time {
          type yang:date-and-time;
          config false;
          description
            "Time when a user goes online.";
        }
        leaf accounting-session-id {
          type string {
            length "1..64";
          }
          config false;
          description
            "ID of an accounting session.";
        }
        leaf terminal-type {
          type terminal-type;
          config false;
          description
            "Terminal device type of a user.";
        }
        leaf authen-type {
          type aaa-authen-access-type;
          config false;
          description
            "Authentication Type.";
        }
        leaf authen-method {
          type aaa-authen-mode;
          config false;
          description
            "Alive user current authentication mode.";
        }
        leaf authen-state {
          type aaa-authen-state-type;
          config false;
          description
            "Authentication state.";
        }
        leaf author-method {
          type aaa-author-mode;
          config false;
          description
            "Current authorization mode.";
        }
        leaf author-state {
          type aaa-author-state-type;
          config false;
          description
            "Author state.";
        }
        leaf acct-method {
          type aaa-acct-mode;
          config false;
          description
            "Current accounting Mode.";
        }
        leaf acct-state {
          type aaa-acct-state-type;
          config false;
          description
            "Accounting state.";
        }
        leaf in-octets {
          type uint64 {
            range "0..max";
          }
          config false;
          description
            "Input octets.";
        }
        leaf in-packets {
          type uint64 {
            range "0..max";
          }
          config false;
          description
            "Input packets.";
        }
        leaf out-octets {
          type uint64 {
            range "0..max";
          }
          config false;
          description
            "Output octets.";
        }
        leaf out-packets {
          type uint64 {
            range "0..max";
          }
          config false;
          description
            "Output packets.";
        }
      }
    }
    container management-user-qrys {
      config false;
      description
        "List of management users.";
      list management-user-qry {
        key "name";
        description
          "Statistics of management users.";
        leaf name {
          type string {
            length "1..253";
          }
          description
            "Name of an management user, it is not case sensitive.";
        }
        leaf alive-num {
          type uint32;
          description
            "Online number of the management user.";
        }
        container user-infos {
          config false;
          description
            "List of user information.";
          list user-info {
            key "user-id";
            description
              "Statistics of user information.";
            leaf user-id {
              type uint32;
              description
                "User ID.";
            }
            leaf access-type {
              type aaa-user-access-type;
              description
                "Access type.";
            }
            leaf ip {
              type inet:ip-address-no-zone;
              description
                "IP address of a user.";
            }
          }
        }
        container last-login-infos {
          config false;
          description
            "List of last login information.";
          list last-login-info {
            key "last-login-ip";
            description
              "Statistics of last login information.";
            leaf last-login-ip {
              type inet:ip-address-no-zone;
              description
                "Last login IP address.";
            }
            leaf last-login-success {
              type boolean;
              default "true";
              description
                "Enable/disable last login success.";
            }
            leaf last-login-time {
              type string {
                length "1..25";
              }
              description
                "Last login time.";
            }
          }
        }
      }
    }
    container global-policy {
      description
        "Configure global policy.";
      leaf domain-location {
        type aaa-domain-location-type;
        default "after-delimiter";
        description
          "Domain Location.";
      }
      leaf domain-parse-direction {
        type aaa-parse-direction-type;
        default "left-to-right";
        description
          "Domain Parse Direction.";
      }
      leaf domain-delimiter {
        type string {
          length "1";
        }
        default "@";
        description
          "Specifies a domain name delimiter of only one bit.";
      }
      leaf default-admin-domain {
        type leafref {
          path "../../domains/domain/name";
        }
        default "default_admin";
        description
          "Admin user default domain.";
      }
      leaf default-access-domain {
        type leafref {
          path "../../domains/domain/name";
        }
        default "default1";
        description
          "Access user default domain.";
      }
      leaf parse-priority {
        type aaa-parse-priority-type;
        default "domain-first";
        description
          "Specifies priorities for parsing domain names.";
      }
      leaf realm-location {
        type aaa-realm-location-type;
        default "before-delimiter";
        description
          "Specifies a position for a realm domain name.";
      }
      leaf real-name-delimiter {
        type string {
          length "1";
          pattern "[/:<>\\|@%']";
        }
        description
          "Specifies a realm name delimiter used to parse the user account. The value is a single character. It can be one of the following symbols: back-slant, /, :, <, >, |, @, %, '.";
      }
      leaf real-name-parse-direction {
        type aaa-parse-direction-type;
        default "left-to-right";
        description
          "Specifies a parsing direction for the realm name.";
      }
      leaf roam-character {
        type string {
          length "1";
          pattern "[/:*<>\\|]";
        }
        default ":";
        description
          "Specifies an identifier for a roaming user. The value is a single character. It can be one of the following symbols: back-slant, /, :, *, <, >, |.";
      }
      leaf security-name-delimiter-enable {
        type boolean;
        default "true";
        description
          "Enable/disable the security string function.";
      }
      leaf security-name-delimiter {
        type string {
          length "1";
        }
        default "*";
        description
          "Specifies a delimiter for a security string.";
      }
    }
    container recording {
      description
        "Configure recording function.";
      container function {
        description
          "Configure recording function.";
        leaf cmd-record-scheme {
          type leafref {
            path "../../schemes/scheme/name";
          }
          description
            "The recording scheme used by cmd recording.";
        }
        leaf system-record-scheme {
          type leafref {
            path "../../schemes/scheme/name";
          }
          description
            "Configures a solution to record system events. Currently, only events triggered by the reboot command are recorded.";
        }
        leaf outbound-record-scheme {
          type leafref {
            path "../../schemes/scheme/name";
          }
          description
            "Records remote login operations for the device that functions as the client.";
        }
      }
      container schemes {
        description
          "List of recording scheme.";
        list scheme {
          key "name";
          description
            "Configure recording scheme.";
          leaf name {
            type string {
              length "1..32";
              pattern "[^/\\*\":?<>|]+";
            }
            description
              "Recording scheme name.";
          }
          leaf tacacs-group {
            type leafref {
              path "/hwtacacs:hwtacacs/hwtacacs:templates/hwtacacs:template/hwtacacs:name";
            }
            description
              "The bound HWTACACS server.";
          }
        }
      }
    }
    container invalid-session-timeout {
      description
        "Configure preventing a device from disconnecting or reauthenticating users when the RADIUS server delivers session-timeout with value 0.";
      leaf enable {
        type boolean;
        default "false";
        description
          "Enable/disable function.";
      }
    }
    container authorization-modify {
      description
        "Configure the update mode for user authorization information delivered by the authorization server.";
      leaf mode {
        type enumeration {
          enum "modify" {
            value 0;
            description
              "Value of modify.";
          }
          enum "overlay" {
            value 1;
            description
              "Value of overlay.";
          }
        }
        default "overlay";
        description
          "Authorization modify mode.";
      }
    }
    container remote-user-policy {
      description
        "Configure the remote administrator account locking function, and sets the authentication retry interval, maximum number of consecutive authentication failures, and account locking period.";
      leaf enable {
        type boolean;
        default "true";
        description
          "Enable/disable the remote administrator account locking function.";
      }
      leaf retry-interval {
        when "../enable='true'";
        type int32 {
          range "5..65535";
        }
        units "min";
        default "5";
        description
          "Specifies the authentication retry interval.";
      }
      leaf retry-times {
        when "../enable='true'";
        type int32 {
          range "3..65535";
        }
        default "30";
        description
          "Specifies the maximum number of consecutive authentication failures.";
      }
      leaf block-time {
        when "../enable='true'";
        type int32 {
          range "5..65535";
        }
        units "min";
        default "5";
        description
          "Specifies the account locking period.";
      }
    }
    container remote-access-user-policy {
      description
        "Configure the remote access-user account locking function, and sets the authentication retry interval, maximum number of consecutive authentication failures, and account locking period.";
      leaf enable {
        type boolean;
        default "false";
        description
          "Enable/disable the remote access-user account locking function.";
      }
      leaf retry-interval {
        when "../enable='true'";
        type int32 {
          range "5..65535";
        }
        units "min";
        default "5";
        description
          "Specifies the authentication retry interval.";
      }
      leaf retry-times {
        when "../enable='true'";
        type int32 {
          range "3..65535";
        }
        default "30";
        description
          "Specifies the maximum number of consecutive authentication failures.";
      }
      leaf block-time {
        when "../enable='true'";
        type int32 {
          range "5..65535";
        }
        units "min";
        default "5";
        description
          "Specifies the account locking period.";
      }
    }
    container ipv6-statistics {
      description
        "Configure IPv6 statistics function.";
      leaf enable {
        type boolean;
        default "false";
        description
          "Enable/disable IPv6 statistics.";
      }
    }
    container user-queue {
      description
        "Configure SQ authorization based on a single user function.";
      leaf enable {
        type boolean;
        default "false";
        description
          "Enable/disable SQ authorization based on a single user.";
      }
    }
    container bypass {
      presence "Create bypass function.";
      description
        "Configure bypass related function.";
      container authentication {
        description
          "Configure the bypass authentication timeout interval.";
        leaf bypass-enable {
          type boolean;
          default "false";
          description
            "Enable/disable remote bypass authentication.";
        }
        leaf bypass-time {
          when "../bypass-enable='true'";
          type uint16 {
            range "1..1440";
          }
          units "min";
          mandatory true;
          description
            "Specifies the bypass authentication timeout interval.";
        }
      }
      container authorization {
        description
          "Configure the bypass authorization timeout interval.";
        leaf bypass-enable {
          type boolean;
          default "false";
          description
            "Enable/disable remote bypass authorization.";
        }
        leaf bypass-time {
          when "../bypass-enable='true'";
          type uint16 {
            range "1..1440";
          }
          units "min";
          mandatory true;
          description
            "Specifies the bypass authorization timeout interval.";
        }
      }
      container authorization-cmd {
        description
          "Configure the command-line bypass authorization timeout interval.";
        leaf bypass-enable {
          type boolean;
          default "false";
          description
            "Enable/disable remote command-line bypass authorization.";
        }
        leaf bypass-time {
          when "../bypass-enable='true'";
          type uint16 {
            range "1..1440";
          }
          units "min";
          mandatory true;
          description
            "Specifies the command-line bypass authorization timeout interval.";
        }
      }
    }
    container authorization-info-check {
      description
        "Configure the command-line bypass authorization timeout interval.";
      leaf fail-policy {
        type enumeration {
          enum "offline" {
            value 0;
            description
              "Indicates that the device prohibits users from going online after the authorization information check fails.";
          }
          enum "online" {
            value 1;
            description
              "Indicates that the device allows users to go online after the authorization information check fails.";
          }
        }
        default "online";
        description
          "Set the command-line bypass authorization timeout interval.";
      }
    }
    container global-domain {
      description
        "Configure a global default domain.";
      leaf default-domain {
        type leafref {
          path "../../domains/domain/name";
        }
        description
          "Specifies the name of a global default domain.";
      }
      leaf default-admin-domain {
        type leafref {
          path "../../domains/domain/name";
        }
        description
          "Configures a domain for administrators.";
      }
    }
    container traffic-groups {
      description
        "List of traffic group item.";
      list traffic-group {
        key "name";
        description
          "Configure traffic group item.";
        leaf name {
          type string {
            length "1..31";
          }
          description
            "Create a traffic group and displays the traffic group content, or displays the content of an existing traffic group.";
        }
        leaf enable {
          type boolean;
          default "false";
          description
            "Enable/disable a traffic group to the device globally.";
        }
        container acl-tariff-levels {
          description
            "List of a tariff level for traffic.";
          list acl-tariff-level {
            key "acl-id";
            description
              "Configure a tariff level for traffic list.";
            leaf acl-id {
              type leafref {
                path "/acl:acl/acl:groups/acl:group/acl:identity";
              }
              description
                "Specifies the number of an ACL.";
            }
            leaf traffic-level {
              type uint8 {
                range "1..6";
              }
              description
                "Specifies the tariff level.";
            }
          }
        }
        container acl-tariff-level-ipv6s {
          description
            "List of a tariff level for IPv6 ACL traffic.";
          list acl-tariff-level-ipv6 {
            key "acl-id";
            description
              "Configure a tariff level for IPv6 ACL traffic list.";
            leaf acl-id {
              type leafref {
                path "/acl:acl/acl:group6s/acl:group6/acl:identity";
              }
              description
                "Specifies the number of an ACL.";
            }
            leaf traffic-level {
              type uint8 {
                range "1..6";
              }
              description
                "Specifies the tariff level.";
            }
          }
        }
      }
    }
    container online-offline-rec-switch {
      description
        "Configure whether to enable login failure and logout recording for management users.";
      leaf login-fail-rec-switch {
        type aaa-enable-type;
        default "enable";
        description
          "Enables recording of login failures.";
      }
      leaf logout-rec-switch {
        type aaa-enable-type;
        default "enable";
        description
          "Enables recording of normal and abnormal logouts.";
      }
      leaf abnormal-logout-rec-switch {
        type aaa-enable-type;
        default "enable";
        description
          "Enables recording of abnormal logouts.";
      }
      leaf normal-logout-rec-switch {
        type aaa-enable-type;
        default "enable";
        description
          "Enables recording of normal logouts.";
      }
    }
    container abnormal-offline-hidens {
      description
        "List of the function that replaces the abnormal offline reason with 'the user requests to go offline'.";
      list abnormal-offline-hiden {
        key "hidden-id";
        description
          "Configure the function that replaces the abnormal offline reason with 'the user requests to go offline'.";
        leaf hidden-id {
          type uint32 {
            range "2..18";
          }
          description
            "Specifies an ID for an abnormal logout reason.";
        }
      }
    }
    container lam {
      description
        "Configure the local account and related policy management functions.";
      uses aaa:aaa-lam-type;
    }
    container local-server {
      description
        "Configure a local AAA server. You can perform access security configurations for local users.";
      uses aaa:aaa-local-server-type;
    }
    container access-user-qrys {
      config false;
      description
        "List of access users.";
      list access-user-qry {
        key "user-id";
        description
          "Statistics of active users.";
        leaf user-id {
          type uint32;
          description
            "User ID.";
        }
        leaf user-name {
          type string {
            length "1..253";
          }
          description
            "Name of an access user, it is not case sensitive.";
        }
        leaf access-type {
          type uint32;
          description
            "1 : wireless access; 0 : wired access.";
        }
        leaf auth-type {
          type enumeration {
            enum "unauthen" {
              value 1;
              description
                "Unauthentic user.";
            }
            enum "mac-authen" {
              value 2;
              description
                "MAC authentic user.";
            }
            enum "dot1x-authen" {
              value 3;
              description
                "Dot1x authentic user.";
            }
            enum "portal-authen" {
              value 4;
              description
                "Portal authentic user.";
            }
            enum "ipsec-authen" {
              value 5;
              description
                "IPSEC authentic user.";
            }
            enum "ppp-authen" {
              value 6;
              description
                "PPP authentic user.";
            }
            enum "sslvpn-authen" {
              value 7;
              description
                "SSLVPN authentic user.";
            }
            enum "pppoe-authen" {
              value 8;
              description
                "PPPOE authentic user.";
            }
          }
          description
            "User authen type.";
        }
        leaf access-interface {
          type string {
            length "1..63";
          }
          description
            "Access interface of a user.";
        }
        leaf user-vlan {
          type string {
            length "1..8";
          }
          description
            "VLAN that a user belongs to.";
        }
        leaf mac {
          type yang:mac-address;
          description
            "MAC address of a user.";
        }
        leaf ip {
          type inet:ip-address-no-zone;
          description
            "IP address of a user.";
        }
        leaf access-time {
          type yang:date-and-time;
          description
            "Time when a user goes online.";
        }
        leaf user-status {
          type enumeration {
            enum "success" {
              value 1;
              description
                "Authentication succeeded.";
            }
            enum "pre-authen" {
              value 2;
              description
                "Waiting for Authentication.";
            }
            enum "client-no-resp" {
              value 3;
              description
                "Client no response.";
            }
            enum "fail-authorized" {
              value 4;
              description
                "Authentication failed.";
            }
            enum "web-server-down" {
              value 5;
              description
                "Web server down.";
            }
            enum "aaa-server-down" {
              value 6;
              description
                "AAA server down.";
            }
            enum "open" {
              value 7;
              description
                "Loacl Authenticated.";
            }
            enum "running" {
              value 8;
              description
                "Process running.";
            }
          }
          description
            "User Status.";
        }
        leaf online-time-length {
          type uint64;
          units "s";
          description
            "Online time from latest access.";
        }
        leaf as-name {
          type string {
            length "1..256";
          }
          description
            "Name of an access switch.";
        }
        leaf as-port {
          type string {
            length "1..64";
          }
          description
            "Access interface of an access switch.";
        }
        leaf as-mac {
          type pub-type:mac-address;
          description
            "MAC address of an access switch.";
        }
        leaf-list ipv6 {
          type inet:ipv6-address-no-zone;
          max-elements 10;
          description
            "User's IPv6 address state.";
        }
        leaf upward-bytes {
          type uint64;
          description
            "User upstream traffic. Units: byte.";
        }
        leaf downward-bytes {
          type uint64;
          description
            "User downstream traffic. Units: byte.";
        }
        leaf upward-speed {
          type uint64;
          description
            "User uplink rate. Units: bps.";
        }
        leaf downward-speed {
          type uint64;
          description
            "User downlink rate. Units: bps.";
        }
        leaf duration-auth {
          type uint32;
          description
            "Duration of processing user authentication. Units: ms.";
        }
        leaf up-bytes-v6 {
          type uint64;
          units "Byte";
          description
            "User upstream v6 traffic.";
        }
        leaf down-bytes-v6 {
          type uint64;
          units "Byte";
          description
            "User downstream v6 traffic.";
        }
      }
    }
    container access-user-records {
      config false;
      description
        "List of terminal abnormal records.";
      list access-user-record {
        key "user-id";
        description
          "Operational data of terminal abnormal record.";
        leaf user-id {
          type uint32;
          description
            "User ID.";
        }
        leaf user-name {
          type string {
            length "1..253";
          }
          description
            "Name of related user, it is not case sensitive.";
        }
        leaf user-vlan {
          type string {
            length "1..8";
          }
          description
            "VLAN that a user belongs to.";
        }
        leaf mac {
          type yang:mac-address;
          description
            "MAC address of the abnormal terminal.";
        }
        leaf ip {
          type inet:ip-address-no-zone;
          description
            "IP address of the abnormal terminal.";
        }
        leaf access-type {
          type aaa-user-access-type;
          description
            "Access type.";
        }
        leaf terminal-operation {
          type enumeration {
            enum online-failed {
              value 0;
              description
                "Terminal take online failed.";
            }
            enum offline-success {
              value 1;
              description
                "Terminal take offline succeeded.";
            }
            enum offline-failed {
              value 2;
              description
                "Terminal take offline failed.";
            }
            enum online-success {
              value 3;
              description
                "Terminal take online succeeded.";
            }
          }
          description
            "Operation of the abnormal terminal.";
        }
        leaf login-time {
          type yang:date-and-time;
          description
            "Time when a user goes online.";
        }
        leaf offline-time {
          type yang:date-and-time;
          description
            "Time when a user goes offline.";
        }
        leaf fail-reason {
          type string {
            length "1..253";
          }
          description
            "Reason of failure.";
        }
      }
    }
    container re-authorization-users {
      config false;
      description
        "List of re-authorization users.";
      list re-authorization-user {
        key "user-name";
        description
          "Statistics of re-authorization user.";
        leaf user-name {
          type string {
            length "1..253";
          }
          description
            "Name of an re-authorization user.";
        }
        leaf remain-operation-time {
          type uint32 {
            range "1..1440";
          }
          units "min";
          description
            "Remain operation time of authorized user in re-authorization mode.";
        }
      }
    }
    container global-user-policy {
      description
          "Configure global user policy.";
      leaf level {
        type uint32 {
          range "0..2";
        }
        description
          "Default user level.";
      }
    }
  }
  rpc test-server-connectivity {
    description
      "Test the connectivity between the device and the authentication server or accounting server.";
    input  {
      leaf user-name {
        type string {
          length "1..253";
        }
        mandatory true;
        description
          "Specifies a user name.";
      }
      leaf user-password {
        type pub-type:password;
        mandatory true;
        description
          "Specifies a user password.";
      }
      leaf server-type {
        type enumeration {
          enum "radius" {
            value 0;
            description
              "RADIUS server.";
          }
          enum "hwtacacs" {
            value 1;
            description
              "HWTACACS server.";
          }
        }
        mandatory true;
        description
          "The type of server.";
      }
      leaf template-name {
        type string {
          length "1..32";
        }
        mandatory true;
        description
          "Specifies the name of a server template.";
      }
      leaf test-type {
        type enumeration {
          enum "chap" {
            value 0;
            description
              "Indicates Challenge Handshake Authentication Protocol (CHAP) authentication.";
          }
          enum "pap" {
            value 1;
            description
              "Indicates Password Authentication Protocol (PAP) authentication.";
          }
          enum "accounting" {
            value 2;
            description
              "Indicates accounting.";
          }
        }
        description
          "The type of authentication server or accounting server.";
      }
      leaf accounting-type {
        type enumeration {
          enum "start" {
            value 0;
            description
              "Indicates that the sent packet is an accounting-start packet.";
          }
          enum "realtime" {
            value 1;
            description
              "Indicates that the sent packet is a real-time accounting packet.";
          }
          enum "stop" {
            value 2;
            description
              "Indicates that the sent packet is an accounting-stop packet.";
          }
        }
        must "../test-type = 'accounting'";
        description
          "The type of accounting packet.";
      }
      leaf called-station-id {
        type boolean;
        default "false";
        description 
          "Indicates to carry device info.";
      }
      leaf ssid-name {
        type string {
          length "1..32";
        }
        description 
          "Ssid name.";
      }
    }
    output  {
      leaf result-code {
        type string {
          length "1..16";
        }
        description
          "Result code of aaa test.";
      }
      leaf result-info {
        type string {
          length "1..256";
        }
        description
          "Result information of aaa test.";
      }
    }
  }
  rpc cut-user-by-domain {
    ext:node-ref "/aaa/alive-user-qrys/alive-user-qry";
    description
      "Cut all access users by specified domain name.";
    input  {
      leaf domain-name {
        type string {
          length "1..64";
        }
        mandatory true;
        description
          "Name of a domain, it is not case sensitive.";
      }
    }
  }
  rpc cut-user-by-user-id {
    ext:node-ref "/aaa/alive-user-qrys/alive-user-qry";
    description
      "Cut all access users by specified range of user id.";
    input  {
      leaf begin-user-id {
        type uint32;
        mandatory true;
        description
          "Start user ID, which specifies a range with the end user ID. Users within this range will be disconnected.";
      }
      leaf end-user-id {
        type uint32;
        description
          "End user ID, which specifies a range with the start user ID. Users within this range will be disconnected. This ID cannot be smaller than the start user ID.";
      }
    }
  }
  rpc cut-user-by-user-name {
    ext:node-ref "/aaa/alive-user-qrys/alive-user-qry";
    description
      "Cut all access users by specified user name.";
    input  {
      leaf user-name {
        type string {
          length "1..253";
        }
        mandatory true;
        description
          "Name of a alive user to be cut, it is not case sensitive.";
      }
    }
  }
  rpc reset-online-failoroffline-record {
    description
      "Reset online fail or offline record.";
    input  {
      leaf rectype {
        type offline-record-type;
        mandatory true;
        description
          "Offline record type.";
      }
    }
  }
  rpc reactivate-user {
    description
      "Reactivate local user.";
    input  {
      leaf user-name {
        type leafref {
          path "/aaa:aaa/aaa:lam/aaa:users/aaa:user/aaa:name";
        }
        mandatory true;
        description
          "Name of local user to be reactivated, it is not case sensitive.";
      }
    }
  }
  rpc change-my-password {
    description
      "Change password function.";
    input  {
      leaf old-password {
        type pub-type:password-extend;
        mandatory true;
        description
          "The old password of the local user.";
      }
      leaf new-password {
        type pub-type:password-extend;
        mandatory true;
        description
          "New password to set.";
      }
    }
  }
  rpc cut-access-user {
    description
      "Disconnecting one or multiple access user connections.";
    input {
      leaf user-type {
        type enumeration {
          enum "access-user" {
            value 0;
            description
              "Select access user to cut.";
          }
          enum "management-user" {
            value 1;
            description
              "Select management user to cut.";
          }
        }
        description
          "Specify the user type to be cut off.";
      }
      container access-type {
        description
          "Select the user's access type.";
        leaf access {
          when "../../user-type='access-user'";
          type enumeration {
            enum "dot1x" {
              value 0;
              description
                "Dot1x access type.";
            }
            enum "portal" {
              value 1;
              description
                "Portal access type.";
            }
            enum "mac" {
              value 2;
              description
                "Mac access type.";
            }
          }
          description
            "Select the access user's access type.";
        }
        leaf admin {
          when "../../user-type='management-user'";
          type enumeration {
            enum "ftp" {
              value 0;
              description
                "FTP access type.";
            }
            enum "ssh" {
              value 1;
              description
                "SSH access type.";
            }
            enum "telnet" {
              value 2;
              description
                "Telnet access type.";
            }
            enum "terminal" {
              value 3;
              description
                "Terminal access type.";
            }
            enum "http" {
              value 4;
              description
                "Http access type.";
            }
            enum "api" {
              value 5;
              description
                "API access type.";
            }
          }
          description
            "Select the management user's access type.";
        }
      }
      leaf authen-method {
        type enumeration {
          enum "all" {
            value 0;
            description
              "All users.";
          }
          enum "hwtacacs" {
            value 1;
            description
              "HWTACACS authentication users.";
          }
          enum "local" {
            value 2;
            description
              "Local authentication users.";
          }
          enum "radius" {
            value 3;
            description
              "RADIUS authentication users.";
          }
          enum "haca" {
            value 4;
            description
              "HACA authentication users.";
          }
        }
        description
          "Specifies the authentication mode.";
      }
      leaf user-name {
        type string {
          length "1..253";
        }
        description
          "Specify the user name.";
      }
      leaf domain-name {
        type string {
          length '1..64';
        }
        description
          "Specify the domain name.";
      }
      choice user-ip {
        description
          "Select ip address of the user to be cutoff.";
        case ipv4-type {
          description
            "IPv4 address type.";
          leaf ip {
            type inet:ip-address;
            description
              "Specifies the IP address.";
          }
        }
        case ipv6-type {
          description
            "IPv6 address type.";
          leaf ipv6 {
            type inet:ipv6-address;
            description
              "Specifies the IPv6 address.";
          }
        }
      }
      leaf user-mac {
        type pub-type:mac-address;
        description
          "Specifies the MAC address.";
      }
      leaf service-scheme-name {
        type string {
          length "1..64";
        }
        description
          "Specifies the service scheme name.";
      }
      leaf ssid-name {
        type string {
          length "1..32";
        }
        description
          "Specifies the ssid name.";
      }
    }
  }
  rpc re-authorize-user {
    description
      "Re-authorization users perform high-risk operations.";
    input  {
      leaf user-name {
        type string {
          length "1..253";
          pattern "[^A-Z]+";
        }
        mandatory true;
        description
          "Authorized user name in re-authorization mode.";
      }
      leaf operation-time {
        type uint32 {
          range "1..1440";
        }
        units "min";
        mandatory true;
        description
          "Operation time of authorized users in re-authorization mode.";
      }
    }
  }
  rpc clear-re-authorize-user {
    description
      "Clear re-authorization users.";
    input  {
      leaf user-name {
        type string {
          length "1..253";
          pattern "[^A-Z]+";
        }
        mandatory true;
        description
          "Authorized user name in re-authorization mode.";
      }
    }
  }
  ext:task-name "aaa";
}
