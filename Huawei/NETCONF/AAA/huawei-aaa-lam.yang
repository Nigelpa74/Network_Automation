/*
Copyright (C) 2020-2025 Huawei Technologies Co., Ltd. All rights reserved.
*/
submodule huawei-aaa-lam {
  yang-version 1.1;
  belongs-to huawei-aaa {
    prefix aaa;
  }
  import huawei-pub-type {
    prefix pub-type;
  }
  import ietf-inet-types {
    prefix inet;
  }
  import ietf-yang-types {
    prefix yang;
  }
  import huawei-nac-group {
    prefix hw-nac-group;
  }
  import huawei-extension {
    prefix ext;
  }
  include huawei-aaa-type;

  organization
    "Huawei Technologies Co., Ltd.";

  contact
    "Huawei Industrial Base
     Bantian, Longgang
     Shenzhen 518129
     People's Republic of China
     Website: http://www.huawei.com
     Email: support@huawei.com";
  description
    "Description of local access manage submodule.";
  revision 2025-08-14 {
    description
      "Modify the maximum length of change-current-password node.";
    reference
      "Huawei private.";
 }
  revision 2025-06-24 {
    description
      "Modify yang-version 1.1.";
    reference
      "Huawei private.";
  }
  revision 2025-06-05 {
    description
      "Add leaf of password similar-to-name-check-type and modify spelling of words.";
    reference
      "Huawei private.";
  }
  revision 2025-05-09 {
    description
      "Add leaf of access-user password complexity-check.";
    reference
      "Huawei private.";
  }
  revision 2025-03-28 {
    description
      "Modify the length of the access user name.";
    reference
      "Huawei private.";
  }
  revision 2025-03-10 {
    description
      "Add leaf of virtual and add two containers node for bind IP.";
    reference
      "Huawei private.";
  }
  revision 2025-01-22 {
    description
      "Add leaf of mac and leaf of mac-exclusive.";
    reference
      "Huawei private.";
  }
  revision 2024-11-28 {
    description
      "Add leaf of private user.";
    reference
      "Huawei private.";
  }
  revision 2024-11-19 {
    description
      "Add leaf of ou UCL group.";
    reference
      "Huawei private.";
  }
  revision 2024-11-01 {
    description
      "Synchronize code.";
    reference
      "Huawei private.";
  }
  revision 2024-07-24 {
    description
      "Modify pattern of users/name.";
    reference
      "Huawei private.";
  }
  revision 2024-06-26 {
    description
      "Add must condition for end-life-date and time-range. Add leaf pwd-salt.";
    reference
      "Huawei private.";
  }
  revision 2024-05-28 {
    description
      "Add must condition for user/name. Modify the type of time-range.";
    reference
      "Huawei private.";
  }
  revision 2024-05-25 {
    description
      "Add must condition for complexity-check-four.";
    reference
      "Huawei private.";
  }
  revision 2024-05-24 {
    description
      "Add must condition for password. Modify the must condition of password-type.";
    reference
      "Huawei private.";
  }
  revision 2024-05-13 {
    description
      "Check the spelling of words.";
    reference
      "Huawei private.";
  }
  revision 2024-03-12 {
    description
      "Add a node for querying the user creation time.";
    reference
      "Huawei private.";
  }
  revision 2023-01-26 {
    description
      "Add node enable of original-alert, bind mac and bind IPv4.";
    reference
      "Huawei private.";
  }
  revision 2022-12-01 {
    description
      "Add node enable of service-ppp and ftp user directory access permission.";
    reference
      "Huawei private.";
  }
  revision 2022-04-01 {
    description
      "Add node enable of complexity-check-four, username-complexity-check and similar-to-name-check.";
    reference
      "Huawei private.";
  }
  revision 2022-03-31 {
    description
      "Modify description.";
    reference
      "Huawei private.";
  }
  revision 2022-03-08 {
    description
      "Add the user password policy default entry criteria.";
    reference
      "Huawei private.";
  }
  revision 2021-02-05 {
    description
      "Add node enable of login-failed-limit.";
    reference
      "Huawei private.";
  }
  revision 2020-03-02 {
    description
      "Init revision.";
    reference
      "Huawei private.";
  }
  
  grouping aaa-lam-type {
    description
      "Local management.";
    container login-failed-limit {
      description
        "Configure login failed times limit in special period.";
      leaf enable {
        type boolean;
        default "true";
        description 
          "Enable/disable the local account locking function.";
      }
      leaf failed-times {
        type uint32 {
          range "0..65535";
        }
        default "5";
        description
          "Indicates the consecutive failure times. 0 indicates that the number of times for a user to fail the authentification continuously is not restricted.";
      }
      leaf period {
        type uint32 {
          range "1..65535";
        }
        units "min";
        default "5";
        description
          "Specifies a period for consecutive authentication failures.";
      }
      leaf reactive-time {
        type uint32 {
          range "0..65535";
        }
        units "min";
        default "5";
        description
          "Specifies an automatic activation time for a locked account. 0 indicates that the locked account will not be unlocked automatically.";
      }
    }
    container user-security-policy {
      description
        "Configure local user security policy.";
      leaf security-policy {
        type boolean;
        default "true";
        description
          "Enable/disable the local user security policy function.";
      }
      leaf user-aging-period {
        type uint32 {
          range "1..365";
        }
        description
          "The period of user age.";
      }
      leaf user-name-min-len {
        type uint32 {
          range "0..253";
        }
        default "0";
        description
          "The minimum length of username, 0 indicates that the length is not limited.";
      }
    }
    container password-policy {
      must "(./complexity-check = 'true' and ./complexity-check-three = 'false' and ./complexity-check-four = 'false') or (./complexity-check = 'false' and ./complexity-check-three = 'true' and ./complexity-check-four = 'false') or (./complexity-check = 'false' and ./complexity-check-three = 'false' and ./complexity-check-four = 'true')";
      description
        "Configure local-user password policy.";
      leaf enable {
        type boolean;
        default "false";
        description 
          "Enable/disable the password policy for local administrators and enters the local administrator password policy.";
      }
      leaf expire-days {
        type uint16 {
          range "0..999";
        }
        units "d";
        must "../prompt-days<=../expire-days";
        default "0";
        description
          "Password expire days, 0 indicates that password is useful forever.";
      }
      leaf prompt-days {
        type uint16 {
          range "0..999";
        }
        units "d";
        must "../prompt-days<=../expire-days";
        default "0";
        description
          "Password prompt days.";
      }
      leaf change-check {
        type boolean;
        default "false";
        description
          "Enable/disable the function to prompt a user to change the password upon first-time use.";
      }
      leaf history-record-number {
        type uint8 {
          range "0..12";
        }
        default "5";
        description "Indicates the maximum number of historical passwords recorded for each user.";
      }
      leaf complexity-check {
        type boolean;
        default "false";
        description
          "Enable/disable password complexity check.";
      }
      leaf complexity-check-three {
        type boolean;
        default "false";
        description
          "Enable/disable that a password must contain at least three of the following: uppercase letters, lowercase letters, digits, and special characters.";
      }
      leaf pwd-min-length {
        type uint32 {
          range "3..128";
        }
        description
          "Specifies a minimum password length for local users.";
      }
      leaf expired-pwd-reuse-num {
        type uint32;
        config false;
        description
          "Max. Number of times to reuse expired password.";
      }
      leaf history-pwd-num {
        type uint32 {
          range "1..20";
        }
        default "10";
        description
          "History password number.";
      }
      leaf pwd-expire-days {
        type uint32;
        units "d";
        config false;
        description
          "The password will expire in the special days.";
      }
      leaf pwd-force-change {
        type boolean;
        default "true";
        description
          "Enable/disable the function of forcing a user to change the password upon first use.";
      }
      leaf complexity-check-four {
        type boolean;
        default "true";
        description
          "Enable/disable that a password must contain at least four of the following: uppercase letters, lowercase letters, digits, and special characters.";
      }
	  leaf similar-to-name-check {
        type boolean;
        default "true";
        description
          "Enable/disable user-name similar check.";
      }
      leaf similar-to-name-check-type{
        when "../similar-to-name-check='true'";
        type enumeration {
          enum "normal" {
            value 0;
            description
              "Enable normal user-name similar check.";
          }
          enum "enhance" {
            value 1;
            description
              "Enable enhanced user-name similar check.";
          }
        }
        default "normal";
        description
          "Specify user-name similar check type.";
      }      
	  leaf pwd-salt {
        type aaa-pwd-salt-type;
        default "default-salt";
        description
          "User password salt type.";
      }
    }
    container username-policy {
        description
            "Configure local-user name policy.";
        leaf username-complexity-check {
            type boolean;
            default "true";
            description
            "Enable/disable user-name complexity check.";
        }
    }
    container user-password-policy {
      description 
        "Configure access user password policy.";
      leaf enable {
        type boolean;
        default "false";
        description "Enable/disable the password policy for local access users and enters the local access user password policy.";
      }
      leaf history-record-number {
        when "../enable='true'";
        type uint8 {
          range "0..12";
        }
        default "5";
        description "Indicates the maximum number of historical passwords recorded for each user.";
      }
      leaf expire-days {
        when "../enable='true'";
        type uint16 {
          range "0..999";
        }
        units "d";
        default "90";
        description
          "Password expire days, 0 indicates that password is useful forever.";
      }
      leaf original-alert {
        when "../enable='true'";
        type boolean;
        default "true";
        description
          "Enable/disable the function to prompt a user to change the password upon first-time use.";
      }
      leaf complexity-check {
          type enumeration {
            enum "complexity-check-two" {
                value 2;
                description
                  "Password must contain at least two of the following: uppercase letters, lowercase letters, digits, and special characters.";
            }
            enum "complexity-check-three" {
                value 3;
                description
                  "Password must contain at least three of the following: uppercase letters, lowercase letters, digits, and special characters.";
            }
            enum "complexity-check-four" {
                value 4;
                description
                  "Password must contain at least four of the following: uppercase letters, lowercase letters, digits, and special characters.";
            }
          }
          default "complexity-check-two";
          description
            "Configure the password complexity-check.";
        }
    }
    container forbidden-word-rules {
      description
        "List of password black.";
      list forbidden-word-rule {
        key "forbidden-word";
        description
          "Configure password forbidden rule.";
        leaf forbidden-word {
          type string {
            length "1..255";
          }
          ext:case-sensitivity lower-or-upper;
          description
            "Forbidden word.";
        }
      }
    }
    container users {
      description
        "List of local user.";
      list user {
        must "not (./end-life-date and ./time-range)";
        key "name";
        description
          "Configure local user.";
        leaf name {
          type string {
            length "1..253";
          }
          must "(../../../aaa:username-policy/aaa:username-complexity-check='true' and (string-length(current())>=6)) or ../../../aaa:username-policy/aaa:username-complexity-check='false'";
          description
            "Name of a local user. The minimum length of a username is determined by user-name-min-len and security-policy. If security-policy is set to false and user-name-min-len is configured, the configuration takes effect. When security-policy is set to true, the minimum length of the username must be at least 6 characters. If user-name-min-len is configured and the user-name-min-len value is greater than 6 characters, the minimum length of the username is equal to the user-name-min-len value. If security-policy is set to false and user-name-min-len is not configured, the minimum length of the username is 1. If the username contains more than 32 characters, service-snmp cannot be set to true.";
        }
        leaf end-life-date {
          type pub-type:date;
          description
            "The end date of local user's life.";
        }
        leaf time-range {
          type string {
            length "1..32";
            pattern '([a-zA-Z]([^\s]*))';
          }
          description "Time range.";
        }
        leaf is-login-anytime {
          type boolean;
          must "(not(../begin-login-day='sun' and ../end-login-day='sat' and ../begin-login-time='00:00:00' and ../end-login-time='23:59:59') and ../is-login-anytime='false') or (../begin-login-day='sun' and ../end-login-day='sat' and ../begin-login-time='00:00:00' and ../end-login-time='23:59:59' and ../is-login-anytime='true')";
          default "true";
          description
            "Enable/disable the flag of login anytime.";
        }
        leaf begin-login-day {
          type lam-weekday-type;
          must "not(../is-login-anytime='true') or (../is-login-anytime='true' and ../begin-login-day='sun')";
          default "sun";
          description
            "The begin day of week for login.";
        }
        leaf end-login-day {
          type lam-weekday-type;
          must "not(../is-login-anytime='true') or (../is-login-anytime='true' and ../end-login-day='sat')";
          default "sat";
          description
            "The end day of week for login.";
        }
        leaf begin-login-time {
          type pub-type:time;
          must "not(../is-login-anytime='true') or (../is-login-anytime='true' and ../begin-login-time='00:00:00')";
          default "00:00:00";
          description
            "The begin time of every login day. The begin-login-time must be five or more minutes earlier than the end-login-time.";
        }
        leaf end-login-time {
          type pub-type:time;
          must "not(../is-login-anytime='true') or (../is-login-anytime='true' and ../end-login-time='23:59:59')";
          default "23:59:59";
          description
            "The end time of every login day. The end-login-time must be five or more minutes later than the begin-login-time.";
        }
        leaf aging-in-days {
          type uint32 {
            range "0..365";
          }
          units "d";
          description
            "The user will age if not online in the special days.";
        }
        leaf password-expire-in-days {
          type uint32 {
            range "0..999";
          }
          units "d";
          description
            "The password will expire in the special days.";
        }
        leaf group-name {
          type string {
            length "1..32";
          }
          description
            "Name of the user group where the user belongs, it must be an existing user group. The user inherits all the rights of the user group.";
        }
        leaf state {
          type user-state-type;
          default "active";
          description
            "Activated state of a user.";
        }
        leaf failed-times {
          when "../state='active'";
          type uint32 {
            range "0..10";
          }
          must "(../interval!=0) or (../failed-times=0 and ../interval=0)";
          default "0";
          description
            "When user continuous authen failed times reach the limit, the user is locked.";
        }
        leaf interval {
          when "../state='active'";
          type uint32 {
            range "0..65535";
          }
          units "min";
          must "(../failed-times!=0) or (../failed-times=0 and ../interval=0)";
          default "0";
          description
            "Set a user lockout period (in minutes). If a user is locked due to consecutive authentication failures, the user is automatically unlocked after the set period expires. 0 indicats that the locked user is not automatically unlocked.";
        }
        leaf password-type {
          type aaa-pwd-mode-type;
          must "../password";
          default "irreversible-cipher";
          description
            "Set a password type, which can be cipher or irreversible-cipher. Cipher passwords are encrypted and generated using the reversible algorithm, while irreversible-cipher passwords are encrypted and generated using the irreversible algorithm.";
        }
        leaf password {
          type pub-type:password-extend {
            length "1..268";
          }
          mandatory true;
          description
            "Login password of a user, which is a string ranging from 1 to 128 characters for a unencrypted password and 32 to 268 characters for a encrypted password. The password can contain letters, numbers, and special characters. Chinese characters are not supported. The minimum length and complexity of a user password are restricted by pwd-min-length, security-policy, complexity-check, and forbidden-word. In addition, complexity verification is enabled. The complexity requirements are as follows: (1) A password must contain digits, uppercase letters, lowercase letters, and special characters. Spaces and question marks are not supported. If the password is enclosed in quotation marks, spaces are allowed in the password. (2) The password cannot contain an account or the reverse string of an account. (3) The new password cannot be the same as any of the previous 10 passwords. (If the new password is the same as the current password, the new password is also considered as a history password. That is, the current password is included in the 10 history passwords.) This parameter takes effect when the password complexity check is enabled (complexity-check is set to true). If forbidden-word is configured, the password cannot contain forbidden words. If only the pwd-min-length value is set, the pwd-min-length setting takes effect. If the minimum length of a password is set and the pwd-min-length value is greater than 6 characters, the minimum length of a password is determined by the pwd-min-length value.";
        }
        leaf level {
          type uint32 {
            range "0..15";
          }
          description
            "Login level of a local user. If the command level adjustment function is disabled, the value of user level ranges from 0 to 3. If the command level adjustment function is enabled, the value of user level ranges from 0 to 15.";
        }
        leaf ftp-dir {
          type string {
            length "1..255";
          }
          description
            "FTP user directory.";
        }
        leaf ftp-dir-access {
          when "../ftp-dir";
          type aaa-directory-type;
          default "read-write-execute";
          description
            "FTP user directory access permission.";
        }
        leaf http-dir {
          type string {
            length "1..64";
          }
          description 
            "Access directory.";
        }
        leaf service-none {
          type boolean;
          default "true";
          description
            "Enable/disable login through none.";
        }
        leaf service-terminal {
          type boolean;
          default "false";
          description
            "Enable/disable login through a terminal.";
        }
        leaf service-telnet {
          type boolean;
          default "false";
          description
            "Enable/disable login through Telnet.";
        }
        leaf service-ftp {
          type boolean;
          default "false";
          description
            "Enable/disable login through FTP.";
        }
        leaf service-ppp {
          type boolean;
          default "false";
          description
            "Enable/disable login through PPP.";
        }
        leaf service-ssh {
          type boolean;
          default "false";
          description
            "Enable/disable login through SSH.";
        }
        leaf service-qx {
          type boolean;
          default "false";
          description
            "Enable/disable login through QX.";
        }
        leaf service-snmp {
          type boolean;
          must "(../service-snmp='false') or (../service-snmp='true' and string-length(current()/../name)<32)";
          default "false";
          description
            "Enable/disable login through SNMP.";
        }
        leaf service-mml {
          type boolean;
          default "false";
          description
            "Enable/disable login through MML.";
        }
        leaf service-http {
          type boolean;
          default "false";
          description
            "Enable/disable login through HTTP.";
        }
        leaf service-mdcli {
          type boolean;
          default "false";
          description
            "Enable/disable login through MD-CLI.";
        }
        leaf service-bind {
          type boolean;
          default "false";
          description
            "Enable/disable login through BIND.";
        }
        leaf service-sslvpn {
          type boolean;
          default "false";
          description
            "Enable/disable login through SSLVPN.";
        }
        leaf service-web {
          type boolean;
          default "false";
          description
            "Enable/disable login through WEB.";
        }
        leaf service-x25-pad {
          type boolean;
          default "false";
          description
            "Enable/disable login through X25-PAD.";
        }
        leaf service-api {
          type boolean;
          default "false";
          description
            "Enable/disable login through API.";
        }
        leaf max-access-num {
          type uint32 {
            range "1..4294967295";
          }
          default "4294967295";
          description
            "The local user max access number.";
        }
        leaf idle-cut-enable {
          type boolean;
          default "true";
          description
            "Enable/disable configures the idle cut function for a local user.";
        }
        leaf idle-time {
          type int32 {
            range "0..2147483647";
          }
          units "s";
          description 
            "Specifies the timeout period for disconnection of the user.";
        }
        leaf user-type {
          type boolean;
          default "false";
          description 
            "Enable/disable a local user as the NMS user.";
        }
        leaf acl {
          type string {
            length "1..64";
            pattern '([1-9]\d{3})|(10[0-9]{3})|(23[0-9]{3})|(99999)|([0-9a-zA-Z]([^\s]*))';
          }
          description 
            "Access control list to which the administrator bind.";
        }
        leaf password-force-change {
          type boolean;
          default "true";
          description
            "Enable/disable the function of forcibly changing the initial password for a specified user.";
        }
        leaf-list device-type {
          type string {
            length "1..31";
          }
          description 
            "Configure a terminal type. Case-insensitive characters without spaces.";
        }
        leaf begin-life-date {
          type pub-type:date;
          config false;
          description
            "The begin date of local user's life.";
        }
        leaf last-login-time {
          type yang:date-and-time;
          config false;
          description
            "The last login time.";
        }
        leaf is-aged {
          type aaa-bool-type;
          config false;
          description
            "Whether the user is aged now.";
        }
        leaf is-locked {
          type aaa-bool-type;
          config false;
          description
            "Whether the user is locked now.";
        }
        leaf left-lock-time {
          type uint32 {
            range "1..4294967295";
          }
          units "s";
          config false;
          description
            "Left lock time of locked user.";
        }
        leaf is-terminal-locked {
          type aaa-bool-type;
          config false;
          description
            "Whether the user is terminal locked now.";
        }
        leaf terminal-left-lock-time {
          type uint32 {
            range "1..4294967295";
          }
          units "s";
          config false;
          description
            "Left lock time of terminal locked user.";
        }
        leaf pass-modify-time {
          type yang:date-and-time;
          config false;
          description
            "Password modify time.";
        }
        leaf is-pass-expired {
          type is-pass-expired-type;
          config false;
          description
            "Whether the password of this user name expires.";
        }
        leaf is-pass-changed {
          type boolean;
          config false;
          description
            "Whether the password of this user name is changed by the user.";
        }
        leaf alive-num {
          type int32 {
            range "0..2147483647";
          }
          config false;
          description
            "Online number of the local user.";
        }
        leaf create-time {
          type yang:date-and-time;
          config false;
          description
            "User creation time.";
        }
        leaf private {
          type boolean;
          default "false";
          description
            "Enable/disable Private user.";
        }
        container bind-addresses{
          description
            "List of IP address bound to local user.";
          list bind-address {
            key "ip-address mask-length";
            max-elements  "15";
            description
              "Configure local user bind IP address.";
            leaf ip-address {
              type inet:ip-address-no-zone;
              description
                "Specify the destination IP address.";
            }
            leaf mask-length {
              type uint8;
              must "(contains(../ip-address, ':') and (. >= 1 and . <= 128)) or (not(contains(../ip-address, ':')) and (. >= 1 and . <= 32))";
              description
                "Specify the subnet mask length for the IP address: 1-32 for IPv4 and 1-128 for IPv6.";
            }
          }
        }       
      }
    }
    container access-users {
      description
        "List of Local access user.";
      list access-user {
        must "(./password-type and ./password) or (not (./password-type) and not (./password))";
        must "(not(service-none='true' and (service-portal='true' or service-dot1x='true' or service-sslvpn='true' or service-ppp='true')))";
        must "(not(service-none='false' and (service-portal='false' and service-dot1x='false' and service-sslvpn='false' and service-ppp='false')))";
        key "name";
        description
          "Configure to Local access user.";
        leaf name {
          type string {
            length "1..66";
          }
          description
            "Name of a local user, it is not case sensitive.";
        }
        leaf state {
          type user-state-type;
          default "active";
          description
            "Activated state of a user.";
        }
        leaf service-none {
          type boolean;
          default "true";
          description
            "Enable/disable login through none.";
        }
        leaf service-portal {
          type boolean;
          default "false";
          description
            "Enable/disable indicates a portal user.";
        }
        leaf service-dot1x {
          type boolean;
          default "false";
          description
            "Enable/disable indicates a dot1x user.";
        }
        leaf service-sslvpn {
          type boolean;
          default "false";
          description
            "Enable/disable indicates a SSLVPN user.";
        }
        leaf service-ppp {
          type boolean;
          default "false";
          description
            "Enable/disable indicates a ppp user.";
        }
        leaf access-limit {
          type uint32 {
            range "1..4294967295";
          }
          default "4294967295";
          description
            "Local access user max access number. The default value is defined in the PAF file and is restored when the node is deleted.";
        }
        leaf end-life-date {
          type pub-type:date;
          description
            "The end date of local user's life.";
        }
        leaf time-range {
          type string {
            length "1..32";
            pattern '([a-zA-Z]([^\s]*))';
          }
          description
            "Time range.";
        }
        leaf password-type {
          type aaa-pwd-mode-type;
          description
            "Set a password type, which can be cipher or irreversible-cipher. Cipher passwords are encrypted and generated using the reversible algorithm, while irreversible-cipher passwords are encrypted and generated using the irreversible algorithm.";
        }
        leaf password {
          type pub-type:password-extend;
          description
            "Login password of a user, which is a string ranging from 1 to 128 characters for a unencrypted password and 32 to 268 characters for a encrypted password. The password can contain letters, numbers, and special characters. Chinese characters are not supported.";
        }
        leaf assigned-ip {
            type inet:ipv4-address-no-zone;
            description
                "Assign an IP address to a specified access-user.";
        }
        leaf-list ucl-group {
          type leafref {
            path "/hw-nac-group:nac-group/hw-nac-group:ucl-groups/hw-nac-group:ucl-group/hw-nac-group:name";
          }
          description
            "Configure to ucl group."; 
        }
        leaf-list ou-ucl-group {
          type leafref {
            path "/hw-nac-group:nac-group/hw-nac-group:ucl-groups/hw-nac-group:ucl-group/hw-nac-group:name";
          }
          must "/hw-nac-group:nac-group/hw-nac-group:ucl-groups/hw-nac-group:ucl-group[hw-nac-group:name=current()]/hw-nac-group:type='ou'";
          max-elements 1;
          description
            "Configure to organizational unit ucl group."; 
        }
        container bind-ipv4s {
          description
            "List of the IPv4 address bound a local access-user.";
          list bind-ipv4 {
            key "ip-address";
            description
              "Configure bind-IPv4.";
            leaf ip-address {
              type inet:ipv4-address-no-zone;
              description
                "Specifies a Local access user bind IPv4.";
            }        
            leaf ip-exclusive {
              type boolean;
              must "../ip-address";
              default "false";
              description
                "Enable/disable the bind IPv4 config exclusive.";
            }
            leaf mac {
              type pub-type:mac-address;
              must "../ip-address";
              description
                "Specifies a Local access user bind mac after ip.";
            }
            leaf mac-exclusive {
              type boolean;
              must "(../ip-address) and (../mac)";
              default "false";
              description
                "Enable/disable the bind mac after ip config exclusive.";
            }
          }
        }
        container bind-macs {
          description
            "List of the mac address bound a local access-user.";
          list bind-mac {
            key "mac";
            description
              "Configure bind-mac.";
            leaf mac {
              type pub-type:mac-address;
              description
                "Specifies a Local access user bind mac.";
            }
            leaf mac-exclusive {
              type boolean;
              must "../mac";
              default "false";
              description
                "Enable/disable the bind mac config exclusive.";
            }
          }
        }
      }
    }
  }
  grouping aaa-local-server-type {
    description
      "Local aaa server.";
    container login-failed-limit {
      description
        "Configure the maximum number of login attempts allowed in the specified period.";
      leaf failed-times {
        type uint32 {
          range "0..10";
        }
        default "5";
        description
          "Indicates the consecutive failure times. 0 indicates that the number of times that a user fails authentication continuously is not restricted.";
      }
      leaf period {
        type uint32 {
          range "1..120";
        }
        units "min";
        default "5";
        description
          "Specifies a period for consecutive authentication failures.";
      }
      leaf reactive-time {
        type uint32 {
          range "0..1000";
        }
        units "min";
        default "5";
        description
          "Specifies an automatic activation time for a locked account. 0 indicates that the locked account will not be unlocked automatically.";
      }
    }
    container user-security-policy {
      description
        "Configure a local user security policy.";
      leaf user-aging-period {
        type uint32 {
          range "1..365";
        }
        description
          "Specifies an aging period for an administrator.";
      }
      leaf user-name-min-len {
        type uint32 {
          range "0..253";
        }
        default "0";
        description
          "Specifies the minimum length for user names. 0 indicates that the length is not limited.";
      }
    }
    container password-policy {
      description
        "Configure a local user password policy.";
      leaf expire-days {
        type uint16 {
          range "0..365";
        }
        units "d";
        must "../prompt-days<=../expire-days";
        default "0";
        description
          "Specifies an expiration period for a password. 0 indicates that a password is permanently valid.";
      }
      leaf prompt-days {
        type uint16 {
          range "0..180";
        }
        units "d";
        must "../prompt-days<=../expire-days";
        default "0";
        description
          "Specifies a remaining validity period for a password.";
      }
      leaf change-check {
        type boolean;
        default "false";
        description
          "Enable/disable mandatory password change when a password is used for the first time.";
      }
      leaf complexity-check {
        type boolean;
        default "false";
        description
          "Enable/disable password complexity enhancement.";
      }
      leaf pwd-min-length {
        type uint32 {
          range "3..128";
        }
        description
          "Specifies the minimum length for passwords configured for local users.";
      }
    }
  }
  rpc change-current-password {
    description
      "Modify password of current access-user.";
    input {
      leaf old-password {
        type pub-type:one-input-password-extend {
             length "1..268";
        }
        mandatory true;
        description
          "The old password of the local user.";
      }
      leaf new-password {
        type pub-type:password-extend {
             length "1..268";
        }
        mandatory true;
        description
          "New password to set.";
      }
    }
  }
}
