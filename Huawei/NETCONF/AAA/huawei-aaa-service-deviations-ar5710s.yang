/*
Copyright (C) 2019 Huawei Technologies Co., Ltd. All rights reserved.
*/
module huawei-aaa-service-deviations-ar5710s {
  yang-version 1;
  namespace "urn:huawei:yang:huawei-aaa-service-deviations-ar5710s";
  prefix aaa-service-devs-ar5710s;

  import huawei-aaa-service {
    prefix aaa-service;
  }
  import huawei-aaa {
    prefix aaa;
  }

  organization
    "Huawei Technologies Co., Ltd.";
  contact
    "Huawei Industrial Base
     Bantian, Longgang
     Shenzhen 518129
     People's Republic of China
     Website: http://www.huawei.com
     Email: support@huawei.com";
  description
    "This module defines deviation statements for huawei-aaa-service module.";

  revision 2019-11-06 {
    description
      "Initial revision.";
    reference "Huawei private.";
  }

  deviation "/aaa-service:aaa-service/aaa-service:service-schemes/aaa-service:service-scheme/aaa-service:dhcp-group" {
    deviate not-supported;
  }
  deviation "/aaa-service:aaa-service/aaa-service:service-schemes/aaa-service:service-scheme/aaa-service:voice-vlan-enable" {
    deviate not-supported;
  }
  deviation "/aaa-service:aaa-service/aaa-service:service-schemes/aaa-service:service-scheme/aaa-service:sac-profile" {
    deviate not-supported;
  }
  deviation "/aaa-service:aaa-service/aaa-service:service-schemes/aaa-service:service-scheme/aaa-service:ucl-group" {
    deviate not-supported;
  }
  deviation "/aaa-service:aaa-service/aaa-service:service-schemes/aaa-service:service-scheme/aaa-service:user-name-access-max-num" {
    deviate not-supported;
  }
  deviation "/aaa-service:aaa-service/aaa-service:service-schemes/aaa-service:service-scheme/aaa-service:vlan-pool" {
    deviate not-supported;
  }
  deviation "/aaa-service:aaa-service/aaa-service:service-schemes/aaa-service:service-scheme/aaa-service:ip-pool" {
    deviate not-supported;
  }
  deviation "/aaa-service:aaa-service/aaa-service:service-schemes/aaa-service:service-scheme/aaa-service:acl-ipv6" {
    deviate not-supported;
  }
  deviation "/aaa-service:aaa-service/aaa-service:service-schemes/aaa-service:service-scheme/aaa-service:l2-lan-isolate" {
    deviate not-supported;
  }
  deviation "/aaa-service:aaa-service/aaa-service:service-schemes/aaa-service:service-scheme/aaa-service:split-tunnel-enable" {
    deviate not-supported;
  }
  deviation "/aaa-service:aaa-service/aaa-service:service-schemes/aaa-service:service-scheme/aaa-service:split-tunnel-acl" {
    deviate not-supported;
  }
  deviation "/aaa-service:aaa-service/aaa-service:service-schemes/aaa-service:service-scheme/aaa-service:defence-profile" {
    deviate not-supported;
  }
  deviation "/aaa-service:aaa-service/aaa-service:service-schemes/aaa-service:service-scheme/aaa-service:dns" {
    deviate not-supported;
  }
  deviation "/aaa-service:aaa-service/aaa-service:service-schemes/aaa-service:service-scheme/aaa-service:wins" {
    deviate not-supported;
  }
  deviation "/aaa-service:aaa-service/aaa-service:service-schemes/aaa-service:service-scheme/aaa-service:daas" {
    deviate not-supported;
  }
  deviation "/aaa-service:aaa-service/aaa-service:service-schemes/aaa-service:service-scheme/aaa-service:policy-route" {
    deviate not-supported;
  }
  deviation "/aaa-service:aaa-service/aaa-service:service-schemes/aaa-service:service-scheme/aaa-service:redirect-acl-ipv6" {
    deviate not-supported;
  }
  deviation "/aaa-service:aaa-service/aaa-service:service-schemes/aaa-service:service-scheme/aaa-service:auto-update-url" {
    deviate not-supported;
  }
  deviation "/aaa-service:aaa-service/aaa-service:service-schemes/aaa-service:service-scheme/aaa-service:route-set" {
    deviate not-supported;
  }
  deviation "/aaa-service:aaa-service/aaa-service:service-schemes/aaa-service:service-scheme/aaa-service:egress-vlans" {
    deviate not-supported;
  }
  deviation "/aaa:aaa/aaa:domains/aaa:domain/aaa-service:daas" {
    deviate not-supported;
  }
  deviation "/aaa:aaa/aaa:lam/aaa:access-users/aaa:access-user/aaa-service:service-scheme" {
    deviate not-supported;
  }
  deviation "/aaa-service:aaa-service/aaa-service:service-schemes/aaa-service:service-scheme/aaa-service:name" {
    deviate replace {
      type string {
        length "1..32";
        pattern '[!-~]+';
        pattern '([^/\*":?<>|]{3,32})|([^/\*":?<>|-]-)|(-[^/\*":?<>|-])|([^/\*":?<>|-]{1,2})';
      }
    }
  }
  deviation "/aaa-service:aaa-service/aaa-service:service-schemes/aaa-service:service-scheme/aaa-service:admin-user-privilege-level" {
    deviate replace {
      type uint8 {
        range "0..3";
      }
    }
  }
  deviation "/aaa-service:aaa-service/aaa-service:service-schemes/aaa-service:service-scheme/aaa-service:acl" {
    deviate add {
      max-elements 1;
    }
    deviate replace {
      type string {
        length "1..64";
        pattern '3\d{3}';
      }
    }
  }
  deviation "/aaa-service:aaa-service/aaa-service:service-schemes/aaa-service:service-scheme/aaa-service:idle-cut-function/aaa-service:idle-flow/aaa-service:flow-direction" {
    deviate replace {
      type enumeration {
        enum inbound {
          value 0;
          description
            "Indicates that the idle-cut function takes effect for only upstream traffic of users.";
        }
        enum outbound {
          value 1;
          description
            "Indicates that the idle-cut function takes effect for only downstream traffic of users.";
        }
      }
    }
  }
}
