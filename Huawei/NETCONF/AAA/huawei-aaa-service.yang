/*
Copyright (C) 2020-2025 Huawei Technologies Co., Ltd. All rights reserved.
*/
module huawei-aaa-service {
  yang-version 1;
  namespace "urn:huawei:yang:huawei-aaa-service";
  prefix aaa-service;
  import huawei-aaa {
    prefix aaa;
  }
  import huawei-qos {
    prefix qos;
  }
  import huawei-acl {
    prefix acl;
  }
  import huawei-extension {
    prefix ext;
  }
  import huawei-dhcp {
    prefix dhcp;
  }
  import ietf-inet-types {
    prefix inet;
  }
  import huawei-pub-type {
    prefix pub-type;
  }
  organization
    "Huawei Technologies Co., Ltd.";
  contact
    "Huawei Industrial Base
    Bantian, Longgang
    Shenzhen 518129
    People's Republic of China
    Website: http://www.huawei.com
    Email: support@huawei.com";
  description
    "Security management, which includes the management on service scheme.";
  revision 2025-04-17 {
    description
      "Modify flow-value and flow-direction, the length of ucl-group and defence-profile.";
    reference
      "Huawei private.";
  }
  revision 2025-03-01 {
    description
      "Modify defence profile.";
    reference
      "Huawei private.";
  }
  revision 2024-10-21 {
    description
      "Add defence profile.";
    reference
      "Huawei private.";
  }
  revision 2024-08-20 {
    description
      "Add l2-lan-isolate.";
    reference
      "Huawei private.";
  }
  revision 2024-08-14 {
    description
      "Add split-tunnel.";
    reference
      "Huawei private.";
  }
  revision 2024-07-09 {
    description
      "Add egress-VLAN.";
    reference
      "Huawei private.";
  }
  revision 2024-05-25 {
    description
      "Add must condition for redirect-acl. Add must condition for redirect-acl-IPv6.";
    reference
      "Huawei private.";
  }
  revision 2024-05-14 {
    description
      "Modify the maximum length of the service scheme name.";
    reference
      "Huawei private.";
  }
  revision 2024-03-14 {
    description
      "Delete container remote-authorize and local-authorize.";
    reference
      "Huawei private.";
  }
  revision 2023-12-22 {
    description
      "Add nodes for NAC.";
    reference
      "Huawei private.";
  }
  revision 2023-07-25 {
    description
      "Add sac-profile.";
    reference
      "Huawei private.";
  }
  revision 2023-02-23 {
    description
      "Modify qos-profile leafref path.";
    reference
      "Huawei private.";
  }
  revision 2022-09-22 {
    description
      "Add leaf node VLAN-POOL in list service-scheme.";
    reference
      "Huawei private.";
  }
  revision 2020-03-02 {
    description
      "Init revision.";
    reference
      "Huawei private.";
  }
  grouping daa-parameters {
    description
      "Configure the QoS profile and accounting function.";
    container daas {
      description
        "List of the QoS profile and accounting function.";
      list daa {
        key "traffic-level";
        description
          "Configure the QoS profile and accounting function list.";
        leaf traffic-level {
          type uint8 {
            range "1..6";
          }
          description
            "Specifies the tariff level.";
        }
        leaf accounting-on {
          type boolean;
          default "false";
          description
            "Enable/disable accounting for the tariff level.";
        }
        leaf qos-profile {
          type leafref {
            path "/qos:qos/qos:integration-template/qos:profiles/qos:profile/qos:name";
          }
          description
            "Specifies the name of the QoS profile corresponding to the tariff level.";
        }
      }
    }
  }
  container aaa-service {
    description
      "Security management, which includes the management on authentication, authorization, accounting, domains, and users.";
    container service-schemes {
      description
        "List of service scheme.";
      list service-scheme {
        key "name";
        description
          "Configure service scheme.";
        leaf name {
          type string {
            length "1..64";
          }
          description
            "Specifies the name of a service scheme.";
        }
        leaf admin-user-privilege-level {
          type uint8 {
            range "0..15";
          }
          description
            "Configure a user as an administrator to log in to the device and sets the user level.";
        }
        leaf dhcp-group {
          type string {
            length "1..32";
          }
          description
            "Specifies the name of a DHCP server group.";
        }
        leaf vlan {
          type uint16 {
            range "1..4094";
          }
          description
            "Specifies the VLAN ID.";
        }
        leaf voice-vlan-enable {
          type boolean;
          default "false";
          description
            "Enable/disable the voice VLAN in a service scheme.";
        }
        leaf qos-profile {
          type leafref {
            path "/qos:qos/qos:integration-template/qos:profiles/qos:profile/qos:name";
          }
          description
            "Specifies the name of the QoS profile bound to the service scheme.";
        }
        leaf sac-profile {
          type string {
            length "1..35";
          }
          description
            "Specifies the name of the SAC profile bound to the service scheme.";
        }
        leaf ucl-group {
          type string {
            length "1..255";
          }
          description
            "Specifies the name of a UCL group.";
        }
        leaf priority {
          type uint8 {
            range "0..1";
          }
          default "0";
          description
            "Configure the user priority in a service scheme.";
        }
        leaf user-name-access-max-num {
          type uint32 {
              range "0..10035";
          }
          description
            "Configure the maximum number of users who are allowed to access the network using the same user name. Default is determined by the maximum number of access users supported by the device.";
        }
        leaf vlan-pool {
          type string {
            length "1..31";
          }
          description
            "Specifies the VLAN POOL name.";
        }
        leaf-list ip-pool {
          type leafref {
            path "/dhcp:dhcp/dhcp:server/dhcp:global-ip-pools/dhcp:global-ip-pool/dhcp:ip-pool-name";
          }
          description
            "Configure the IP address pool name.";
        }
        leaf-list acl {
          type string {
            length "1..64";
            pattern '([1-9]\d{3})|(10[0-9]{3})|(23[0-9]{3})|(99999)|([0-9a-zA-Z]([^\s]*))';
          }
          description
            "Configure the number of an ACL bound to a service scheme.";
        }
        leaf-list acl-ipv6 {
          type string {
            length "1..64";
            pattern '([1-3]\d{3})|([6-9]\d{3})|([0-9a-zA-Z]([^\s]*))';
          }
          description
            "Configure the number of an IPv6 ACL bound to a service scheme.";
        }
        leaf l2-lan-isolate {
          type boolean;
          default "false";
          description "Enable/disable the l2-lan isolate in a service scheme.";
        }
        leaf split-tunnel-enable {
          type boolean;
            default "false";
            description
              "Enable/disable the split-tunnel function.";
        }
        leaf split-tunnel-acl {
          when "../split-tunnel-enable='true'" {
            description
              "When split-tunnel enable is true.";
          }
          type uint32 {
            range "3000..3031";
          }
          description
            "Specifies the acl num of the split tunnel.";
        }
        leaf defence-profile {
          type string {
            length "1..32";
          }
          description
            "Specifies the name of the defence profile name bound to the service scheme.";
        }
        container dns {
          description
            "Configure the primary or secondary DNS server in a service scheme.";
          leaf primary-ip-address {
            type inet:ip-address-no-zone;
            description
              "Specifies the IP address of a DNS server.";
          }
          leaf secondary-ip-address {
            type inet:ip-address-no-zone;
            description
              "Specifies the secondary DNS server.";
          }
          leaf dns-name {
            type string {
              length "1..255";
            }
            description
              "Specifies the default DNS domain name.";
          }
        }
        container wins {
          description
            "Configure the primary or secondary WINS server address in the service scheme.";
          leaf primary-ip-address {
            type inet:ip-address-no-zone;
            description
              "Indicates the WINS server address configured in a service scheme.";
          }
          leaf secondary-ip-address {
            type inet:ip-address-no-zone;
            description
              "Indicates that the IP address of the secondary WINS server is configured.";
          }
        }
        container idle-cut-function {
          description
            "Configure the idle-cut function for domain users and sets the idle-cut parameters.";
          leaf idle-time {
            type uint16 {
              range "1..1440";
            }
            units "min";
            description
              "Specifies the period in which an idle user can stay online.";
          }
          container idle-flow {
            description
              "Configure idle flow.";
            leaf flow-value {
              when "../../idle-time";
              type uint32 {
                range "0..4294967295";
              }
              units "kB";
              description
                "Specifies the traffic threshold for idle-cut function.";
            }
            leaf flow-direction {
              when "../flow-value";
              type enumeration {
                enum "inbound" {
                  value 0;
                  description
                    "Indicates that the idle-cut function takes effect for only upstream traffic of users.";
                }
                enum "outbound" {
                  value 1;
                  description
                    "Indicates that the idle-cut function takes effect for only downstream traffic of users.";
                }
                enum "allbound" {
                  value 2;
                  description
                    "Indicates that the idle-cut function takes effect for upstream and downstream traffic of users.";
                }
              }
              description
                "Flow direction. If neither inbound nor outbound is specified, the idle-cut function takes effect for both upstream and downstream traffic.";
            }
          }
        }
        uses daa-parameters;
        container policy-route {
          description
            "Configure the policy route function for users bound to the service scheme.";
          leaf next-hop {
            type inet:ip-address-no-zone;
            description
              "Specifies the next hop address of policy-based routing.";
          }
          leaf vlan {
            type uint16 {
              range "1..4094";
            }
            description
              "Specifies the VLAN ID of the source route.";
          }
        }
        container redirect-acl {
          description
            "Configure the ACL used for redirection in a service scheme.";
          leaf acl {
            type leafref {
              path "/acl:acl/acl:groups/acl:group/acl:identity";
            }
            must "/acl:acl/acl:groups/acl:group[acl:identity=current()]/acl:type='advance'";
            description
              "Specifies the number or name of the ACL used for redirection.";
          }
        }
        container redirect-acl-ipv6 {
          description
            "Configure the IPv6 ACL used for redirection in a service scheme.";
          leaf acl {
            type leafref {
              path "/acl:acl/acl:group6s/acl:group6/acl:identity";
            }
            must "/acl:acl/acl:group6s/acl:group6[acl:identity=current()]/acl:type='advance'";
            description
              "Specifies the number or name of the ACL used for redirection.";
          }
        }
        container auto-update-url {
          description
            "Configure the URL and version number of a service scheme.";
          leaf url {
            type string {
              length "1..192";
            }
            description
              "Indicates the URL without password.";
          }
          leaf password {
            type pub-type:password;
            description
              "The password of the URL.";
          }
          leaf version {
            type uint32 {
              range "1..4294967294";
            }
            description
              "Indicates the version number.";
          }
        }
        container route-set {
          description
            "Configure the local subnet information to be sent to the remote end.";
          leaf acl-id {
            type string {
              length "1..64";
              pattern '([1-9]\d{3})|(10[0-9]{3})|(23[0-9]{3})|(99999)|([0-9a-zA-Z]([^\s]*))';
            }
            description
              "Specifies the number of the ACL to be sent to the remote end.";
          }
          leaf set-interface-enable {
            type boolean;
            default "false";
            description
              "Enable/disable the address of the interface bound to the IPSec tunnel to be sent to the remote end.";
          }
        }
        container egress-vlans {
          description
            "List of user egress VLAN ID.";
          list egress-vlan {
            key "vlan-id";
              description
                "Configure egress VLAN ID list.";
            leaf vlan-id {
              type uint16 {
                 range "1..4094"; 
              }
              description
                "Specifies the user egress VLAN ID.";
            }
            leaf vlan-type {
              type enumeration {
                enum "tagged" {
                  value 0;
                  description
                    "Indicates that the user egress VLAN type is tagged.";
                }
                enum "untagged" {
                  value 1;
                    description
                      "Indicates that the user egress VLAN type is untagged.";
                }
              }
              mandatory true;
              description
                "Specifies the user egress VLAN type.";
            }
          }
        }
      }
    }
  }
  augment /aaa:aaa/aaa:domains/aaa:domain {
    description
      "Augment aaa domain.";
    container service-scheme {
      description
        "Configure the service scheme used by the domain.";
      leaf name {
        type leafref {
          path "/aaa-service:aaa-service/aaa-service:service-schemes/aaa-service:service-scheme/aaa-service:name";
        }
        description
          "Name of the service scheme used by the domain, it is not case sensitive. The default value varies according to domains. The default value is restored when the node is deleted.";
      }
    }
    uses daa-parameters;
  }
  augment /aaa:aaa/aaa:lam/aaa:access-users/aaa:access-user {
    description
      "Augment aaa local access user.";
    container service-scheme {
      description
        "Configure the service scheme used by the access user.";
      leaf name {
        type leafref {
          path "/aaa-service:aaa-service/aaa-service:service-schemes/aaa-service:service-scheme/aaa-service:name";
        }
        description
          "Name of the service scheme used by the access-user, it is not case sensitive. The default value is empty.";
      }
    }
  }
  ext:task-name "aaa-service";
}
