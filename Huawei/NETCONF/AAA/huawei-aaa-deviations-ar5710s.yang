/*
Copyright (C) 2019 Huawei Technologies Co., Ltd. All rights reserved.
*/
module huawei-aaa-deviations-ar5710s {
  yang-version 1.1;
  namespace "urn:huawei:yang:huawei-aaa-deviations-ar5710s";
  prefix aaa-devs-ar5710s;

  import huawei-aaa {
    prefix aaa;
  }
  import huawei-extension {
    prefix ext;
  }
  import huawei-time-range {
    prefix timerange;
  }
  import huawei-pub-type {
    prefix pub-type;
  }
  import huawei-nac-portal {
    prefix hw-nac-portal;
  }

  organization
    "Huawei Technologies Co., Ltd.";
  contact
    "Huawei Industrial Base
     Bantian, Longgang
     Shenzhen 518129
     People's Republic of China
     Website: http://www.huawei.com
     Email: support@huawei.com";
  description
    "This module defines deviation statements for huawei-aaa module.";

  revision 2019-11-06 {
    description
      "Initial revision.";
    reference "Huawei private.";
  }

  deviation "/aaa:aaa/aaa:access-codes/aaa:access-code" {
    deviate not-supported;
  }
  deviation "/aaa:aaa/aaa:task-groups/aaa:task-group/aaa:task-group-task-maps/aaa:task-group-task-map/aaa:execute" {
    deviate not-supported;
  }
  deviation "/aaa:aaa/aaa:user-groups/aaa:user-group/aaa:user-group-task-group-maps/aaa:user-group-task-group-map/aaa:execute" {
    deviate not-supported;
  }
  deviation "/aaa:aaa/aaa:user-groups/aaa:user-group/aaa:user-group-include-maps" {
    deviate not-supported;
  }
  deviation "/aaa:aaa/aaa:authentication-schemes/aaa:authentication-scheme/aaa:authen-mode-type/aaa:ordered-strictly" {
    deviate not-supported;
  }
  deviation "/aaa:aaa/aaa:authentication-schemes/aaa:authentication-scheme/aaa:authentication-change" {
    deviate not-supported;
  }
  deviation "/aaa:aaa/aaa:authentication-schemes/aaa:authentication-scheme/aaa:authentication-super-mode" {
    deviate not-supported;
  }
  deviation "/aaa:aaa/aaa:authorization-schemes/aaa:authorization-scheme/aaa:author-mode-type/aaa:ordered-strictly" {
    deviate not-supported;
  }
  deviation "/aaa:aaa/aaa:authorization-schemes/aaa:authorization-scheme/aaa:no-lvl-first-cmd-author" {
    deviate not-supported;
  }
  deviation "/aaa:aaa/aaa:authorization-schemes/aaa:authorization-scheme/aaa:no-lvl-second-cmd-author" {
    deviate not-supported;
  }
  deviation "/aaa:aaa/aaa:authorization-schemes/aaa:authorization-scheme/aaa:authorization-cmds/aaa:authorization-cmd/aaa:cmd-author-mode-type/aaa:ordered-strictly" {
    deviate not-supported;
  }
  deviation "/aaa:aaa/aaa:domains/aaa:domain/aaa:admin-level" {
    deviate not-supported;
  }
  deviation "/aaa:aaa/aaa:domains/aaa:domain/aaa:access-limit" {
    deviate not-supported;
  }
  deviation "/aaa:aaa/aaa:domains/aaa:domain/aaa:time-range-enable" {
    deviate not-supported;
  }
  deviation "/aaa:aaa/aaa:domains/aaa:domain/aaa:service-terminal" {
    deviate not-supported;
  }
  deviation "/aaa:aaa/aaa:domains/aaa:domain/aaa:service-telnet" {
    deviate not-supported;
  }
  deviation "/aaa:aaa/aaa:domains/aaa:domain/aaa:service-ftp" {
    deviate not-supported;
  }
  deviation "/aaa:aaa/aaa:domains/aaa:domain/aaa:service-ppp" {
    deviate not-supported;
  }
  deviation "/aaa:aaa/aaa:domains/aaa:domain/aaa:service-ssh" {
    deviate not-supported;
  }
  deviation "/aaa:aaa/aaa:domains/aaa:domain/aaa:service-qx" {
    deviate not-supported;
  }
  deviation "/aaa:aaa/aaa:domains/aaa:domain/aaa:service-snmp" {
    deviate not-supported;
  }
  deviation "/aaa:aaa/aaa:domains/aaa:domain/aaa:service-mml" {
    deviate not-supported;
  }
  deviation "/aaa:aaa/aaa:domains/aaa:domain/aaa:service-http" {
    deviate not-supported;
  }
  deviation "/aaa:aaa/aaa:domains/aaa:domain/aaa:account-separate" {
    deviate not-supported;
  }
  deviation "/aaa:aaa/aaa:domains/aaa:domain/aaa:online-num" {
    deviate not-supported;
  }
  deviation "/aaa:aaa/aaa:domains/aaa:domain/aaa:band-width" {
    deviate not-supported;
  }
  deviation "/aaa:aaa/aaa:login-alarm-threshold" {
    deviate not-supported;
  }
  deviation "/aaa:aaa/aaa:alive-user-statistics" {
    deviate not-supported;
  }
  deviation "/aaa:aaa/aaa:alive-user-qrys" {
    deviate not-supported;
  }
  deviation "/aaa:aaa/aaa:management-user-qrys/aaa:management-user-qry/aaa:alive-num" {
    deviate not-supported;
  }
  deviation "/aaa:aaa/aaa:management-user-qrys/aaa:management-user-qry/aaa:last-login-infos" {
    deviate not-supported;
  }
  deviation "/aaa:aaa/aaa:global-policy/aaa:default-admin-domain" {
    deviate not-supported;
  }
  deviation "/aaa:aaa/aaa:global-policy/aaa:default-access-domain" {
    deviate not-supported;
  }
  deviation "/aaa:aaa/aaa:global-policy/aaa:parse-priority" {
    deviate not-supported;
  }
  deviation "/aaa:aaa/aaa:global-policy/aaa:realm-location" {
    deviate not-supported;
  }
  deviation "/aaa:aaa/aaa:global-policy/aaa:real-name-delimiter" {
    deviate not-supported;
  }
  deviation "/aaa:aaa/aaa:global-policy/aaa:real-name-parse-direction" {
    deviate not-supported;
  }
  deviation "/aaa:aaa/aaa:global-policy/aaa:roam-character" {
    deviate not-supported;
  }
  deviation "/aaa:aaa/aaa:global-policy/aaa:security-name-delimiter-enable" {
    deviate not-supported;
  }
  deviation "/aaa:aaa/aaa:global-policy/aaa:security-name-delimiter" {
    deviate not-supported;
  }
  deviation "/aaa:aaa/aaa:ipv6-statistics" {
    deviate not-supported;
  }
  deviation "/aaa:aaa/aaa:user-queue" {
    deviate not-supported;
  }
  deviation "/aaa:aaa/aaa:traffic-groups" {
    deviate not-supported;
  }
  deviation "/aaa:aaa/aaa:online-offline-rec-switch" {
    deviate not-supported;
  }
  deviation "/aaa:aaa/aaa:abnormal-offline-hidens" {
    deviate not-supported;
  }
  deviation "/aaa:aaa/aaa:lam/aaa:user-security-policy/aaa:user-aging-period" {
    deviate not-supported;
  }
  deviation "/aaa:aaa/aaa:lam/aaa:user-security-policy/aaa:user-name-min-len" {
    deviate not-supported;
  }
  deviation "/aaa:aaa/aaa:lam/aaa:password-policy/aaa:enable" {
    deviate not-supported;
  }
  deviation "/aaa:aaa/aaa:lam/aaa:password-policy/aaa:expired-pwd-reuse-num" {
    deviate not-supported;
  }
  deviation "/aaa:aaa/aaa:lam/aaa:password-policy/aaa:history-pwd-num" {
    deviate not-supported;
  }
  deviation "/aaa:aaa/aaa:lam/aaa:password-policy/aaa:pwd-expire-days" {
    deviate not-supported;
  }
  deviation "/aaa:aaa/aaa:lam/aaa:password-policy/aaa:pwd-force-change" {
    deviate not-supported;
  }
  deviation "/aaa:aaa/aaa:lam/aaa:password-policy/aaa:pwd-salt" {
    deviate not-supported;
  }
  deviation "/aaa:aaa/aaa:lam/aaa:user-password-policy/aaa:expire-days" {
    deviate not-supported;
  }
  deviation "/aaa:aaa/aaa:lam/aaa:user-password-policy/aaa:original-alert" {
    deviate not-supported;
  }
  deviation "/aaa:aaa/aaa:lam/aaa:forbidden-word-rules" {
    deviate not-supported;
  }
  deviation "/aaa:aaa/aaa:lam/aaa:users/aaa:user/aaa:is-login-anytime" {
    deviate not-supported;
  }
  deviation "/aaa:aaa/aaa:lam/aaa:users/aaa:user/aaa:begin-login-day" {
    deviate not-supported;
  }
  deviation "/aaa:aaa/aaa:lam/aaa:users/aaa:user/aaa:end-login-day" {
    deviate not-supported;
  }
  deviation "/aaa:aaa/aaa:lam/aaa:users/aaa:user/aaa:begin-login-time" {
    deviate not-supported;
  }
  deviation "/aaa:aaa/aaa:lam/aaa:users/aaa:user/aaa:end-login-time" {
    deviate not-supported;
  }
  deviation "/aaa:aaa/aaa:lam/aaa:users/aaa:user/aaa:aging-in-days" {
    deviate not-supported;
  }
  deviation "/aaa:aaa/aaa:lam/aaa:users/aaa:user/aaa:failed-times" {
    deviate not-supported;
  }
  deviation "/aaa:aaa/aaa:lam/aaa:users/aaa:user/aaa:interval" {
    deviate not-supported;
  }
  deviation "/aaa:aaa/aaa:lam/aaa:users/aaa:user/aaa:http-dir" {
    deviate not-supported;
  }
  deviation "/aaa:aaa/aaa:lam/aaa:users/aaa:user/aaa:service-none" {
    deviate not-supported;
  }
  deviation "/aaa:aaa/aaa:lam/aaa:users/aaa:user/aaa:service-ppp" {
    deviate not-supported;
  }
  deviation "/aaa:aaa/aaa:lam/aaa:users/aaa:user/aaa:service-qx" {
    deviate not-supported;
  }
  deviation "/aaa:aaa/aaa:lam/aaa:users/aaa:user/aaa:service-snmp" {
    deviate not-supported;
  }
  deviation "/aaa:aaa/aaa:lam/aaa:users/aaa:user/aaa:service-mml" {
    deviate not-supported;
  }
  deviation "/aaa:aaa/aaa:lam/aaa:users/aaa:user/aaa:service-mdcli" {
    deviate not-supported;
  }
  deviation "/aaa:aaa/aaa:lam/aaa:users/aaa:user/aaa:service-bind" {
    deviate not-supported;
  }
  deviation "/aaa:aaa/aaa:lam/aaa:users/aaa:user/aaa:service-sslvpn" {
    deviate not-supported;
  }
  deviation "/aaa:aaa/aaa:lam/aaa:users/aaa:user/aaa:service-web" {
    deviate not-supported;
  }
  deviation "/aaa:aaa/aaa:lam/aaa:users/aaa:user/aaa:service-x25-pad" {
    deviate not-supported;
  }
  deviation "/aaa:aaa/aaa:lam/aaa:users/aaa:user/aaa:service-api" {
    deviate not-supported;
  }
  deviation "/aaa:aaa/aaa:lam/aaa:users/aaa:user/aaa:idle-cut-enable" {
    deviate not-supported;
  }
  deviation "/aaa:aaa/aaa:lam/aaa:users/aaa:user/aaa:user-type" {
    deviate not-supported;
  }
  deviation "/aaa:aaa/aaa:lam/aaa:users/aaa:user/aaa:acl" {
    deviate not-supported;
  }
  deviation "/aaa:aaa/aaa:lam/aaa:users/aaa:user/aaa:device-type" {
    deviate not-supported;
  }
  deviation "/aaa:aaa/aaa:lam/aaa:users/aaa:user/aaa:begin-life-date" {
    deviate not-supported;
  }
  deviation "/aaa:aaa/aaa:lam/aaa:users/aaa:user/aaa:is-aged" {
    deviate not-supported;
  }
  deviation "/aaa:aaa/aaa:lam/aaa:users/aaa:user/aaa:is-terminal-locked" {
    deviate not-supported;
  }
  deviation "/aaa:aaa/aaa:lam/aaa:users/aaa:user/aaa:terminal-left-lock-time" {
    deviate not-supported;
  }
  deviation "/aaa:aaa/aaa:lam/aaa:users/aaa:user/aaa:create-time" {
    deviate not-supported;
  }
  deviation "/aaa:aaa/aaa:lam/aaa:users/aaa:user/aaa:private" {
    deviate not-supported;
  }
  deviation "/aaa:aaa/aaa:lam/aaa:access-users/aaa:access-user/aaa:service-sslvpn" {
    deviate not-supported;
  }
  deviation "/aaa:aaa/aaa:lam/aaa:access-users/aaa:access-user/aaa:assigned-ip" {
    deviate not-supported;
  }
  deviation "/aaa:aaa/aaa:lam/aaa:access-users/aaa:access-user/aaa:ou-ucl-group" {
    deviate not-supported;
  }
  deviation "/aaa:aaa/aaa:lam/aaa:access-users/aaa:access-user/aaa:bind-ipv4s" {
    deviate not-supported;
  }
  deviation "/aaa:aaa/aaa:lam/aaa:access-users/aaa:access-user/aaa:bind-macs" {
    deviate not-supported;
  }
  deviation "/aaa:aaa/aaa:local-server" {
    deviate not-supported;
  }
  deviation "/aaa:aaa/aaa:access-user-qrys" {
    deviate not-supported;
  }
  deviation "/aaa:aaa/aaa:re-authorization-users" {
    deviate not-supported;
  }
  deviation "/aaa:aaa/aaa:global-user-policy" {
    deviate not-supported;
  }
  deviation "/aaa:test-server-connectivity/aaa:output/aaa:result-code" {
    deviate not-supported;
  }
  deviation "/aaa:cut-user-by-domain" {
    deviate not-supported;
  }
  deviation "/aaa:reset-online-failoroffline-record" {
    deviate not-supported;
  }
  deviation "/aaa:reactivate-user" {
    deviate not-supported;
  }
  deviation "/aaa:change-my-password" {
    deviate not-supported;
  }
  deviation "/aaa:re-authorize-user" {
    deviate not-supported;
  }
  deviation "/aaa:clear-re-authorize-user" {
    deviate not-supported;
  }
  deviation "/aaa:change-current-password/aaa:input/aaa:old-password" {
    deviate replace {
      type pub-type:one-input-password-extend {
        length "1..128";
      }
    }
  }
  deviation "/aaa:change-current-password/aaa:input/aaa:new-password" {
    deviate replace {
      type pub-type:password-extend {
        length "1..128";
      }
    }
  }
  deviation "/aaa:aaa/aaa:task-groups/aaa:task-group/aaa:task-group-task-maps/aaa:task-group-task-map/aaa:task-name" {
    deviate delete {
      must "(../write='enable' or ../execute='enable' or ../debug='enable' or ../read='enable')";
    }
    deviate add {
      must "(../write='enable' or ../debug='enable' or ../read='enable')";
    }
  }
  deviation "/aaa:aaa/aaa:task-groups/aaa:task-group/aaa:task-group-task-maps/aaa:task-group-task-map/aaa:read" {
    deviate delete {
      must "not(../write='disable' and ../execute='disable' and ../debug='disable') or (../write='disable' and ../execute='disable' and ../debug='disable' and ../read!=../write)";
    }
    deviate add {
      must "not(../write='enable'  and ../read='disable')";
    }
  }
  deviation "/aaa:aaa/aaa:user-groups/aaa:user-group/aaa:user-group-task-group-maps/aaa:user-group-task-group-map/aaa:task-group-name" {
    deviate delete {
      must "(../execute='enable' or ../debug='enable' or ../read='enable' or ../write='enable')";
    }
    deviate add {
      must "(../debug='enable' or ../read='enable' or ../write='enable')";
    }
  }
  deviation "/aaa:aaa/aaa:authentication-schemes/aaa:authentication-scheme/aaa:authen-scheme-name" {
    deviate replace {
      type string {
        length "1..32";
        pattern '[!-~]+';
        pattern '([^/\*":?<>|]{3,32})|([^/\*":?<>|-]-)|(-[^/\*":?<>|-])|([^/\*":?<>|-]{1,2})';
      }
    }
  }
  deviation "/aaa:aaa/aaa:authentication-schemes/aaa:authentication-scheme/aaa:authen-mode" {
    deviate add {
      default "local";
    }
    deviate add {
      must "count(../authen-mode[. = 'local']) + count(../authen-mode[. = 'local-case']) <= 1";
    }
    deviate replace {
      type enumeration {
        enum local {
          value 1;
          description
            "Local authentication mode.";
        }
        enum hwtacacs {
          value 2;
          description
            "HWTACACS authentication mode.";
        }
        enum radius {
          value 3;
          description
            "RADIUS authentication mode.";
        }
        enum none {
          value 4;
          description
            "In this mode, users can pass with authentication.";
        }
        enum ldap {
          value 7;
          description
            "LDAP authentication mode.";
        }
        enum ad {
          value 8;
          description
            "AD authentication mode.";
        }
        enum local-case {
          value 10;
          description
            "Local-case authentication mode.";
        }
      }
    }
  }
  deviation "/aaa:aaa/aaa:authentication-schemes/aaa:authentication-scheme/aaa:radius-chap/aaa:access-type" {
    deviate replace {
      type enumeration {
        enum ftp {
          value 0;
          description
            "Configure replace PAP authentication with CHAP authentication when RADIUS authentication is performed on administrators who access the device using FTP.";
        }
        enum ssh {
          value 1;
          description
            "Replaces PAP authentication with CHAP authentication when RADIUS authentication is performed on administrators who access the device using SSH.";
        }
        enum telnet {
          value 2;
          description
            "Replaces PAP authentication with CHAP authentication when RADIUS authentication is performed on administrators who access the device using Telnet.";
        }
        enum terminal {
          value 3;
          description
            "Replaces PAP authentication with CHAP authentication when RADIUS authentication is performed on administrators who access the device using a terminal.";
        }
        enum http {
          value 4;
          description
            "Replaces PAP authentication with CHAP authentication when RADIUS authentication is performed on administrators who access the device using a web management system.";
        }
      }
    }
  }
  deviation "/aaa:aaa/aaa:authorization-schemes/aaa:authorization-scheme/aaa:author-scheme-name" {
    deviate replace {
      type string {
        length "1..32";
        pattern '[!-~]+';
        pattern '([^/\*":?<>|]{3,32})|([^/\*":?<>|-]-)|(-[^/\*":?<>|-])|([^/\*":?<>|-]{1,2})';
      }
    }
  }
  deviation "/aaa:aaa/aaa:authorization-schemes/aaa:authorization-scheme/aaa:author-mode" {
    deviate add {
      default "local";
    }
    deviate add {
      must "count(../author-mode[. = 'local']) + count(../author-mode[. = 'local-case']) <= 1";
    }
    deviate replace {
      type enumeration {
        enum local {
          value 1;
          description
            "Specifies that the local mode is applied.";
        }
        enum hwtacacs {
          value 2;
          description
            "Specifies that the HWTACACS mode is applied.";
        }
        enum if-authenticated {
          value 3;
          description
            "Specifies that the If-authenticated mode is adopted. If users pass the authentication and the authentication is not in this mode, it indicates that the user authorization is passed. Otherwise, the authorization is not passed.";
        }
        enum none {
          value 4;
          description
            "Users can pass without authorization.";
        }
        enum ad {
          value 5;
          description
            "AD authorization mode.";
        }
        enum ldap {
          value 6;
          description
            "LDAP authorization mode.";
        }
        enum local-case {
          value 7;
          description
            "Specifies that the local-case mode is applied.";
        }
      }
    }
  }
  deviation "/aaa:aaa/aaa:authorization-schemes/aaa:authorization-scheme/aaa:authorization-cmds/aaa:authorization-cmd/aaa:level" {
    deviate add {
      must '../author-mode';
    }
    deviate replace {
      type uint32 {
        range "0..4";
      }
    }
  }
  deviation "/aaa:aaa/aaa:authorization-schemes/aaa:authorization-scheme/aaa:authorization-cmds/aaa:authorization-cmd/aaa:author-mode" {
    deviate replace {
      type enumeration {
        enum local {
          value 1;
          description
            "Specifies that the local mode is applied.";
        }
        enum hwtacacs {
          value 2;
          description
            "Specifies that the HWTACACS mode is applied.";
        }
        enum none {
          value 3;
          description
            "Specifies that the none mode is applied.";
        }
      }
    }
  }
  deviation "/aaa:aaa/aaa:accounting-schemes/aaa:accounting-scheme/aaa:acct-scheme-name" {
    deviate replace {
      type string {
        length "1..32";
        pattern '[!-~]+';
        pattern '([^/\*":?<>|]{3,32})|([^/\*":?<>|-]-)|(-[^/\*":?<>|-])|([^/\*":?<>|-]{1,2})';
      }
    }
  }
  deviation "/aaa:aaa/aaa:accounting-schemes/aaa:accounting-scheme/aaa:accounting-mode" {
    deviate delete {
      must "../accounting-mode='radius' or ../accounting-mode='hwtacacs' or ../accounting-mode='none'";
    }
    deviate replace {
      type enumeration {
        enum radius {
          value 1;
          description
            "RADIUS accounting mode.";
        }
        enum hwtacacs {
          value 2;
          description
            "HWTACACS accounting mode.";
        }
        enum none {
          value 3;
          description
            "In this mode, users do not be accounting.";
        }
      }
    }
  }
  deviation "/aaa:aaa/aaa:accounting-schemes/aaa:accounting-scheme/aaa:start-accounting-fail/aaa:fail-policy" {
    deviate replace {
      default "online";
    }
  }
  deviation "/aaa:aaa/aaa:accounting-schemes/aaa:accounting-scheme/aaa:realtime-accounting/aaa:realtime-interval" {
    deviate add {
      default "0";
    }
  }
  deviation "/aaa:aaa/aaa:domains/aaa:domain/aaa:name" {
    deviate replace {
      type string {
        length "1..64";
        pattern '[!-~]+';
        pattern '[^A-Z*?"]{3,64}|([^A-Z*?"-]-)|(-[^A-Z*?"-])|([^A-Z*?"-]{1,2})';
      }
    }
  }
  deviation "/aaa:aaa/aaa:domains/aaa:domain/aaa:authen-scheme-name" {
    deviate add {
      default "default";
    }
  }
  deviation "/aaa:aaa/aaa:domains/aaa:domain/aaa:acct-scheme-name" {
    deviate add {
      default "default";
    }
  }
  deviation "/aaa:aaa/aaa:domains/aaa:domain/aaa:force-push-function/aaa:url-source/aaa:template/aaa:url-template" {
    deviate replace {
      type leafref {
        path "/hw-nac-portal:nac-portal/hw-nac-portal:url-templates/hw-nac-portal:url-template/hw-nac-portal:name";
      }
    }
  }
  deviation "/aaa:aaa/aaa:global-policy/aaa:domain-delimiter" {
    deviate replace {
      type string {
        length "1";
        pattern "[\\\\/|@%':<>]";
      }
    }
  }
  deviation "/aaa:aaa/aaa:recording/aaa:schemes/aaa:scheme/aaa:name" {
    deviate replace {
      type string {
        length "1..32";
        pattern '[!-~]+';
        pattern '([^/\*":?<>|]{3,32})|([^/\*":?<>|-]-)|(-[^/\*":?<>|-])|([^/\*":?<>|-]{1,2})';
      }
    }
  }
  deviation "/aaa:aaa/aaa:global-domain/aaa:default-domain" {
    deviate add {
      default "default";
    }
  }
  deviation "/aaa:aaa/aaa:global-domain/aaa:default-admin-domain" {
    deviate add {
      default "default_admin";
    }
  }
  deviation "/aaa:aaa/aaa:lam/aaa:login-failed-limit" {
    deviate add {
      must '(./period and ./failed-times and ./reactive-time) or (not(./failed-times) and not(./period) and not(./reactive-time))';
    }
  }
  deviation "/aaa:aaa/aaa:lam/aaa:login-failed-limit/aaa:failed-times" {
    deviate replace {
      type uint32 {
        range "3..65535";
      }
    }
    deviate replace {
      default "3";
    }
  }
  deviation "/aaa:aaa/aaa:lam/aaa:login-failed-limit/aaa:period" {
    deviate replace {
      type uint32 {
        range "5..65535";
      }
    }
  }
  deviation "/aaa:aaa/aaa:lam/aaa:login-failed-limit/aaa:reactive-time" {
    deviate replace {
      type uint32 {
        range "5..65535";
      }
    }
  }
  deviation "/aaa:aaa/aaa:lam/aaa:password-policy/aaa:expire-days" {
    deviate delete {
      must '../prompt-days<=../expire-days';
    }
    deviate replace {
      default "90";
    }
  }
  deviation "/aaa:aaa/aaa:lam/aaa:password-policy/aaa:prompt-days" {
    deviate delete {
      must '../prompt-days<=../expire-days';
    }
    deviate replace {
      default "30";
    }
  }
  deviation "/aaa:aaa/aaa:lam/aaa:password-policy/aaa:change-check" {
    deviate replace {
      default "true";
    }
  }
  deviation "/aaa:aaa/aaa:lam/aaa:password-policy/aaa:history-record-number" {
    deviate replace {
      default "10";
    }
  }
  deviation "/aaa:aaa/aaa:lam/aaa:password-policy/aaa:pwd-min-length" {
    deviate add {
      default "8";
    }
    deviate replace {
      type uint32 {
        range "6..128";
      }
    }
  }
  deviation "/aaa:aaa/aaa:lam/aaa:users/aaa:user/aaa:name" {
    deviate replace {
      type string {
        length "1..253";
        pattern '[^*?"]{1,253}';
      }
    }
  }
  deviation "/aaa:aaa/aaa:lam/aaa:users/aaa:user/aaa:end-life-date" {
    deviate add {
      must '(not(../time-range))';
    }
    deviate replace {
      type string {
        pattern '(20[0-9]{2}-((0[1-9]|1[0-2])-(0[1-9]|1[0-9]|2[0-8])|(0[13-9]|1[0-2])-(29|30)|(0[13578]|1[02])-31)|(20(0[48]|[2468][048]|[13579][26])|(2000))-02-29)';
      }
    }
  }
  deviation "/aaa:aaa/aaa:lam/aaa:users/aaa:user/aaa:time-range" {
    deviate add {
      must '(not(../end-life-date))';
    }
    deviate replace {
      type leafref {
        path "/timerange:time-range/timerange:time-range-instances/timerange:time-range-instance/timerange:name";
      }
    }
  }
  deviation "/aaa:aaa/aaa:lam/aaa:users/aaa:user/aaa:group-name" {
    deviate replace {
      config false;
    }
  }
  deviation "/aaa:aaa/aaa:lam/aaa:users/aaa:user/aaa:password-type" {
    deviate delete {
      must '../password';
    }
    deviate replace {
      type enumeration {
        enum irreversible-cipher {
          value 2;
          description
            "Irreversible-cipher PasswordType.";
        }
      }
    }
  }
  deviation "/aaa:aaa/aaa:lam/aaa:users/aaa:user/aaa:password" {
    deviate add {
      must 'string-length(../password) >= /aaa:aaa/aaa:lam/aaa:password-policy/aaa:pwd-min-length';
    }
    deviate replace {
      type pub-type:password-extend {
        length "6..128";
      }
    }
    deviate replace {
      mandatory false;
    }
  }
  deviation "/aaa:aaa/aaa:lam/aaa:users/aaa:user/aaa:level" {
    deviate replace {
      type uint32 {
        range "0..3";
      }
    }
  }
  deviation "/aaa:aaa/aaa:lam/aaa:users/aaa:user/aaa:ftp-dir-access" {
    deviate replace {
      type enumeration {
        enum read-execute {
          value 4;
          description
            "Access permissions of directory are read and execute.";
        }
        enum read-write-execute {
          value 6;
          description
            "Access permissions of directory are read, write, and execute.";
        }
      }
    }
  }
  deviation "/aaa:aaa/aaa:lam/aaa:users/aaa:user/aaa:idle-time" {
    deviate replace {
      type int32 {
        range "0..2147519";
      }
    }
  }
  deviation "/aaa:aaa/aaa:lam/aaa:access-users/aaa:access-user" {
    deviate delete {
      must "(not(service-none='false' and (service-portal='false' and service-dot1x='false' and service-sslvpn='false' and service-ppp='false')))";
    }
    deviate delete {
      must "(not(service-none='true' and (service-portal='true' or service-dot1x='true' or service-sslvpn='true' or service-ppp='true')))";
    }
    deviate add {
      must "(not(service-none='false' and (service-portal='false' and service-dot1x='false' and service-ppp='false')))";
    }
    deviate add {
      must "(not(service-none='true' and (service-portal='true' or service-dot1x='true' or service-ppp='true')))";
    }
  }
  deviation "/aaa:aaa/aaa:lam/aaa:access-users/aaa:access-user/aaa:name" {
    deviate replace {
      type string {
        length "1..64";
        pattern '[^?"]{1,64}';
      }
    }
  }
  deviation "/aaa:aaa/aaa:lam/aaa:access-users/aaa:access-user/aaa:end-life-date" {
    deviate add {
      must '(not(../time-range))';
    }
    deviate replace {
      type string {
        pattern '(20[0-9]{2}-((0[1-9]|1[0-2])-(0[1-9]|1[0-9]|2[0-8])|(0[13-9]|1[0-2])-(29|30)|(0[13578]|1[02])-31)|(20(0[48]|[2468][048]|[13579][26])|(2000))-02-29)';
      }
    }
  }
  deviation "/aaa:aaa/aaa:lam/aaa:access-users/aaa:access-user/aaa:time-range" {
    deviate add {
      must '(not(../end-life-date))';
    }
  }
  deviation "/aaa:aaa/aaa:lam/aaa:access-users/aaa:access-user/aaa:password-type" {
    deviate replace {
      type enumeration {
        enum cipher {
          value 1;
          description
            "Cipher PasswordType.";
        }
      }
    }
  }
  deviation "/aaa:aaa/aaa:lam/aaa:access-users/aaa:access-user/aaa:password" {
    deviate add {
      must '../password-type';
    }
    deviate replace {
      type pub-type:password-extend {
        length "8..268";
      }
    }
  }
  deviation "/aaa:test-server-connectivity/aaa:input/aaa:server-type" {
    deviate replace {
      type enumeration {
        enum radius {
          value 0;
          description
            "RADIUS server.";
        }
      }
    }
  }
  ext:deviation-ext "/aaa:aaa/aaa:task-groups/aaa:task-group" {
    ext:deviate-ext "add" {
      ext:operation-exclude "delete" {
        ext:filter "name = 'manage-tg'";
        description
          "The default manage-tg cannot be deleted.";
      }
    }
    ext:deviate-ext "add" {
      ext:operation-exclude "delete" {
        ext:filter "name = 'monitor-tg'";
        description
          "The default monitor-tg cannot be deleted.";
      }
    }
    ext:deviate-ext "add" {
      ext:operation-exclude "delete" {
        ext:filter "name = 'system-tg'";
        description
          "The default system-tg cannot be deleted.";
      }
    }
    ext:deviate-ext "add" {
      ext:operation-exclude "delete" {
        ext:filter "name = 'visit-tg'";
        description
          "The default visit-tg cannot be deleted.";
      }
    }
    ext:deviate-ext "add" {
      ext:generated-by "system" {
        ext:filter "name = 'manage-tg'";
        description
          "The default manage-tg is generated by system.";
      }
    }
    ext:deviate-ext "add" {
      ext:generated-by "system" {
        ext:filter "name = 'monitor-tg'";
        description
          "The default monitor-tg is generated by system.";
      }
    }
    ext:deviate-ext "add" {
      ext:generated-by "system" {
        ext:filter "name = 'system-tg'";
        description
          "The default system-tg is generated by system.";
      }
    }
    ext:deviate-ext "add" {
      ext:generated-by "system" {
        ext:filter "name = 'visit-tg'";
        description
          "The default visit-tg is generated by system.";
      }
    }
  }
  ext:deviation-ext "/aaa:aaa/aaa:task-groups/aaa:task-group/aaa:task-group-task-maps/aaa:task-group-task-map" {
    ext:deviate-ext "add" {
      ext:generated-by "system" {
        ext:filter "task-name = 'interface-mgr' or task-name = 'config' or task-name = 'vlan' or task-name = 'shell' or task-name = 'cli' or task-name = 'system-view'";
        description
          "The must task-map generated by system.";
      }
    }
  }
  ext:deviation-ext "/aaa:aaa/aaa:user-groups/aaa:user-group" {
    ext:deviate-ext "add" {
      ext:operation-exclude "delete" {
        ext:filter "name = 'manage-tg'";
        description
          "The default manage-tg cannot be deleted.";
      }
    }
    ext:deviate-ext "add" {
      ext:operation-exclude "delete" {
        ext:filter "name = 'monitor-tg'";
        description
          "The default monitor-tg cannot be deleted.";
      }
    }
    ext:deviate-ext "add" {
      ext:operation-exclude "delete" {
        ext:filter "name = 'system-tg'";
        description
          "The default monitor-tg cannot be deleted.";
      }
    }
    ext:deviate-ext "add" {
      ext:operation-exclude "delete" {
        ext:filter "name = 'visit-tg'";
        description
          "The default monitor-tg cannot be deleted.";
      }
    }
    ext:deviate-ext "add" {
      ext:generated-by "system" {
        ext:filter "name = 'manage-tg'";
        description
          "The default manage-tg is generated by system.";
      }
    }
    ext:deviate-ext "add" {
      ext:generated-by "system" {
        ext:filter "name = 'monitor-tg'";
        description
          "The default monitor-tg is generated by system.";
      }
    }
    ext:deviate-ext "add" {
      ext:generated-by "system" {
        ext:filter "name = 'system-tg'";
        description
          "The default system-tg is generated by system.";
      }
    }
    ext:deviate-ext "add" {
      ext:generated-by "system" {
        ext:filter "name = 'visit-tg'";
        description
          "The default visit-tg is generated by system.";
      }
    }
  }
  ext:deviation-ext "/aaa:aaa/aaa:authentication-schemes" {
    ext:deviate-ext "add" {
      ext:operation-exclude "delete";
    }
  }
  ext:deviation-ext "/aaa:aaa/aaa:authentication-schemes/aaa:authentication-scheme" {
    ext:deviate-ext "add" {
      ext:operation-exclude "delete" {
        ext:filter "authen-scheme-name = 'default'";
        description
          "The instances whose name is 'default' cannot be deleted.";
      }
    }
    ext:deviate-ext "add" {
      ext:generated-by "system" {
        ext:filter "authen-scheme-name = 'default'";
        description
          "The instances whose name is 'default' are generated automatically.";
      }
    }
  }
  ext:deviation-ext "/aaa:aaa/aaa:authorization-schemes" {
    ext:deviate-ext "add" {
      ext:operation-exclude "delete";
    }
  }
  ext:deviation-ext "/aaa:aaa/aaa:authorization-schemes/aaa:authorization-scheme" {
    ext:deviate-ext "add" {
      ext:operation-exclude "delete" {
        ext:filter "author-scheme-name = 'default'";
        description
          "The instances whose name is 'default' cannot be deleted.";
      }
    }
    ext:deviate-ext "add" {
      ext:generated-by "system" {
        ext:filter "author-scheme-name = 'default'";
        description
          "The instances whose name is 'default' are generated automatically.";
      }
    }
  }
  ext:deviation-ext "/aaa:aaa/aaa:accounting-schemes" {
    ext:deviate-ext "add" {
      ext:operation-exclude "delete";
    }
  }
  ext:deviation-ext "/aaa:aaa/aaa:accounting-schemes/aaa:accounting-scheme" {
    ext:deviate-ext "add" {
      ext:operation-exclude "delete" {
        ext:filter "acct-scheme-name = 'default'";
        description
          "The instances whose name is 'default' cannot be deleted.";
      }
    }
    ext:deviate-ext "add" {
      ext:generated-by "system" {
        ext:filter "acct-scheme-name = 'default'";
        description
          "The instances whose name is 'default' are generated automatically.";
      }
    }
  }
  ext:deviation-ext "/aaa:aaa/aaa:domains" {
    ext:deviate-ext "add" {
      ext:operation-exclude "delete";
    }
  }
  ext:deviation-ext "/aaa:aaa/aaa:domains/aaa:domain" {
    ext:deviate-ext "add" {
      ext:operation-exclude "delete" {
        ext:filter "name = 'default' or name = 'default_admin'";
        description
          "The instances whose name is 'default' or 'default_admin' cannot be deleted.";
      }
    }
    ext:deviate-ext "add" {
      ext:generated-by "system" {
        ext:filter "name = 'default' or name = 'default_admin'";
        description
          "The instances whose name is 'default' or 'default_admin' are generated automatically.";
      }
    }
  }
}
