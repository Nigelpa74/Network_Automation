module zxr10-pm-license {
  namespace 'http://www.zte.com.cn/zxr10/netconf/schema/rosng/pm-license'
            ;
  prefix pm-license ;
  yang-version 1 ;
  import zxr10-netconf-defs {
    prefix ncd ;
  }
  organization 'ZTE Corporation'
               ;
  contact 'ZTE Corporation'+"\n"
        + '   Nanjing Institute of ZTE Corporation'+"\n"
        + '   No.68 Zijinghua Rd. Yuhuatai District, Nanjing, China'+"\n"
        + '   Tel: +86-25-52870000'
          ;
  revision 2022-04-19 {
    description 'Add container cards to show the information of license-card.Ad'
              + 'd container files, performances,devids to show the details of '
              + 'license file.Add container permit-ports to support to permit t'
              + 'he ports.Add container license-install,license-uninstall,licen'
              + 'se-update to support to install/uninstall/update the licnese f'
              + 'ile.'
                ;
  }
  revision 2022-02-10 {
    description 'add container resource-permanents,resource-permanent-briefs,po'
              + 'rt-states and port-type-summarys to show port license informat'
              + 'ion.'
                ;
  }
  revision 2021-01-28 {
    description 'Initial version.'
                ;
  }
  container configuration {
    container ports {
      container active-ports {
        list active-port {
          key 'shelf slot subslot portno restype itemname'
              ;
          leaf shelf {
            type uint8 ;
          }
          leaf slot {
            type uint8 ;
          }
          leaf subslot {
            type uint8 ;
          }
          leaf portno {
            type uint32 ;
          }
          leaf restype {
            type uint16 ;
          }
          leaf itemname {
            type string {
              length 1..64 ;
            }
          }
          leaf activeflag {
            type enumeration {
              enum active {
                value 1 ;
              }
              enum inactive {
                value 0 ;
              }
            }
            default inactive ;
          }
        }
      }
      container permit-ports {
        description 'Permit port license with license file.'
                    ;
        list permit-port-with-file {
          description 'Permit port license with license file.'
                      ;
          key 'itemname shelf slot subslot demoname'
              ;
          leaf itemname {
            description 'The name of port control item.'
                        ;
            type uint16 {
              range 1..1000 ;
            }
          }
          leaf shelf {
            description 'The shelf number.'
                        ;
            type uint8 {
              range 0..255 ;
            }
          }
          leaf slot {
            description 'The slot number.'
                        ;
            type uint8 {
              range 0..255 ;
            }
          }
          leaf subslot {
            description 'The subslot number.'
                        ;
            type uint8 {
              range 0..3 ;
            }
          }
          leaf portno {
            description 'The port number.'
                        ;
            type ncd:bitmap {
              length 0..200 ;
            }
            default 0 ;
          }
          leaf demoname {
            description 'The name of demo license file.'
                        ;
            type string {
              length 1..79 ;
            }
          }
          ncd:revise-date 2022-04-19 ;
        }
        list permit-port {
          description 'Permit port license.'
                      ;
          key 'itemname shelf slot subslot'
              ;
          leaf itemname {
            description 'The name of port control item.'
                        ;
            type uint16 {
              range 1..1000 ;
            }
          }
          leaf shelf {
            description 'The shelf number.'
                        ;
            type uint8 {
              range 0..255 ;
            }
          }
          leaf slot {
            description 'The slot number.'
                        ;
            type uint8 {
              range 0..255 ;
            }
          }
          leaf subslot {
            description 'The subslot number.'
                        ;
            type uint8 {
              range 0..3 ;
            }
          }
          leaf portno {
            description 'The port number.'
                        ;
            type ncd:bitmap {
              length 0..200 ;
            }
            default 0 ;
          }
        }
        ncd:revise-date 2022-02-10 ;
      }
    }
  }
  container operation {
    config false ;
    container license {
      description 'license operation'
                  ;
      container license-install {
        description 'Install license file.'
                    ;
        leaf filename {
          description 'The file name.'
                      ;
          type string {
            length 1..79 ;
          }
        }
      }
      container license-uninstall {
        description 'Uninstall license file.'
                    ;
        leaf filename {
          description 'The file name.'
                      ;
          type string {
            length 0..79 ;
          }
        }
        leaf all {
          description 'delete all license file.'
                      ;
          type enumeration {
            enum all {
              value 1 ;
            }
          }
          ncd:revise-date 2022-02-10 ;
        }
      }
      container license-update {
        description 'Update license file.'
                    ;
        leaf update {
          description 'Update license file.'
                      ;
          type enumeration {
            enum update {
              value 1 ;
            }
          }
        }
      }
    }
    ncd:revise-date 2022-02-10 ;
  }
  container state {
    config false ;
    container license {
      description 'Show license information.'
                  ;
      container files {
        list file {
          description 'The license file information.'
                      ;
          key file-name ;
          leaf file-name {
            description 'license file name.'
                        ;
            type string {
              length 1..80 ;
            }
          }
          leaf serial-number {
            description 'the serial number of license file.'
                        ;
            type string {
              length 1..2000 ;
            }
          }
          leaf type {
            description 'the type of license file.'
                        ;
            type string {
              length 1..12 ;
            }
          }
          leaf status {
            description 'the status of license file.'
                        ;
            type ncd:string-with-blank ;
          }
          leaf publish-date {
            description 'the publish date of license file.'
                        ;
            type string {
              length 1..12 ;
            }
          }
          leaf invalid-date {
            description 'the invalid date of license file.'
                        ;
            type string {
              length 1..12 ;
            }
          }
          container performances {
            description 'The performance item of license file.'
                        ;
            list performance {
              description 'The performance item of license file.'
                          ;
              key name ;
              leaf name {
                description 'the performance name of liccense file.'
                            ;
                type string {
                  length 1..64 ;
                }
              }
              leaf authority {
                description 'the performance authority number of license file.'
                            ;
                type string {
                  length 1..32 ;
                }
              }
            }
          }
          container devids {
            description 'The devids of license file.'
                        ;
            list devid {
              description 'The devids of license file.'
                          ;
              key system-devid ;
              leaf system-devid {
                description 'the system-devids of license file.'
                            ;
                type string {
                  length 1..29 ;
                }
              }
            }
          }
        }
        ncd:revise-date 2022-02-10 ;
      }
      container port-enables {
        description 'Show port enable license information.'
                    ;
        container port-states {
          list port-state {
            key if-name ;
            leaf if-name {
              description 'The interface name.'
                          ;
              type string {
                length 1..32 ;
              }
            }
            leaf trial {
              description 'The port license is trial license or not.'
                          ;
              type enumeration {
                enum yes {
                  value 0 ;
                }
                enum no {
                  value 1 ;
                }
              }
            }
            leaf demo {
              description 'The port license is demo license or not.'
                          ;
              type enumeration {
                enum yes {
                  value 0 ;
                }
                enum no {
                  value 1 ;
                }
              }
            }
            leaf permit-status {
              description 'The permit status of port license.'
                          ;
              type enumeration {
                enum no-permit {
                  value 0 ;
                }
                enum matched {
                  value 1 ;
                }
                enum overAllocation-matched {
                  value 2 ;
                }
                enum unmatched {
                  value 3 ;
                }
                enum overAllocation-unmatched {
                  value 4 ;
                }
              }
            }
            leaf status {
              description 'The status of license port.'
                          ;
              type enumeration {
                enum activated {
                  value 0 ;
                }
                enum inactivated {
                  value 1 ;
                }
              }
            }
          }
        }
        container resource-permanents {
          list resource-permanent {
            description 'The license resources info.'
                        ;
            key 'item-name demo-file'
                ;
            leaf item-name {
              description 'The license item name.'
                          ;
              type string {
                length 1..63 ;
              }
            }
            leaf demo-file {
              description 'The license demo file name.'
                          ;
              type string {
                length 1..80 ;
              }
            }
            leaf total {
              description 'The total number of license resources.'
                          ;
              type uint32 ;
            }
            leaf available {
              description 'The available number of license resources.'
                          ;
              type uint32 ;
            }
            leaf matched {
              description 'The matched number of license resources.'
                          ;
              type uint32 ;
            }
            leaf unmatched {
              description 'The unmatched number of license resources.'
                          ;
              type uint32 ;
            }
            leaf over-allocation {
              description 'The over-allocation number of license resources.'
                          ;
              type uint32 ;
            }
            ncd:select item-name ;
            ncd:select 'item-name demo-file'
                       ;
          }
        }
        container resource-permanent-briefs {
          list resouce-permanent-brief {
            description 'The license resources info in a position.'
                        ;
            key 'item-name location demo-file'
                ;
            leaf item-name {
              description 'The license item name.'
                          ;
              type string {
                length 1..63 ;
              }
            }
            leaf location {
              description 'The license port location.'
                          ;
              type string {
                length 1..31 ;
              }
            }
            leaf demo-file {
              description 'The license demo file name.'
                          ;
              type string {
                length 1..79 ;
              }
            }
            leaf permit-status {
              description 'The license port permit status.'
                          ;
              type enumeration {
                enum matched {
                  value 0 ;
                  description 'The port license status is matched.'
                              ;
                }
                enum unmatched {
                  value 1 ;
                  description 'The port license status is unmatched.'
                              ;
                }
                enum over-allocation {
                  value 2 ;
                  description 'The port license status is over-allocation.'
                              ;
                }
              }
            }
            leaf physical-status {
              description 'The license port physical status.'
                          ;
              type enumeration {
                enum online {
                  value 0 ;
                  description 'The port is online.'
                              ;
                }
                enum offline {
                  value 1 ;
                  description 'The port is offline.'
                              ;
                }
              }
            }
            leaf invalid-date {
              description 'The invalid date of license demo file.'
                          ;
              type string {
                length 1..12 ;
              }
            }
            ncd:select item-name ;
            ncd:select location ;
            ncd:select 'item-name location'
                       ;
            ncd:select 'item-name location demo-file'
                       ;
          }
        }
        container port-type-summarys {
          list port-type-summary {
            description 'The license resources of port type info.'
                        ;
            key port-type ;
            leaf port-type {
              description 'The port type of license port.'
                          ;
              type string {
                length 1..16 ;
              }
            }
            leaf total {
              description 'The total number of license port in one port type.'
                          ;
              type uint32 ;
            }
            leaf trial {
              description 'The trial port number of license in one port type.'
                          ;
              type uint32 ;
            }
            leaf demo {
              description 'The demo port number of license in one port type.'
                          ;
              type uint32 ;
            }
            leaf no-permit {
              description 'The no-permit port number of license in one port typ'
                        + 'e.'
                          ;
              type uint32 ;
            }
            leaf matched {
              description 'The matched port number of license in one port type.'
                          ;
              type uint32 ;
            }
            leaf unmatched {
              description 'The unmatched port number of license in one port typ'
                        + 'e.'
                          ;
              type uint32 ;
            }
            leaf over-allocation-matched {
              description 'The matched over-allocation port number of license i'
                        + 'n one port type.'
                          ;
              type uint32 ;
            }
            leaf over-allocation-unmatched {
              description 'The unmatched over-allocation port number of license'
                        + ' in one port type.'
                          ;
              type uint32 ;
            }
          }
        }
        container cards {
          description 'The license control information of cards.'
                      ;
          list card {
            description 'The license control information of cards.'
                        ;
            key location ;
            leaf location {
              description 'the location of license-control card.'
                          ;
              type string {
                length 0..11 ;
              }
            }
            leaf board-name {
              description 'the board-name of license-control card.'
                          ;
              type string {
                length 0..31 ;
              }
            }
            leaf license-control {
              description 'the license control flag of cards.'
                          ;
              type string {
                length 0..4 ;
              }
            }
          }
          ncd:revise-date 2022-02-10 ;
        }
        container devids {
          list devid {
            key shelf ;
            leaf shelf {
              description 'the shelf number of the device'
                          ;
              type uint8 {
                range 0..127 {
                  description 'shelf range'
                              ;
                }
              }
            }
            leaf system-devid {
              description 'the device system id'
                          ;
              type ncd:string-all {
                length 0..28 ;
              }
            }
          }
        }
      }
    }
    ncd:revise-date 2022-02-10 ;
  }
}
