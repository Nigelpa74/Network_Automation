module zte-an-interface-brg-perf {
    namespace 'http://www.zte.com.cn/zxr10/netconf/schema/rosng/zx-brg-pm';
    prefix zx-brg-pm;

    organization "ZTE Corporation";
    contact "Zhang Weiping   ZTE Corporation
                         Mail: zhang.weiping@zte.com.cn
                         Tel : 021-68896470";
    description "The MIB module for the Performance Management of ZTE Access
                 Node interface.";
    revision 2011-09-13 {
        description "Modify this mib according to standard.";
    }
    revision 2011-09-10 {
        description "Modify the description.";
    }
    revision 2011-07-02 {
        description "Initial version of this MIB module.";
    }
    container zxAnInterfaceBrgPerf {
        description "";
        container zxAnBrgIfPerfObjects {
            description "";
            container zxAnBrgIfCurr15MinPerfTable {
                description "The 15 minutes interval performance data table of the bridge interfaces.";
                list zxAnBrgIfCurr15MinPerfEntry {
                    description "The 15 minutes interval performance data entry of the bridge interfaces.";
                    max-elements 20;
                    key "ifIndex zxAnSubIfIndex";
                    leaf ifIndex {
                        description "A unique value, greater than zero, for each interface.  It
                                     is recommended that values are assigned contiguously
                                     starting from 1.  The value for each interface sub-layer
                                     must remain constant at least from one re-initialization of
                                     the entity's network management system to the next re-
                                     initialization.";
                        type int32 {
                            range 1..2147483647;
                        }
                    }
                    leaf zxAnSubIfIndex {
                        description "Sub-interface index at this interface.";
                        type int32;
                    }
                    leaf brgIfC15MTimeElapsed {
                        config false;
                        description "Number of seconds that have elapsed since the beginning of the 
                                     current 15 minutes interval.";
                        type uint32 {
                            range 0..899;
                        }
                    }
                    leaf brgIfC15MInOctets {
                        config false;
                        description "The total number of octets received on the interface,
                                     including framing characters in current 15 minutes interval.";
                        type uint64;
                    }
                    leaf brgIfC15MInUcastPkts {
                        config false;
                        description "The number of packets, delivered by this sub-layer to a
                                     higher (sub-)layer, which were not addressed to a multicast
                                     or broadcast address at this sub-layer and in current 15 
                                     minutes interval.";
                        type uint64;
                    }
                    leaf brgIfC15MInMcastPkts {
                        config false;
                        description "The number of packets, delivered by this sub-layer to a
                                     higher (sub-)layer, which were addressed to a multicast
                                     address at this sub-layer and in current 15 minutes interval. 
                                     For a MAC layer protocol, this includes both Group and 
                                     Functional addresses.";
                        type uint64;
                    }
                    leaf brgIfC15MInBcastPkts {
                        config false;
                        description "The number of packets, delivered by this sub-layer to a
                                     higher (sub-)layer, which were addressed to a broadcast
                                     address at this sub-layer and in current 15 minutes interval.";
                        type uint64;
                    }
                    leaf brgIfC15MOutOctets {
                        config false;
                        description "The total number of octets transmitted out of the interface, 
                                     including framing characters in curent 15 minutes interval.";
                        type uint64;
                    }
                    leaf brgIfC15MOutUcastPkts {
                        config false;
                        description "The total number of packets that higher-level protocols
                                     requested be transmitted, and which were not addressed to a
                                     multicast or broadcast address at this sub-layer, including
                                     those that were discarded or not sent in current 15 minutes interval.";
                        type uint64;
                    }
                    leaf brgIfC15MOutMcastPkts {
                        config false;
                        description "The total number of packets that higher-level protocols
                                     requested be transmitted, and which were addressed to a
                                     multicast address at this sub-layer, including those that
                                     were discarded or not sent and in current 15 minutes interval.
                                     For a MAC layer protocol, this includes both Group and 
                                     Functional addresses.";
                        type uint64;
                    }
                    leaf brgIfC15MOutBcastPkts {
                        config false;
                        description "The total number of packets that higher-level protocols
                                     requested be transmitted, and which were addressed to a
                                     broadcast address at this sub-layer, including those that
                                     were discarded or not sent in 15 current minutes interval.";
                        type uint64;
                    }
                    leaf brgIfC15MInErroredPktRate {
                        config false;
                        description "The received errored packet rate in current 15 minutes.";
                        type uint32;
                    }
                    leaf brgIfC15MInBwUsingRatio {
                        config false;
                        description "An estimate of the interface's current received bandwidth using 
                                     ratio in current 15 minutes.";
                        type int32 {
                            range 0..100;
                        }
                    }
                    leaf brgIfC15MOutBwUsingRatio {
                        config false;
                        description "An estimate of the interface's current transmitted bandwidth using
                                     ratio in current 15 minutes.";
                        type int32 {
                            range 0..100;
                        }
                    }
                    leaf brgIfC15MReset {
                        description "Clear all the current 15 minutes performance variables.
                                     When get this variable, always return 1.";
                        type enumeration {
                            enum perfReset {
                                value 1;
                                description "";
                            }
                        }
                    }
                }
            }
            container zxAnBrgIfCurr1DayPerfTable {
                description "The 1 day interval performance data table of the bridge interfaces.";
                list zxAnBrgIfCurr1DayPerfEntry {
                    description "The 1 day interval performance data entry of the bridge interfaces.";
                    max-elements 20;
                    key "ifIndex zxAnSubIfIndex";
                    leaf ifIndex {
                        description "A unique value, greater than zero, for each interface.  It
                                     is recommended that values are assigned contiguously
                                     starting from 1.  The value for each interface sub-layer
                                     must remain constant at least from one re-initialization of
                                     the entity's network management system to the next re-
                                     initialization.";
                        type int32 {
                            range 1..2147483647;
                        }
                    }
                    leaf zxAnSubIfIndex {
                        description "Sub-interface index at this interface.";
                        type int32;
                    }
                    leaf brgIfC1DTimeElapsed {
                        config false;
                        description "Number of seconds that have elapsed since the beginning of the 
                                     current 1 day interval.";
                        type uint32 {
                            range 0..86399;
                        }
                    }
                    leaf brgIfC1DInOctets {
                        config false;
                        description "The total number of octets received on the interface,
                                     including framing characters in current one day interval.";
                        type uint64;
                    }
                    leaf brgIfC1DInUcastPkts {
                        config false;
                        description "The total number of octets received on the interface,
                                     including framing characters in current one day interval.";
                        type uint64;
                    }
                    leaf brgIfC1DInMcastPkts {
                        config false;
                        description "The number of packets, delivered by this sub-layer to a
                                     higher (sub-)layer, which were addressed to a multicast
                                     address at this sub-layer and in current one day interval.
                                     For a MAC layer protocol, this includes both Group and 
                                     Functional addresses.";
                        type uint64;
                    }
                    leaf brgIfC1DInBcastPkts {
                        config false;
                        description "The number of packets, delivered by this sub-layer to a
                                     higher (sub-)layer, which were addressed to a broadcast
                                     address at this sub-layer and in current one day interval.";
                        type uint64;
                    }
                    leaf brgIfC1DOutOctets {
                        config false;
                        description "The total number of octets transmitted out of the interface, 
                                     including framing characters in curent one day interval.";
                        type uint64;
                    }
                    leaf brgIfC1DOutUcastPkts {
                        config false;
                        description "The total number of packets that higher-level protocols
                                     requested be transmitted, and which were not addressed to a
                                     multicast or broadcast address at this sub-layer, including
                                     those that were discarded or not sent in current one day interval.";
                        type uint64;
                    }
                    leaf brgIfC1DOutMcastPkts {
                        config false;
                        description "The total number of packets that higher-level protocols
                                     requested be transmitted, and which were addressed to a
                                     multicast address at this sub-layer, including those that
                                     were discarded or not sent and in current one day interval. 
                                     For a MAC layer protocol, this includes both Group and 
                                     Functional addresses.";
                        type uint64;
                    }
                    leaf brgIfC1DOutBcastPkts {
                        config false;
                        description "The number of packets that higher-level protocols
                                     requested be transmitted, and which were addressed to a
                                     broadcast address at this sub-layer, including those that
                                     were discarded or not sent in current one day interval.";
                        type uint64;
                    }
                    leaf brgIfC1DInDiscardPkts {
                        config false;
                        description "The total number of packets that higher-level protocols
                                     requested be transmitted and which were discarded  
                                     in current one day interval.";
                        type uint64;
                    }
                    leaf brgIfC1DOutDiscardPkts {
                        config false;
                        description "The total number of packets received on the interface,
                                     and which were discarded  in current one day interval.";
                        type uint64;
                    }
                    leaf brgIfC1DInErroredPktRate {
                        config false;
                        description "The received errored packet rate in current one day.";
                        type uint32;
                    }
                    leaf brgIfC1DInBwUsingRatio {
                        config false;
                        description "An estimate of the interface's received bandwidth using ratio 
                                     in current one day.";
                        type int32 {
                            range 0..100;
                        }
                    }
                    leaf brgIfC1DOutBwUsingRatio {
                        config false;
                        description "An estimate of the interface's transmitted bandwidth using ratio 
                                     in current one day.";
                        type int32 {
                            range 0..100;
                        }
                    }
                    leaf brgIfC1DReset {
                        description "Clear all the current 1 day performance variables.
                                     When get this variable, always return 1.";
                        type enumeration {
                            enum perfReset {
                                value 1;
                                description "";
                            }
                        }
                    }
                }
            }
            container zxAnBrgIfHis15MinPerfTable {
                description "The 15 minutes interval history performance data table of the bridge interfaces.";
                list zxAnBrgIfHis15MinPerfEntry {
                    config false;
                    description "The 15 minutes interval performance data entry of the bridge interfaces.";
                    max-elements 20;
                    key "ifIndex zxAnSubIfIndex brgIfH15MIntervalNo";
                    leaf ifIndex {
                        description "A unique value, greater than zero, for each interface.  It
                                     is recommended that values are assigned contiguously
                                     starting from 1.  The value for each interface sub-layer
                                     must remain constant at least from one re-initialization of
                                     the entity's network management system to the next re-
                                     initialization.";
                        type int32 {
                            range 1..2147483647;
                        }
                    }
                    leaf zxAnSubIfIndex {
                        description "Sub-interface index at this interface.";
                        type int32;
                    }
                    leaf brgIfH15MIntervalNo {
                        config false;
                        description "Performance data interval number 1 is the the most recent 
                                     previous interval; interval 96 is 24 hours ago.  
                                     Intervals 2..96 are optional.";
                        type int32 {
                            range 1..96;
                        }
                    }
                    leaf brgIfH15MIntervalValidData {
                        config false;
                        description "Performance data valid flag. 
                                     true(1) means valid.  
                                     false(2) means invalidm and the performace data is useless.";
                        type int32;
                    }
                    leaf brgIfH15MDateTime {
                        config false;
                        description "The 15 minutes interval performance data generation time.";
                        type binary;
                    }
                    leaf brgIfH15MInOctets {
                        config false;
                        description "The total number of octets received on the interface,
                                     including framing characters in current 15 historical interval.";
                        type uint64;
                    }
                    leaf brgIfH15MInUcastPkts {
                        config false;
                        description "The number of packets, delivered by this sub-layer to a
                                     higher (sub-)layer, which were not addressed to a multicast
                                     or broadcast address at this sub-layer and in historical 15 
                                     minutes interval.";
                        type uint64;
                    }
                    leaf brgIfH15MInMcastPkts {
                        config false;
                        description "The number of packets, delivered by this sub-layer to a
                                     higher (sub-)layer, which were addressed to a multicast
                                     address at this sub-layer and in historical 15 minutes 
                                     interval.For a MAC layer protocol, this includes both 
                                     Group and Functional addresses.";
                        type uint64;
                    }
                    leaf brgIfH15MInBcastPkts {
                        config false;
                        description "The number of packets, delivered by this sub-layer to a
                                     higher (sub-)layer, which were addressed to a broadcast
                                     address at this sub-layer and in historical 15 minutes interval.";
                        type uint64;
                    }
                    leaf brgIfH15MOutOctets {
                        config false;
                        description "The total number of octets transmitted out of the interface, 
                                     including framing characters in historical 15 minutes interval.";
                        type uint64;
                    }
                    leaf brgIfH15MOutUcastPkts {
                        config false;
                        description "The total number of packets that higher-level protocols
                                     requested be transmitted, and which were not addressed to a
                                     multicast or broadcast address at this sub-layer, including
                                     those that were discarded or not sent in historical 15 minutes
                                     interval.";
                        type uint64;
                    }
                    leaf brgIfH15MOutMcastPkts {
                        config false;
                        description "The total number of packets that higher-level protocols
                                     requested be transmitted, and which were addressed to a
                                     multicast address at this sub-layer, including those that
                                     were discarded or not sent and in historical 15 minutes 
                                     interval.For a MAC layer protocol, this includes both Group
                                     and Functional addresses.";
                        type uint64;
                    }
                    leaf brgIfH15MOutBcastPkts {
                        config false;
                        description "The total number of packets that higher-level protocols
                                     requested be transmitted, and which were addressed to a
                                     broadcast address at this sub-layer, including those that
                                     were discarded or not sent in 15 historical minutes interval.";
                        type uint64;
                    }
                    leaf brgIfH15MInErroredPktRate {
                        config false;
                        description "The received errored packet rate in historical 15 minutes.";
                        type uint32;
                    }
                    leaf brgIfH15MInBwUsingRatio {
                        config false;
                        description "An estimate of the interface's received bandwidth using ratio 
                                     in historical 15 minutes.";
                        type int32 {
                            range 0..100;
                        }
                    }
                    leaf brgIfH15MOutBwUsingRatio {
                        config false;
                        description "An estimate of the interface's transmitted bandwidth using ratio 
                                     in historical 15 minutes.";
                        type int32 {
                            range 0..100;
                        }
                    }
                }
            }
            container zxAnBrgIfHis1DayPerfTable {
                description "The 1 day interval history performance data table of the bridge interfaces.";
                list zxAnBrgIfHis1DayPerfEntry {
                    config false;
                    description "The 1 day interval performance data entry of the bridge interfaces.";
                    max-elements 20;
                    key "ifIndex zxAnSubIfIndex brgIfH1DIntervalNo";
                    leaf ifIndex {
                        description "A unique value, greater than zero, for each interface.  It
                                     is recommended that values are assigned contiguously
                                     starting from 1.  The value for each interface sub-layer
                                     must remain constant at least from one re-initialization of
                                     the entity's network management system to the next re-
                                     initialization.";
                        type int32 {
                            range 1..2147483647;
                        }
                    }
                    leaf zxAnSubIfIndex {
                        description "Sub-interface index at this interface.";
                        type int32;
                    }
                    leaf brgIfH1DIntervalNo {
                        config false;
                        description "Performance data interval number 1 is the the most recent 
                                     previous interval; interval 7 is 1 week ago.  
                                     Intervals 2..7 are optional.";
                        type int32 {
                            range 1..7;
                        }
                    }
                    leaf brgIfH1DIntervalValidData {
                        config false;
                        description "Performance data valid flag. 
                                     true(1) means valid.  
                                     false(2) means invalidm and the performace data is useless.";
                        type int32;
                    }
                    leaf brgIfH1DDateTime {
                        config false;
                        description "The 1 day interval performance data generation time.";
                        type binary;
                    }
                    leaf brgIfH1DInOctets {
                        config false;
                        description "The total number of octets received on the interface,
                                     including framing characters in historical one day interval.";
                        type uint64;
                    }
                    leaf brgIfH1DInUcastPkts {
                        config false;
                        description "The total number of octets received on the interface,
                                     including framing characters in historical one day interval.";
                        type uint64;
                    }
                    leaf brgIfH1DInMcastPkts {
                        config false;
                        description "The number of packets, delivered by this sub-layer to a
                                     higher (sub-)layer, which were addressed to a multicast
                                     address at this sub-layer and in historical one day interval.
                                     For a MAC layer protocol, this includes both Group and 
                                     Functional addresses.";
                        type uint64;
                    }
                    leaf brgIfH1DInBcastPkts {
                        config false;
                        description "The number of packets, delivered by this sub-layer to a
                                     higher (sub-)layer, which were addressed to a broadcast
                                     address at this sub-layer and in historical one day interval.";
                        type uint64;
                    }
                    leaf brgIfH1DOutOctets {
                        config false;
                        description "The total number of octets transmitted out of the interface, 
                                     including framing characters in historical one day interval.";
                        type uint64;
                    }
                    leaf brgIfH1DOutUcastPkts {
                        config false;
                        description "The total number of packets that higher-level protocols
                                     requested be transmitted, and which were not addressed to a
                                     multicast or broadcast address at this sub-layer, including
                                     those that were discarded or not sent in historical one day
                                     interval.";
                        type uint64;
                    }
                    leaf brgIfH1DOutMcastPkts {
                        config false;
                        description "The total number of packets that higher-level protocols
                                     requested be transmitted, and which were addressed to a
                                     multicast address at this sub-layer, including those that
                                     were discarded or not sent and in historical one day interval. 
                                     For a MAC layer protocol, this includes both Group and 
                                     Functional addresses.";
                        type uint64;
                    }
                    leaf brgIfH1DOutBcastPkts {
                        config false;
                        description "The total number of packets that higher-level protocols
                                     requested be transmitted, and which were addressed to a
                                     broadcast address at this sub-layer, including those that
                                     were discarded or not sent in historical one day interval.";
                        type uint64;
                    }
                    leaf brgIfH1DInDiscardPkts {
                        config false;
                        description "The total number of packets that higher-level protocols
                                     requested be transmitted and were discarded in historical 
                                     one day interval.";
                        type uint64;
                    }
                    leaf brgIfH1DOutDiscardPkts {
                        config false;
                        description "The total number of packets received on the interface,
                                     and were discarded in historical one day interval.";
                        type uint64;
                    }
                    leaf brgIfH1DInErroredPktRate {
                        config false;
                        description "The received errored packet rate in historical one day.";
                        type uint32;
                    }
                    leaf brgIfH1DInBwUsingRatio {
                        config false;
                        description "An estimate of the interface's received bandwidth using ratio 
                                     in historical one day.";
                        type int32 {
                            range 0..100;
                        }
                    }
                    leaf brgIfH1DOutBwUsingRatio {
                        config false;
                        description "An estimate of the interface's transmitted bandwidth using ratio 
                                     in historical one day.";
                        type int32 {
                            range 0..100;
                        }
                    }
                }
            }
            container zxAnBrgIfAlmProfileConfTable {
                description "The performance alarm threshold profile table of the bridge interfaces.";
                list zxAnBrgIfAlmProfileConfEntry {
                    description "The performance alarm threshold profile table of the bridge interfaces.These
                                 variables in the profile configuration is optional,if not configured,
                                 it means the correspongding alarm is not reported, but the alarm and
                                 clear alarm threshold configuration is needed to bind. ";
                    max-elements 20;
                    key "brgIfAlmProfileName brgIfPerfVariable";
                    leaf brgIfAlmProfileName {
                        description "The profile name.";
                        type string {
                            length 1..32;
                        }
                    }
                    leaf brgIfPerfVariable {
                        description "The object identifier of performance variables.";
                        type binary;
                    }
                    leaf brgIfRiseAlmThresh {
                        description "The threshold for rising alarm.";
                        type uint64;
                    }
                    leaf brgIfClrRiseAlmThresh {
                        description "The threshold for rising alarm restore.";
                        type uint64;
                    }
                    leaf brgIfRiseWarnThresh {
                        description "The threshold for rising warning.";
                        type uint64;
                    }
                    leaf brgIfClrRiseWarnThresh {
                        description "The threshold for rising warning restore.";
                        type uint64;
                    }
                    leaf brgIfFallWarnThresh {
                        description "The threshold for falling warning.";
                        type uint64;
                    }
                    leaf brgIfClrFallWarnThresh {
                        description "The threshold for falling warning restore.";
                        type uint64;
                    }
                    leaf brgIfFallAlmThresh {
                        description "The threshold for falling alarm.";
                        type uint64;
                    }
                    leaf brgIfClrFallAlmThresh {
                        description "The threshold for falling alarm restore.";
                        type uint64;
                    }
                    leaf brgIfThreshUsed {
                        description "The threshold used flag.";
                        type bits {
                            bit riseAlmThresh {
                                description "";
                                reference "";
                            }
                            bit riseAlmClrThresh {
                                description "";
                                reference "";
                            }
                            bit riseWarnThresh {
                                description "";
                                reference "";
                            }
                            bit riseWarnClrThresh {
                                description "";
                                reference "";
                            }
                            bit fallWarnThresh {
                                description "";
                                reference "";
                            }
                            bit fallWarnClrThresh {
                                description "";
                                reference "";
                            }
                            bit fallAlmThresh {
                                description "";
                                reference "";
                            }
                            bit fallAlmClrThresh {
                                description "";
                                reference "";
                            }
                        }
                    }
                }
            }
            container zxAnBrgIfAlmProfileApplyTable {
                description "The performance alarm threshold profile configuration table of 
                             the bridge interfaces.";
                list zxAnBrgIfAlmProfileApplyEntry {
                    description "The performance alarm threshold profile configuration entry of 
                                 the bridge interfaces.";
                    max-elements 20;
                    key "ifIndex zxAnSubIfIndex";
                    leaf ifIndex {
                        description "A unique value, greater than zero, for each interface.  It
                                     is recommended that values are assigned contiguously
                                     starting from 1.  The value for each interface sub-layer
                                     must remain constant at least from one re-initialization of
                                     the entity's network management system to the next re-
                                     initialization.";
                        type int32 {
                            range 1..2147483647;
                        }
                    }
                    leaf zxAnSubIfIndex {
                        description "Sub-interface index at this interface.";
                        type int32;
                    }
                    leaf brgIfAlmPrf {
                        description "The performance alarm threshold profile.";
                        type string {
                            length 1..32;
                        }
                    }
                }
            }
            container zxAnBrgIfAlmProfileTable {
                description "The performance alarm threshold profile table of the bridge interfaces.
                             It can be used to delete all of the performance alarm threshold profiles
                             which has the same name configured in 'zxAnBrgIfAlmProfileConfTable'.";
                list zxAnBrgIfAlmProfileEntry {
                    description "The performance alarm threshold profile entry of the bridge interfaces.";
                    max-elements 20;
                    key "brgIfAlmProfileName";
                    leaf brgIfAlmProfileName {
                        description "The profile name.";
                        type string {
                            length 1..32;
                        }
                    }
                }
            }
            container zxAnBrgIfCurrMinPerfTable {
                description "The minutes interval performance data table of the
                             bridge interfaces.";
                list zxAnBrgIfCurrMinPerfEntry {
                    description "The minutes interval performance data entry of the
                                 bridge interfaces.";
                    max-elements 20;
                    key "ifIndex zxAnSubIfIndex";
                    leaf ifIndex {
                        description "A unique value, greater than zero, for each interface.  It
                                     is recommended that values are assigned contiguously
                                     starting from 1.  The value for each interface sub-layer
                                     must remain constant at least from one re-initialization of
                                     the entity's network management system to the next re-
                                     initialization.";
                        type int32 {
                            range 1..2147483647;
                        }
                    }
                    leaf zxAnSubIfIndex {
                        description "Sub-interface index at this interface.";
                        type int32;
                    }
                    leaf brgIfCMinTimeElapsed {
                        config false;
                        description "Number of seconds that have elapsed since the beginning of the
                                     current minutes interval.";
                        type uint32;
                    }
                    leaf brgIfCMinInOctets {
                        config false;
                        description "The total number of octets received on the interface,
                                     including framing characters in current minutes interval.";
                        type uint64;
                    }
                    leaf brgIfCMinInUcastPkts {
                        config false;
                        description "The number of packets, delivered by this sub-layer to a
                                     higher (sub-)layer, which were not addressed to a multicast
                                     or broadcast address at this sub-layer and in current
                                     minutes interval.";
                        type uint64;
                    }
                    leaf brgIfCMinInMcastPkts {
                        config false;
                        description "The number of packets, delivered by this sub-layer to a
                                     higher (sub-)layer, which were addressed to a multicast
                                     address at this sub-layer and in current minutes interval.
                                     For a MAC layer protocol, this includes both Group and
                                     Functional addresses.";
                        type uint64;
                    }
                    leaf brgIfCMinInBcastPkts {
                        config false;
                        description "The number of packets, delivered by this sub-layer to a
                                     higher (sub-)layer, which were addressed to a broadcast
                                     address at this sub-layer and in current minutes interval.";
                        type uint64;
                    }
                    leaf brgIfCMinOutOctets {
                        config false;
                        description "The total number of octets transmitted out of the interface,
                                     including framing characters in curent minutes interval.";
                        type uint64;
                    }
                    leaf brgIfCMinOutUcastPkts {
                        config false;
                        description "The total number of packets that higher-level protocols
                                     requested be transmitted, and which were not addressed to a
                                     multicast or broadcast address at this sub-layer, including
                                     those that were discarded or not sent in current minutes interval.";
                        type uint64;
                    }
                    leaf brgIfCMinOutMcastPkts {
                        config false;
                        description "The total number of packets that higher-level protocols
                                     requested be transmitted, and which were addressed to a
                                     multicast address at this sub-layer, including those that
                                     were discarded or not sent and in current minutes interval.
                                     For a MAC layer protocol, this includes both Group and
                                     Functional addresses.";
                        type uint64;
                    }
                    leaf brgIfCMinOutBcastPkts {
                        config false;
                        description "The total number of packets that higher-level protocols
                                     requested be transmitted, and which were addressed to a
                                     broadcast address at this sub-layer, including those that
                                     were discarded or not sent in current minutes interval.";
                        type uint64;
                    }
                    leaf brgIfCMinInDiscardPkts {
                        config false;
                        description "The total number of packets that higher-level protocols
                                     requested be transmitted and were discarded in current 
                                     minutes interval.";
                        type uint64;
                    }
                    leaf brgIfCMinOutDiscardPkts {
                        config false;
                        description "The total number of packets received on the interface,
                                     and were discarded in current minutes interval.";
                        type uint64;
                    }
                    leaf brgIfCMinInErroredPktRate {
                        config false;
                        description "The received errored packet rate in current minutes.";
                        type uint32;
                    }
                    leaf brgIfCMinInBwUsingRatio {
                        config false;
                        description "An estimate of the interface's current received bandwidth using
                                     ratio in current minutes.";
                        type int32 {
                            range 0..100;
                        }
                    }
                    leaf brgIfCMinOutBwUsingRatio {
                        config false;
                        description "An estimate of the interface's current transmitted bandwidth using
                                     ratio in current minutes.";
                        type int32 {
                            range 0..100;
                        }
                    }
                    leaf brgIfCMinReset {
                        description "Clear all the current minutes performance variables.
                                     When get this variable, always return 1.";
                        type enumeration {
                            enum perfReset {
                                value 1;
                                description "";
                            }
                        }
                    }
                }
            }
            container zxAnBrgIfHisMinPerfTable {
                description "The minutes interval history performance data table of the
                             bridge interfaces.";
                list zxAnBrgIfHisMinPerfEntry {
                    config false;
                    description "The minutes interval history performance data entry of the
                                 bridge interfaces.";
                    max-elements 20;
                    key "ifIndex zxAnSubIfIndex brgIfHMinIntervalNo";
                    leaf ifIndex {
                        description "A unique value, greater than zero, for each interface.  It
                                     is recommended that values are assigned contiguously
                                     starting from 1.  The value for each interface sub-layer
                                     must remain constant at least from one re-initialization of
                                     the entity's network management system to the next re-
                                     initialization.";
                        type int32 {
                            range 1..2147483647;
                        }
                    }
                    leaf zxAnSubIfIndex {
                        description "Sub-interface index at this interface.";
                        type int32;
                    }
                    leaf brgIfHMinIntervalNo {
                        config false;
                        description "Performance data interval number.";
                        type int32;
                    }
                    leaf brgIfHMinIntervalValidData {
                        config false;
                        description "Performance data valid flag.
                                     true(1) means valid.
                                     false(2) means invalidm and the performace data is useless.";
                        type int32;
                    }
                    leaf brgIfHMinDateTime {
                        config false;
                        description "The minutes interval performance data generation time.";
                        type binary;
                    }
                    leaf brgIfHMinInOctets {
                        config false;
                        description "The total number of octets received on the interface,
                                     including framing characters in current historical interval.";
                        type uint64;
                    }
                    leaf brgIfHMinInUcastPkts {
                        config false;
                        description "The number of packets, delivered by this sub-layer to a
                                     higher (sub-)layer, which were not addressed to a multicast
                                     or broadcast address at this sub-layer and in historical
                                     minutes interval.";
                        type uint64;
                    }
                    leaf brgIfHMinInMcastPkts {
                        config false;
                        description "The number of packets, delivered by this sub-layer to a
                                     higher (sub-)layer, which were addressed to a multicast
                                     address at this sub-layer and in historical minutes
                                     interval.For a MAC layer protocol, this includes both
                                     Group and Functional addresses.";
                        type uint64;
                    }
                    leaf brgIfHMinInBcastPkts {
                        config false;
                        description "The number of packets, delivered by this sub-layer to a
                                     higher (sub-)layer, which were addressed to a broadcast
                                     address at this sub-layer and in historical minutes interval.";
                        type uint64;
                    }
                    leaf brgIfHMinOutOctets {
                        config false;
                        description "The total number of octets transmitted out of the interface,
                                     including framing characters in historical minutes interval.";
                        type uint64;
                    }
                    leaf brgIfHMinOutUcastPkts {
                        config false;
                        description "The total number of packets that higher-level protocols
                                     requested be transmitted, and which were not addressed to a
                                     multicast or broadcast address at this sub-layer, including
                                     those that were discarded or not sent in historical minutes
                                     interval.";
                        type uint64;
                    }
                    leaf brgIfHMinOutMcastPkts {
                        config false;
                        description "The total number of packets that higher-level protocols
                                     requested be transmitted, and which were addressed to a
                                     multicast address at this sub-layer, including those that
                                     were discarded or not sent and in historical minutes 
                                     interval.For a MAC layer protocol, this includes both Group
                                     and Functional addresses.";
                        type uint64;
                    }
                    leaf brgIfHMinOutBcastPkts {
                        config false;
                        description "The total number of packets that higher-level protocols
                                     requested be transmitted, and which were addressed to a
                                     broadcast address at this sub-layer, including those that
                                     were discarded or not sent in historical minutes interval.";
                        type uint64;
                    }
                    leaf brgIfHMinInDiscardPkts {
                        config false;
                        description "The total number of packets that higher-level protocols
                                     requested be transmitted and were discarded in historical 
                                     minutes interval.";
                        type uint64;
                    }
                    leaf brgIfHMinOutDiscardPkts {
                        config false;
                        description "The total number of packets received on the interface,
                                     and were discarded in historical minutes interval.";
                        type uint64;
                    }
                    leaf brgIfHMinInErroredPktRate {
                        config false;
                        description "The received errored packet rate in historical minutes.";
                        type uint32;
                    }
                    leaf brgIfHMinInBwUsingRatio {
                        config false;
                        description "An estimate of the interface's received bandwidth using ratio
                                     in historical minutes.";
                        type int32 {
                            range 0..100;
                        }
                    }
                    leaf brgIfHMinOutBwUsingRatio {
                        config false;
                        description "An estimate of the interface's transmitted bandwidth using ratio
                                     in historical minutes.";
                        type int32 {
                            range 0..100;
                        }
                    }
                }
            }
            container zxAnBrgIfMinPerfTable {
                description "";
                list zxAnBrgIfMinPerfEntry {
                    config false;
                    description " ";
                    max-elements 1;
                    key "ifIndex zxAnSubIfIndex";
                    leaf ifIndex {
                        description "A unique value, greater than zero, for each interface.  It
                                     is recommended that values are assigned contiguously
                                     starting from 1.  The value for each interface sub-layer
                                     must remain constant at least from one re-initialization of
                                     the entity's network management system to the next re-
                                     initialization.";
                        type int32 {
                            range 1..2147483647;
                        }
                    }
                    leaf zxAnSubIfIndex {
                        description "Sub-interface index at this interface.";
                        type int32;
                    }
                    leaf numberOfMinIntervals {
                        config false;
                        description "The total number of 15-minute PM intervals for which data was collected.";
                        type int32 {
                            range 0..96;
                        }
                    }
                    leaf nonValidMinIntervals {
                        config false;
                        description "The number of 15-minute PM intervals for which the data is considered to be invalid or incomplete.";
                        type int32 {
                            range 0..96;
                        }
                    }
                }
            }
            container zxAnBrgIf1DayPerfTable {
                description "";
                list zxAnBrgIf1DayPerfEntry {
                    config false;
                    description "";
                    max-elements 1;
                    key "ifIndex zxAnSubIfIndex";
                    leaf ifIndex {
                        description "A unique value, greater than zero, for each interface.  It
                                     is recommended that values are assigned contiguously
                                     starting from 1.  The value for each interface sub-layer
                                     must remain constant at least from one re-initialization of
                                     the entity's network management system to the next re-
                                     initialization.";
                        type int32 {
                            range 1..2147483647;
                        }
                    }
                    leaf zxAnSubIfIndex {
                        description "Sub-interface index at this interface.";
                        type int32;
                    }
                    leaf numberOf1DayIntervals {
                        config false;
                        description "The total number of 15-minute PM intervals for which data was collected.";
                        type int32 {
                            range 0..7;
                        }
                    }
                    leaf nonValid1DayIntervals {
                        config false;
                        description "The number of 15-minute PM intervals for which the data is considered to be invalid or incomplete.";
                        type int32 {
                            range 0..7;
                        }
                    }
                }
            }
        }
    }
}
