module zxr10-iccp {
  namespace 'http://www.zte.com.cn/zxr10/netconf/schema/rosng/iccp'
            ;
  prefix ICCP ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The netconf model to describe redundency group.'
              ;
  revision 2019-07-03 {
    description 'Add enum value apply-vlan in enum app-type.'+"\n"
              + 'Add container iccp-apply-vlan in list /configuration/iccp/rg.
'
              + ''+"\n"
              + 'Add leaf node apply-vlan in container iccp-apply-vlan.'+"\n"
              + 'Modify the description of leaf node app-type in /state/iccp/ic'
              + 'cp-state.'+"\n"
              + 'Modify the description of leaf node app-type in /state/iccp/ic'
              + 'cp-v6peer-state.'+"\n"
              + 'Add leaf node msgs-sent in list /state/iccp/iccp-state.'+"\n"
              + 'Add leaf node msgs-rcvd in list /state/iccp/iccp-state.'+"\n"
              + 'Add leaf node msgs-sent in list /state/iccp/iccp-v6peer-state.'
              + ''+"\n"
              + 'Add leaf node msgs-rcvd in list /state/iccp/iccp-v6peer-state.'
                ;
  }
  revision 2018-11-13 {
    description 'Add enum value apply-stp in enum app-type.'+"\n"
              + 'Add feature label_stp.'+"\n"
              + 'Add container iccp-apply-stp in list /configuration/iccp/rg.'+"\n"
              + 'Add leaf node apply-stp in container iccp-apply-stp.'+"\n"
              + 'Modify the description of leaf node app-type in /state/iccp/ic'
              + 'cp-state.'
                ;
  }
  revision 2018-09-11 {
    description 'Add enum value apply-dhcpsnoop in enum app-type.'+"\n"
              + 'Add feature label_dhcpsnoop.'+"\n"
              + 'Add container iccp-apply-dhcpsnoop in list /configuration/iccp'
              + '/rg.'+"\n"
              + 'Add leaf node apply-dhcpsnoop in container iccp-apply-dhcpsnoo'
              + 'p.'+"\n"
              + 'Modify the description of leaf node app-type in /state/iccp/ic'
              + 'cp-state.'
                ;
  }
  revision 2018-06-19 {
    description "Add enum value apply-nd in enum app-type.
\nModify the status "
              + "to 'obsolete' of leaf node rg-peer-addr in /configuration/iccp"
              + "/rg/peer-addr.
\nAdd choice rg-peer in /configuration/iccp/rg/"
              + "peer-addr.
\nAdd case rg-peer-v4-addr in choice rg-peer.
\nAdd"
              + " leaf node rg-peer-v4-addr in /configuration/iccp/rg/peer-addr"
              + ".
\nAdd case rg-peer-v6-addr in choice rg-peer.
\nAdd leaf nod"
              + "e rg-peer-v6-addr in /configuration/iccp/rg/peer-addr.
\nAdd l"
              + "ist iccp-v6peer-state in /state/iccp.
\nAdd leaf node rg-id in"
              + " /state/iccp/iccp-v6peer-state.
\nAdd leaf node rg-state in /s"
              + "tate/iccp/iccp-v6peer-state.
\nAdd leaf node v6-peer-addr in /"
              + "state/iccp/iccp-v6peer-state.
\nAdd leaf node total-iccp-sessi"
              + "ons in /state/iccp/iccp-v6peer-state.
\nAdd leaf node app-type"
              + " in /state/iccp/iccp-v6peer-state.
\nAdd leaf node app-state i"
              + "n /state/iccp/iccp-v6peer-state.
\nAdd leaf node hostname in /"
              + "state/iccp/iccp-v6peer-state.
\nAdd leaf node active-mode in /"
              + "state/iccp/iccp-v6peer-state."
                ;
  }
  revision 2017-01-10 {
    description 'Add enum value apply-igmpsnoop in enum app-type.'+"\n"
              + 'Add feature label_igmpsnoop.'+"\n"
              + 'Add container iccp-apply-igmpsnoop in list /configuration/iccp'
              + '/rg.'+"\n"
              + 'Add leaf node apply-igmpsnoop in container iccp-apply-igmpsnoo'
              + 'p.'+"\n"
              + 'Modify the description of leaf node app-type in /state/iccp/ic'
              + 'cp-state.'
                ;
  }
  revision 2016-01-25 {
    description 'Add enum value apply-vxlan in enum app-type.'+"\n"
              + 'Add feature label_vxlan.'+"\n"
              + 'Add container iccp-apply-vxlan in list /configuration/iccp/rg.'
              + ''+"\n"
              + 'Add leaf node apply-vxlan in container iccp-apply-vxlan.'+"\n"
              + 'Modify the description of leaf node app-type in /state/iccp/ic'
              + 'cp-state.'
                ;
  }
  revision 2015-10-27 {
    description 'Add enum type app-connecting in enum app-state.'+"\n"
              + 'Add enum type active-mode.'+"\n"
              + 'Add enum value PRIVATE in enum active-mode.'+"\n"
              + 'Add enum value STANDARD in enum active-mode.'+"\n"
              + 'Add container rg-peer-mode in list /configuration/iccp.'+"\n"
              + 'Add leaf node standard-mode-acl in container rg-peer-mode.'+"\n"
              + 'Add leaf node active-mode in list iccp-state.'
                ;
  }
  revision 2015-05-11 {
    description 'Delete the default value of leaf node rg-host-name in \configu'
              + 'ration\iccp\rg.'+"\n"
              + 'Add reset null of leaf node rg-host-name in \configuration\icc'
              + 'p\rg.'
                ;
  }
  revision 2015-01-23 {
    description 'Add leaf node hostname in  \state\iccp\iccp-state.'
                ;
  }
  revision 2014-05-06 {
    description 'Add enum value apply-mac ins enum app-type.'+"\n"
              + 'Add container iccp-apply-mac in list /configuration/iccp/rg.'+"\n"
              + 'Add leaf node apply-mac in container iccp-apply-mac.'+"\n"
              + 'Modify the description of leaf node app-type in /state/iccp/ic'
              + 'cp-state.'
                ;
  }
  revision 2013-12-12 {
    description '1.Modefy the type of apply-mc-port-group,apply-mc-pw-group,app'
              + 'ly-arp and apply-mlacp to empty and add value .'+"\n"
              + '2.Modefy the mandatory of leaf node apply-mc-port-group,apply-'
              + 'mc-pw-group,apply-arp ,apply-mlacp and rg-peer-addr from false'
              + ' to true.'+"\n"
              + '3.Add the Presence of apply-mc-port-group,apply-mc-pw-group,ap'
              + 'ply-arp ,apply-mlacp and rg-peer-addr containers.'
                ;
  }
  revision 2013-08-30 {
    description 'Modefy the node type of apply-mc-port-group,apply-mc-pw-group,'
              + 'apply-arp and apply-mlacp from choice to container'
                ;
  }
  revision 2013-07-18 {
    description 'Initial version.'
                ;
  }
  feature label_vxlan {
    description 'Feature label of ICCP apply vxlan.'
                ;
  }
  feature label_igmpsnoop {
    description 'Feature label of ICCP apply igmpsnoop.'
                ;
  }
  feature label_dhcpsnoop {
    description 'Feature label of ICCP apply dhcpsnoop.'
                ;
  }
  feature label_stp {
    description 'Feature label of ICCP apply stp.'
                ;
  }
  typedef rg-state {
    type enumeration {
      enum nonconnect {
        value 0 ;
        description 'The state of redundency group is nonconnect.'
                    ;
      }
      enum connecting-send {
        value 1 ;
        description 'The state of redundency group is connecting send.'
                    ;
      }
      enum connecting-rcv {
        value 2 ;
        description 'The state of redundency group is connecting receive.'
                    ;
      }
      enum connected {
        value 3 ;
        description 'The state of redundency group is connected.'
                    ;
      }
    }
    description 'The state of redundency group.'
                ;
  }
  typedef app-state {
    type enumeration {
      enum app-nonconnect {
        value 4 ;
        description 'Application state of redundency group is nonconnect.'
                    ;
      }
      enum app-connect-send {
        value 5 ;
        description 'Application state of redundency group is connect send.'
                    ;
      }
      enum app-connect-rcv {
        value 6 ;
        description 'Application state of redundency group is connect receive.'
                    ;
      }
      enum app-connected {
        value 7 ;
        description 'Application state of redundency group is connected.'
                    ;
      }
      enum app-connecting {
        value 8 ;
        description 'Application state of redundency group is connecting.'
                    ;
      }
    }
    description 'Application state of redundency group.'
                ;
  }
  typedef app-type {
    type enumeration {
      enum no-app {
        value 0 ;
        description 'Application type of redundency group is no app.'
                    ;
      }
      enum app-mlacp {
        value 1 ;
        description 'Application type of redundency group is app mlacp.'
                    ;
      }
      enum app-mc-portgroup {
        value 3 ;
        description 'Application type of redundency group is app mc-portgroup.'
                    ;
      }
      enum app-mc-pwgroup {
        value 4 ;
        description 'Application type of redundency group is app mc-pwgroup.'
                    ;
      }
      enum app-arp {
        value 5 ;
        description 'Application type of redundency group is app arp.'
                    ;
      }
      enum app-mac {
        value 6 ;
        description 'Application type of redundency group is app mac.'
                    ;
      }
      enum app-vxlan {
        value 7 ;
        description 'Application type of redundency group is app vxlan.'
                    ;
      }
      enum app-igmpsnoop {
        value 8 ;
        description 'Application type of redundency group is app igmpsnoop.'
                    ;
      }
      enum app-nd {
        value 9 ;
        description 'Application type of redundency group is app nd.'
                    ;
      }
      enum app-dhcpsnoop {
        value 10 ;
        description 'Application type of redundency group is app dhcpsnoop.'
                    ;
      }
      enum app-stp {
        value 11 ;
        description 'Application type of redundency group is app stp.'
                    ;
      }
      enum app-vlan {
        value 12 ;
        description 'Application type of redundency group is app vlan.'
                    ;
      }
    }
    description 'Application type of redundency group.'
                ;
  }
  typedef active-mode {
    type enumeration {
      enum PRIVATE {
        value 1 ;
        description 'The active mode of redundency group is private.'
                    ;
      }
      enum STANDARD {
        value 2 ;
        description 'The active mode of redundency group is standard.'
                    ;
      }
    }
    description 'The active mode of redundency group.'
                ;
  }
  container configuration {
    description 'Configuration model info.'
                ;
    container iccp {
      description 'Configure ICCP parameters.'
                  ;
      list rg {
        description 'Config redundancy group.'
                    ;
        key rg-id ;
        leaf rg-id {
          description 'Redundancy group index.'
                      ;
          type uint32 {
            range 1..4294967295 {
              description 'Redundancy group index.'
                          ;
            }
          }
        }
        leaf rg-host-name {
          description 'Redundancy group host name.'
                      ;
          type string {
            length 1..80 {
              description 'Redundancy group host name.'
                          ;
            }
          }
        }
        container apply-mc-port-group {
          description 'The apply app of the redundency group is apply mc-port g'
                    + 'roup.'
                      ;
          presence apply-mc-port-group ;
          leaf apply-mc-port-group {
            description 'The apply app of the redundency group is apply mc-port'
                      + ' group.'
                        ;
            type empty ;
            mandatory true ;
          }
        }
        container peer-addr {
          description 'Config apply application of peer address.'
                      ;
          presence peer-addr ;
          leaf rg-peer-addr {
            description 'Redundancy group peer ip address.'
                        ;
            status obsolete ;
            type ncd:ipv4-address ;
            mandatory true ;
          }
          choice rg-peer {
            description 'Config rg peer ip address.'
                        ;
            mandatory true ;
            case rg-peer-v4-addr {
              description 'Config IPv4 address.'
                          ;
              leaf rg-peer-v4-addr {
                description 'Config IPv4 address.'
                            ;
                type ncd:ipv4-address ;
              }
            }
            case rg-peer-v6-addr {
              description 'Config IPv6 address.'
                          ;
              leaf rg-peer-v6-addr {
                description 'Config IPv6 address.'
                            ;
                type ncd:ipv6-address ;
              }
            }
          }
        }
        container apply-mc-pw-group {
          description 'The apply app of the redundency group is apply mc-pw gro'
                    + 'up.'
                      ;
          presence apply-mc-pw-group ;
          leaf apply-mc-pw-group {
            description 'The apply app of the redundency group is apply mc-pw g'
                      + 'roup.'
                        ;
            type empty ;
            mandatory true ;
          }
        }
        container apply-arp {
          description 'The apply app of the redundency group is apply arp.'
                      ;
          presence apply-arp ;
          leaf apply-arp {
            description 'The apply app of the redundency group is apply arp.'
                        ;
            type empty ;
            mandatory true ;
          }
        }
        container apply-mlacp {
          description 'The apply app of the redundency group is apply m-lacp.'
                      ;
          presence apply-mlacp ;
          leaf apply-mlacp {
            description 'The apply app of the redundency group is apply m-lacp.'
                        ;
            type empty ;
            mandatory true ;
          }
        }
        container iccp-apply-mac {
          description 'The apply app of the redundency group is apply mac.'
                      ;
          leaf apply-mac {
            description 'The apply app of the redundency group is apply mac.'
                        ;
            type empty ;
          }
        }
        container iccp-apply-vxlan {
          if-feature label_vxlan ;
          description 'The apply app of the redundency group is apply vxlan.'
                      ;
          presence apply-vxlan ;
          leaf apply-vxlan {
            if-feature label_vxlan ;
            description 'The apply app of the redundency group is apply vxlan.'
                        ;
            type empty ;
            mandatory true ;
          }
        }
        container iccp-apply-igmpsnoop {
          if-feature label_igmpsnoop ;
          description 'The apply app of the redundency group is apply IGMPSNOOP.'
                      ;
          presence apply-igmpsnoop ;
          leaf apply-igmpsnoop {
            if-feature label_igmpsnoop ;
            description 'The apply app of the redundency group is apply IGMPSNO'
                      + 'OP.'
                        ;
            type empty ;
            mandatory true ;
          }
        }
        container iccp-apply-nd {
          description 'The apply app of the redundency group is apply ND.'
                      ;
          presence apply-nd ;
          leaf apply-nd {
            description 'The apply app of the redundency group is apply nd.'
                        ;
            type empty ;
            mandatory true ;
          }
        }
        container iccp-apply-dhcpsnoop {
          if-feature label_dhcpsnoop ;
          description 'The apply app of the redundency group is apply DHCPSNOOP.'
                      ;
          presence apply-dhcpsnoop ;
          leaf apply-dhcpsnoop {
            if-feature label_dhcpsnoop ;
            description 'The apply app of the redundency group is apply DHCPSNO'
                      + 'OP.'
                        ;
            type empty ;
            mandatory true ;
          }
        }
        container iccp-apply-stp {
          if-feature label_stp ;
          description 'The apply app of the redundency group is apply STP.'
                      ;
          presence apply-stp ;
          leaf apply-stp {
            if-feature label_stp ;
            description 'The apply app of the redundency group is apply STP.'
                        ;
            type empty ;
            mandatory true ;
          }
        }
        container iccp-apply-vlan {
          if-feature label_stp ;
          description 'The apply app of the redundency group is apply VLAN.'
                      ;
          presence apply-vlan ;
          leaf apply-vlan {
            if-feature label_stp ;
            description 'The apply app of the redundency group is apply VLAN.'
                        ;
            type empty ;
          }
        }
      }
      container rg-peer-mode {
        description 'Configure RG peer mode.'
                    ;
        presence rg-peer-mode ;
        leaf standard-mode-acl {
          description 'IP ACL for RG standard mode'
                      ;
          type string {
            length 1..31 ;
          }
          mandatory true ;
        }
      }
    }
  }
  container state {
    description 'State model info.'
                ;
    config false ;
    container iccp {
      description 'ICCP state information.'
                  ;
      list iccp-state {
        description 'The state information of ICCP state.'
                    ;
        key 'rg-id peer-addr app-type'
            ;
        leaf rg-id {
          description 'Redundancy group index.'
                      ;
          type uint32 {
            range 1..4294967295 {
              description 'Redundancy group index.'
                          ;
            }
          }
        }
        leaf rg-state {
          description 'ICCP state:'+"\n"
                    + 'NONCONNECT (0), '+"\n"
                    + 'CONNECTING_SENT (1),'+"\n"
                    + 'CONNECTING_RCV (2),'+"\n"
                    + 'CONNECTED (3)'
                      ;
          type rg-state ;
        }
        leaf peer-addr {
          description 'Peer ip address.'
                      ;
          type ncd:ipv4-address ;
        }
        leaf total-iccp-sessions {
          description 'Total iccp sessions.'
                      ;
          type uint32 ;
        }
        leaf app-type {
          description 'App type:'+"\n"
                    + '0- no APP'+"\n"
                    + '1- APP_mLACP'+"\n"
                    + '3- APP_MCPORTGROUP'+"\n"
                    + '4- APP_MCPWGROUP'+"\n"
                    + '5- APP_ARP'+"\n"
                    + '6- APP_MAC'+"\n"
                    + '7- APP_VXLAN'+"\n"
                    + '8- APP_IGMPSNOOP'+"\n"
                    + '9- APP_ND'+"\n"
                    + '10- APP_DHCPSNOOP'+"\n"
                    + '11- APP_STP'+"\n"
                    + '12- APP_VLAN'
                      ;
          type app-type ;
        }
        leaf app-state {
          description 'App state:'+"\n"
                    + 'APP_NONCONNECT(4), '+"\n"
                    + 'APP_CONNECTING_SENT (5), '+"\n"
                    + 'APP_CONNECTING_RCV (6),'+"\n"
                    + 'APP_CONNECTED (7)'
                      ;
          type app-state ;
        }
        leaf hostname {
          description 'Redundancy group host name.'
                      ;
          type string ;
        }
        leaf active-mode {
          description 'ICCP active mode:
PRIVATE (1), 
STANDARD (2)'
                      ;
          type active-mode ;
        }
        leaf msgs-sent {
          description 'Sent messages.'
                      ;
          type uint32 ;
        }
        leaf msgs-rcvd {
          description 'Received messages.'
                      ;
          type uint32 ;
        }
      }
      list iccp-v6peer-state {
        description 'The state information of ICCP IPv6 state.'
                    ;
        key 'rg-id v6-peer-addr app-type'
            ;
        leaf rg-id {
          description 'Redundancy group index.'
                      ;
          type uint32 {
            range 1..4294967295 {
              description 'Redundancy group index.'
                          ;
            }
          }
        }
        leaf rg-state {
          description 'ICCP state:'+"\n"
                    + 'NONCONNECT (0), '+"\n"
                    + 'CONNECTING_SENT (1),'+"\n"
                    + 'CONNECTING_RCV (2),'+"\n"
                    + 'CONNECTED (3)'
                      ;
          type rg-state ;
        }
        leaf v6-peer-addr {
          description 'Peer IPv6 address.'
                      ;
          type ncd:ipv6-address ;
        }
        leaf total-iccp-sessions {
          description 'Total iccp sessions.'
                      ;
          type uint32 ;
        }
        leaf app-type {
          description 'App type:'+"\n"
                    + '0- no APP'+"\n"
                    + '1- APP_mLACP'+"\n"
                    + '3- APP_MCPORTGROUP'+"\n"
                    + '4- APP_MCPWGROUP'+"\n"
                    + '5- APP_ARP'+"\n"
                    + '6- APP_MAC'+"\n"
                    + '7- APP_VXLAN'+"\n"
                    + '8- APP_IGMPSNOOP'+"\n"
                    + '9- APP_ND'+"\n"
                    + '10- APP_DHCPSNOOP'+"\n"
                    + '11- APP_STP'+"\n"
                    + '12- APP_VLAN'
                      ;
          type app-type ;
        }
        leaf app-state {
          description 'App state:'+"\n"
                    + 'APP_NONCONNECT(4), '+"\n"
                    + 'APP_CONNECTING_SENT (5), '+"\n"
                    + 'APP_CONNECTING_RCV (6),'+"\n"
                    + 'APP_CONNECTED (7)'
                      ;
          type app-state ;
        }
        leaf hostname {
          description 'Redundancy group host name.'
                      ;
          type string ;
        }
        leaf active-mode {
          description 'ICCP active mode:
PRIVATE (1), 
STANDARD (2)'
                      ;
          type active-mode ;
        }
        leaf msgs-sent {
          description 'Sent messages.'
                      ;
          type uint32 ;
        }
        leaf msgs-rcvd {
          description 'Received messages.'
                      ;
          type uint32 ;
        }
      }
    }
  }
}
