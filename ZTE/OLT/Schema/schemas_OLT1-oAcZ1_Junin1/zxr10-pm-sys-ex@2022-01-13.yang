module zxr10-pm-sys-ex {
  namespace 'http://www.zte.com.cn/zxr10/netconf/schema/rosng/pm-sys-ex'
            ;
  prefix pm-sys-ex ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  revision 2022-01-13 {
    description 'add zxr10-pm-sys-ex.'
                ;
  }
  feature switch ;
  container state {
    config false ;
    container sys {
      container racks {
        list rack {
          key 'shelf slot'
              ;
          leaf shelf {
            description 'Shelf number.'
                        ;
            type uint8 {
              range 0..255 {
                description 'shelf range.'
                            ;
              }
            }
          }
          leaf slot {
            description 'Slot number.'
                        ;
            type uint8 {
              range 0..255 {
                description 'slot range.'
                            ;
              }
            }
          }
          leaf character {
            description 'Active/Standby status.'
                        ;
            type string {
              length 1..28 ;
            }
          }
          leaf boardtype {
            description 'Network management functions id.'
                        ;
            type uint32 ;
          }
          leaf portnum {
            description 'Number of ports.'
                        ;
            type uint8 ;
          }
          leaf pcb {
            description 'PCB version.'
                        ;
            type ncd:string-with-blank {
              length 1..80 ;
            }
          }
          leaf fpga {
            description 'FPGA version.'
                        ;
            type ncd:string-all ;
          }
          leaf epld {
            description 'EPLD version.'
                        ;
            type ncd:string-all ;
          }
          leaf sn {
            description 'Serial number.'
                        ;
            type ncd:string-all ;
          }
          leaf manufacture {
            description 'The Manufacture Date of the card.'
                        ;
            type ncd:string-all ;
          }
          leaf boardname {
            description 'The card name.'
                        ;
            type ncd:string-all ;
          }
          leaf assemblysn {
            description 'Assembly serial number.'
                        ;
            type ncd:string-all ;
          }
          leaf harddisk {
            description 'Peripheral capacity.'
                        ;
            type uint32 ;
          }
          leaf installstate {
            description 'The install state of real board.'
                        ;
            type enumeration {
              enum down {
                value 0 ;
                description 'The board is down.'
                            ;
              }
              enum up {
                value 1 ;
                description 'The board is up.'
                            ;
              }
            }
          }
          leaf software-version {
            description 'Software version.'
                        ;
            type ncd:string-with-blank {
              length 1..80 ;
            }
          }
          leaf mc-version {
            description 'Mc version.'
                        ;
            type ncd:string-with-blank {
              length 1..80 ;
            }
          }
          leaf panel {
            if-feature switch ;
            description 'Panel number.'
                        ;
            type ncd:string-with-blank {
              length 1..8 ;
            }
          }
          leaf baud {
            description 'System baud.'
                        ;
            type uint32 ;
          }
          leaf type {
            if-feature switch ;
            description 'Board logic type.'
                        ;
            type enumeration {
              enum MPU {
                value 1 ;
                description 'The board is MPU.'
                            ;
              }
              enum PFU {
                value 3 ;
                description 'The board is PFU.'
                            ;
              }
              enum SFU {
                value 4 ;
                description 'The board is SFU.'
                            ;
              }
            }
          }
          list subslots {
            key subslot ;
            leaf subslot {
              description 'Subslot number.'
                          ;
              type uint8 {
                range '0..15 | 255'
                      {
                  description 'subslot range.'
                              ;
                }
              }
            }
            leaf character {
              description 'Active/Standby status.'
                          ;
              type string {
                length 1..28 ;
              }
            }
            leaf boardtype {
              description 'Network management functions id.'
                          ;
              type uint32 ;
            }
            leaf portnum {
              description 'Number of ports.'
                          ;
              type uint8 ;
            }
            leaf pcb {
              description 'PCB version.'
                          ;
              type ncd:string-with-blank {
                length 1..80 ;
              }
            }
            leaf fpga {
              description 'FPGA version.'
                          ;
              type ncd:string-all ;
            }
            leaf epld {
              description 'EPLD version.'
                          ;
              type ncd:string-all ;
            }
            leaf sn {
              description 'Serial number.'
                          ;
              type ncd:string-all ;
            }
            leaf manufacture {
              description 'The Manufacture Date of the card.'
                          ;
              type ncd:string-all ;
            }
            leaf boardname {
              description 'The card name.'
                          ;
              type ncd:string-all ;
            }
            leaf assemblysn {
              description 'Assembly serial number.'
                          ;
              type ncd:string-all ;
            }
            leaf harddisk {
              description 'Peripheral capacity.'
                          ;
              type uint32 ;
            }
            leaf installstate {
              description 'The install state of real board.'
                          ;
              type enumeration {
                enum down {
                  value 0 ;
                  description 'The board is down.'
                              ;
                }
                enum up {
                  value 1 ;
                  description 'The board is up.'
                              ;
                }
              }
            }
            leaf software-version {
              description 'Software version.'
                          ;
              type ncd:string-with-blank {
                length 1..80 ;
              }
            }
            leaf mc-version {
              description 'Mc version.'
                          ;
              type ncd:string-with-blank {
                length 1..80 ;
              }
            }
            leaf panel {
              if-feature switch ;
              description 'Panel number.'
                          ;
              type ncd:string-with-blank {
                length 1..8 ;
              }
            }
            leaf baud {
              description 'System baud.'
                          ;
              type uint32 ;
            }
          }
          ncd:select 'shelf slot'
                     ;
          ncd:select 'shelf panel'
                     ;
        }
      }
      container virtual-boards {
        list virtual-board {
          key 'shelf slot subslot'
              ;
          leaf shelf {
            description 'Shelf number.'
                        ;
            type uint8 {
              range 0..255 {
                description 'shelf range.'
                            ;
              }
            }
          }
          leaf slot {
            description 'Slot number.'
                        ;
            type uint8 {
              range 0..255 {
                description 'slot range.'
                            ;
              }
            }
          }
          leaf subslot {
            description 'Subslot number.'
                        ;
            type uint8 ;
          }
          leaf portnum {
            description 'Port number.'
                        ;
            type uint8 ;
          }
          leaf boardtype {
            description 'Virtual board type.'
                        ;
            type uint32 ;
          }
          leaf panel {
            if-feature switch ;
            description 'Panel number.'
                        ;
            type ncd:string-with-blank {
              length 1..8 ;
            }
          }
          ncd:select 'shelf slot'
                     ;
          ncd:select 'shelf panel'
                     ;
          ncd:select 'shelf slot subslot'
                     ;
          ncd:select 'shelf subslot panel'
                     ;
        }
      }
      container cards {
        list card {
          key 'shelf slot'
              ;
          leaf shelf {
            description 'Shelf number.'
                        ;
            type uint8 {
              range 0..255 {
                description 'shelf range.'
                            ;
              }
            }
          }
          leaf slot {
            description 'Slot number.'
                        ;
            type uint8 {
              range 0..255 {
                description 'slot range.'
                            ;
              }
            }
          }
          leaf cpu {
            description 'Cpu number.'
                        ;
            type uint8 ;
          }
          leaf run-time {
            description 'Run time.'
                        ;
            type ncd:string-all {
              length 1..40 ;
            }
          }
          leaf panel {
            if-feature switch ;
            description 'Panel number.'
                        ;
            type ncd:string-with-blank {
              length 1..8 ;
            }
          }
          list subslots {
            key subslot ;
            leaf subslot {
              description 'Subslot number.'
                          ;
              type uint8 ;
            }
            leaf cpu {
              description 'Cpu number.'
                          ;
              type uint8 ;
            }
            leaf run-time {
              description 'Run time.'
                          ;
              type ncd:string-all {
                length 1..40 ;
              }
            }
            leaf panel {
              if-feature switch ;
              description 'Panel number.'
                          ;
              type ncd:string-with-blank {
                length 1..8 ;
              }
            }
          }
          ncd:select 'shelf slot'
                     ;
          ncd:select 'shelf panel'
                     ;
        }
      }
    }
  }
}
