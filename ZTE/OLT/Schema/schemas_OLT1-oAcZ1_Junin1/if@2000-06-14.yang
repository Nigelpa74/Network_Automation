module if {
    namespace 'http://www.zte.com.cn/zxr10/netconf/schema/rosng/zx-if';
    prefix zx-if;
    import zxr10-netconf-defs {
        prefix ncd;
        revision-date 2017-08-15;
		}
    organization "IETF Interfaces MIB Working Group";
    contact "   Keith McCloghrie
                Cisco Systems, Inc.
                170 West Tasman Drive
                San Jose, CA  95134-1706
                US

                408-526-5260
                kzm@cisco.com";
    description "The MIB module to describe generic objects for network
                 interface sub-layers.  This MIB is an updated version of
                 MIB-II's ifTable, and incorporates the extensions defined in
                 RFC 1229.";
    revision 2000-06-14 {
        description "Clarifications agreed upon by the Interfaces MIB WG, and
                     published as RFC 2863.";
    }
    revision 1996-02-28 {
        description "Revisions made by the Interfaces MIB WG, and published in
                     RFC 2233.";
    }
    revision 1993-11-08 {
        description "Initial revision, published as part of RFC 1573.";
    }
    container interfaces {
        description "";
        leaf ifNumber {
            config false;
            description "The number of network interfaces (regardless of their
                         current state) present on this system.";
            type int32;
        }
        container ifTable {
            description "A list of interface entries.  The number of entries is
                         given by the value of ifNumber.";
            list ifEntry {
                description "An entry containing management information applicable to a
                             particular interface.";
                max-elements 1000;
                key "ifIndex";
                leaf ifIndex {
                    description "A unique value, greater than zero, for each interface.  It
                                 is recommended that values are assigned contiguously
                                 starting from 1.  The value for each interface sub-layer
                                 must remain constant at least from one re-initialization of
                                 the entity's network management system to the next re-
                                 initialization.";
                    type int32 {
                        range 1..2147483647;
                    }
                }
                leaf ifDescr {
                    config false;
                    description "A textual string containing information about the
                                 interface.  This string should include the name of the
                                 manufacturer, the product name and the version of the
                                 interface hardware/software.";
                    type string {
                        length 0..255;
                    }
                }
                leaf ifType {
                    config false;
                    description "The type of interface.  Additional values for ifType are
                                 assigned by the Internet Assigned Numbers Authority (IANA),
                                 through updating the syntax of the IANAifType textual
                                 convention.";
                    type int32;
                }
                leaf ifMtu {
                    config false;
                    description "The size of the largest packet which can be sent/received
                                 on the interface, specified in octets.  For interfaces that
                                 are used for transmitting network datagrams, this is the
                                 size of the largest network datagram that can be sent on the
                                 interface.";
                    type int32;
                }
                leaf ifSpeed {
                    config false;
                    description "An estimate of the interface's current bandwidth in bits
                                 per second.  For interfaces which do not vary in bandwidth
                                 or for those where no accurate estimation can be made, this
                                 object should contain the nominal bandwidth.  If the
                                 bandwidth of the interface is greater than the maximum value
                                 reportable by this object then this object should report its
                                 maximum value (4,294,967,295) and ifHighSpeed must be used
                                 to report the interace's speed.  For a sub-layer which has
                                 no concept of bandwidth, this object should be zero.";
                    type uint32;
                }
                leaf ifPhysAddress {
                    config false;
                    description "The interface's address at its protocol sub-layer.  For
                                 example, for an 802.x interface, this object normally
                                 contains a MAC address.  The interface's media-specific MIB
                                 must define the bit and byte ordering and the format of the
                                 value of this object.  For interfaces which do not have such
                                 an address (e.g., a serial line), this object should contain
                                 an octet string of zero length.";
                    type ncd:mac-address;
                }
                leaf ifAdminStatus {
                    description "The desired state of the interface.  The testing(3) state
                                 indicates that no operational packets can be passed.  When a
                                 managed system initializes, all interfaces start with
                                 ifAdminStatus in the down(2) state.  As a result of either
                                 explicit management action or per configuration information
                                 retained by the managed system, ifAdminStatus is then
                                 changed to either the up(1) or testing(3) states (or remains
                                 in the down(2) state).";
                    type enumeration {
                        enum up {
                            value 1;
                            description "";
                        }
                        enum down {
                            value 2;
                            description "";
                        }
                        enum testing {
                            value 3;
                            description "";
                        }
                    }
                }
                leaf ifOperStatus {
                    config false;
                    description "The current operational state of the interface.  The
                                 testing(3) state indicates that no operational packets can
                                 be passed.  If ifAdminStatus is down(2) then ifOperStatus
                                 should be down(2).  If ifAdminStatus is changed to up(1)
                                 then ifOperStatus should change to up(1) if the interface is
                                 ready to transmit and receive network traffic; it should
                                 change to dormant(5) if the interface is waiting for
                                 external actions (such as a serial line waiting for an
                                 incoming connection); it should remain in the down(2) state
                                 if and only if there is a fault that prevents it from going
                                 to the up(1) state; it should remain in the notPresent(6)
                                 state if the interface has missing (typically, hardware)
                                 components.";
                    type enumeration {
                        enum up {
                            value 1;
                            description "";
                        }
                        enum down {
                            value 2;
                            description "";
                        }
                        enum testing {
                            value 3;
                            description "";
                        }
                        enum unknown {
                            value 4;
                            description "";
                        }
                        enum dormant {
                            value 5;
                            description "";
                        }
                        enum notPresent {
                            value 6;
                            description "";
                        }
                        enum lowerLayerDown {
                            value 7;
                            description "";
                        }
                    }
                }
                leaf ifLastChange {
                    config false;
                    description "The value of sysUpTime at the time the interface entered
                                 its current operational state.  If the current state was
                                 entered prior to the last re-initialization of the local
                                 network management subsystem, then this object contains a
                                 zero value.";
                    type uint32;
                }
                leaf ifInOctets {
                    config false;
                    description "The total number of octets received on the interface,
                                 including framing characters.
                                 
                                 Discontinuities in the value of this counter can occur at
                                 re-initialization of the management system, and at other
                                 times as indicated by the value of
                                 ifCounterDiscontinuityTime.";
                    type uint32;
                }
                leaf ifInUcastPkts {
                    config false;
                    description "The number of packets, delivered by this sub-layer to a
                                 higher (sub-)layer, which were not addressed to a multicast
                                 or broadcast address at this sub-layer.
                                 
                                 Discontinuities in the value of this counter can occur at
                                 re-initialization of the management system, and at other
                                 times as indicated by the value of
                                 ifCounterDiscontinuityTime.";
                    type uint32;
                }
                leaf ifInNUcastPkts {
                    config false;
                    description "The number of packets, delivered by this sub-layer to a
                                 higher (sub-)layer, which were addressed to a multicast or
                                 broadcast address at this sub-layer.
                                 
                                 Discontinuities in the value of this counter can occur at
                                 re-initialization of the management system, and at other
                                 times as indicated by the value of
                                 ifCounterDiscontinuityTime.
                                 
                                 This object is deprecated in favour of ifInMulticastPkts and
                                 ifInBroadcastPkts.";
                    type uint32;
                }
                leaf ifInDiscards {
                    config false;
                    description "The number of inbound packets which were chosen to be
                                 discarded even though no errors had been detected to prevent
                                 their being deliverable to a higher-layer protocol.  One
                                 possible reason for discarding such a packet could be to
                                 free up buffer space.
                                 
                                 Discontinuities in the value of this counter can occur at
                                 re-initialization of the management system, and at other
                                 times as indicated by the value of
                                 ifCounterDiscontinuityTime.";
                    type uint32;
                }
                leaf ifInErrors {
                    config false;
                    description "For packet-oriented interfaces, the number of inbound
                                 packets that contained errors preventing them from being
                                 deliverable to a higher-layer protocol.  For character-
                                 oriented or fixed-length interfaces, the number of inbound
                                 transmission units that contained errors preventing them
                                 from being deliverable to a higher-layer protocol.
                                 
                                 Discontinuities in the value of this counter can occur at
                                 re-initialization of the management system, and at other
                                 times as indicated by the value of
                                 ifCounterDiscontinuityTime.";
                    type uint32;
                }
                leaf ifInUnknownProtos {
                    config false;
                    description "For packet-oriented interfaces, the number of packets
                                 received via the interface which were discarded because of
                                 an unknown or unsupported protocol.  For character-oriented
                                 or fixed-length interfaces that support protocol
                                 multiplexing the number of transmission units received via
                                 the interface which were discarded because of an unknown or
                                 unsupported protocol.  For any interface that does not
                                 support protocol multiplexing, this counter will always be
                                 0.
                                 
                                 Discontinuities in the value of this counter can occur at
                                 re-initialization of the management system, and at other
                                 times as indicated by the value of
                                 ifCounterDiscontinuityTime.";
                    type uint32;
                }
                leaf ifOutOctets {
                    config false;
                    description "The total number of octets transmitted out of the
                                 interface, including framing characters.
                                 
                                 Discontinuities in the value of this counter can occur at
                                 re-initialization of the management system, and at other
                                 times as indicated by the value of
                                 ifCounterDiscontinuityTime.";
                    type uint32;
                }
                leaf ifOutUcastPkts {
                    config false;
                    description "The total number of packets that higher-level protocols
                                 requested be transmitted, and which were not addressed to a
                                 multicast or broadcast address at this sub-layer, including
                                 those that were discarded or not sent.
                                 
                                 Discontinuities in the value of this counter can occur at
                                 re-initialization of the management system, and at other
                                 times as indicated by the value of
                                 ifCounterDiscontinuityTime.";
                    type uint32;
                }
                leaf ifOutNUcastPkts {
                    config false;
                    description "The total number of packets that higher-level protocols
                                 requested be transmitted, and which were addressed to a
                                 multicast or broadcast address at this sub-layer, including
                                 those that were discarded or not sent.
                                 
                                 Discontinuities in the value of this counter can occur at
                                 re-initialization of the management system, and at other
                                 times as indicated by the value of
                                 ifCounterDiscontinuityTime.
                                 
                                 This object is deprecated in favour of ifOutMulticastPkts
                                 and ifOutBroadcastPkts.";
                    type uint32;
                }
                leaf ifOutDiscards {
                    config false;
                    description "The number of outbound packets which were chosen to be
                                 discarded even though no errors had been detected to prevent
                                 their being transmitted.  One possible reason for discarding
                                 such a packet could be to free up buffer space.
                                 
                                 Discontinuities in the value of this counter can occur at
                                 re-initialization of the management system, and at other
                                 times as indicated by the value of
                                 ifCounterDiscontinuityTime.";
                    type uint32;
                }
                leaf ifOutErrors {
                    config false;
                    description "For packet-oriented interfaces, the number of outbound
                                 packets that could not be transmitted because of errors.
                                 For character-oriented or fixed-length interfaces, the
                                 number of outbound transmission units that could not be
                                 transmitted because of errors.
                                 
                                 Discontinuities in the value of this counter can occur at
                                 re-initialization of the management system, and at other
                                 times as indicated by the value of
                                 ifCounterDiscontinuityTime.";
                    type uint32;
                }
                leaf ifOutQLen {
                    config false;
                    description "The length of the output packet queue (in packets).";
                    type uint32;
                }
                leaf ifSpecific {
                    config false;
                    description "A reference to MIB definitions specific to the particular
                                 media being used to realize the interface.  It is
                                 recommended that this value point to an instance of a MIB
                                 object in the media-specific MIB, i.e., that this object
                                 have the semantics associated with the InstancePointer
                                 textual convention defined in RFC 2579.  In fact, it is
                                 recommended that the media-specific MIB specify what value
                                 ifSpecific should/can take for values of ifType.  If no MIB
                                 definitions specific to the particular media are available,
                                 the value should be set to the OBJECT IDENTIFIER { 0 0 }.";
                    type binary;
                }
            }
        }
    }
    container if {
        description "";
        container ifMIBObjects {
            description "";
            container ifXTable {
                description "A list of interface entries.  The number of entries is
                             given by the value of ifNumber.  This table contains
                             additional objects for the interface table.";
                list ifXEntry {
                    description "An entry containing additional management information
                                 applicable to a particular interface.";
                    max-elements 1000;
                    key "ifIndex";
                    leaf ifIndex {
                        description "A unique value, greater than zero, for each interface.  It
                                     is recommended that values are assigned contiguously
                                     starting from 1.  The value for each interface sub-layer
                                     must remain constant at least from one re-initialization of
                                     the entity's network management system to the next re-
                                     initialization.";
                        type int32 {
                            range 1..2147483647;
                        }
                    }
                    leaf ifName {
                        config false;
                        description "The textual name of the interface.  The value of this
                                     object should be the name of the interface as assigned by
                                     the local device and should be suitable for use in commands
                                     entered at the device's `console'.  This might be a text
                                     name, such as `le0' or a simple port number, such as `1',
                                     depending on the interface naming syntax of the device.  If
                                     several entries in the ifTable together represent a single
                                     interface as named by the device, then each will have the
                                     same value of ifName.  Note that for an agent which responds
                                     to SNMP queries concerning an interface on some other
                                     (proxied) device, then the value of ifName for such an
                                     interface is the proxied device's local name for it.
                                     
                                     If there is no local name, or this object is otherwise not
                                     applicable, then this object contains a zero-length string.";
                        type string {
                            length 0..255;
                        }
                    }
                    leaf ifInMulticastPkts {
                        config false;
                        description "The number of packets, delivered by this sub-layer to a
                                     higher (sub-)layer, which were addressed to a multicast
                                     address at this sub-layer.  For a MAC layer protocol, this
                                     includes both Group and Functional addresses.
                                     
                                     Discontinuities in the value of this counter can occur at
                                     re-initialization of the management system, and at other
                                     times as indicated by the value of
                                     ifCounterDiscontinuityTime.";
                        type uint32;
                    }
                    leaf ifInBroadcastPkts {
                        config false;
                        description "The number of packets, delivered by this sub-layer to a
                                     higher (sub-)layer, which were addressed to a broadcast
                                     address at this sub-layer.
                                     
                                     Discontinuities in the value of this counter can occur at
                                     re-initialization of the management system, and at other
                                     times as indicated by the value of
                                     ifCounterDiscontinuityTime.";
                        type uint32;
                    }
                    leaf ifOutMulticastPkts {
                        config false;
                        description "The total number of packets that higher-level protocols
                                     requested be transmitted, and which were addressed to a
                                     multicast address at this sub-layer, including those that
                                     were discarded or not sent.  For a MAC layer protocol, this
                                     includes both Group and Functional addresses.
                                     
                                     Discontinuities in the value of this counter can occur at
                                     re-initialization of the management system, and at other
                                     times as indicated by the value of
                                     ifCounterDiscontinuityTime.";
                        type uint32;
                    }
                    leaf ifOutBroadcastPkts {
                        config false;
                        description "The total number of packets that higher-level protocols
                                     requested be transmitted, and which were addressed to a
                                     broadcast address at this sub-layer, including those that
                                     were discarded or not sent.
                                     
                                     Discontinuities in the value of this counter can occur at
                                     re-initialization of the management system, and at other
                                     times as indicated by the value of
                                     ifCounterDiscontinuityTime.";
                        type uint32;
                    }
                    leaf ifHCInOctets {
                        config false;
                        description "The total number of octets received on the interface,
                                     including framing characters.  This object is a 64-bit
                                     version of ifInOctets.
                                     
                                     Discontinuities in the value of this counter can occur at
                                     re-initialization of the management system, and at other
                                     times as indicated by the value of
                                     ifCounterDiscontinuityTime.";
                        type uint64;
                    }
                    leaf ifHCInUcastPkts {
                        config false;
                        description "The number of packets, delivered by this sub-layer to a
                                     higher (sub-)layer, which were not addressed to a multicast
                                     or broadcast address at this sub-layer.  This object is a
                                     64-bit version of ifInUcastPkts.
                                     
                                     Discontinuities in the value of this counter can occur at
                                     re-initialization of the management system, and at other
                                     times as indicated by the value of
                                     ifCounterDiscontinuityTime.";
                        type uint64;
                    }
                    leaf ifHCInMulticastPkts {
                        config false;
                        description "The number of packets, delivered by this sub-layer to a
                                     higher (sub-)layer, which were addressed to a multicast
                                     address at this sub-layer.  For a MAC layer protocol, this
                                     includes both Group and Functional addresses.  This object
                                     is a 64-bit version of ifInMulticastPkts.
                                     
                                     Discontinuities in the value of this counter can occur at
                                     re-initialization of the management system, and at other
                                     times as indicated by the value of
                                     ifCounterDiscontinuityTime.";
                        type uint64;
                    }
                    leaf ifHCInBroadcastPkts {
                        config false;
                        description "The number of packets, delivered by this sub-layer to a
                                     higher (sub-)layer, which were addressed to a broadcast
                                     address at this sub-layer.  This object is a 64-bit version
                                     of ifInBroadcastPkts.
                                     
                                     Discontinuities in the value of this counter can occur at
                                     re-initialization of the management system, and at other
                                     times as indicated by the value of
                                     ifCounterDiscontinuityTime.";
                        type uint64;
                    }
                    leaf ifHCOutOctets {
                        config false;
                        description "The total number of octets transmitted out of the
                                     interface, including framing characters.  This object is a
                                     64-bit version of ifOutOctets.
                                     
                                     Discontinuities in the value of this counter can occur at
                                     re-initialization of the management system, and at other
                                     times as indicated by the value of
                                     ifCounterDiscontinuityTime.";
                        type uint64;
                    }
                    leaf ifHCOutUcastPkts {
                        config false;
                        description "The total number of packets that higher-level protocols
                                     requested be transmitted, and which were not addressed to a
                                     multicast or broadcast address at this sub-layer, including
                                     those that were discarded or not sent.  This object is a
                                     64-bit version of ifOutUcastPkts.
                                     
                                     Discontinuities in the value of this counter can occur at
                                     re-initialization of the management system, and at other
                                     times as indicated by the value of
                                     ifCounterDiscontinuityTime.";
                        type uint64;
                    }
                    leaf ifHCOutMulticastPkts {
                        config false;
                        description "The total number of packets that higher-level protocols
                                     requested be transmitted, and which were addressed to a
                                     multicast address at this sub-layer, including those that
                                     were discarded or not sent.  For a MAC layer protocol, this
                                     includes both Group and Functional addresses.  This object
                                     is a 64-bit version of ifOutMulticastPkts.
                                     
                                     Discontinuities in the value of this counter can occur at
                                     re-initialization of the management system, and at other
                                     times as indicated by the value of
                                     ifCounterDiscontinuityTime.";
                        type uint64;
                    }
                    leaf ifHCOutBroadcastPkts {
                        config false;
                        description "The total number of packets that higher-level protocols
                                     requested be transmitted, and which were addressed to a
                                     broadcast address at this sub-layer, including those that
                                     were discarded or not sent.  This object is a 64-bit version
                                     of ifOutBroadcastPkts.
                                     
                                     Discontinuities in the value of this counter can occur at
                                     re-initialization of the management system, and at other
                                     times as indicated by the value of
                                     ifCounterDiscontinuityTime.";
                        type uint64;
                    }
                    leaf ifLinkUpDownTrapEnable {
                        description "Indicates whether linkUp/linkDown traps should be generated
                                     for this interface.
                                     
                                     By default, this object should have the value enabled(1) for
                                     interfaces which do not operate on 'top' of any other
                                     interface (as defined in the ifStackTable), and disabled(2)
                                     otherwise.";
                        type enumeration {
                            enum enabled {
                                value 1;
                                description "";
                            }
                            enum disabled {
                                value 2;
                                description "";
                            }
                        }
                    }
                    leaf ifHighSpeed {
                        config false;
                        description "An estimate of the interface's current bandwidth in units
                                     of 1,000,000 bits per second.  If this object reports a
                                     value of `n' then the speed of the interface is somewhere in
                                     the range of `n-500,000' to `n+499,999'.  For interfaces
                                     which do not vary in bandwidth or for those where no
                                     accurate estimation can be made, this object should contain
                                     the nominal bandwidth.  For a sub-layer which has no concept
                                     of bandwidth, this object should be zero.";
                        type uint32;
                    }
                    leaf ifPromiscuousMode {
                        description "This object has a value of false(2) if this interface only
                                     accepts packets/frames that are addressed to this station.
                                     This object has a value of true(1) when the station accepts
                                     all packets/frames transmitted on the media.  The value
                                     true(1) is only legal on certain types of media.  If legal,
                                     setting this object to a value of true(1) may require the
                                     interface to be reset before becoming effective.
                                     
                                     The value of ifPromiscuousMode does not affect the reception
                                     of broadcast and multicast packets/frames by the interface.";
                        type int32;
                    }
                    leaf ifConnectorPresent {
                        config false;
                        description "This object has the value 'true(1)' if the interface
                                     sublayer has a physical connector and the value 'false(2)'
                                     otherwise.";
                        type int32;
                    }
                    leaf ifAlias {
                        description "This object is an 'alias' name for the interface as
                                     specified by a network manager, and provides a non-volatile
                                     'handle' for the interface.
                                     
                                     On the first instantiation of an interface, the value of
                                     ifAlias associated with that interface is the zero-length
                                     string.  As and when a value is written into an instance of
                                     ifAlias through a network management set operation, then the
                                     agent must retain the supplied value in the ifAlias instance
                                     associated with the same interface for as long as that
                                     interface remains instantiated, including across all re-
                                     initializations/reboots of the network management system,
                                     including those which result in a change of the interface's
                                     ifIndex value.
                                     
                                     An example of the value which a network manager might store
                                     in this object for a WAN interface is the (Telco's) circuit
                                     number/identifier of the interface.
                                     
                                     Some agents may support write-access only for interfaces
                                     having particular values of ifType.  An agent which supports
                                     write access to this object is required to keep the value in
                                     non-volatile storage, but it may limit the length of new
                                     values depending on how much storage is already occupied by
                                     the current values for other interfaces.";
                        type string {
                            length 0..64;
                        }
                    }
                    leaf ifCounterDiscontinuityTime {
                        config false;
                        description "The value of sysUpTime on the most recent occasion at which
                                     any one or more of this interface's counters suffered a
                                     discontinuity.  The relevant counters are the specific
                                     instances associated with this interface of any Counter32 or
                                     Counter64 object contained in the ifTable or ifXTable.  If
                                     no such discontinuities have occurred since the last re-
                                     initialization of the local management subsystem, then this
                                     object contains a zero value.";
                        type uint32;
                    }
                }
            }
        }
    }
}
