module zxr10-lsp-man {
  namespace 'http://www.zte.com.cn/zxr10/netconf/schema/rosng/lsp-man'
            ;
  prefix lspm ;
  yang-version 1 ;
  import zxr10-netconf-defs {
    prefix ncd ;
    revision-date 2013-11-22 ;
  }
  organization 'ZTE Corporation.'
               ;
  contact 'ZTE Corporation  '+"\n"
        + '   Nanjing Institute of ZTE Corporation '+"\n"
        + '   No.68 Zijinghua Rd. Yuhuatai District, Nanjing, China '+"\n"
        + '   Tel: +86-25-52870000'
          ;
  description 'The netconf model to describe LSP management.'
              ;
  revision 2022-06-15 {
    description '1.Adding leaf /configuration/lspm/segment-routing/srv6-te-frr/'
              + 'downgrade'
                ;
  }
  revision 2021-12-17 {
    description '1.Adding container /configuration/lspm/segment-routing/srv6-sr'
              + 'h-reduce;'+"\n"
              + '2.Adding container /configuration/lspm/segment-routing/srv6-sr'
              + 'h-local-end.x-reduce.'
                ;
  }
  revision 2021-06-24 {
    description 'Adding container /configuration/lspm/segment-routing/srv6-loca'
              + 'l-repair.'
                ;
  }
  revision 2021-05-13 {
    description '2.Adding container /configuration/lspm/segment-routing/srv6-tt'
              + 'l-mode.'
                ;
  }
  revision 2021-01-13 {
    description '2.Adding container /configuration/lspm/segment-routing/srv6-te'
              + '-frr.'
                ;
  }
  revision 2020-09-03 {
    description '2.Adding container /configuration/lspm/segment-routing/encapsu'
              + 'lation.'
                ;
  }
  revision 2020-06-12 {
    description 'Add one proto type ospfv3 to the enumeration of proto-type.'
                ;
  }
  revision 2020-04-18 {
    description '1.Adding container /state/sr-tilfa'+"\n"
              + '2.Adding container /state/adjacency-sid'+"\n"
              + '3.Adding leaves in /state/lspm/label-forwarding-table,/state/l'
              + 'spm/ipv4-fec-forwarding-table and /state/lspm/ipv6-forwarding-'
              + 'table for unicast lsp'
                ;
  }
  revision 2019-11-25 {
    description '1.Adding type attribute to distinguishe vpn is invalid;'+"\n"
              + '2.Adding container /configuration/lspm/segment-routing.'
                ;
  }
  revision 2019-08-06 {
    description 'Add leaf and case for IPv6 SR tunnel and SR path.'
                ;
  }
  revision 2018-05-10 {
    description 'Add contain named "lsp-select-sequence" in /configuration/lspm'
              + ';'+"\n"
              + 'Add typedef named te-select-sequence.'
                ;
  }
  revision 2017-09-25 {
    description 'Add contain named sr-te in /lspm:state.'+"\n"
              + 'Add typedef named te-lsp-role.'+"\n"
              + 'Add typedef named te-lsp-direction.'+"\n"
              + 'Add typedef named te-forward-status.'+"\n"
              + 'Add typedef named te-lsp-self-state.'+"\n"
              + 'Add feature named lspm-sr.'
                ;
  }
  revision 2017-02-16 {
    description 'Add BIER container.'
                ;
  }
  revision 2016-11-23 {
    description 'In order to support MVPN segment,do the following changes: '+"\n"
              + '1.Add leaf: "state/lspm:lspm/lspm:mldp/lspm:get-by-inlabel/lsp'
              + 'm:mldp-inlabel/lspm:nexthop-entries/lspm:nexthop-entry/lspm:p2'
              + 'mp-segment"'+"\n"
              + '2.Add leaf: "state/lspm:lspm/lspm:mldp/lspm:gen-lspid/lspm:gen'
              + '-lspid-fec/lspm:nexthop-entries/lspm:nexthop-entry/lspm:p2mp-s'
              + 'egment"'+"\n"
              + '3.Add leaf: "/state/lspm:lspm/lspm:mte/lspm:mte-lsp/lspm:nexth'
              + 'op-entries/lspm:nexthop-entry/lspm:p2mp-segment"'+"\n"
              + 'In order to facilitate the filtering of dynamic MTE LSP, do th'
              + 'e following changes:'+"\n"
              + '1.Add leaf: "/state/lspm:lspm/lspm:mte/lspm:mte-lsp/lspm:ingre'
              + 'ss-id"'+"\n"
              + '2.Add leaf: "/state/lspm:lspm/lspm:mte/lspm:mte-lsp/lspm:ingre'
              + 'ss-tunnel-id"'+"\n"
              + '3.Add select clauses for list "mte-lsp", the filter field is "'
              + 'ingress-id" and "ingress-tunnel-id"'
                ;
  }
  revision 2016-11-03 {
    description '1.Add leaf: "state/lspm/ipv4-fec-forwarding-table/ipv4-fec/nex'
              + 'thop-entries/nexthop-entry/bytes-switched-num"'+"\n"
              + '2.Add leaf: "state/lspm/ipv4-fec-forwarding-table/ipv4-fec/nex'
              + 'thop-entries/nexthop-entry/packets-switched-num"'
                ;
  }
  revision 2016-09-13 {
    description 'Modify leaf node "/state/lspm/mldp/gen-lspid/gen-lspid-fec/lsp'
              + '-id" value range from [1-4294967295] to [0-4294967295];'+"\n"
              + 'Modify leaf node "/state/lspm/mldp/pub-recursive-gen-lspid/pub'
              + '-recursive-gen-lspid-fec/inner-lsp-id" value range from [1-429'
              + '4967295] to [0-4294967295];'+"\n"
              + 'Modify leaf node "/state/lspm/mldp/vpn-recursive-gen-lspid/vpn'
              + '-recursive-gen-lspid-fec/inner-lsp-id" value range from [1-429'
              + '4967295] to [0-4294967295].'
                ;
  }
  revision 2016-05-16 {
    description 'Modify leaf node "/state/lspm/mldp/gen-lspid/gen-lspid-fec/lsp'
              + '-id" value range from [1-4000] to [1-4294967295];'+"\n"
              + 'Modify leaf node "/state/lspm/mldp/pub-recursive-gen-lspid/pub'
              + '-recursive-gen-lspid-fec/inner-lsp-id" value range from [1-400'
              + '0] to [1-4294967295];'+"\n"
              + 'Modify leaf node "/state/lspm/mldp/vpn-recursive-gen-lspid/vpn'
              + '-recursive-gen-lspid-fec/inner-lsp-id" value range from [1-400'
              + '0] to [1-4294967295].'
                ;
  }
  revision 2015-04-03 {
    description "Modification in revision 2015-02-12 is incompatible with befor"
              + "e,now revise it.
\n1.Modify list named '/state/lspm/mte/mte-fe"
              + "c' to '/state/lspm/mte/mte-lsp';
\n2.Restore list '/state/lspm"
              + "/mte/mte-fec'and its member nodes ,which have modified at revi"
              + "sion 2015-02-12,and chang its status to obsolete;
\n3.In state"
              + " container,change all attribute values of mandatory to false i"
              + "f not."
                ;
  }
  revision 2015-02-12 {
    description "1. Modify leaf '/state/lspm/mte/mte-fec/ingress-tunnel-id' to "
              + "'/state/lspm/mte/mte-fec/ingress-tunnel-id/local-tunnel-id';
\n"
              + "2. Delete the following leaf nodes:'/state/lspm/mte/mte-fec/p2"
              + "mp-id','/state/lspm/mte/mte-fec/extend-tunnel-id','/state/lspm"
              + "/mte/mte-fec/ingress-id','/state/lspm/mte/mte-fec/egress-id','"
              + "/state/lspm/mte/mte-fec/prehop';
\n3. Change ncd:select option"
              + "s from ingress-tunnel-id,'ingress-tunnel-id p2mp-id','ingress-"
              + "tunnel-id p2mp-id ingress-id',in-label to 'local-tunnel-id','l"
              + "ocal-tunnel-id lsp-id',in-label;
\n4. Change key clause from '"
              + "ingress-tunnel-id p2mp-id extend-tunnel-id ingress-id egress-i"
              + "d lsp-id prehop' to 'local-tunnel-id lsp-id'."
                ;
  }
  revision 2014-07-03 {
    description '1. Adding vrf-name and type leaf nodes in all the list nodes w'
              + 'hitch path is "/state/lspm/mldp/xxx/xxx", such as "/state/lspm'
              + '/mldp/get-by-inlabel/mldp-inlabel", "/state/lspm/mldp/gen-lspi'
              + 'd/gen-lspid-fec", and so on.'+"\n"
              + '2. Adding the value range of out-interface and aggregate-nexth'
              + 'op-vrf leaf nodes in the following lists:'+"\n"
              + '"/state/lspm/mldp/rosen-mdt/rosen-mdt-fec/nexthop-entries/next'
              + 'hop-entry/", '+"\n"
              + '"/state/lspm/mldp/pub-recursive-vpnv4-source/pub-recursive-vpn'
              + 'v4-source-fec/nexthop-entries/nexthop-entry/", '+"\n"
              + '"/state/lspm/mldp/pub-recursive-vpnv6-source/pub-recursive-vpn'
              + 'v6-source-fec/nexthop-entries/nexthop-entry/", '+"\n"
              + '"/state/lspm/mldp/pub-recursive-vpnv4-bidir/pub-recursive-vpnv'
              + '4-bidir-fec/nexthop-entries/nexthop-entry/", '+"\n"
              + '"/state/lspm/mldp/pub-recursive-vpnv6-bidir/pub-recursive-vpnv'
              + '6-bidir-fec/nexthop-entries/nexthop-entry/", '+"\n"
              + '"/state/lspm/mldp/pub-recursive-rosen-mdt/pub-recursive-rosen-'
              + 'mdt-fec/nexthop-entries/nexthop-entry/", '+"\n"
              + '"/state/lspm/mldp/vpn-recursive-vpnv4-source/pub-recursive-vpn'
              + 'v4-source-fec/nexthop-entries/nexthop-entry/", '+"\n"
              + '"/state/lspm/mldp/vpn-recursive-vpnv6-source/vpn-recursive-vpn'
              + 'v6-source-fec/nexthop-entries/nexthop-entry/", '+"\n"
              + '"/state/lspm/mldp/vpn-recursive-vpnv4-bidir/vpn-recursive-vpnv'
              + '4-bidir-fec/nexthop-entries/nexthop-entry/", '+"\n"
              + '"/state/lspm/mldp/vpn-recursive-vpnv6-bidir/vpn-recursive-vpnv'
              + '6-bidir-fec/nexthop-entries/nexthop-entry/", '+"\n"
              + '"/state/lspm/mldp/vpn-recursive-rosen-mdt/vpn-recursive-rosen-'
              + 'mdt-fec/nexthop-entries/nexthop-entry/".'
                ;
  }
  revision 2014-05-14 {
    description 'Modify the length of derived type ifname in slsp-outseg-entrie'
              + 's container.'
                ;
  }
  revision 2014-05-04 {
    description 'Adding type attribute to distinguishe network is global or VPN'
              + '. And modify the description of aggregate-nexthop-vrf and out-'
              + 'interface in mldp and mte model.'
                ;
  }
  revision 2014-04-28 {
    description 'Modify leaf named "dest_input" to "dest-input" in list "ipv6-f'
              + 'ec".'
                ;
  }
  revision 2014-04-18 {
    description 'Add interface filter number in out-interface of slsp-outseg. T'
              + 'he maximun lenth of lsp-name change from 31 to 20.'
                ;
  }
  revision 2014-03-25 {
    description 'For mldp add new FEC type, mldp forwarding table creates some '
              + 'new sulists.'
                ;
  }
  revision 2014-01-15 {
    description 'Initial version.'
                ;
  }
  feature lspm-bier {
    description 'BIER support project.'
                ;
  }
  feature lspm-sr {
    description 'LSPM sr support project.'
                ;
  }
  typedef te-lsp-role {
    type enumeration {
      enum INVALID {
        value 0 ;
      }
      enum TRANSIT {
        value 2 ;
      }
      enum EGRESS {
        value 3 ;
      }
      enum INGRESS {
        value 1 ;
      }
    }
    description "TE LSP's role,0:INVALID,1:INGRESS,2:TRANSIT,3:EGRESS."
                ;
  }
  typedef te-lsp-direction {
    type enumeration {
      enum POSITIVE {
        value 0 ;
      }
      enum REVERSE {
        value 1 ;
      }
    }
    description "TE LSP's direction,POSITIVE:0,REVERSE:1."
                ;
  }
  typedef te-forward-status {
    type enumeration {
      enum OK {
        value 0 ;
      }
      enum SF {
        value 1 ;
      }
      enum SD {
        value 2 ;
      }
    }
    description 'Tunnel integrated forwarding state,OK:0,SF:1,SD:2.'
                ;
  }
  typedef te-lsp-self-state {
    type enumeration {
      enum OK {
        value 0 ;
      }
      enum SF {
        value 1 ;
      }
      enum SD {
        value 2 ;
      }
    }
    description "LSP's self state,OK:0,SF:1,SD:2."
                ;
  }
  typedef lsp-select-sequence {
    type enumeration {
      enum SELECT-SEQUENCE-FIRST {
        value 3 ;
      }
      enum SELECT-SEQUENCE-SECOND {
        value 2 ;
      }
      enum SELECT-SEQUENCE-THIRD {
        value 1 ;
      }
    }
    description 'LSP select sequence definition.'
                ;
  }
  typedef adjacency-sid-status {
    type enumeration {
      enum OK {
        value 0 ;
      }
      enum SF {
        value 1 ;
      }
      enum SD {
        value 2 ;
      }
    }
    description 'Adjacency SID status,OK:0,SF:1,SD:2.'
                ;
  }
  typedef adjacency-sid-protect-status {
    type enumeration {
      enum Ready {
        value 0 ;
      }
      enum Inuse {
        value 1 ;
      }
      enum Invalid {
        value 2 ;
      }
    }
    description 'Adjacency SID protect status,Ready:0,Inuse:1,Invalid:2.'
                ;
  }
  typedef lsp-nexthop-flag {
    type enumeration {
      enum direct {
        value 0 ;
        description 'Direct nexthop.'
                    ;
      }
      enum undirect {
        value 1 ;
        description 'Undirect nexthop.'
                    ;
      }
      enum remote-lfa {
        value 2 ;
        description 'Remote-lfa nexthop.'
                    ;
      }
      enum ti-lfa {
        value 3 ;
        description 'Ti-lfa nexthop'
                    ;
      }
    }
    description 'Nexthop Flag.'
                ;
  }
  typedef proto-type {
    type enumeration {
      enum ospf {
        value 16 ;
      }
      enum isis {
        value 18 ;
      }
      enum bgp {
        value 19 ;
      }
      enum ospfv3 {
        value 17 ;
      }
    }
    description 'Proto Type.'
                ;
  }
  container state {
    config false ;
    description 'State information.'
                ;
    container lspm {
      description 'State information of LSP management.'
                  ;
      container mldp {
        description 'lspm mpls mldp forwarding table.Mldp forwarding table cont'
                  + 'ains many sublists.A sublist in this table describe a cert'
                  + 'ain type of FEC which correspond with specific mpls mldp b'
                  + 'usiness.There are 10 fundamental FEC types and 2 recursive'
                  + ' FEC types.Fundamental FEC type is nested in recursive typ'
                  + 'e.According to different fundamental FEC types,each recurs'
                  + 'ive table is splited into 10 tables.'
                    ;
        container get-by-inlabel {
          description 'Sublist of mldp forwarding table.Geting forwarding info '
                    + 'by incoming label.'
                      ;
          list mldp-inlabel {
            description 'Key info and filter parameters info.'
                        ;
            key in-label ;
            leaf in-label {
              description 'The incoming label of this lsp.'
                          ;
              type uint32 {
                range 16..1048575 ;
              }
            }
            leaf type {
              description 'A value distinguishes network is global or VPN.'
                          ;
              type enumeration {
                enum global {
                  value 0 ;
                }
                enum vpn {
                  value 1 ;
                }
              }
            }
            leaf vrf-name {
              description 'VRF name.'
                          ;
              type string {
                length 0..35 ;
              }
            }
            container nexthop-entries {
              description 'Outgoing infomation of FEC.'
                          ;
              list nexthop-entry {
                description 'A entry of Outgoing infomation, include nexthop\ou'
                          + 'tgong interface\outgong label and so on.'
                            ;
                key num ;
                leaf num {
                  description '"num" is  a speical id, which is used to disting'
                            + 'uish different out segments who has the same inl'
                            + 'abel.'
                              ;
                  type uint32 ;
                }
                leaf type {
                  description 'A value distinguishes network is global or VPN.'
                              ;
                  type enumeration {
                    enum global {
                      value 0 ;
                    }
                    enum vpn {
                      value 1 ;
                    }
                    enum invalid-vpn {
                      value 2 ;
                    }
                  }
                }
                leaf aggregate-nexthop-vrf {
                  description 'VRF name.'
                              ;
                  type string {
                    length 1..35 ;
                  }
                }
                leaf nexthop {
                  description 'The IP address of the next hop of this lsp.'
                              ;
                  type ncd:ipv4-address ;
                }
                leaf out-interface {
                  description 'The name of the outcoming interface.'
                              ;
                  type string {
                    length 1..31 ;
                  }
                }
                leaf out-label {
                  description 'The outgoing label of this LSP.'
                              ;
                  type uint32 ;
                }
                leaf p2mp-segment {
                  description 'The p2mp segment of this LSP.'
                              ;
                  type uint32 ;
                }
              }
            }
            ncd:select in-label ;
          }
        }
        container gen-lspid {
          description 'Sublist of mldp forwarding table. It is used to get info'
                    + 'rmation of FEC whose type is gen-lspid.'
                      ;
          list gen-lspid-fec {
            description 'Key info and filter parameters info.'
                        ;
            key 'root lsp-id type vrf-name'
                ;
            leaf root {
              description 'IPv4 root address.'
                          ;
              type ncd:ipv4-address ;
            }
            leaf lsp-id {
              description Lsp-id. ;
              type uint32 {
                range 0..4294967295 ;
              }
            }
            leaf type {
              description 'A value distinguishes network is global or VPN.'
                          ;
              type enumeration {
                enum global {
                  value 0 ;
                }
                enum vpn {
                  value 1 ;
                }
              }
            }
            leaf vrf-name {
              description 'VRF name.'
                          ;
              type string {
                length 0..35 ;
              }
            }
            container nexthop-entries {
              description 'Outgoing infomation of FEC whose type is gen-lspid.'
                          ;
              list nexthop-entry {
                description 'A entry of Outgoing infomation, include nexthop\ou'
                          + 'tgong interface\outgong label and so on.'
                            ;
                key num ;
                leaf num {
                  description '"num" is  a speical id, which is used to disting'
                            + 'uish different out segments who has the same fec'
                            + ' type.'
                              ;
                  type uint32 ;
                }
                leaf type {
                  description 'A value distinguishes network is global or VPN.'
                              ;
                  type enumeration {
                    enum global {
                      value 0 ;
                    }
                    enum vpn {
                      value 1 ;
                    }
                    enum invalid-vpn {
                      value 2 ;
                    }
                  }
                }
                leaf aggregate-nexthop-vrf {
                  description 'VRF name.'
                              ;
                  type string {
                    length 1..35 ;
                  }
                }
                leaf nexthop {
                  description 'The IP address of the next hop of this lsp.'
                              ;
                  type ncd:ipv4-address ;
                }
                leaf out-interface {
                  description 'The name of the outcoming interface.'
                              ;
                  type string {
                    length 1..31 ;
                  }
                }
                leaf out-label {
                  description 'The outgoing label of this LSP.'
                              ;
                  type uint32 ;
                }
                leaf p2mp-segment {
                  description 'The p2mp segment of this LSP.'
                              ;
                  type uint32 ;
                }
              }
            }
            ncd:select root ;
            ncd:select 'root lsp-id'
                       ;
            ncd:select vrf-name ;
            ncd:select 'root lsp-id vrf-name'
                       ;
          }
        }
        container ipv4-source {
          description 'Sublist of mldp forwarding table. It is used to get info'
                    + 'rmation of FEC whose type is IPv4-source.'
                      ;
          list ipv4-source-fec {
            description 'Key info and filter parameters info.'
                        ;
            key 'root ipv4-source-address ipv4-group-address type vrf-name'
                ;
            leaf root {
              description 'IPv4 root address.'
                          ;
              type ncd:ipv4-address ;
            }
            leaf ipv4-source-address {
              description 'IPv4 multicast source address.'
                          ;
              type ncd:ipv4-address ;
            }
            leaf ipv4-group-address {
              description 'IPv4 multicast group address.'
                          ;
              type ncd:ipv4-address ;
            }
            leaf type {
              description 'A value distinguishes network is global or VPN.'
                          ;
              type enumeration {
                enum global {
                  value 0 ;
                }
                enum vpn {
                  value 1 ;
                }
              }
            }
            leaf vrf-name {
              description 'VRF name.'
                          ;
              type string {
                length 0..35 ;
              }
            }
            container nexthop-entries {
              description 'Outgoing infomation of FEC whose type is IPv4-source.'
                          ;
              list nexthop-entry {
                description 'A entry of Outgoing infomation, include nexthop\ou'
                          + 'tgong interface\outgong label and so on.'
                            ;
                key num ;
                leaf num {
                  description '"num" is  a speical id, which is used to disting'
                            + 'uish different out segments who has the same fec'
                            + ' type.'
                              ;
                  type uint32 ;
                }
                leaf type {
                  description 'A value distinguishes network is global or VPN.'
                              ;
                  type enumeration {
                    enum global {
                      value 0 ;
                    }
                    enum vpn {
                      value 1 ;
                    }
                  }
                }
                leaf aggregate-nexthop-vrf {
                  description 'VRF name.'
                              ;
                  type string {
                    length 1..35 ;
                  }
                }
                leaf nexthop {
                  description 'The IP address of the next hop of this lsp.'
                              ;
                  type ncd:ipv4-address ;
                }
                leaf out-interface {
                  description 'The name of the outcoming interface.'
                              ;
                  type string {
                    length 1..31 ;
                  }
                }
                leaf out-label {
                  description 'The outgoing label of this LSP.'
                              ;
                  type uint32 ;
                }
              }
            }
            ncd:select root ;
            ncd:select 'root ipv4-source-address ipv4-group-address'
                       ;
            ncd:select vrf-name ;
            ncd:select 'root ipv4-source-address ipv4-group-address vrf-name'
                       ;
          }
        }
        container ipv6-source {
          description 'Sublist of mldp forwarding table. It is used to get info'
                    + 'rmation of FEC whose type is IPv6-source.'
                      ;
          list ipv6-source-fec {
            description 'Key info and filter parameters info.'
                        ;
            key 'root ipv6-source-address ipv6-group-address type vrf-name'
                ;
            leaf root {
              description 'IPv4 root address.'
                          ;
              type ncd:ipv4-address ;
            }
            leaf ipv6-source-address {
              description 'IPv6 multicast source address.'
                          ;
              type ncd:ipv6-address ;
            }
            leaf ipv6-group-address {
              description 'IPv6 multicast group address.'
                          ;
              type ncd:ipv6-address ;
            }
            leaf type {
              description 'A value distinguishes network is global or VPN.'
                          ;
              type enumeration {
                enum global {
                  value 0 ;
                }
                enum vpn {
                  value 1 ;
                }
              }
            }
            leaf vrf-name {
              description 'VRF name.'
                          ;
              type string {
                length 0..35 ;
              }
            }
            container nexthop-entries {
              description 'Outgoing infomation of FEC whose type is IPv6-source.'
                          ;
              list nexthop-entry {
                description 'A entry of Outgoing infomation, include nexthop\ou'
                          + 'tgong interface\outgong label and so on.'
                            ;
                key num ;
                leaf num {
                  description '"num" is  a speical id, which is used to disting'
                            + 'uish different out segments who has the same fec'
                            + ' type.'
                              ;
                  type uint32 ;
                }
                leaf type {
                  description 'A value distinguishes network is global or VPN.'
                              ;
                  type enumeration {
                    enum global {
                      value 0 ;
                    }
                    enum vpn {
                      value 1 ;
                    }
                  }
                }
                leaf aggregate-nexthop-vrf {
                  description 'VRF name.'
                              ;
                  type string {
                    length 1..35 ;
                  }
                }
                leaf nexthop {
                  description 'The IP address of the next hop of this lsp.'
                              ;
                  type ncd:ipv4-address ;
                }
                leaf out-interface {
                  description 'The name of the outcoming interface.'
                              ;
                  type string {
                    length 1..31 ;
                  }
                }
                leaf out-label {
                  description 'The outgoing label of this LSP.'
                              ;
                  type uint32 ;
                }
              }
            }
            ncd:select root ;
            ncd:select 'root ipv6-source-address ipv6-group-address'
                       ;
            ncd:select vrf-name ;
            ncd:select 'root ipv6-source-address ipv6-group-address vrf-name'
                       ;
          }
        }
        container ipv4-bidir {
          description 'Sublist of mldp forwarding table. It is used to get info'
                    + 'rmation of FEC whose type is IPv4-bidir.'
                      ;
          list ipv4-bidir-fec {
            description 'Key info and filter parameters info.'
                        ;
            key 'root ipv4-rp-address ipv4-group-address mask-length type vrf-n'
              + 'ame'
                ;
            leaf root {
              description 'IPv4 root address.'
                          ;
              type ncd:ipv4-address ;
            }
            leaf ipv4-rp-address {
              description 'IPv4 RP address.'
                          ;
              type ncd:ipv4-address ;
            }
            leaf ipv4-group-address {
              description 'IPv4 multicast group address.'
                          ;
              type ncd:ipv4-address ;
            }
            leaf mask-length {
              description 'Mask length,range from 0 to 128.'
                          ;
              type uint32 {
                range 0..128 ;
              }
            }
            leaf type {
              description 'A value distinguishes network is global or VPN.'
                          ;
              type enumeration {
                enum global {
                  value 0 ;
                }
                enum vpn {
                  value 1 ;
                }
              }
            }
            leaf vrf-name {
              description 'VRF name.'
                          ;
              type string {
                length 0..35 ;
              }
            }
            container nexthop-entries {
              description 'Outgoing infomation of FEC whose type is IPv4-bidir.'
                          ;
              list nexthop-entry {
                description 'A entry of Outgoing infomation, include nexthop\ou'
                          + 'tgong interface\outgong label and so on.'
                            ;
                key num ;
                leaf num {
                  description '"num" is  a speical id, which is used to disting'
                            + 'uish different out segments who has the same fec'
                            + ' type.'
                              ;
                  type uint32 ;
                }
                leaf type {
                  description 'A value distinguishes network is global or VPN.'
                              ;
                  type enumeration {
                    enum global {
                      value 0 ;
                    }
                    enum vpn {
                      value 1 ;
                    }
                  }
                }
                leaf aggregate-nexthop-vrf {
                  description 'VRF name.'
                              ;
                  type string {
                    length 1..35 ;
                  }
                }
                leaf nexthop {
                  description 'The IP address of the next hop of this lsp.'
                              ;
                  type ncd:ipv4-address ;
                }
                leaf out-interface {
                  description 'The name of the outcoming interface.'
                              ;
                  type string {
                    length 1..31 ;
                  }
                }
                leaf out-label {
                  description 'The outgoing label of this LSP.'
                              ;
                  type uint32 ;
                }
              }
            }
            ncd:select root ;
            ncd:select 'root ipv4-rp-address ipv4-group-address mask-length'
                       ;
            ncd:select vrf-name ;
            ncd:select 'root ipv4-rp-address ipv4-group-address mask-length vrf'
                     + '-name'
                       ;
          }
        }
        container ipv6-bidir {
          description 'Sublist of mldp forwarding table. It is used to get info'
                    + 'rmation of FEC whose type is IPv6-source.'
                      ;
          list ipv6-bidir-fec {
            description 'Key info and filter parameters info.'
                        ;
            key 'root ipv6-rp-address ipv6-group-address mask-length type vrf-n'
              + 'ame'
                ;
            leaf root {
              description 'IPv4 root address.'
                          ;
              type ncd:ipv4-address ;
            }
            leaf ipv6-rp-address {
              description 'IPv6 RP address.'
                          ;
              type ncd:ipv6-address ;
            }
            leaf ipv6-group-address {
              description 'IPv6 multicast group address.'
                          ;
              type ncd:ipv6-address ;
            }
            leaf mask-length {
              description 'Mask length,range from 0 to 128.'
                          ;
              type uint32 {
                range 0..128 ;
              }
            }
            leaf type {
              description 'A value distinguishes network is global or VPN.'
                          ;
              type enumeration {
                enum global {
                  value 0 ;
                }
                enum vpn {
                  value 1 ;
                }
              }
            }
            leaf vrf-name {
              description 'VRF name.'
                          ;
              type string {
                length 0..35 ;
              }
            }
            container nexthop-entries {
              description 'Outgoing infomation of FEC whose type is IPv6-bidir.'
                          ;
              list nexthop-entry {
                description 'A entry of Outgoing infomation, include nexthop\ou'
                          + 'tgong interface\outgong label and so on.'
                            ;
                key num ;
                leaf num {
                  description '"num" is  a speical id, which is used to disting'
                            + 'uish different out segments who has the same fec'
                            + ' type.'
                              ;
                  type uint32 ;
                }
                leaf type {
                  description 'A value distinguishes network is global or VPN.'
                              ;
                  type enumeration {
                    enum global {
                      value 0 ;
                    }
                    enum vpn {
                      value 1 ;
                    }
                  }
                }
                leaf aggregate-nexthop-vrf {
                  description 'VRF name.'
                              ;
                  type string {
                    length 1..35 ;
                  }
                }
                leaf nexthop {
                  description 'The IP address of the next hop of this lsp.'
                              ;
                  type ncd:ipv4-address ;
                }
                leaf out-interface {
                  description 'The name of the outcoming interface.'
                              ;
                  type string {
                    length 1..31 ;
                  }
                }
                leaf out-label {
                  description 'The outgoing label of this LSP.'
                              ;
                  type uint32 ;
                }
              }
            }
            ncd:select root ;
            ncd:select 'root ipv6-rp-address ipv6-group-address mask-length'
                       ;
            ncd:select vrf-name ;
            ncd:select 'root ipv6-rp-address ipv6-group-address mask-length vrf'
                     + '-name'
                       ;
          }
        }
        container vpnv4-source {
          description 'Sublist of mldp forwarding table. It is used to get info'
                    + 'rmation of FEC whose type is VPNv4-source.'
                      ;
          list vpnv4-source-fec {
            description 'Key info and filter parameters info.'
                        ;
            key 'root ipv4-source-address ipv4-group-address rd type vrf-name'
                ;
            leaf root {
              description 'IPv4 root address.'
                          ;
              type ncd:ipv4-address ;
            }
            leaf ipv4-source-address {
              description 'IPv4 multicast source address.'
                          ;
              type ncd:ipv4-address ;
            }
            leaf ipv4-group-address {
              description 'IPv4 multicast group address.'
                          ;
              type ncd:ipv4-address ;
            }
            leaf rd {
              description 'RD.There are thress input format:<0-65535>:<0-429496'
                        + '7265> or <1-65535>.<0-65535>:<0-65535> or <0-255>.<0'
                        + '-255>.<0-255>.<0-255>:<0-65535>.'
                          ;
              type union {
                type ncd:asn-nn ;
                type ncd:asnd-nn ;
                type ncd:ipadd-nn ;
              }
            }
            leaf type {
              description 'A value distinguishes network is global or VPN.'
                          ;
              type enumeration {
                enum global {
                  value 0 ;
                }
                enum vpn {
                  value 1 ;
                }
              }
            }
            leaf vrf-name {
              description 'VRF name.'
                          ;
              type string {
                length 0..35 ;
              }
            }
            container nexthop-entries {
              description 'Outgoing infomation of FEC whose type is VPNv4-sourc'
                        + 'e.'
                          ;
              list nexthop-entry {
                description 'A entry of Outgoing infomation, include nexthop\ou'
                          + 'tgong interface\outgong label and so on.'
                            ;
                key num ;
                leaf num {
                  description '"num" is  a speical id, which is used to disting'
                            + 'uish different out segments who has the same fec'
                            + ' type.'
                              ;
                  type uint32 ;
                }
                leaf type {
                  description 'A value distinguishes network is global or VPN.'
                              ;
                  type enumeration {
                    enum global {
                      value 0 ;
                    }
                    enum vpn {
                      value 1 ;
                    }
                  }
                }
                leaf aggregate-nexthop-vrf {
                  description 'VRF name.'
                              ;
                  type string {
                    length 1..35 ;
                  }
                }
                leaf nexthop {
                  description 'The IP address of the next hop of this lsp.'
                              ;
                  type ncd:ipv4-address ;
                }
                leaf out-interface {
                  description 'The name of the outcoming interface.'
                              ;
                  type string {
                    length 1..31 ;
                  }
                }
                leaf out-label {
                  description 'The outgoing label of this LSP.'
                              ;
                  type uint32 ;
                }
              }
            }
            ncd:select root ;
            ncd:select 'root ipv4-source-address ipv4-group-address rd'
                       ;
            ncd:select vrf-name ;
            ncd:select 'root ipv4-source-address ipv4-group-address rd vrf-name'
                       ;
          }
        }
        container vpnv6-source {
          description 'Sublist of mldp forwarding table. It is used to get info'
                    + 'rmation of FEC whose type is VNPv6-source.'
                      ;
          list vpnv6-source-fec {
            description 'Key info and filter parameters info.'
                        ;
            key 'root ipv6-source-address ipv6-group-address rd type vrf-name'
                ;
            leaf root {
              description 'IPv4 root address.'
                          ;
              type ncd:ipv4-address ;
            }
            leaf ipv6-source-address {
              description 'IPv6 multicast source address.'
                          ;
              type ncd:ipv6-address ;
            }
            leaf ipv6-group-address {
              description 'IPv6 multicast group address.'
                          ;
              type ncd:ipv6-address ;
            }
            leaf rd {
              description 'RD.There are thress input format:<0-65535>:<0-429496'
                        + '7265> or <1-65535>.<0-65535>:<0-65535> or <0-255>.<0'
                        + '-255>.<0-255>.<0-255>:<0-65535>.'
                          ;
              type union {
                type ncd:asn-nn ;
                type ncd:asnd-nn ;
                type ncd:ipadd-nn ;
              }
            }
            leaf type {
              description 'A value distinguishes network is global or VPN.'
                          ;
              type enumeration {
                enum global {
                  value 0 ;
                }
                enum vpn {
                  value 1 ;
                }
              }
            }
            leaf vrf-name {
              description 'VRF name.'
                          ;
              type string {
                length 0..35 ;
              }
            }
            container nexthop-entries {
              description 'Outgoing infomation of FEC whose type is VPNv6-sourc'
                        + 'e.'
                          ;
              list nexthop-entry {
                description 'A entry of Outgoing infomation, include nexthop\ou'
                          + 'tgong interface\outgong label and so on.'
                            ;
                key num ;
                leaf num {
                  description '"num" is  a speical id, which is used to disting'
                            + 'uish different out segments who has the same fec'
                            + ' type.'
                              ;
                  type uint32 ;
                }
                leaf type {
                  description 'A value distinguishes network is global or VPN.'
                              ;
                  type enumeration {
                    enum global {
                      value 0 ;
                    }
                    enum vpn {
                      value 1 ;
                    }
                  }
                }
                leaf aggregate-nexthop-vrf {
                  description 'VRF name.'
                              ;
                  type string {
                    length 1..35 ;
                  }
                }
                leaf nexthop {
                  description 'The IP address of the next hop of this lsp.'
                              ;
                  type ncd:ipv4-address ;
                }
                leaf out-interface {
                  description 'The name of the outcoming interface.'
                              ;
                  type string {
                    length 1..31 ;
                  }
                }
                leaf out-label {
                  description 'The outgoing label of this LSP.'
                              ;
                  type uint32 ;
                }
              }
            }
            ncd:select root ;
            ncd:select 'root ipv6-source-address ipv6-group-address rd'
                       ;
            ncd:select vrf-name ;
            ncd:select 'root ipv6-source-address ipv6-group-address rd vrf-name'
                       ;
          }
        }
        container vpnv4-bidir {
          description 'Sublist of mldp forwarding table. It is used to get info'
                    + 'rmation of FEC whose type is VPNv4-bidir.'
                      ;
          list vpnv4-bidir-fec {
            description 'Key info and filter parameters info.'
                        ;
            key 'root ipv4-rp-address ipv4-group-address mask-length rd type vr'
              + 'f-name'
                ;
            leaf root {
              description 'IPv4 root address.'
                          ;
              type ncd:ipv4-address ;
            }
            leaf ipv4-rp-address {
              description 'IPv4 RP address.'
                          ;
              type ncd:ipv4-address ;
            }
            leaf ipv4-group-address {
              description 'IPv4 multicast group address.'
                          ;
              type ncd:ipv4-address ;
            }
            leaf mask-length {
              description 'Mask length,range from 0 to 128.'
                          ;
              type uint32 {
                range 0..128 ;
              }
            }
            leaf rd {
              description 'RD.There are thress input format:<0-65535>:<0-429496'
                        + '7265> or <1-65535>.<0-65535>:<0-65535> or <0-255>.<0'
                        + '-255>.<0-255>.<0-255>:<0-65535>.'
                          ;
              type union {
                type ncd:asn-nn ;
                type ncd:asnd-nn ;
                type ncd:ipadd-nn ;
              }
            }
            leaf type {
              description 'A value distinguishes network is global or VPN.'
                          ;
              type enumeration {
                enum global {
                  value 0 ;
                }
                enum vpn {
                  value 1 ;
                }
              }
            }
            leaf vrf-name {
              description 'VRF name.'
                          ;
              type string {
                length 0..35 ;
              }
            }
            container nexthop-entries {
              description 'Outgoing infomation of FEC whose type is VPNv4-bidir.'
                          ;
              list nexthop-entry {
                description 'A entry of Outgoing infomation, include nexthop\ou'
                          + 'tgong interface\outgong label and so on.'
                            ;
                key num ;
                leaf num {
                  description '"num" is  a speical id, which is used to disting'
                            + 'uish different out segments who has the same fec'
                            + ' type.'
                              ;
                  type uint32 ;
                }
                leaf type {
                  description 'A value distinguishes network is global or VPN.'
                              ;
                  type enumeration {
                    enum global {
                      value 0 ;
                    }
                    enum vpn {
                      value 1 ;
                    }
                  }
                }
                leaf aggregate-nexthop-vrf {
                  description 'VRF name.'
                              ;
                  type string {
                    length 1..35 ;
                  }
                }
                leaf nexthop {
                  description 'The IP address of the next hop of this lsp.'
                              ;
                  type ncd:ipv4-address ;
                }
                leaf out-interface {
                  description 'The name of the outcoming interface.'
                              ;
                  type string {
                    length 1..31 ;
                  }
                }
                leaf out-label {
                  description 'The outgoing label of this LSP.'
                              ;
                  type uint32 ;
                }
              }
            }
            ncd:select root ;
            ncd:select 'root ipv4-rp-address ipv4-group-address mask-length rd'
                       ;
            ncd:select vrf-name ;
            ncd:select 'root ipv4-rp-address ipv4-group-address mask-length rd '
                     + 'vrf-name'
                       ;
          }
        }
        container vpnv6-bidir {
          description 'Sublist of mldp forwarding table. It is used to get info'
                    + 'rmation of FEC whose type is VPNv6-bidir.'
                      ;
          list vpnv6-bidir-fec {
            description 'Key info and filter parameters info.'
                        ;
            key 'root ipv6-rp-address ipv6-group-address mask-length rd type vr'
              + 'f-name'
                ;
            leaf root {
              description 'IPv4 root address.'
                          ;
              type ncd:ipv4-address ;
            }
            leaf ipv6-rp-address {
              description 'IPv6 RP address.'
                          ;
              type ncd:ipv6-address ;
            }
            leaf ipv6-group-address {
              description 'IPv6 multicast group address.'
                          ;
              type ncd:ipv6-address ;
            }
            leaf mask-length {
              description 'Mask length,range from 0 to 128.'
                          ;
              type uint32 {
                range 0..128 ;
              }
            }
            leaf rd {
              description 'RD.There are thress input format:<0-65535>:<0-429496'
                        + '7265> or <1-65535>.<0-65535>:<0-65535> or <0-255>.<0'
                        + '-255>.<0-255>.<0-255>:<0-65535>.'
                          ;
              type union {
                type ncd:asn-nn ;
                type ncd:asnd-nn ;
                type ncd:ipadd-nn ;
              }
            }
            leaf type {
              description 'A value distinguishes network is global or VPN.'
                          ;
              type enumeration {
                enum global {
                  value 0 ;
                }
                enum vpn {
                  value 1 ;
                }
              }
            }
            leaf vrf-name {
              description 'VRF name.'
                          ;
              type string {
                length 0..35 ;
              }
            }
            container nexthop-entries {
              description 'Outgoing infomation of FEC whose type is VPNv6-bidir.'
                          ;
              list nexthop-entry {
                description 'A entry of Outgoing infomation, include nexthop\ou'
                          + 'tgong interface\outgong label and so on.'
                            ;
                key num ;
                leaf num {
                  description '"num" is  a speical id, which is used to disting'
                            + 'uish different out segments who has the same fec'
                            + ' type.'
                              ;
                  type uint32 ;
                }
                leaf type {
                  description 'A value distinguishes network is global or VPN.'
                              ;
                  type enumeration {
                    enum global {
                      value 0 ;
                    }
                    enum vpn {
                      value 1 ;
                    }
                  }
                }
                leaf aggregate-nexthop-vrf {
                  description 'VRF name.'
                              ;
                  type string {
                    length 1..35 ;
                  }
                }
                leaf nexthop {
                  description 'The IP address of the next hop of this lsp.'
                              ;
                  type ncd:ipv4-address ;
                }
                leaf out-interface {
                  description 'The name of the outcoming interface.'
                              ;
                  type string {
                    length 1..31 ;
                  }
                }
                leaf out-label {
                  description 'The outgoing label of this LSP.'
                              ;
                  type uint32 ;
                }
              }
            }
            ncd:select root ;
            ncd:select 'root ipv6-rp-address ipv6-group-address mask-length rd'
                       ;
            ncd:select vrf-name ;
            ncd:select 'root ipv6-rp-address ipv6-group-address mask-length rd '
                     + 'vrf-name'
                       ;
          }
        }
        container rosen-mdt {
          description 'Sublist of mldp forwarding table. It is used to get info'
                    + 'rmation of FEC whose type is rosen-mdt.'
                      ;
          list rosen-mdt-fec {
            description 'Key info and filter parameters info.'
                        ;
            key 'root vpn-id mdt-num type vrf-name'
                ;
            leaf root {
              description 'IPv4 root address.'
                          ;
              type ncd:ipv4-address ;
            }
            leaf vpn-id {
              description 'VPN ID.'
                          ;
              type string {
                length 0..15 ;
                pattern '([0-9a-fA-F]{1,6}):([0-9a-fA-F]{1,8})'
                        ;
              }
            }
            leaf mdt-num {
              description 'The number of MDT,range from 0 to 5000.'
                          ;
              type uint32 {
                range 0..5000 ;
              }
            }
            leaf type {
              description 'A value distinguishes network is global or VPN.'
                          ;
              type enumeration {
                enum global {
                  value 0 ;
                }
                enum vpn {
                  value 1 ;
                }
              }
            }
            leaf vrf-name {
              description 'VRF name.'
                          ;
              type string {
                length 0..35 ;
              }
            }
            container nexthop-entries {
              description 'Outgoing infomation of FEC whose type is rosen-mdt.'
                          ;
              list nexthop-entry {
                description 'A entry of Outgoing infomation, include nexthop\ou'
                          + 'tgong interface\outgong label and so on.'
                            ;
                key num ;
                leaf num {
                  description '"num" is  a speical id, which is used to disting'
                            + 'uish different out segments who has the same fec'
                            + ' type.'
                              ;
                  type uint32 ;
                }
                leaf type {
                  description 'A value distinguishes network is global or VPN.'
                              ;
                  type enumeration {
                    enum global {
                      value 0 ;
                    }
                    enum vpn {
                      value 1 ;
                    }
                  }
                }
                leaf aggregate-nexthop-vrf {
                  description 'VRF name.'
                              ;
                  type string {
                    length 1..35 ;
                  }
                }
                leaf nexthop {
                  description 'The IP address of the next hop of this lsp.'
                              ;
                  type ncd:ipv4-address ;
                }
                leaf out-interface {
                  description 'The name of the outcoming interface.'
                              ;
                  type string {
                    length 1..31 ;
                  }
                }
                leaf out-label {
                  description 'The outgoing label of this LSP.'
                              ;
                  type uint32 ;
                }
              }
            }
            ncd:select root ;
            ncd:select 'root vpn-id mdt-num'
                       ;
            ncd:select vrf-name ;
            ncd:select 'root vpn-id mdt-num vrf-name'
                       ;
          }
        }
        container pub-recursive-gen-lspid {
          description 'Sublist of mldp forwarding table. It is used to get info'
                    + 'rmation of FEC whose type is pub-recursive nested with g'
                    + 'en-lspid type.'
                      ;
          list pub-recursive-gen-lspid-fec {
            description 'Key info and filter parameters info.'
                        ;
            key 'root inner-root inner-lsp-id type vrf-name'
                ;
            leaf root {
              description 'IPv4 root address.'
                          ;
              type ncd:ipv4-address ;
            }
            leaf inner-root {
              description 'Inner IPv4 root address.'
                          ;
              type ncd:ipv4-address ;
            }
            leaf inner-lsp-id {
              description 'Inner lsp-id.'
                          ;
              type uint32 {
                range 0..4294967295 ;
              }
            }
            leaf type {
              description 'A value distinguishes network is global or VPN.'
                          ;
              type enumeration {
                enum global {
                  value 0 ;
                }
                enum vpn {
                  value 1 ;
                }
              }
            }
            leaf vrf-name {
              description 'VRF name.'
                          ;
              type string {
                length 0..35 ;
              }
            }
            container nexthop-entries {
              description 'Outgoing infomation of FEC whose type is pub-recursi'
                        + 've nested with gen-lspid type.'
                          ;
              list nexthop-entry {
                description 'A entry of Outgoing infomation, include nexthop\ou'
                          + 'tgong interface\outgong label and so on.'
                            ;
                key num ;
                leaf num {
                  description '"num" is  a speical id, which is used to disting'
                            + 'uish different out segments who has the same fec'
                            + ' type.'
                              ;
                  type uint32 ;
                }
                leaf type {
                  description 'A value distinguishes network is global or VPN.'
                              ;
                  type enumeration {
                    enum global {
                      value 0 ;
                    }
                    enum vpn {
                      value 1 ;
                    }
                  }
                }
                leaf aggregate-nexthop-vrf {
                  description 'VRF name.'
                              ;
                  type string {
                    length 1..35 ;
                  }
                }
                leaf nexthop {
                  description 'The IP address of the next hop of this lsp.'
                              ;
                  type ncd:ipv4-address ;
                }
                leaf out-interface {
                  description 'The name of the outcoming interface.'
                              ;
                  type string {
                    length 1..31 ;
                  }
                }
                leaf out-label {
                  description 'The outgoing label of this LSP.'
                              ;
                  type uint32 ;
                }
              }
            }
            ncd:select root ;
            ncd:select 'root inner-root inner-lsp-id'
                       ;
            ncd:select vrf-name ;
            ncd:select 'root inner-root inner-lsp-id vrf-name'
                       ;
          }
        }
        container pub-recursive-ipv4-source {
          description 'Sublist of mldp forwarding table. It is used to get info'
                    + 'rmation of FEC whose type is pub-recursive nested with I'
                    + 'Pv4-source type.'
                      ;
          list pub-recursive-ipv4-source-fec {
            description 'Key info and filter parameters info.'
                        ;
            key 'root inner-root inner-ipv4-source-address inner-ipv4-group-add'
              + 'ress type vrf-name'
                ;
            leaf root {
              description 'IPv4 root address.'
                          ;
              type ncd:ipv4-address ;
            }
            leaf inner-root {
              description 'Inner IPv4 root address.'
                          ;
              type ncd:ipv4-address ;
            }
            leaf inner-ipv4-source-address {
              description 'Inner IPv4 multicast source address.'
                          ;
              type ncd:ipv4-address ;
            }
            leaf inner-ipv4-group-address {
              description 'Inner IPv4 multicast group address.'
                          ;
              type ncd:ipv4-address ;
            }
            leaf type {
              description 'A value distinguishes network is global or VPN.'
                          ;
              type enumeration {
                enum global {
                  value 0 ;
                }
                enum vpn {
                  value 1 ;
                }
              }
            }
            leaf vrf-name {
              description 'VRF name.'
                          ;
              type string {
                length 0..35 ;
              }
            }
            container nexthop-entries {
              description 'Outgoing infomation of FEC whose type is pub-recursi'
                        + 've nested with IPv4-source type.'
                          ;
              list nexthop-entry {
                description 'A entry of Outgoing infomation, include nexthop\ou'
                          + 'tgong interface\outgong label and so on.'
                            ;
                key num ;
                leaf num {
                  description '"num" is  a speical id, which is used to disting'
                            + 'uish different out segments who has the same fec'
                            + ' type.'
                              ;
                  type uint32 ;
                }
                leaf type {
                  description 'A value distinguishes network is global or VPN.'
                              ;
                  type enumeration {
                    enum global {
                      value 0 ;
                    }
                    enum vpn {
                      value 1 ;
                    }
                  }
                }
                leaf aggregate-nexthop-vrf {
                  description 'VRF name.'
                              ;
                  type string {
                    length 1..35 ;
                  }
                }
                leaf nexthop {
                  description 'The IP address of the next hop of this lsp.'
                              ;
                  type ncd:ipv4-address ;
                }
                leaf out-interface {
                  description 'The name of the outcoming interface.'
                              ;
                  type string {
                    length 1..31 ;
                  }
                }
                leaf out-label {
                  description 'The outgoing label of this LSP.'
                              ;
                  type uint32 ;
                }
              }
            }
            ncd:select root ;
            ncd:select 'root inner-root inner-ipv4-source-address inner-ipv4-gr'
                     + 'oup-address'
                       ;
            ncd:select vrf-name ;
            ncd:select 'root inner-root inner-ipv4-source-address inner-ipv4-gr'
                     + 'oup-address vrf-name'
                       ;
          }
        }
        container pub-recursive-ipv6-source {
          description 'Sublist of mldp forwarding table. It is used to get info'
                    + 'rmation of FEC whose type is pub-recursive nested with I'
                    + 'Pv6-source type.'
                      ;
          list pub-recursive-ipv6-source-fec {
            description 'Key info and filter parameters info.'
                        ;
            key 'root inner-root inner-ipv6-source-address inner-ipv6-group-add'
              + 'ress type vrf-name'
                ;
            leaf root {
              description 'IPv4 root address.'
                          ;
              type ncd:ipv4-address ;
            }
            leaf inner-root {
              description 'Inner IPv4 root address.'
                          ;
              type ncd:ipv4-address ;
            }
            leaf inner-ipv6-source-address {
              description 'Inner IPv6 multicast source address.'
                          ;
              type ncd:ipv6-address ;
            }
            leaf inner-ipv6-group-address {
              description 'Inner IPv6 multicast group address.'
                          ;
              type ncd:ipv6-address ;
            }
            leaf type {
              description 'A value distinguishes network is global or VPN.'
                          ;
              type enumeration {
                enum global {
                  value 0 ;
                }
                enum vpn {
                  value 1 ;
                }
              }
            }
            leaf vrf-name {
              description 'VRF name.'
                          ;
              type string {
                length 0..35 ;
              }
            }
            container nexthop-entries {
              description 'Outgoing infomation of FEC whose type is pub-recursi'
                        + 've nested with IPv6-source type.'
                          ;
              list nexthop-entry {
                description 'A entry of Outgoing infomation, include nexthop\ou'
                          + 'tgong interface\outgong label and so on.'
                            ;
                key num ;
                leaf num {
                  description '"num" is  a speical id, which is used to disting'
                            + 'uish different out segments who has the same fec'
                            + ' type.'
                              ;
                  type uint32 ;
                }
                leaf type {
                  description 'A value distinguishes network is global or VPN.'
                              ;
                  type enumeration {
                    enum global {
                      value 0 ;
                    }
                    enum vpn {
                      value 1 ;
                    }
                  }
                }
                leaf aggregate-nexthop-vrf {
                  description 'VRF name.'
                              ;
                  type string {
                    length 1..35 ;
                  }
                }
                leaf nexthop {
                  description 'The IP address of the next hop of this lsp.'
                              ;
                  type ncd:ipv4-address ;
                }
                leaf out-interface {
                  description 'The name of the outcoming interface.'
                              ;
                  type string {
                    length 1..31 ;
                  }
                }
                leaf out-label {
                  description 'The outgoing label of this LSP.'
                              ;
                  type uint32 ;
                }
              }
            }
            ncd:select root ;
            ncd:select 'root inner-root inner-ipv6-source-address inner-ipv6-gr'
                     + 'oup-address'
                       ;
            ncd:select vrf-name ;
            ncd:select 'root inner-root inner-ipv6-source-address inner-ipv6-gr'
                     + 'oup-address vrf-name'
                       ;
          }
        }
        container pub-recursive-ipv4-bidir {
          description 'Sublist of mldp forwarding table. It is used to get info'
                    + 'rmation of FEC whose type is pub-recursive nested with I'
                    + 'Pv4-bidir type.'
                      ;
          list pub-recursive-ipv4-bidir-fec {
            description 'Key info and filter parameters info.'
                        ;
            key 'root inner-root inner-ipv4-rp-address inner-ipv4-group-address'
              + ' inner-mask-length type vrf-name'
                ;
            leaf root {
              description 'IPv4 root address.'
                          ;
              type ncd:ipv4-address ;
            }
            leaf inner-root {
              description 'Inner IPv4 root address.'
                          ;
              type ncd:ipv4-address ;
            }
            leaf inner-ipv4-rp-address {
              description 'Inner IPv4 RP address.'
                          ;
              type ncd:ipv4-address ;
            }
            leaf inner-ipv4-group-address {
              description 'Inner IPv4 multicast group address.'
                          ;
              type ncd:ipv4-address ;
            }
            leaf inner-mask-length {
              description 'Inner mask length,range from 0 to 128.'
                          ;
              type uint32 ;
            }
            leaf type {
              description 'A value distinguishes network is global or VPN.'
                          ;
              type enumeration {
                enum global {
                  value 0 ;
                }
                enum vpn {
                  value 1 ;
                }
              }
            }
            leaf vrf-name {
              description 'VRF name.'
                          ;
              type string {
                length 0..35 ;
              }
            }
            container nexthop-entries {
              description 'Outgoing infomation of FEC whose type is pub-recursi'
                        + 've nested with IPv4-bidir type.'
                          ;
              list nexthop-entry {
                description 'A entry of Outgoing infomation, include nexthop\ou'
                          + 'tgong interface\outgong label and so on.'
                            ;
                key num ;
                leaf num {
                  description '"num" is  a speical id, which is used to disting'
                            + 'uish different out segments who has the same fec'
                            + ' type.'
                              ;
                  type uint32 ;
                }
                leaf type {
                  description 'A value distinguishes network is global or VPN.'
                              ;
                  type enumeration {
                    enum global {
                      value 0 ;
                    }
                    enum vpn {
                      value 1 ;
                    }
                  }
                }
                leaf aggregate-nexthop-vrf {
                  description 'VRF name.'
                              ;
                  type string {
                    length 1..35 ;
                  }
                }
                leaf nexthop {
                  description 'The IP address of the next hop of this lsp.'
                              ;
                  type ncd:ipv4-address ;
                }
                leaf out-interface {
                  description 'The name of the outcoming interface.'
                              ;
                  type string {
                    length 1..31 ;
                  }
                }
                leaf out-label {
                  description 'The outgoing label of this LSP.'
                              ;
                  type uint32 ;
                }
              }
            }
            ncd:select root ;
            ncd:select 'root inner-root inner-ipv4-rp-address inner-ipv4-group-'
                     + 'address inner-mask-length'
                       ;
            ncd:select vrf-name ;
            ncd:select 'root inner-root inner-ipv4-rp-address inner-ipv4-group-'
                     + 'address inner-mask-length vrf-name'
                       ;
          }
        }
        container pub-recursive-ipv6-bidir {
          description 'Sublist of mldp forwarding table. It is used to get info'
                    + 'rmation of FEC whose type is pub-recursive nested with I'
                    + 'Pv6-bidir type.'
                      ;
          list pub-recursive-ipv6-bidir-fec {
            description 'Key info and filter parameters info.'
                        ;
            key 'root inner-root inner-ipv6-rp-address inner-ipv6-group-address'
              + ' inner-mask-length type vrf-name'
                ;
            leaf root {
              description 'IPv4 root address.'
                          ;
              type ncd:ipv4-address ;
            }
            leaf inner-root {
              description 'Inner IPv4 root address.'
                          ;
              type ncd:ipv4-address ;
            }
            leaf inner-ipv6-rp-address {
              description 'Inner IPv6 RP address.'
                          ;
              type ncd:ipv6-address ;
            }
            leaf inner-ipv6-group-address {
              description 'Inner IPv6 multicast group address.'
                          ;
              type ncd:ipv6-address ;
            }
            leaf inner-mask-length {
              description 'Inner mask length,range from 0 to 128.'
                          ;
              type uint32 {
                range 0..128 ;
              }
            }
            leaf type {
              description 'A value distinguishes network is global or VPN.'
                          ;
              type enumeration {
                enum global {
                  value 0 ;
                }
                enum vpn {
                  value 1 ;
                }
              }
            }
            leaf vrf-name {
              description 'VRF name.'
                          ;
              type string {
                length 0..35 ;
              }
            }
            container nexthop-entries {
              description 'Outgoing infomation of FEC whose type is pub-recursi'
                        + 've nested with IPv6-bidir type.'
                          ;
              list nexthop-entry {
                description 'A entry of Outgoing infomation, include nexthop\ou'
                          + 'tgong interface\outgong label and so on.'
                            ;
                key num ;
                leaf num {
                  description '"num" is  a speical id, which is used to disting'
                            + 'uish different out segments who has the same fec'
                            + ' type.'
                              ;
                  type uint32 ;
                }
                leaf type {
                  description 'A value distinguishes network is global or VPN.'
                              ;
                  type enumeration {
                    enum global {
                      value 0 ;
                    }
                    enum vpn {
                      value 1 ;
                    }
                  }
                }
                leaf aggregate-nexthop-vrf {
                  description 'VRF name.'
                              ;
                  type string {
                    length 1..35 ;
                  }
                }
                leaf nexthop {
                  description 'The IP address of the next hop of this lsp.'
                              ;
                  type ncd:ipv4-address ;
                }
                leaf out-interface {
                  description 'The name of the outcoming interface.'
                              ;
                  type string {
                    length 1..31 ;
                  }
                }
                leaf out-label {
                  description 'The outgoing label of this LSP.'
                              ;
                  type uint32 ;
                }
              }
            }
            ncd:select root ;
            ncd:select 'root inner-root inner-ipv6-rp-address inner-ipv6-group-'
                     + 'address inner-mask-length'
                       ;
            ncd:select vrf-name ;
            ncd:select 'root inner-root inner-ipv6-rp-address inner-ipv6-group-'
                     + 'address inner-mask-length vrf-name'
                       ;
          }
        }
        container pub-recursive-vpnv4-source {
          description 'Sublist of mldp forwarding table. It is used to get info'
                    + 'rmation of FEC whose type is pub-recursive nested with V'
                    + 'PNv4-source type.'
                      ;
          list pub-recursive-vpnv4-source-fec {
            description 'Key info and filter parameters info.'
                        ;
            key 'root inner-root inner-ipv4-source-address inner-ipv4-group-add'
              + 'ress inner-rd type vrf-name'
                ;
            leaf root {
              description 'IPv4 root address.'
                          ;
              type ncd:ipv4-address ;
            }
            leaf inner-root {
              description 'Inner IPv4 root address.'
                          ;
              type ncd:ipv4-address ;
            }
            leaf inner-ipv4-source-address {
              description 'Inner IPv4 multicast source address.'
                          ;
              type ncd:ipv4-address ;
            }
            leaf inner-ipv4-group-address {
              description 'Inner IPv4 multicast group address.'
                          ;
              type ncd:ipv4-address ;
            }
            leaf inner-rd {
              description 'Inner RD.There are thress input format:<0-65535>:<0-'
                        + '4294967265> or <1-65535>.<0-65535>:<0-65535> or <0-2'
                        + '55>.<0-255>.<0-255>.<0-255>:<0-65535>.'
                          ;
              type union {
                type ncd:asn-nn ;
                type ncd:asnd-nn ;
                type ncd:ipadd-nn ;
              }
            }
            leaf type {
              description 'A value distinguishes network is global or VPN.'
                          ;
              type enumeration {
                enum global {
                  value 0 ;
                }
                enum vpn {
                  value 1 ;
                }
              }
            }
            leaf vrf-name {
              description 'VRF name.'
                          ;
              type string {
                length 0..35 ;
              }
            }
            container nexthop-entries {
              description 'Outgoing infomation of FEC whose type is pub-recursi'
                        + 've nested with VPNv4-source type.'
                          ;
              list nexthop-entry {
                description 'A entry of Outgoing infomation, include nexthop\ou'
                          + 'tgong interface\outgong label and so on.'
                            ;
                key num ;
                leaf num {
                  description '"num" is  a speical id, which is used to disting'
                            + 'uish different out segments who has the same fec'
                            + ' type.'
                              ;
                  type uint32 ;
                }
                leaf type {
                  description 'A value distinguishes network is global or VPN.'
                              ;
                  type enumeration {
                    enum global {
                      value 0 ;
                    }
                    enum vpn {
                      value 1 ;
                    }
                  }
                }
                leaf aggregate-nexthop-vrf {
                  description 'VRF name.'
                              ;
                  type string {
                    length 1..35 ;
                  }
                }
                leaf nexthop {
                  description 'The IP address of the next hop of this lsp.'
                              ;
                  type ncd:ipv4-address ;
                }
                leaf out-interface {
                  description 'The name of the outcoming interface.'
                              ;
                  type string {
                    length 1..31 ;
                  }
                }
                leaf out-label {
                  description 'The outgoing label of this LSP.'
                              ;
                  type uint32 ;
                }
              }
            }
            ncd:select root ;
            ncd:select 'root inner-root inner-ipv4-source-address inner-ipv4-gr'
                     + 'oup-address inner-rd'
                       ;
            ncd:select vrf-name ;
            ncd:select 'root inner-root inner-ipv4-source-address inner-ipv4-gr'
                     + 'oup-address inner-rd vrf-name'
                       ;
          }
        }
        container pub-recursive-vpnv6-source {
          description 'Sublist of mldp forwarding table. It is used to get info'
                    + 'rmation of FEC whose type is pub-recursive nested with V'
                    + 'PNv6-source type.'
                      ;
          list pub-recursive-vpnv6-source-fec {
            description 'Key info and filter parameters info.'
                        ;
            key 'root inner-root inner-ipv6-source-address inner-ipv6-group-add'
              + 'ress inner-rd type vrf-name'
                ;
            leaf root {
              description 'IPv4 root address.'
                          ;
              type ncd:ipv4-address ;
            }
            leaf inner-root {
              description 'Inner IPv4 root address.'
                          ;
              type ncd:ipv4-address ;
            }
            leaf inner-ipv6-source-address {
              description 'Inner IPv6 multicast source address.'
                          ;
              type ncd:ipv6-address ;
            }
            leaf inner-ipv6-group-address {
              description 'Inner IPv6 multicast group address.'
                          ;
              type ncd:ipv6-address ;
            }
            leaf inner-rd {
              description 'Inner RD.There are thress input format:<0-65535>:<0-'
                        + '4294967265> or <1-65535>.<0-65535>:<0-65535> or <0-2'
                        + '55>.<0-255>.<0-255>.<0-255>:<0-65535>.'
                          ;
              type union {
                type ncd:asn-nn ;
                type ncd:asnd-nn ;
                type ncd:ipadd-nn ;
              }
            }
            leaf type {
              description 'A value distinguishes network is global or VPN.'
                          ;
              type enumeration {
                enum global {
                  value 0 ;
                }
                enum vpn {
                  value 1 ;
                }
              }
            }
            leaf vrf-name {
              description 'VRF name.'
                          ;
              type string {
                length 0..35 ;
              }
            }
            container nexthop-entries {
              description 'Outgoing infomation of FEC whose type is pub-recursi'
                        + 've nested with VPNv6-source type.'
                          ;
              list nexthop-entry {
                description 'A entry of Outgoing infomation, include nexthop\ou'
                          + 'tgong interface\outgong label and so on.'
                            ;
                key num ;
                leaf num {
                  description '"num" is  a speical id, which is used to disting'
                            + 'uish different out segments who has the same fec'
                            + ' type.'
                              ;
                  type uint32 ;
                }
                leaf type {
                  description 'A value distinguishes network is global or VPN.'
                              ;
                  type enumeration {
                    enum global {
                      value 0 ;
                    }
                    enum vpn {
                      value 1 ;
                    }
                  }
                }
                leaf aggregate-nexthop-vrf {
                  description 'VRF name.'
                              ;
                  type string {
                    length 1..35 ;
                  }
                }
                leaf nexthop {
                  description 'The IP address of the next hop of this lsp.'
                              ;
                  type ncd:ipv4-address ;
                }
                leaf out-interface {
                  description 'The name of the outcoming interface.'
                              ;
                  type string {
                    length 1..31 ;
                  }
                }
                leaf out-label {
                  description 'The outgoing label of this LSP.'
                              ;
                  type uint32 ;
                }
              }
            }
            ncd:select root ;
            ncd:select 'root inner-root inner-ipv6-source-address inner-ipv6-gr'
                     + 'oup-address inner-rd'
                       ;
            ncd:select vrf-name ;
            ncd:select 'root inner-root inner-ipv6-source-address inner-ipv6-gr'
                     + 'oup-address inner-rd vrf-name'
                       ;
          }
        }
        container pub-recursive-vpnv4-bidir {
          description 'Sublist of mldp forwarding table. It is used to get info'
                    + 'rmation of FEC whose type is pub-recursive nested with V'
                    + 'PNv4-bidir type.'
                      ;
          list pub-recursive-vpnv4-bidir-fec {
            description 'Key info and filter parameters info.'
                        ;
            key 'root inner-root inner-ipv4-rp-address inner-ipv4-group-address'
              + ' inner-mask-length inner-rd type vrf-name'
                ;
            leaf root {
              description 'IPv4 root address.'
                          ;
              type ncd:ipv4-address ;
            }
            leaf inner-root {
              description 'Inner IPv4 root address.'
                          ;
              type ncd:ipv4-address ;
            }
            leaf inner-ipv4-rp-address {
              description 'Inner IPv4 RP address.'
                          ;
              type ncd:ipv4-address ;
            }
            leaf inner-ipv4-group-address {
              description 'Inner IPv4 multicast group address.'
                          ;
              type ncd:ipv4-address ;
            }
            leaf inner-mask-length {
              description 'Inner mask length,range from 0 to 128.'
                          ;
              type uint32 {
                range 0..128 ;
              }
            }
            leaf inner-rd {
              description 'Inner RD.There are thress input format:<0-65535>:<0-'
                        + '4294967265> or <1-65535>.<0-65535>:<0-65535> or <0-2'
                        + '55>.<0-255>.<0-255>.<0-255>:<0-65535>.'
                          ;
              type union {
                type ncd:asn-nn ;
                type ncd:asnd-nn ;
                type ncd:ipadd-nn ;
              }
            }
            leaf type {
              description 'A value distinguishes network is global or VPN.'
                          ;
              type enumeration {
                enum global {
                  value 0 ;
                }
                enum vpn {
                  value 1 ;
                }
              }
            }
            leaf vrf-name {
              description 'VRF name.'
                          ;
              type string {
                length 0..35 ;
              }
            }
            container nexthop-entries {
              description 'Outgoing infomation of FEC whose type is pub-recursi'
                        + 've nested with VPNv4-bidir type.'
                          ;
              list nexthop-entry {
                description 'A entry of Outgoing infomation, include nexthop\ou'
                          + 'tgong interface\outgong label and so on.'
                            ;
                key num ;
                leaf num {
                  description '"num" is  a speical id, which is used to disting'
                            + 'uish different out segments who has the same fec'
                            + ' type.'
                              ;
                  type uint32 ;
                }
                leaf type {
                  description 'A value distinguishes network is global or VPN.'
                              ;
                  type enumeration {
                    enum global {
                      value 0 ;
                    }
                    enum vpn {
                      value 1 ;
                    }
                  }
                }
                leaf aggregate-nexthop-vrf {
                  description 'VRF name.'
                              ;
                  type string {
                    length 1..35 ;
                  }
                }
                leaf nexthop {
                  description 'The IP address of the next hop of this lsp.'
                              ;
                  type ncd:ipv4-address ;
                }
                leaf out-interface {
                  description 'The name of the outcoming interface.'
                              ;
                  type string {
                    length 1..31 ;
                  }
                }
                leaf out-label {
                  description 'The outgoing label of this LSP.'
                              ;
                  type uint32 ;
                }
              }
            }
            ncd:select root ;
            ncd:select 'root inner-root inner-ipv4-rp-address inner-ipv4-group-'
                     + 'address inner-mask-length inner-rd'
                       ;
            ncd:select vrf-name ;
            ncd:select 'root inner-root inner-ipv4-rp-address inner-ipv4-group-'
                     + 'address inner-mask-length inner-rd vrf-name'
                       ;
          }
        }
        container pub-recursive-vpnv6-bidir {
          description 'Sublist of mldp forwarding table. It is used to get info'
                    + 'rmation of FEC whose type is pub-recursive nested with V'
                    + 'PNv6-bidir type.'
                      ;
          list pub-recursive-vpnv6-bidir-fec {
            description 'Key info and filter parameters info.'
                        ;
            key 'root inner-root inner-ipv6-rp-address inner-ipv6-group-address'
              + ' inner-mask-length inner-rd type vrf-name'
                ;
            leaf root {
              description 'IPv4 root address.'
                          ;
              type ncd:ipv4-address ;
            }
            leaf inner-root {
              description 'Inner IPv4 root address.'
                          ;
              type ncd:ipv4-address ;
            }
            leaf inner-ipv6-rp-address {
              description 'Inner IPv6 RP address.'
                          ;
              type ncd:ipv6-address ;
            }
            leaf inner-ipv6-group-address {
              description 'Inner IPv6 multicast group address.'
                          ;
              type ncd:ipv6-address ;
            }
            leaf inner-mask-length {
              description 'Inner mask length,range from 0 to 128.'
                          ;
              type uint32 {
                range 0..128 ;
              }
            }
            leaf inner-rd {
              description 'Inner RD.There are thress input format:<0-65535>:<0-'
                        + '4294967265> or <1-65535>.<0-65535>:<0-65535> or <0-2'
                        + '55>.<0-255>.<0-255>.<0-255>:<0-65535>.'
                          ;
              type union {
                type ncd:asn-nn ;
                type ncd:asnd-nn ;
                type ncd:ipadd-nn ;
              }
            }
            leaf type {
              description 'A value distinguishes network is global or VPN.'
                          ;
              type enumeration {
                enum global {
                  value 0 ;
                }
                enum vpn {
                  value 1 ;
                }
              }
            }
            leaf vrf-name {
              description 'VRF name.'
                          ;
              type string {
                length 0..35 ;
              }
            }
            container nexthop-entries {
              description 'Outgoing infomation of FEC whose type is pub-recursi'
                        + 've nested with VPNv6-bidir type.'
                          ;
              list nexthop-entry {
                description 'A entry of Outgoing infomation, include nexthop\ou'
                          + 'tgong interface\outgong label and so on.'
                            ;
                key num ;
                leaf num {
                  description '"num" is  a speical id, which is used to disting'
                            + 'uish different out segments who has the same fec'
                            + ' type.'
                              ;
                  type uint32 ;
                }
                leaf type {
                  description 'A value distinguishes network is global or VPN.'
                              ;
                  type enumeration {
                    enum global {
                      value 0 ;
                    }
                    enum vpn {
                      value 1 ;
                    }
                  }
                }
                leaf aggregate-nexthop-vrf {
                  description 'VRF name.'
                              ;
                  type string {
                    length 1..35 ;
                  }
                }
                leaf nexthop {
                  description 'The IP address of the next hop of this lsp.'
                              ;
                  type ncd:ipv4-address ;
                }
                leaf out-interface {
                  description 'The name of the outcoming interface.'
                              ;
                  type string {
                    length 1..31 ;
                  }
                }
                leaf out-label {
                  description 'The outgoing label of this LSP.'
                              ;
                  type uint32 ;
                }
              }
            }
            ncd:select root ;
            ncd:select 'root inner-root inner-ipv6-rp-address inner-ipv6-group-'
                     + 'address inner-mask-length inner-rd'
                       ;
            ncd:select vrf-name ;
            ncd:select 'root inner-root inner-ipv6-rp-address inner-ipv6-group-'
                     + 'address inner-mask-length inner-rd vrf-name'
                       ;
          }
        }
        container pub-recursive-rosen-mdt {
          description 'Sublist of mldp forwarding table. It is used to get info'
                    + 'rmation of FEC whose type is pub-recursive nested with r'
                    + 'osen-mdt type.'
                      ;
          list pub-recursive-rosen-mdt-fec {
            description 'Key info and filter parameters info.'
                        ;
            key 'root inner-root inner-vpn-id inner-mdt-num type vrf-name'
                ;
            leaf root {
              description 'IPv4 root address.'
                          ;
              type ncd:ipv4-address ;
            }
            leaf inner-root {
              description 'Inner IPv4 root address.'
                          ;
              type ncd:ipv4-address ;
            }
            leaf inner-vpn-id {
              description 'Inner VPN ID.'
                          ;
              type string {
                length 0..15 ;
                pattern '([0-9a-fA-F]{1,6}):([0-9a-fA-F]{1,8})'
                        ;
              }
            }
            leaf inner-mdt-num {
              description 'The inner number of MDT,range from 0 to 5000.'
                          ;
              type uint32 {
                range 0..5000 ;
              }
            }
            leaf type {
              description 'A value distinguishes network is global or VPN.'
                          ;
              type enumeration {
                enum global {
                  value 0 ;
                }
                enum vpn {
                  value 1 ;
                }
              }
            }
            leaf vrf-name {
              description 'VRF name.'
                          ;
              type string {
                length 0..35 ;
              }
            }
            container nexthop-entries {
              description 'Outgoing infomation of FEC whose type is pub-recursi'
                        + 've nested with rosen-mdt type.'
                          ;
              list nexthop-entry {
                description 'A entry of Outgoing infomation, include nexthop\ou'
                          + 'tgong interface\outgong label and so on.'
                            ;
                key num ;
                leaf num {
                  description '"num" is  a speical id, which is used to disting'
                            + 'uish different out segments who has the same fec'
                            + ' type.'
                              ;
                  type uint32 ;
                }
                leaf type {
                  description 'A value distinguishes network is global or VPN.'
                              ;
                  type enumeration {
                    enum global {
                      value 0 ;
                    }
                    enum vpn {
                      value 1 ;
                    }
                  }
                }
                leaf aggregate-nexthop-vrf {
                  description 'VRF name.'
                              ;
                  type string {
                    length 1..35 ;
                  }
                }
                leaf nexthop {
                  description 'The IP address of the next hop of this lsp.'
                              ;
                  type ncd:ipv4-address ;
                }
                leaf out-interface {
                  description 'The name of the outcoming interface.'
                              ;
                  type string {
                    length 1..31 ;
                  }
                }
                leaf out-label {
                  description 'The outgoing label of this LSP.'
                              ;
                  type uint32 ;
                }
              }
            }
            ncd:select root ;
            ncd:select 'root inner-root inner-vpn-id inner-mdt-num'
                       ;
            ncd:select vrf-name ;
            ncd:select 'root inner-root inner-vpn-id inner-mdt-num vrf-name'
                       ;
          }
        }
        container vpn-recursive-gen-lspid {
          description 'Sublist of mldp forwarding table. It is used to get info'
                    + 'rmation of FEC whose type is vpn-recursive nested with g'
                    + 'en-lspid type.'
                      ;
          list vpn-recursive-gen-lspid-fec {
            description 'Key info and filter parameters info.'
                        ;
            key 'root rd inner-root inner-lsp-id type vrf-name'
                ;
            leaf root {
              description 'IPv4 root address.'
                          ;
              type ncd:ipv4-address ;
            }
            leaf rd {
              description 'RD.There are thress input format:<0-65535>:<0-429496'
                        + '7265> or <1-65535>.<0-65535>:<0-65535> or <0-255>.<0'
                        + '-255>.<0-255>.<0-255>:<0-65535>.'
                          ;
              type union {
                type ncd:asn-nn ;
                type ncd:asnd-nn ;
                type ncd:ipadd-nn ;
              }
            }
            leaf inner-root {
              description 'Inner IPv4 root address.'
                          ;
              type ncd:ipv4-address ;
            }
            leaf inner-lsp-id {
              description 'Inner lsp-id.'
                          ;
              type uint32 {
                range 0..4294967295 ;
              }
            }
            leaf type {
              description 'A value distinguishes network is global or VPN.'
                          ;
              type enumeration {
                enum global {
                  value 0 ;
                }
                enum vpn {
                  value 1 ;
                }
              }
            }
            leaf vrf-name {
              description 'VRF name.'
                          ;
              type string {
                length 0..35 ;
              }
            }
            container nexthop-entries {
              description 'Outgoing infomation of FEC whose type is vpn-recursi'
                        + 've nested with gen-lspid type.'
                          ;
              list nexthop-entry {
                description 'A entry of Outgoing infomation, include nexthop\ou'
                          + 'tgong interface\outgong label and so on.'
                            ;
                key num ;
                leaf num {
                  description '"num" is  a speical id, which is used to disting'
                            + 'uish different out segments who has the same fec'
                            + ' type.'
                              ;
                  type uint32 ;
                }
                leaf type {
                  description 'A value distinguishes network is global or VPN.'
                              ;
                  type enumeration {
                    enum global {
                      value 0 ;
                    }
                    enum vpn {
                      value 1 ;
                    }
                  }
                }
                leaf aggregate-nexthop-vrf {
                  description 'VRF name.'
                              ;
                  type string {
                    length 1..35 ;
                  }
                }
                leaf nexthop {
                  description 'The IP address of the next hop of this lsp.'
                              ;
                  type ncd:ipv4-address ;
                }
                leaf out-interface {
                  description 'The name of the outcoming interface.'
                              ;
                  type string {
                    length 1..31 ;
                  }
                }
                leaf out-label {
                  description 'The outgoing label of this LSP.'
                              ;
                  type uint32 ;
                }
              }
            }
            ncd:select root ;
            ncd:select 'root rd inner-root inner-lsp-id'
                       ;
            ncd:select vrf-name ;
            ncd:select 'root rd inner-root inner-lsp-id vrf-name'
                       ;
          }
        }
        container vpn-recursive-ipv4-source {
          description 'Sublist of mldp forwarding table. It is used to get info'
                    + 'rmation of FEC whose type is vpn-recursive nested with I'
                    + 'Pv4-source type.'
                      ;
          list vpn-recursive-ipv4-source-fec {
            description 'Key info and filter parameters info.'
                        ;
            key 'root rd inner-root inner-ipv4-source-address inner-ipv4-group-'
              + 'address type vrf-name'
                ;
            leaf root {
              description 'IPv4 root address.'
                          ;
              type ncd:ipv4-address ;
            }
            leaf rd {
              description 'RD.There are thress input format:<0-65535>:<0-429496'
                        + '7265> or <1-65535>.<0-65535>:<0-65535> or <0-255>.<0'
                        + '-255>.<0-255>.<0-255>:<0-65535>.'
                          ;
              type union {
                type ncd:asn-nn ;
                type ncd:asnd-nn ;
                type ncd:ipadd-nn ;
              }
            }
            leaf inner-root {
              description 'Inner IPv4 root address.'
                          ;
              type ncd:ipv4-address ;
            }
            leaf inner-ipv4-source-address {
              description 'Inner IPv4 multicast source address.'
                          ;
              type ncd:ipv4-address ;
            }
            leaf inner-ipv4-group-address {
              description 'Inner IPv4 multicast group address.'
                          ;
              type ncd:ipv4-address ;
            }
            leaf type {
              description 'A value distinguishes network is global or VPN.'
                          ;
              type enumeration {
                enum global {
                  value 0 ;
                }
                enum vpn {
                  value 1 ;
                }
              }
            }
            leaf vrf-name {
              description 'VRF name.'
                          ;
              type string {
                length 0..35 ;
              }
            }
            container nexthop-entries {
              description 'Outgoing infomation of FEC whose type is vpn-recursi'
                        + 've nested with IPv4-source type.'
                          ;
              list nexthop-entry {
                description 'A entry of Outgoing infomation, include nexthop\ou'
                          + 'tgong interface\outgong label and so on.'
                            ;
                key num ;
                leaf num {
                  description '"num" is  a speical id, which is used to disting'
                            + 'uish different out segments who has the same fec'
                            + ' type.'
                              ;
                  type uint32 ;
                }
                leaf type {
                  description 'A value distinguishes network is global or VPN.'
                              ;
                  type enumeration {
                    enum global {
                      value 0 ;
                    }
                    enum vpn {
                      value 1 ;
                    }
                  }
                }
                leaf aggregate-nexthop-vrf {
                  description 'VRF name.'
                              ;
                  type string {
                    length 1..35 ;
                  }
                }
                leaf nexthop {
                  description 'The IP address of the next hop of this lsp.'
                              ;
                  type ncd:ipv4-address ;
                }
                leaf out-interface {
                  description 'The name of the outcoming interface.'
                              ;
                  type string {
                    length 1..31 ;
                  }
                }
                leaf out-label {
                  description 'The outgoing label of this LSP.'
                              ;
                  type uint32 ;
                }
              }
            }
            ncd:select root ;
            ncd:select 'root rd inner-root inner-ipv4-source-address inner-ipv4'
                     + '-group-address'
                       ;
            ncd:select vrf-name ;
            ncd:select 'root rd inner-root inner-ipv4-source-address inner-ipv4'
                     + '-group-address vrf-name'
                       ;
          }
        }
        container vpn-recursive-ipv6-source {
          description 'Sublist of mldp forwarding table. It is used to get info'
                    + 'rmation of FEC whose type is vpn-recursive nested with I'
                    + 'Pv6-source type.'
                      ;
          list vpn-recursive-ipv6-source-fec {
            description 'Key info and filter parameters info.'
                        ;
            key 'root rd inner-root inner-ipv6-source-address inner-ipv6-group-'
              + 'address type vrf-name'
                ;
            leaf root {
              description 'IPv4 root address.'
                          ;
              type ncd:ipv4-address ;
            }
            leaf rd {
              description 'RD.There are thress input format:<0-65535>:<0-429496'
                        + '7265> or <1-65535>.<0-65535>:<0-65535> or <0-255>.<0'
                        + '-255>.<0-255>.<0-255>:<0-65535>.'
                          ;
              type union {
                type ncd:asn-nn ;
                type ncd:asnd-nn ;
                type ncd:ipadd-nn ;
              }
            }
            leaf inner-root {
              description 'Inner IPv4 root address.'
                          ;
              type ncd:ipv4-address ;
            }
            leaf inner-ipv6-source-address {
              description 'Inner IPv6 multicast source address.'
                          ;
              type ncd:ipv6-address ;
            }
            leaf inner-ipv6-group-address {
              description 'Inner IPv6 multicast group address.'
                          ;
              type ncd:ipv6-address ;
            }
            leaf type {
              description 'A value distinguishes network is global or VPN.'
                          ;
              type enumeration {
                enum global {
                  value 0 ;
                }
                enum vpn {
                  value 1 ;
                }
              }
            }
            leaf vrf-name {
              description 'VRF name.'
                          ;
              type string {
                length 0..35 ;
              }
            }
            container nexthop-entries {
              description 'Outgoing infomation of FEC whose type is vpn-recursi'
                        + 've nested with IPv6-source type.'
                          ;
              list nexthop-entry {
                description 'A entry of Outgoing infomation, include nexthop\ou'
                          + 'tgong interface\outgong label and so on.'
                            ;
                key num ;
                leaf num {
                  description '"num" is  a speical id, which is used to disting'
                            + 'uish different out segments who has the same fec'
                            + ' type.'
                              ;
                  type uint32 ;
                }
                leaf type {
                  description 'A value distinguishes network is global or VPN.'
                              ;
                  type enumeration {
                    enum global {
                      value 0 ;
                    }
                    enum vpn {
                      value 1 ;
                    }
                  }
                }
                leaf aggregate-nexthop-vrf {
                  description 'VRF name.'
                              ;
                  type string {
                    length 1..35 ;
                  }
                }
                leaf nexthop {
                  description 'The IP address of the next hop of this lsp.'
                              ;
                  type ncd:ipv4-address ;
                }
                leaf out-interface {
                  description 'The name of the outcoming interface.'
                              ;
                  type string {
                    length 1..31 ;
                  }
                }
                leaf out-label {
                  description 'The outgoing label of this LSP.'
                              ;
                  type uint32 ;
                }
              }
            }
            ncd:select root ;
            ncd:select 'root rd inner-root inner-ipv6-source-address inner-ipv6'
                     + '-group-address'
                       ;
            ncd:select vrf-name ;
            ncd:select 'root rd inner-root inner-ipv6-source-address inner-ipv6'
                     + '-group-address vrf-name'
                       ;
          }
        }
        container vpn-recursive-ipv4-bidir {
          description 'Sublist of mldp forwarding table. It is used to get info'
                    + 'rmation of FEC whose type is vpn-recursive nested with I'
                    + 'Pv4-bidir type.'
                      ;
          list vpn-recursive-ipv4-bidir-fec {
            description 'Key info and filter parameters info.'
                        ;
            key 'root rd inner-root inner-ipv4-rp-address inner-ipv4-group-addr'
              + 'ess inner-mask-length type vrf-name'
                ;
            leaf root {
              description 'IPv4 root address.'
                          ;
              type ncd:ipv4-address ;
            }
            leaf rd {
              description 'RD.There are thress input format:<0-65535>:<0-429496'
                        + '7265> or <1-65535>.<0-65535>:<0-65535> or <0-255>.<0'
                        + '-255>.<0-255>.<0-255>:<0-65535>.'
                          ;
              type union {
                type ncd:asn-nn ;
                type ncd:asnd-nn ;
                type ncd:ipadd-nn ;
              }
            }
            leaf inner-root {
              description 'Inner IPv4 root address.'
                          ;
              type ncd:ipv4-address ;
            }
            leaf inner-ipv4-rp-address {
              description 'Inner IPv4 RP address.'
                          ;
              type ncd:ipv4-address ;
            }
            leaf inner-ipv4-group-address {
              description 'Inner IPv4 multicast group address.'
                          ;
              type ncd:ipv4-address ;
            }
            leaf inner-mask-length {
              description 'Inner mask length,range from 0 to 128.'
                          ;
              type uint32 ;
            }
            leaf type {
              description 'A value distinguishes network is global or VPN.'
                          ;
              type enumeration {
                enum global {
                  value 0 ;
                }
                enum vpn {
                  value 1 ;
                }
              }
            }
            leaf vrf-name {
              description 'VRF name.'
                          ;
              type string {
                length 0..35 ;
              }
            }
            container nexthop-entries {
              description 'Outgoing infomation of FEC whose type is vpn-recursi'
                        + 've nested with IPv4-bidir type.'
                          ;
              list nexthop-entry {
                description 'A entry of Outgoing infomation, include nexthop\ou'
                          + 'tgong interface\outgong label and so on.'
                            ;
                key num ;
                leaf num {
                  description '"num" is  a speical id, which is used to disting'
                            + 'uish different out segments who has the same fec'
                            + ' type.'
                              ;
                  type uint32 ;
                }
                leaf type {
                  description 'A value distinguishes network is global or VPN.'
                              ;
                  type enumeration {
                    enum global {
                      value 0 ;
                    }
                    enum vpn {
                      value 1 ;
                    }
                  }
                }
                leaf aggregate-nexthop-vrf {
                  description 'VRF name.'
                              ;
                  type string {
                    length 1..35 ;
                  }
                }
                leaf nexthop {
                  description 'The IP address of the next hop of this lsp.'
                              ;
                  type ncd:ipv4-address ;
                }
                leaf out-interface {
                  description 'The name of the outcoming interface.'
                              ;
                  type string {
                    length 1..31 ;
                  }
                }
                leaf out-label {
                  description 'The outgoing label of this LSP.'
                              ;
                  type uint32 ;
                }
              }
            }
            ncd:select root ;
            ncd:select 'root rd inner-root inner-ipv4-rp-address inner-ipv4-gro'
                     + 'up-address inner-mask-length'
                       ;
            ncd:select vrf-name ;
            ncd:select 'root rd inner-root inner-ipv4-rp-address inner-ipv4-gro'
                     + 'up-address inner-mask-length vrf-name'
                       ;
          }
        }
        container vpn-recursive-ipv6-bidir {
          description 'Sublist of mldp forwarding table. It is used to get info'
                    + 'rmation of FEC whose type is vpn-recursive nested with I'
                    + 'Pv6-bidir type.'
                      ;
          list vpn-recursive-ipv6-bidir-fec {
            description 'Key info and filter parameters info.'
                        ;
            key 'root rd inner-root inner-ipv6-rp-address inner-ipv6-group-addr'
              + 'ess inner-mask-length type vrf-name'
                ;
            leaf root {
              description 'IPv4 root address.'
                          ;
              type ncd:ipv4-address ;
            }
            leaf rd {
              description 'RD.There are thress input format:<0-65535>:<0-429496'
                        + '7265> or <1-65535>.<0-65535>:<0-65535> or <0-255>.<0'
                        + '-255>.<0-255>.<0-255>:<0-65535>.'
                          ;
              type union {
                type ncd:asn-nn ;
                type ncd:asnd-nn ;
                type ncd:ipadd-nn ;
              }
            }
            leaf inner-root {
              description 'Inner IPv4 root address.'
                          ;
              type ncd:ipv4-address ;
            }
            leaf inner-ipv6-rp-address {
              description 'Inner IPv6 RP address.'
                          ;
              type ncd:ipv6-address ;
            }
            leaf inner-ipv6-group-address {
              description 'Inner IPv6 multicast group address.'
                          ;
              type ncd:ipv6-address ;
            }
            leaf inner-mask-length {
              description 'Inner mask length,range from 0 to 128.'
                          ;
              type uint32 {
                range 0..128 ;
              }
            }
            leaf type {
              description 'A value distinguishes network is global or VPN.'
                          ;
              type enumeration {
                enum global {
                  value 0 ;
                }
                enum vpn {
                  value 1 ;
                }
              }
            }
            leaf vrf-name {
              description 'VRF name.'
                          ;
              type string {
                length 0..35 ;
              }
            }
            container nexthop-entries {
              description 'Outgoing infomation of FEC whose type is vpn-recursi'
                        + 've nested with IPv6-bidir type.'
                          ;
              list nexthop-entry {
                description 'A entry of Outgoing infomation, include nexthop\ou'
                          + 'tgong interface\outgong label and so on.'
                            ;
                key num ;
                leaf num {
                  description '"num" is  a speical id, which is used to disting'
                            + 'uish different out segments who has the same fec'
                            + ' type.'
                              ;
                  type uint32 ;
                }
                leaf type {
                  description 'A value distinguishes network is global or VPN.'
                              ;
                  type enumeration {
                    enum global {
                      value 0 ;
                    }
                    enum vpn {
                      value 1 ;
                    }
                  }
                }
                leaf aggregate-nexthop-vrf {
                  description 'VRF name.'
                              ;
                  type string {
                    length 1..35 ;
                  }
                }
                leaf nexthop {
                  description 'The IP address of the next hop of this lsp.'
                              ;
                  type ncd:ipv4-address ;
                }
                leaf out-interface {
                  description 'The name of the outcoming interface.'
                              ;
                  type string {
                    length 1..31 ;
                  }
                }
                leaf out-label {
                  description 'The outgoing label of this LSP.'
                              ;
                  type uint32 ;
                }
              }
            }
            ncd:select root ;
            ncd:select 'root rd inner-root inner-ipv6-rp-address inner-ipv6-gro'
                     + 'up-address inner-mask-length'
                       ;
            ncd:select vrf-name ;
            ncd:select 'root rd inner-root inner-ipv6-rp-address inner-ipv6-gro'
                     + 'up-address inner-mask-length vrf-name'
                       ;
          }
        }
        container vpn-recursive-vpnv4-source {
          description 'Sublist of mldp forwarding table. It is used to get info'
                    + 'rmation of FEC whose type is vpn-recursive nested with V'
                    + 'PNv4-source type.'
                      ;
          list pub-recursive-vpnv4-source-fec {
            description 'Key info and filter parameters info.'
                        ;
            key 'root rd inner-root inner-ipv4-source-address inner-ipv4-group-'
              + 'address inner-rd type vrf-name'
                ;
            leaf root {
              description 'IPv4 root address.'
                          ;
              type ncd:ipv4-address ;
            }
            leaf rd {
              description 'RD.There are thress input format:<0-65535>:<0-429496'
                        + '7265> or <1-65535>.<0-65535>:<0-65535> or <0-255>.<0'
                        + '-255>.<0-255>.<0-255>:<0-65535>.'
                          ;
              type union {
                type ncd:asn-nn ;
                type ncd:asnd-nn ;
                type ncd:ipadd-nn ;
              }
            }
            leaf inner-root {
              description 'Inner IPv4 root address.'
                          ;
              type ncd:ipv4-address ;
            }
            leaf inner-ipv4-source-address {
              description 'Inner IPv4 multicast source address.'
                          ;
              type ncd:ipv4-address ;
            }
            leaf inner-ipv4-group-address {
              description 'Inner IPv4 multicast group address.'
                          ;
              type ncd:ipv4-address ;
            }
            leaf inner-rd {
              description 'Inner RD.There are thress input format:<0-65535>:<0-'
                        + '4294967265> or <1-65535>.<0-65535>:<0-65535> or <0-2'
                        + '55>.<0-255>.<0-255>.<0-255>:<0-65535>.'
                          ;
              type union {
                type ncd:asn-nn ;
                type ncd:asnd-nn ;
                type ncd:ipadd-nn ;
              }
            }
            leaf type {
              description 'A value distinguishes network is global or VPN.'
                          ;
              type enumeration {
                enum global {
                  value 0 ;
                }
                enum vpn {
                  value 1 ;
                }
              }
            }
            leaf vrf-name {
              description 'VRF name.'
                          ;
              type string {
                length 0..35 ;
              }
            }
            container nexthop-entries {
              description 'Outgoing infomation of FEC whose type is vpn-recursi'
                        + 've nested with VPNv4-source type.'
                          ;
              list nexthop-entry {
                description 'A entry of Outgoing infomation, include nexthop\ou'
                          + 'tgong interface\outgong label and so on.'
                            ;
                key num ;
                leaf num {
                  description '"num" is  a speical id, which is used to disting'
                            + 'uish different out segments who has the same fec'
                            + ' type.'
                              ;
                  type uint32 ;
                }
                leaf type {
                  description 'A value distinguishes network is global or VPN.'
                              ;
                  type enumeration {
                    enum global {
                      value 0 ;
                    }
                    enum vpn {
                      value 1 ;
                    }
                  }
                }
                leaf aggregate-nexthop-vrf {
                  description 'VRF name.'
                              ;
                  type string {
                    length 1..35 ;
                  }
                }
                leaf nexthop {
                  description 'The IP address of the next hop of this lsp.'
                              ;
                  type ncd:ipv4-address ;
                }
                leaf out-interface {
                  description 'The name of the outcoming interface.'
                              ;
                  type string {
                    length 1..31 ;
                  }
                }
                leaf out-label {
                  description 'The outgoing label of this LSP.'
                              ;
                  type uint32 ;
                }
              }
            }
            ncd:select root ;
            ncd:select 'root rd inner-root inner-ipv4-source-address inner-ipv4'
                     + '-group-address inner-rd'
                       ;
            ncd:select vrf-name ;
            ncd:select 'root rd inner-root inner-ipv4-source-address inner-ipv4'
                     + '-group-address inner-rd vrf-name'
                       ;
          }
        }
        container vpn-recursive-vpnv6-source {
          description 'Sublist of mldp forwarding table. It is used to get info'
                    + 'rmation of FEC whose type is vpn-recursive nested with V'
                    + 'PNv6-source type.'
                      ;
          list vpn-recursive-vpnv6-source-fec {
            description 'Key info and filter parameters info.'
                        ;
            key 'root rd inner-root inner-ipv6-source-address inner-ipv6-group-'
              + 'address inner-rd type vrf-name'
                ;
            leaf root {
              description 'IPv4 root address.'
                          ;
              type ncd:ipv4-address ;
            }
            leaf rd {
              description 'RD.There are thress input format:<0-65535>:<0-429496'
                        + '7265> or <1-65535>.<0-65535>:<0-65535> or <0-255>.<0'
                        + '-255>.<0-255>.<0-255>:<0-65535>.'
                          ;
              type union {
                type ncd:asn-nn ;
                type ncd:asnd-nn ;
                type ncd:ipadd-nn ;
              }
            }
            leaf inner-root {
              description 'Inner IPv4 root address.'
                          ;
              type ncd:ipv4-address ;
            }
            leaf inner-ipv6-source-address {
              description 'Inner IPv6 multicast source address.'
                          ;
              type ncd:ipv6-address ;
            }
            leaf inner-ipv6-group-address {
              description 'Inner IPv6 multicast group address.'
                          ;
              type ncd:ipv6-address ;
            }
            leaf inner-rd {
              description 'Inner RD.There are thress input format:<0-65535>:<0-'
                        + '4294967265> or <1-65535>.<0-65535>:<0-65535> or <0-2'
                        + '55>.<0-255>.<0-255>.<0-255>:<0-65535>.'
                          ;
              type union {
                type ncd:asn-nn ;
                type ncd:asnd-nn ;
                type ncd:ipadd-nn ;
              }
            }
            leaf type {
              description 'A value distinguishes network is global or VPN.'
                          ;
              type enumeration {
                enum global {
                  value 0 ;
                }
                enum vpn {
                  value 1 ;
                }
              }
            }
            leaf vrf-name {
              description 'VRF name.'
                          ;
              type string {
                length 0..35 ;
              }
            }
            container nexthop-entries {
              description 'Outgoing infomation of FEC whose type is vpn-recursi'
                        + 've nested with VPNv6-source type.'
                          ;
              list nexthop-entry {
                description 'A entry of Outgoing infomation, include nexthop\ou'
                          + 'tgong interface\outgong label and so on.'
                            ;
                key num ;
                leaf num {
                  description '"num" is  a speical id, which is used to disting'
                            + 'uish different out segments who has the same fec'
                            + ' type.'
                              ;
                  type uint32 ;
                }
                leaf type {
                  description 'A value distinguishes network is global or VPN.'
                              ;
                  type enumeration {
                    enum global {
                      value 0 ;
                    }
                    enum vpn {
                      value 1 ;
                    }
                  }
                }
                leaf aggregate-nexthop-vrf {
                  description 'VRF name.'
                              ;
                  type string {
                    length 1..35 ;
                  }
                }
                leaf nexthop {
                  description 'The IP address of the next hop of this lsp.'
                              ;
                  type ncd:ipv4-address ;
                }
                leaf out-interface {
                  description 'The name of the outcoming interface.'
                              ;
                  type string {
                    length 1..31 ;
                  }
                }
                leaf out-label {
                  description 'The outgoing label of this LSP.'
                              ;
                  type uint32 ;
                }
              }
            }
            ncd:select root ;
            ncd:select 'root rd inner-root inner-ipv6-source-address inner-ipv6'
                     + '-group-address inner-rd'
                       ;
            ncd:select vrf-name ;
            ncd:select 'root rd inner-root inner-ipv6-source-address inner-ipv6'
                     + '-group-address inner-rd vrf-name'
                       ;
          }
        }
        container vpn-recursive-vpnv4-bidir {
          description 'Sublist of mldp forwarding table. It is used to get info'
                    + 'rmation of FEC whose type is vpn-recursive nested with V'
                    + 'PNv4-bidir type.'
                      ;
          list vpn-recursive-vpnv4-bidir-fec {
            description 'Key info and filter parameters info.'
                        ;
            key 'root rd inner-root inner-ipv4-rp-address inner-ipv4-group-addr'
              + 'ess inner-mask-length inner-rd type vrf-name'
                ;
            leaf root {
              description 'IPv4 root address.'
                          ;
              type ncd:ipv4-address ;
            }
            leaf rd {
              description 'RD.There are thress input format:<0-65535>:<0-429496'
                        + '7265> or <1-65535>.<0-65535>:<0-65535> or <0-255>.<0'
                        + '-255>.<0-255>.<0-255>:<0-65535>.'
                          ;
              type union {
                type ncd:asn-nn ;
                type ncd:asnd-nn ;
                type ncd:ipadd-nn ;
              }
            }
            leaf inner-root {
              description 'Inner IPv4 root address.'
                          ;
              type ncd:ipv4-address ;
            }
            leaf inner-ipv4-rp-address {
              description 'Inner IPv4 RP address.'
                          ;
              type ncd:ipv4-address ;
            }
            leaf inner-ipv4-group-address {
              description 'Inner IPv4 multicast group address.'
                          ;
              type ncd:ipv4-address ;
            }
            leaf inner-mask-length {
              description 'Inner mask length,range from 0 to 128.'
                          ;
              type uint32 {
                range 0..128 ;
              }
            }
            leaf inner-rd {
              description 'Inner RD.There are thress input format:<0-65535>:<0-'
                        + '4294967265> or <1-65535>.<0-65535>:<0-65535> or <0-2'
                        + '55>.<0-255>.<0-255>.<0-255>:<0-65535>.'
                          ;
              type union {
                type ncd:asn-nn ;
                type ncd:asnd-nn ;
                type ncd:ipadd-nn ;
              }
            }
            leaf type {
              description 'A value distinguishes network is global or VPN.'
                          ;
              type enumeration {
                enum global {
                  value 0 ;
                }
                enum vpn {
                  value 1 ;
                }
              }
            }
            leaf vrf-name {
              description 'VRF name.'
                          ;
              type string {
                length 0..35 ;
              }
            }
            container nexthop-entries {
              description 'Outgoing infomation of FEC whose type is vpn-recursi'
                        + 've nested with VPNv4-bidir type.'
                          ;
              list nexthop-entry {
                description 'A entry of Outgoing infomation, include nexthop\ou'
                          + 'tgong interface\outgong label and so on.'
                            ;
                key num ;
                leaf num {
                  description '"num" is  a speical id, which is used to disting'
                            + 'uish different out segments who has the same fec'
                            + ' type.'
                              ;
                  type uint32 ;
                }
                leaf type {
                  description 'A value distinguishes network is global or VPN.'
                              ;
                  type enumeration {
                    enum global {
                      value 0 ;
                    }
                    enum vpn {
                      value 1 ;
                    }
                  }
                }
                leaf aggregate-nexthop-vrf {
                  description 'VRF name.'
                              ;
                  type string {
                    length 1..35 ;
                  }
                }
                leaf nexthop {
                  description 'The IP address of the next hop of this lsp.'
                              ;
                  type ncd:ipv4-address ;
                }
                leaf out-interface {
                  description 'The name of the outcoming interface.'
                              ;
                  type string {
                    length 1..31 ;
                  }
                }
                leaf out-label {
                  description 'The outgoing label of this LSP.'
                              ;
                  type uint32 ;
                }
              }
            }
            ncd:select root ;
            ncd:select 'root rd inner-root inner-ipv4-rp-address inner-ipv4-gro'
                     + 'up-address inner-mask-length inner-rd'
                       ;
            ncd:select vrf-name ;
            ncd:select 'root rd inner-root inner-ipv4-rp-address inner-ipv4-gro'
                     + 'up-address inner-mask-length inner-rd vrf-name'
                       ;
          }
        }
        container vpn-recursive-vpnv6-bidir {
          description 'Sublist of mldp forwarding table. It is used to get info'
                    + 'rmation of FEC whose type is vpn-recursive nested with V'
                    + 'PNv6-bidir type.'
                      ;
          list vpn-recursive-vpnv6-bidir-fec {
            description 'Key info and filter parameters info.'
                        ;
            key 'root rd inner-root inner-ipv6-rp-address inner-ipv6-group-addr'
              + 'ess inner-mask-length inner-rd type vrf-name'
                ;
            leaf root {
              description 'IPv4 root address.'
                          ;
              type ncd:ipv4-address ;
            }
            leaf rd {
              description 'RD.There are thress input format:<0-65535>:<0-429496'
                        + '7265> or <1-65535>.<0-65535>:<0-65535> or <0-255>.<0'
                        + '-255>.<0-255>.<0-255>:<0-65535>.'
                          ;
              type union {
                type ncd:asn-nn ;
                type ncd:asnd-nn ;
                type ncd:ipadd-nn ;
              }
            }
            leaf inner-root {
              description 'Inner IPv4 root address.'
                          ;
              type ncd:ipv4-address ;
            }
            leaf inner-ipv6-rp-address {
              description 'Inner IPv6 RP address.'
                          ;
              type ncd:ipv6-address ;
            }
            leaf inner-ipv6-group-address {
              description 'Inner IPv6 multicast group address.'
                          ;
              type ncd:ipv6-address ;
            }
            leaf inner-mask-length {
              description 'Inner mask length,range from 0 to 128.'
                          ;
              type uint32 {
                range 0..128 ;
              }
            }
            leaf inner-rd {
              description 'Inner RD.There are thress input format:<0-65535>:<0-'
                        + '4294967265> or <1-65535>.<0-65535>:<0-65535> or <0-2'
                        + '55>.<0-255>.<0-255>.<0-255>:<0-65535>.'
                          ;
              type union {
                type ncd:asn-nn ;
                type ncd:asnd-nn ;
                type ncd:ipadd-nn ;
              }
            }
            leaf type {
              description 'A value distinguishes network is global or VPN.'
                          ;
              type enumeration {
                enum global {
                  value 0 ;
                }
                enum vpn {
                  value 1 ;
                }
              }
            }
            leaf vrf-name {
              description 'VRF name.'
                          ;
              type string {
                length 0..35 ;
              }
            }
            container nexthop-entries {
              description 'Outgoing infomation of FEC whose type is vpn-recursi'
                        + 've nested with VPNv6-bidir type.'
                          ;
              list nexthop-entry {
                description 'A entry of Outgoing infomation, include nexthop\ou'
                          + 'tgong interface\outgong label and so on.'
                            ;
                key num ;
                leaf num {
                  description '"num" is  a speical id, which is used to disting'
                            + 'uish different out segments who has the same fec'
                            + ' type.'
                              ;
                  type uint32 ;
                }
                leaf type {
                  description 'A value distinguishes network is global or VPN.'
                              ;
                  type enumeration {
                    enum global {
                      value 0 ;
                    }
                    enum vpn {
                      value 1 ;
                    }
                  }
                }
                leaf aggregate-nexthop-vrf {
                  description 'VRF name.'
                              ;
                  type string {
                    length 1..35 ;
                  }
                }
                leaf nexthop {
                  description 'The IP address of the next hop of this lsp.'
                              ;
                  type ncd:ipv4-address ;
                }
                leaf out-interface {
                  description 'The name of the outcoming interface.'
                              ;
                  type string {
                    length 1..31 ;
                  }
                }
                leaf out-label {
                  description 'The outgoing label of this LSP.'
                              ;
                  type uint32 ;
                }
              }
            }
            ncd:select root ;
            ncd:select 'root rd inner-root inner-ipv6-rp-address inner-ipv6-gro'
                     + 'up-address inner-mask-length inner-rd'
                       ;
            ncd:select vrf-name ;
            ncd:select 'root rd inner-root inner-ipv6-rp-address inner-ipv6-gro'
                     + 'up-address inner-mask-length inner-rd vrf-name'
                       ;
          }
        }
        container vpn-recursive-rosen-mdt {
          description 'Sublist of mldp forwarding table. It is used to get info'
                    + 'rmation of FEC whose type is vpn-recursive nested with r'
                    + 'osen-mdt type.'
                      ;
          list vpn-recursive-rosen-mdt-fec {
            description 'Key info and filter parameters info.'
                        ;
            key 'root rd inner-root inner-vpn-id inner-mdt-num type vrf-name'
                ;
            leaf root {
              description 'IPv4 root address.'
                          ;
              type ncd:ipv4-address ;
            }
            leaf rd {
              description 'RD.There are thress input format:<0-65535>:<0-429496'
                        + '7265> or <1-65535>.<0-65535>:<0-65535> or <0-255>.<0'
                        + '-255>.<0-255>.<0-255>:<0-65535>.'
                          ;
              type union {
                type ncd:asn-nn ;
                type ncd:asnd-nn ;
                type ncd:ipadd-nn ;
              }
            }
            leaf inner-root {
              description 'Inner IPv4 root address.'
                          ;
              type ncd:ipv4-address ;
            }
            leaf inner-vpn-id {
              description 'Inner VPN ID.'
                          ;
              type string {
                length 0..15 ;
                pattern '([0-9a-fA-F]{1,6}):([0-9a-fA-F]{1,8})'
                        ;
              }
            }
            leaf inner-mdt-num {
              description 'The inner number of MDT,range from 0 to 5000.'
                          ;
              type uint32 {
                range 0..5000 ;
              }
            }
            leaf type {
              description 'A value distinguishes network is global or VPN.'
                          ;
              type enumeration {
                enum global {
                  value 0 ;
                }
                enum vpn {
                  value 1 ;
                }
              }
            }
            leaf vrf-name {
              description 'VRF name.'
                          ;
              type string {
                length 0..35 ;
              }
            }
            container nexthop-entries {
              description 'Outgoing infomation of FEC whose type is vpn-recursi'
                        + 've nested with rosen-mdt type.'
                          ;
              list nexthop-entry {
                description 'A entry of Outgoing infomation, include nexthop\ou'
                          + 'tgong interface\outgong label and so on.'
                            ;
                key num ;
                leaf num {
                  description '"num" is  a speical id, which is used to disting'
                            + 'uish different out segments who has the same fec'
                            + ' type.'
                              ;
                  type uint32 ;
                }
                leaf type {
                  description 'A value distinguishes network is global or VPN.'
                              ;
                  type enumeration {
                    enum global {
                      value 0 ;
                    }
                    enum vpn {
                      value 1 ;
                    }
                  }
                }
                leaf aggregate-nexthop-vrf {
                  description 'VRF name.'
                              ;
                  type string {
                    length 1..35 ;
                  }
                }
                leaf nexthop {
                  description 'The IP address of the next hop of this lsp.'
                              ;
                  type ncd:ipv4-address ;
                }
                leaf out-interface {
                  description 'The name of the outcoming interface.'
                              ;
                  type string {
                    length 1..31 ;
                  }
                }
                leaf out-label {
                  description 'The outgoing label of this LSP.'
                              ;
                  type uint32 ;
                }
              }
            }
            ncd:select root ;
            ncd:select 'root rd inner-root inner-vpn-id inner-mdt-num'
                       ;
            ncd:select vrf-name ;
            ncd:select 'root rd inner-root inner-vpn-id inner-mdt-num vrf-name'
                       ;
          }
        }
      }
      container mte {
        description 'lspm mpls mte forwarding table.'
                    ;
        list mte-lsp {
          description 'Lspm mpls mte key info and filter parameters info.'
                      ;
          key 'local-tunnel-id lsp-id'
              ;
          leaf local-tunnel-id {
            description 'The mte local tunnelId.'
                        ;
            type uint32 ;
          }
          leaf lsp-id {
            description 'The lsp id of mte lsp.'
                        ;
            type uint32 ;
          }
          leaf ingress-id {
            description 'The ingress id of the mte lsp.'
                        ;
            type ncd:ipv4-address ;
          }
          leaf ingress-tunnel-id {
            description 'The ingress tunnel id of the mte lsp'
                        ;
            type uint32 ;
          }
          leaf in-label {
            description 'The incoming label of this lsp.'
                        ;
            type uint32 ;
          }
          container nexthop-entries {
            description 'The entries of nexthop.'
                        ;
            list nexthop-entry {
              description 'An entry of mte LSP instance table.'
                          ;
              key num ;
              leaf num {
                description '"num" is the key of nexthop parameters. You can us'
                          + 'e it get outsegment info of one lsp.'
                            ;
                type uint8 ;
              }
              leaf type {
                description 'A value distinguishes network is global or VPN.'
                            ;
                type enumeration {
                  enum global {
                    value 0 ;
                  }
                  enum vpn {
                    value 1 ;
                  }
                }
              }
              leaf aggregate-nexthop-vrf {
                description 'VRF name.'
                            ;
                type string {
                  length 1..35 ;
                }
              }
              leaf nexthop {
                description 'The IP address of the next hop of this out segment.'
                            ;
                type ncd:ipv4-address ;
              }
              leaf out-interface {
                description 'The name of the outcoming interface.'
                            ;
                type string {
                  length 1..31 ;
                }
              }
              leaf out-label {
                description 'The outgoing label of this LSP.'
                            ;
                type uint32 ;
              }
              leaf p2mp-segment {
                description 'The MTE LSP jointed segment info.'
                            ;
                type uint32 ;
              }
            }
          }
          ncd:select in-label ;
          ncd:select local-tunnel-id ;
          ncd:select 'local-tunnel-id lsp-id'
                     ;
          ncd:select 'ingress-id ingress-tunnel-id'
                     ;
        }
        list mte-fec {
          status obsolete {
            ncd:revise-date 2021-05-13 ;
          }
          description 'Lspm mpls mte key info and filter parameters info.'
                      ;
          key 'ingress-tunnel-id p2mp-id extend-tunnel-id ingress-id egress-id '
            + 'lsp-id prehop'
              ;
          leaf ingress-tunnel-id {
            description 'The tunnelId of the ingress.'
                        ;
            type uint32 ;
          }
          leaf p2mp-id {
            description 'The p2mpId of the mte lsp.'
                        ;
            type uint32 ;
          }
          leaf extend-tunnel-id {
            description "The extend tunnelid of mte, it's really equal with ing"
                      + "ressId."
                        ;
            type uint32 ;
          }
          leaf ingress-id {
            description 'The ingress id of mte lsp.'
                        ;
            type ncd:ipv4-address ;
          }
          leaf egress-id {
            description 'The egress id of mte lsp.'
                        ;
            type ncd:ipv4-address ;
          }
          leaf lsp-id {
            description 'The lsp id of mte lsp.'
                        ;
            type uint32 ;
          }
          leaf prehop {
            description 'The IP address of the prehop of this mte lsp.'
                        ;
            type ncd:ipv4-address ;
          }
          leaf in-label {
            description 'The incoming label of this lsp.'
                        ;
            type uint32 ;
          }
          container nexthop-entries {
            description 'The entries of nexthop.'
                        ;
            list nexthop-entry {
              description 'An entry of mte LSP instance table.'
                          ;
              key num ;
              leaf num {
                description '"num" is the key of nexthop parameters. You can us'
                          + 'e it get outsegment info of one lsp.'
                            ;
                type uint8 ;
              }
              leaf type {
                description 'A value distinguishes network is global or VPN.'
                            ;
                type enumeration {
                  enum global {
                    value 0 ;
                  }
                  enum vpn {
                    value 1 ;
                  }
                }
              }
              leaf aggregate-nexthop-vrf {
                description 'VRF name.'
                            ;
                type string {
                  length 1..35 ;
                }
              }
              leaf nexthop {
                description 'The IP address of the next hop of this out segment.'
                            ;
                type ncd:ipv4-address ;
              }
              leaf out-interface {
                description 'The name of the outcoming interface.'
                            ;
                type string {
                  length 1..31 ;
                }
              }
              leaf out-label {
                description 'The outgoing label of this LSP.'
                            ;
                type uint32 ;
              }
            }
          }
          ncd:select ingress-tunnel-id ;
          ncd:select 'ingress-tunnel-id p2mp-id'
                     ;
          ncd:select 'ingress-tunnel-id p2mp-id ingress-id'
                     ;
          ncd:select in-label ;
        }
      }
      container label-forwarding-table {
        description 'A table of label forwarding information, which has label f'
                  + 'rom IPv4 LDP\IPv6 LDP and static LSP.'
                    ;
        container items {
          description 'Entries to label forward table.'
                      ;
          list item {
            description 'A entry to label forward table.'
                        ;
            key in-label ;
            leaf in-label {
              description 'Local label of this LSP in the router.'
                          ;
              type uint32 ;
            }
            leaf vrf {
              description 'Name of virtual private network.'
                          ;
              type string {
                length 1..35 ;
              }
            }
            leaf dest {
              description 'The destination IP address of this route.'
                          ;
              type string {
                length 1..52 ;
              }
            }
            leaf mask-len {
              description 'Indicate the mask to be logical-ANDed with the desti'
                        + 'nation address before being compared to the value in'
                        + ' the ipRouteDest field.'
                          ;
              type uint32 ;
            }
            leaf slsp-name {
              description 'Name of static LSP instance.'
                          ;
              type string {
                length 1..31 ;
              }
            }
            container nexthop-entries {
              description 'Outgoing infomation who have the same Dest and Mask '
                        + 'or have the same slsp name.'
                          ;
              list nexthop-entry {
                description 'A entry of Outgoing infomation, include nexthop\ou'
                          + 'tgong interface\outgong label and so on.'
                            ;
                key num ;
                leaf num {
                  description "This value is used to distinguish out segment wh"
                            + "o have the same Dest and Mask.In other words, it"
                            + "'s a speical id for out segment with the same de"
                            + "stination IP address."
                              ;
                  type uint8 {
                    range 1..255 ;
                  }
                }
                leaf nexthop-vrf {
                  description 'The outgoing VRF name.'
                              ;
                  type string ;
                }
                leaf nexthop {
                  description 'Nexthop address of this LSP.'
                              ;
                  type string {
                    length 1..45 ;
                  }
                }
                leaf out-interface {
                  description 'The interface name which uniquely identifies the'
                            + ' local interface through which the next hop of t'
                            + 'his route should be reached.'
                              ;
                  type string {
                    length 1..31 ;
                  }
                }
                leaf out-label {
                  description 'The outgoing label of this LSP.'
                              ;
                  type uint32 ;
                }
                leaf master-or-slave {
                  description 'Indicating the nexthop is master or slave.'
                              ;
                  type enumeration {
                    enum master {
                      value 1 ;
                    }
                    enum slave {
                      value 2 ;
                    }
                  }
                }
                leaf nexthop-flag {
                  description 'Indicating the nexthop is direct, undirect, r-lf'
                            + 'a or ti-lfa.'
                              ;
                  type lsp-nexthop-flag ;
                }
                leaf direct-nexthop {
                  description 'Actually used for the next hop of packet forward'
                            + 'ing; when the next hop is R-LFA or TILFA, the va'
                            + 'lues of nexthop leaf and direct-nexthop leaf are'
                            + ' different.'
                              ;
                  type string {
                    length 1..45 ;
                  }
                }
                leaf direct-out-label {
                  description 'The outgoing label of the forwarding nexthop; wh'
                            + 'en the nexthop is R-LFA or TI-LFA, the values of'
                            + ' out-label and direct-out-label are different.'
                              ;
                  type uint32 ;
                }
                leaf tilfa-index {
                  description 'TI-LFA index.'
                              ;
                  type uint32 ;
                }
              }
            }
            ncd:select in-label ;
          }
        }
      }
      container ipv4-fec-forwarding-table {
        description 'A forward information tabel of IPv4 FECs, which include LD'
                  + 'P and static LSP. It only show FECs who have inlabel or ou'
                  + 'tlabel.'
                    ;
        list ipv4-fec {
          description 'Forwardind information of IPv4 FEC, which include LDP an'
                    + 'd static LSP. It only show FEC who has inlabel or outlab'
                    + 'el.'
                      ;
          key 'type vrf dest mask-len'
              ;
          leaf type {
            description 'A value distinguishes FEC in global or VPN.'
                        ;
            type enumeration {
              enum global {
                value 0 ;
              }
              enum vpn {
                value 1 ;
              }
            }
          }
          leaf vrf {
            description 'VPN Routing/Forwarding instance name.'
                        ;
            type string {
              length 0..35 ;
            }
          }
          leaf dest {
            description 'The destination IP address of this route.'
                        ;
            type ncd:ipv4-address ;
          }
          leaf mask-len {
            description 'Indicate the mask to be logical-ANDed with the destina'
                      + 'tion address before being compared to the value in the'
                      + ' ipRouteDest field.'
                        ;
            type uint32 {
              range 0..32 ;
            }
          }
          leaf ldp-in-label {
            description 'Local label of this LSP in the router distributed by L'
                      + 'DP.'
                        ;
            type uint32 ;
          }
          leaf bgp-in-label {
            description 'Local label of this LSP in the router distributed by B'
                      + 'GP.'
                        ;
            type uint32 ;
          }
          leaf static-lsp-in-label {
            description 'Local label of this LSP in the router configured by St'
                      + 'atic LSP.'
                        ;
            type uint32 ;
          }
          leaf dest-input {
            description 'The destination IP address inputed by user.'
                        ;
            type ncd:ipv4-address ;
          }
          leaf sr-in-label {
            description 'The incoming label of SR LSP.'
                        ;
            type uint32 ;
          }
          container nexthop-entries {
            description 'Outgoing infomation who have the same Dest and Mask.'
                        ;
            list nexthop-entry {
              description 'A entry of Outgoing infomation, include nexthop\outg'
                        + 'ong interface\outgong label and so on.'
                          ;
              key num ;
              leaf num {
                description "This value is used to distinguish out segment who "
                          + "have the same Dest and Mask.In other words, it's a"
                          + " speical id for out segment with the same destinat"
                          + "ion IP address."
                            ;
                type uint8 ;
              }
              leaf nexthop-vrf {
                description 'The outgoing VRF name.'
                            ;
                type string {
                  length 0..35 ;
                }
              }
              leaf nexthop {
                description 'The IP address of the next hop of this route, The '
                          + 'IP address of neighbour to send.'
                            ;
                type ncd:ipv4-address ;
              }
              leaf out-interface {
                description 'The interface name which uniquely identifies the l'
                          + 'ocal interface through which the next hop of this '
                          + 'route should be reached.'
                            ;
                type string {
                  length 0..31 ;
                }
              }
              leaf out-label {
                description 'The outgoing label of this LSP.'
                            ;
                type uint32 ;
              }
              leaf master-or-slave {
                description 'Indicating the nexthop is master or slave.'
                            ;
                type enumeration {
                  enum master {
                    value 1 ;
                  }
                  enum slave {
                    value 2 ;
                  }
                }
              }
              leaf bytes-switched-num {
                description 'The number of swithed bytes'
                            ;
                type string ;
                default ''
                        ;
              }
              leaf packets-switched-num {
                description 'The number of swithed packets'
                            ;
                type string ;
                default ''
                        ;
              }
              leaf nexthop-flag {
                description 'Indicating the nexthop is direct, undirect, r-lfa '
                          + 'or ti-lfa.'
                            ;
                type lsp-nexthop-flag ;
              }
              leaf direct-nexthop {
                description 'Actually used for the nexthop of packet forwarding'
                          + '; when the nexthop is R-LFA or TILFA, the values o'
                          + 'f nexthop leaf and direct-nexthop leaf are differe'
                          + 'nt.'
                            ;
                type ncd:ipv4-address ;
              }
              leaf direct-out-label {
                description 'The outgoing label of the forwarding nexthop; when'
                          + ' the nexthop is R-LFA or TI-LFA, the values of out'
                          + '-label leaf and direct-out-label leaf are differen'
                          + 't.'
                            ;
                type uint32 ;
              }
              leaf tilfa-index {
                description 'TI-LFA index.'
                            ;
                type uint32 ;
              }
              leaf nexthop-belong {
                description 'The nexthop belongs, such as SR or DEFAULT, SR-LSP'
                          + ' nexthop belongs SR. others belong DEFAULT.'
                            ;
                type enumeration {
                  enum DEFAULT {
                    value 0 ;
                    description 'Nexthop belongs to LDP,BGP or STATIC-LSP.'
                                ;
                  }
                  enum SR {
                    value 1 ;
                    description 'Nexthop belongs to SR.'
                                ;
                  }
                }
              }
            }
          }
          ncd:select dest-input ;
          ncd:select 'mask-len dest-input'
                     ;
          ncd:select vrf ;
          ncd:select 'vrf dest-input'
                     ;
          ncd:select 'vrf mask-len dest-input'
                     ;
        }
      }
      container ipv6-forwarding-table {
        description 'A forward information tabel of IPv6 FECs, which include LD'
                  + 'P. It only show FECs who have inlabel or outlabel.'
                    ;
        list ipv6-fec {
          description 'Forwardind information of IPv6 FEC, which include LDP. I'
                    + 't only show FEC who has inlabel or outlabel.'
                      ;
          key 'type vrf dest mask-len'
              ;
          leaf type {
            description 'A value distinguishes FEC in global or VPN.'
                        ;
            type enumeration {
              enum global {
                value 0 ;
              }
              enum vpn {
                value 1 ;
              }
            }
          }
          leaf vrf {
            description 'VPN Routing/Forwarding instance name.'
                        ;
            type string {
              length 0..35 ;
            }
          }
          leaf dest {
            description 'The destination IP address of this route.'
                        ;
            type ncd:ipv6-address ;
          }
          leaf mask-len {
            description 'Indicate the mask to be logical-ANDed with the destina'
                      + 'tion address before being compared to the value in the'
                      + ' ipRouteDest field.'
                        ;
            type uint32 {
              range 0..128 ;
            }
          }
          leaf in-label {
            description 'Local label of this LSP in the router distributed by L'
                      + 'DP.'
                        ;
            type uint32 ;
          }
          leaf dest-input {
            description 'The input destination IP address of this route.'
                        ;
            type ncd:ipv6-address ;
          }
          leaf sr-in-label {
            description 'The incoming label of SR LSP.'
                        ;
            type uint32 ;
          }
          container nexthop-entries {
            description 'Outgoing infomation who have the same Dest and Mask.'
                        ;
            list nexthop-entry {
              description 'A entry of Outgoing infomation, include nexthop\outg'
                        + 'ong interface\outgong label and so on.'
                          ;
              key num ;
              leaf num {
                description "This value is used to distinguish out segment who "
                          + "have the same Dest and Mask.In other words, it's a"
                          + " speical id for out segment with the same destinat"
                          + "ion IP address."
                            ;
                type uint8 {
                  range 1..64 ;
                }
              }
              leaf nexthop-vrf {
                description 'The outgoing VRF name.'
                            ;
                type string {
                  length 0..35 ;
                }
              }
              leaf nexthop {
                description 'The IP address of the next hop of this route, The '
                          + 'IP address of neighbour to send.'
                            ;
                type ncd:ipv6-address ;
              }
              leaf out-interface {
                description 'The interface name which uniquely identifies the l'
                          + 'ocal interface through which the next hop of this '
                          + 'route should be reached.'
                            ;
                type string ;
              }
              leaf out-label {
                description 'The outgoing label of this LSP.'
                            ;
                type uint32 ;
              }
              leaf master-or-slave {
                description 'It is used to Identifying master or slave of the L'
                          + 'SP when FRR is on.'
                            ;
                type enumeration {
                  enum master {
                    value 1 ;
                  }
                  enum slave {
                    value 2 ;
                  }
                }
              }
              leaf nexthop-flag {
                description 'Indicating the nexthop is direct, undirect, r-lfa '
                          + 'or ti-lfa.'
                            ;
                type lsp-nexthop-flag ;
              }
              leaf direct-nexthop {
                description 'Actually used for the nexthop of packet forwarding'
                          + '; when the nexthop is R-LFA or TILFA, the values o'
                          + 'f nexthop leaf and direct-nexthop leaf are differe'
                          + 'nt.'
                            ;
                type ncd:ipv6-address ;
              }
              leaf direct-out-label {
                description 'The outgoing label of the forwarding nexthop; when'
                          + ' the nexthop is R-LFA or TI-LFA, the values of out'
                          + '-label leaf and direct-out-label leaf are differen'
                          + 't.'
                            ;
                type uint32 ;
              }
              leaf tilfa-index {
                description 'TI-LFA index.'
                            ;
                type uint32 ;
              }
              leaf nexthop-belong {
                description 'The nexthop belongs, such as SR or DEFAULT. SR-LSP'
                          + ' nexthop belongs SR. others belong DEFAULT.'
                            ;
                type enumeration {
                  enum DEFAULT {
                    value 0 ;
                    description 'Nexthop belongs to LDP,BGP or STATIC-LSP.'
                                ;
                  }
                  enum SR {
                    value 1 ;
                    description 'Nexthop belongs to SR.'
                                ;
                  }
                }
              }
            }
          }
          ncd:select dest-input ;
          ncd:select 'mask-len dest-input'
                     ;
          ncd:select vrf ;
          ncd:select 'vrf dest-input'
                     ;
          ncd:select 'vrf mask-len dest-input'
                     ;
        }
      }
      container slsp-forwarding-tabel {
        description 'A forwarding table of static LSPs. It only show FECs who h'
                  + 'ave inlabel or outlabel.'
                    ;
        list slsp-instance {
          description 'Forwardind information of static LSP instance. It only s'
                    + 'how FEC who has inlabel or outlabel.'
                      ;
          key lsp-name ;
          leaf lsp-name {
            description 'Name of static LSP instance.'
                        ;
            type string {
              length 1..31 ;
            }
          }
          leaf in-label {
            description 'Local label of this LSP in the router.'
                        ;
            type uint32 ;
          }
          container nexthop-entries {
            description 'Outgoing infomation who have the same slsp name.'
                        ;
            list nexthop-entry {
              description 'A entry of Outgoing infomation, include nexthop\outg'
                        + 'ong interface\outgong label and so on.'
                          ;
              key num ;
              leaf num {
                description "This value is used to distinguish out segment who "
                          + "have the same static lsp name.In other words, it's"
                          + " a speical id for out segment with the same static"
                          + " lsp name."
                            ;
                type uint8 ;
              }
              leaf nexthop {
                description 'The IP address of the next hop of this route, The '
                          + 'IP address of neighbour to send.'
                            ;
                type ncd:ipv4-address ;
              }
              leaf out-interface {
                description 'The interface name which uniquely identifies the l'
                          + 'ocal interface through which the next hop of this '
                          + 'route should be reached.'
                            ;
                type string ;
              }
              leaf out-label {
                description 'The outgoing label of this LSP.'
                            ;
                type uint32 ;
              }
              leaf master-or-slave {
                description 'It is used to Identifying master or slave of the L'
                          + 'SP when FRR is on.'
                            ;
                type enumeration {
                  enum master {
                    value 1 ;
                  }
                  enum slave {
                    value 2 ;
                  }
                }
              }
            }
          }
          ncd:select lsp-name ;
        }
      }
    }
    container bier {
      if-feature lspm-bier ;
      description 'State information of BIER forwarding.'
                  ;
      container bitstring-length-table {
        description 'BIER BitString length of current Sub-domain forward use.'
                    ;
        list items {
          description 'BitString length items of current Sub-domain forward use.'
                      ;
          key sub-domain ;
          leaf sub-domain {
            description 'BIER Sub-domain ID.'
                        ;
            type uint8 ;
          }
          leaf bitstring-length {
            description 'BIER BitString length.'
                        ;
            type uint16 ;
          }
          ncd:select sub-domain ;
        }
      }
      container label-forwarding-table {
        description 'BIER label forwarding table.'
                    ;
        list items {
          description 'Items of BIER label forwarding table.'
                      ;
          key in-label ;
          leaf in-label {
            description 'BIER In-label.'
                        ;
            type uint32 ;
          }
          leaf sub-domain {
            description 'BIER Sub-domain ID.'
                        ;
            type uint8 ;
          }
          leaf bitstring-len {
            description 'BIER BitString length.'
                        ;
            type uint16 ;
          }
          leaf si {
            description 'Set Identifier.'
                        ;
            type uint16 ;
          }
          ncd:select in-label ;
        }
      }
      container bfr-id-forwarding-table {
        description 'BIER BFR ID(Bit-Forwarding Router ID) forwarding table.'
                    ;
        list items {
          description 'Items of BFR ID forwarding.'
                      ;
          key 'sub-domain bfr-id'
              ;
          leaf sub-domain {
            description 'BIER Sub-domain ID.'
                        ;
            type uint8 ;
          }
          leaf bfr-id {
            description 'BFR ID.'
                        ;
            type uint32 ;
          }
          leaf prefix {
            description 'BFR prefix.'
                        ;
            type ncd:ipv4-address ;
          }
          container nexthop-entries {
            description 'Out entries of bfr-id forwarding.'
                        ;
            list nexthop-entry {
              description 'Out entry list of BFR ID forwarding.'
                          ;
              key num ;
              leaf num {
                description 'Serial number of the nexthop.'
                            ;
                type uint8 ;
              }
              leaf out-interface {
                description 'Direct out interface, undirect is NULL.'
                            ;
                type string {
                  length 1..31 ;
                }
              }
              leaf direct-nexthop {
                description 'Direct next hop,undirect is NULL.'
                            ;
                type ncd:ipv4-address ;
              }
              leaf bier-nexthop {
                description 'BIER nexthop.'
                            ;
                type ncd:ipv4-address ;
              }
              leaf master-or-slave {
                description 'Master or slave of the nexthop entry.'
                            ;
                type enumeration {
                  enum master {
                    value 1 ;
                  }
                  enum slave {
                    value 2 ;
                  }
                }
              }
            }
          }
          ncd:select 'sub-domain bfr-id'
                     ;
        }
      }
      container fec-forwarding-table {
        description 'BIER FEC forwarding table.'
                    ;
        list items {
          description 'Items of BIER FEC forwarding.'
                      ;
          key 'sub-domain prefix'
              ;
          leaf sub-domain {
            description 'BEIR Sub-domain ID.'
                        ;
            type uint8 ;
          }
          leaf bfr-id {
            description 'BFR ID.'
                        ;
            type uint32 ;
          }
          leaf prefix {
            description 'BFR prefix.'
                        ;
            type ncd:ipv4-address ;
          }
          container nexthop-entries {
            description 'Out entries of BIER FEC forwarding.'
                        ;
            list nexthop-entry {
              description 'Out entries list of BIER FEC forwarding.'
                          ;
              key num ;
              leaf num {
                description 'Serial number of the out entry.'
                            ;
                type uint8 ;
              }
              leaf out-interface {
                description 'Direct out interface, undirect is NULL.'
                            ;
                type string {
                  length 1..31 ;
                }
              }
              leaf direct-nexthop {
                description 'Direct next hop,undirect is NULL.'
                            ;
                type ncd:ipv4-address ;
              }
              leaf bier-nexthop {
                description 'BIER nexthop.'
                            ;
                type ncd:ipv4-address ;
              }
              leaf master-or-slave {
                description 'Master or slave of the out entry.'
                            ;
                type enumeration {
                  enum master {
                    value 1 ;
                  }
                  enum slave {
                    value 2 ;
                  }
                }
              }
            }
          }
          ncd:select 'sub-domain prefix'
                     ;
        }
      }
      container bier-nexthop-table {
        description 'BIER nexthop table.'
                    ;
        list items {
          description 'Items of BIER nexthop table.'
                      ;
          key 'sub-domain bier-nexthop is-direct out-interface direct-nexthop'
              ;
          leaf sub-domain {
            description 'BIER Sub-domain ID.'
                        ;
            type uint8 ;
          }
          leaf bier-nexthop {
            description 'BIER nexthop.'
                        ;
            type ncd:ipv4-address ;
          }
          leaf is-direct {
            description 'Whether this nextHop is directly connected.'
                        ;
            type enumeration {
              enum DIRECT {
                value 1 ;
                description 'Nexthop is direct'
                            ;
              }
              enum UNDIRECT {
                value 0 ;
                description 'nexthop is undirect'
                            ;
              }
            }
          }
          leaf out-interface {
            description 'The interface of the direct nextHop.'
                        ;
            type string {
              length 0..31 ;
            }
          }
          leaf direct-nexthop {
            description 'Address of the direct nexthop.'
                        ;
            type ncd:ipv4-address ;
          }
          container bfr-id-lists {
            description 'BFR ID lists of the nexthop forwarding.'
                        ;
            list bfr-id-list {
              description 'BFR ID list of the nexthop forwarding table.'
                          ;
              key num ;
              leaf num {
                description 'Serial number of BFR ID list.'
                            ;
                type uint8 ;
              }
              leaf bfr-id {
                description 'BFR ID.'
                            ;
                type uint32 ;
              }
              leaf prefix {
                description 'BFR prefix.'
                            ;
                type ncd:ipv4-address ;
              }
            }
          }
          ncd:select 'sub-domain bier-nexthop'
                     ;
        }
      }
    }
    container sr-te {
      if-feature lspm-sr ;
      description 'SR TE information'
                  ;
      container sr-tunnel {
        description 'SR tunnel information.'
                    ;
        list sr-tunnels {
          description 'SR tunnel lists.'
                      ;
          key local-tunnel-id ;
          leaf local-tunnel-id {
            description "Tunnel's local tunnel ID,rang is [1-4294967295]."
                        ;
            type uint32 {
              range 1..4294967295 ;
            }
          }
          leaf ingress-tunnel-id {
            description "Tunnel's ingress tunnel ID."
                        ;
            type uint32 ;
          }
          leaf ingress-id {
            description "Tunnel's ingress ID."
                        ;
            type ncd:ipv4-address ;
          }
          leaf ipv6-ingress-id {
            description "Tunnel's IPv6 ingress ID."
                        ;
            type ncd:ipv6-address ;
          }
          leaf egress-id {
            description "Tunnel's egress ID."
                        ;
            type ncd:ipv4-address ;
          }
          leaf ipv6-egress-id {
            description "Tunnel's IPv6 egress ID."
                        ;
            type ncd:ipv6-address ;
          }
          leaf status {
            description "Tunnel's forwarding status,OK:sigal is ok,SF:signal fa"
                      + "ult,SD:signal degrade."
                        ;
            type te-forward-status ;
          }
          container sr-path {
            description "Tunnel path's information."
                        ;
            list sr-paths {
              description "Tunnel path's lists."
                          ;
              key 'path-id direction'
                  ;
              leaf path-id {
                description "The tunnel path's ID,rang is [1-65535]."
                            ;
                type uint16 {
                  range 1..65535 ;
                }
              }
              leaf direction {
                description "The tunnel path's direction,POSITIVE or REVERSE."
                            ;
                type te-lsp-direction ;
              }
              leaf role {
                description "The tunnel path's role:INVALID,INGRESS, TRANSIT or"
                          + " EGRESS."
                            ;
                type te-lsp-role ;
              }
              leaf splice-in-label {
                description "The tunnel path's splice in label."
                            ;
                type uint32 {
                  range 16..1048575 ;
                }
              }
              leaf splice-out-label {
                description "The tunnel path's splice out label."
                            ;
                type uint32 ;
              }
              leaf is-active {
                description 'The tunnel path is active or unactive.'
                            ;
                type enumeration {
                  enum active {
                    value 1 ;
                  }
                  enum unactive {
                    value 0 ;
                  }
                }
              }
              leaf state {
                description "The tunnel path's self state,OK:sigal is ok,SF:sig"
                          + "nal fault,SD:signal degrade."
                            ;
                type te-lsp-self-state ;
              }
              container sr-segment {
                description "Tunnel path's segment information."
                            ;
                list sr-segments {
                  description "Tunnel path's segment lists."
                              ;
                  key number ;
                  leaf number {
                    description 'The number of the segment,rang is [1-255].'
                                ;
                    type uint8 {
                      range 1..255 ;
                    }
                  }
                  choice segment {
                    description 'Classification of segmented information.'
                                ;
                    case ipv4-node {
                      description 'Node type of segment information.'
                                  ;
                      leaf node-in-label {
                        description 'The incoming label to this node.'
                                    ;
                        type uint32 ;
                      }
                      leaf destination-id {
                        description 'The loopback address of the node.'
                                    ;
                        type ncd:ipv4-address ;
                      }
                    }
                    case ipv4-adjacency {
                      description 'Adjacency type segment information.'
                                  ;
                      leaf adj-in-label {
                        description 'The incoming label to this adjacency.'
                                    ;
                        type uint32 ;
                      }
                      leaf local-ip {
                        description 'The front interface link address of this a'
                                  + 'djacency.'
                                    ;
                        type ncd:ipv4-address ;
                      }
                      leaf local-id {
                        description 'The front loopback interface address of th'
                                  + 'is adjacency.'
                                    ;
                        type ncd:ipv4-address ;
                      }
                      leaf remote-ip {
                        description 'The remote link interface address of this '
                                  + 'adjacency.'
                                    ;
                        type ncd:ipv4-address ;
                      }
                      leaf remote-id {
                        description 'The remote loopback interface address of t'
                                  + 'his adjacency.'
                                    ;
                        type ncd:ipv4-address ;
                      }
                    }
                    case default {
                      description 'Default type of segment information.'
                                  ;
                      leaf in-label {
                        description 'Incoming label value.'
                                    ;
                        type uint32 ;
                      }
                    }
                    case ipv6-node {
                      description 'IPv6 node type of segment information.'
                                  ;
                      leaf ipv6-node-inlabel {
                        description 'The incoming label to this IPv6 node.'
                                    ;
                        type int32 ;
                      }
                      leaf ipv6-node-id {
                        description 'The loopback IPv6 address of the node.'
                                    ;
                        type ncd:ipv6-address ;
                      }
                    }
                    case ipv6-adjacency {
                      description 'IPv6 adjacency type segment information.'
                                  ;
                      leaf ipv6-adj-inlabel {
                        description 'The IPv6 incoming label to this adjacency.'
                                    ;
                        type uint32 ;
                      }
                      leaf local-ipv6 {
                        description 'The front IPv6 link address of this adjace'
                                  + 'ncy.'
                                    ;
                        type ncd:ipv6-address ;
                      }
                      leaf remote-ipv6 {
                        description 'The remote link IPv6 address of this adjac'
                                  + 'ency.'
                                    ;
                        type ncd:ipv6-address ;
                      }
                    }
                    case srv6 {
                      description 'SRv6 type segment information.'
                                  ;
                      leaf srv6-id {
                        description 'SRv6 segment ID.'
                                    ;
                        type ncd:ipv6-address ;
                      }
                    }
                    case ids-adjacency {
                      description 'ID adjacency type segment information.'
                                  ;
                      leaf ids-adj-inlabel {
                        description 'The incoming label to this adjacency.'
                                    ;
                        type uint32 ;
                      }
                      leaf front-node-id {
                        description 'The front loopback interface address of th'
                                  + 'is adjacency.'
                                    ;
                        type ncd:ipv4-address ;
                      }
                      leaf front-id {
                        description 'The front loopback interface address of th'
                                  + 'is adjacency.'
                                    ;
                        type uint32 ;
                      }
                      leaf end-node-id {
                        description 'The remote loopback interface address of t'
                                  + 'his adjacency.'
                                    ;
                        type ncd:ipv4-address ;
                      }
                      leaf end-id {
                        description 'The remote ID of this adjacency.'
                                    ;
                        type uint32 ;
                      }
                    }
                  }
                }
              }
            }
          }
          ncd:select local-tunnel-id ;
        }
      }
      container splice-lsp {
        description 'splice path information.'
                    ;
        list splice-lsp {
          description "splice path's list."
                      ;
          key splice-label ;
          leaf splice-label {
            description "splice path's splice label,range is [16-1048575]."
                        ;
            type uint32 {
              range 16..1048575 ;
            }
          }
          leaf ingress-tunnel-id {
            description "Splice path's ingress tunnel ID."
                        ;
            type uint32 ;
          }
          leaf ingress-id {
            description "Splice path's ingress ID."
                        ;
            type ncd:ipv4-address ;
          }
          leaf ipv6-ingress-id {
            description "Splice path's IPv6 ingress ID."
                        ;
            type ncd:ipv6-address ;
          }
          leaf egress-id {
            description "Splice path's engress ID."
                        ;
            type ncd:ipv4-address ;
          }
          leaf ipv6-egress-id {
            description "Splice path's IPv6 egress ID."
                        ;
            type ncd:ipv6-address ;
          }
          leaf path-id {
            description "Splice path's ID."
                        ;
            type uint16 ;
          }
          leaf direction {
            description "Splice path's direction,POSITIVE or REVERSE."
                        ;
            type te-lsp-direction ;
          }
          leaf role {
            description "Splice path's role:INVALID,TRANSIT or EGRESS."
                        ;
            type te-lsp-role ;
          }
          leaf out-label {
            description "Splice path's out label."
                        ;
            type uint32 ;
          }
          leaf state {
            description "Splice path's state,OK:sigal is ok,SF:signal fault,SD:"
                      + "signal degrade."
                        ;
            type te-lsp-self-state ;
          }
          container sr-segment {
            description "Splice path's segment information."
                        ;
            list sr-segments {
              description "Splice path's segment lists."
                          ;
              key number ;
              leaf number {
                description 'The number of the segment,rang is [1-255].'
                            ;
                type uint8 {
                  range 1..255 ;
                }
              }
              choice segment {
                description 'Classification of segmented information.'
                            ;
                case ipv4-node {
                  description 'Node type of segment information.'
                              ;
                  leaf node-in-label {
                    description 'The incoming label to this node.'
                                ;
                    type uint32 ;
                  }
                  leaf destination-id {
                    description 'The loopback address of the node.'
                                ;
                    type ncd:ipv4-address ;
                  }
                }
                case ipv4-adjacency {
                  description 'Adjacency type segment information.'
                              ;
                  leaf adj-in-label {
                    description 'The incoming label to this adjacency.'
                                ;
                    type uint32 ;
                  }
                  leaf local-ip {
                    description 'The front interface link address of this adjac'
                              + 'ency.'
                                ;
                    type ncd:ipv4-address ;
                  }
                  leaf local-id {
                    description 'The front loopback interface address of this a'
                              + 'djacency.'
                                ;
                    type ncd:ipv4-address ;
                  }
                  leaf remote-ip {
                    description 'The remote link interface address of this adja'
                              + 'cency.'
                                ;
                    type ncd:ipv4-address ;
                  }
                  leaf remote-id {
                    description 'The remote loopback interface address of this '
                              + 'adjacency.'
                                ;
                    type ncd:ipv4-address ;
                  }
                }
                case default {
                  description 'Default type segment information.'
                              ;
                  leaf in-label {
                    description 'Incoming label value.'
                                ;
                    type uint32 ;
                  }
                }
                case ipv6-node {
                  description 'IPv6 node type of segment information.'
                              ;
                  leaf ipv6-node-inlabel {
                    description 'The incoming label to this IPv6 node.'
                                ;
                    type int32 ;
                  }
                  leaf ipv6-node-id {
                    description 'The loopback IPv6 address of the node.'
                                ;
                    type ncd:ipv6-address ;
                  }
                }
                case ipv6-adjacency {
                  description 'IPv6 adjacency type segment information.'
                              ;
                  leaf ipv6-adj-inlabel {
                    description 'The IPv6 incoming label to this adjacency.'
                                ;
                    type uint32 ;
                  }
                  leaf local-ipv6 {
                    description 'The front IPv6 link address of this adjacency.'
                                ;
                    type ncd:ipv6-address ;
                  }
                  leaf remote-ipv6 {
                    description 'The remote link IPv6 address of this adjacency.'
                                ;
                    type ncd:ipv6-address ;
                  }
                }
                case ids-adjacency {
                  description 'ID adjacency type segment information.'
                              ;
                  leaf ids-adj-inlabel {
                    description 'The incoming label to this adjacency.'
                                ;
                    type uint32 ;
                  }
                  leaf front-node-id {
                    description 'The front loopback interface address of this a'
                              + 'djacency.'
                                ;
                    type ncd:ipv4-address ;
                  }
                  leaf front-id {
                    description 'The front loopback interface address of this a'
                              + 'djacency.'
                                ;
                    type uint32 ;
                  }
                  leaf end-node-id {
                    description 'The remote loopback interface address of this '
                              + 'adjacency.'
                                ;
                    type ncd:ipv4-address ;
                  }
                  leaf end-id {
                    description 'The remote ID of this adjacency.'
                                ;
                    type uint32 ;
                  }
                }
              }
            }
          }
          ncd:select splice-label ;
        }
      }
    }
    container adjacency-sid {
      description 'The query node for adjacency SID information.'
                  ;
      container ipv4-mpls {
        description 'The query node for IPv4 mpls adjacency SID information.'
                    ;
        container local {
          description 'The local type for IPv4 mpls adjacency SID information.'
                      ;
          list information {
            description 'Adjacency SID information.'
                        ;
            key 'local-router-id local-ip remote-router-id remote-ip local-id r'
              + 'emote-id proto'
                ;
            leaf local-router-id {
              description 'The local router ID.'
                          ;
              type ncd:ipv4-address ;
            }
            leaf local-ip {
              description 'The local IP address.'
                          ;
              type ncd:ipv4-address ;
            }
            leaf remote-router-id {
              description 'The remote router ID.'
                          ;
              type ncd:ipv4-address ;
            }
            leaf remote-ip {
              description 'The remote IP address.'
                          ;
              type ncd:ipv4-address ;
            }
            leaf local-id {
              description 'The local ID.'
                          ;
              type uint32 ;
            }
            leaf remote-id {
              description 'The remote ID.'
                          ;
              type uint32 ;
            }
            leaf proto {
              description 'The proto type.'
                          ;
              type proto-type ;
            }
            leaf out-interface {
              description 'The out interface.'
                          ;
              type ncd:string-all ;
            }
            leaf status {
              description 'The status of adjacency SID.'
                          ;
              type adjacency-sid-status ;
            }
            container sid-list {
              description 'The adjacency SID list.'
                          ;
              list sid {
                description 'The adjacency SID info.'
                            ;
                key sid-index ;
                leaf sid-index {
                  description 'The adjacency SID index.'
                              ;
                  type uint8 ;
                }
                leaf sid-label {
                  description 'The label of adjacency SID.'
                              ;
                  type uint32 ;
                }
                leaf primary-protect-tunnel {
                  description 'The primary protect tunnel ID.'
                              ;
                  type uint32 ;
                }
                leaf primary-protect-tunnel-status {
                  description 'The primary protect tunnel status.'
                              ;
                  type te-forward-status ;
                }
                leaf primary-protect-status {
                  description 'The primary protect status.'
                              ;
                  type adjacency-sid-protect-status ;
                }
                leaf secondary-protect-tunnel {
                  description 'The secondary protect tunnel ID.'
                              ;
                  type uint32 ;
                }
                leaf secondary-protect-tunnel-status {
                  description 'The secondary protect tunnel status.'
                              ;
                  type te-forward-status ;
                }
                leaf secondary-protect-status {
                  description 'The secondary protect status.'
                              ;
                  type adjacency-sid-protect-status ;
                }
                leaf weight {
                  description 'The weight.'
                              ;
                  type uint32 ;
                }
                leaf flag {
                  description 'The flag,V6:IPv6,BP:BACKUP,GP:GROUP,PT:PERSISTEN'
                            + 'T.'
                              ;
                  type ncd:string-all ;
                }
              }
            }
            ncd:select 'local-router-id remote-router-id local-id remote-id'
                       ;
            ncd:select 'local-router-id local-ip remote-router-id remote-ip'
                       ;
          }
        }
      }
    }
    container sr-tilfa {
      description "SR TI-LFA's information."
                  ;
      list tilfa-list {
        description "Tunnel path's lists."
                    ;
        key index ;
        leaf index {
          description "The TI-LFA path's ID."
                      ;
          type uint32 ;
        }
        leaf state {
          description "The tunnel path's self state,OK:sigal is ok,SF:signal fa"
                    + "ult,SD:signal degrade."
                      ;
          type te-lsp-self-state ;
        }
        container segment {
          description "Tunnel path's segment information."
                      ;
          list segment-list {
            description "Tunnel path's segment lists."
                        ;
            key number ;
            leaf number {
              description 'The number of the segment.'
                          ;
              type uint8 ;
            }
            choice segment {
              description 'Classification of segmented information.'
                          ;
              case ipv4-node {
                description 'Node type of segment information.'
                            ;
                leaf node-in-label {
                  description 'The incoming label to this node.'
                              ;
                  type uint32 ;
                }
                leaf destination-id {
                  description 'The loopback address of the node.'
                              ;
                  type ncd:ipv4-address ;
                }
              }
              case ipv4-adjacency {
                description 'Adjacency type segment information.'
                            ;
                leaf adj-in-label {
                  description 'The incoming label to this adjacency.'
                              ;
                  type uint32 ;
                }
                leaf local-ip {
                  description 'The front interface link address of this adjacen'
                            + 'cy.'
                              ;
                  type ncd:ipv4-address ;
                }
                leaf remote-ip {
                  description 'The remote link interface address of this adjace'
                            + 'ncy.'
                              ;
                  type ncd:ipv4-address ;
                }
              }
              case ipv6-node {
                description 'IPv6 node type of segment information.'
                            ;
                leaf ipv6-node-inlabel {
                  description 'The incoming label to this IPv6 node.'
                              ;
                  type int32 ;
                }
                leaf ipv6-node-id {
                  description 'The loopback IPv6 address of the node.'
                              ;
                  type ncd:ipv6-address ;
                }
              }
              case ipv6-adjacency {
                description 'IPv6 adjacency type segment information.'
                            ;
                leaf ipv6-adj-inlabel {
                  description 'The IPv6 incoming label to this adjacency.'
                              ;
                  type uint32 ;
                }
                leaf local-ipv6 {
                  description 'The front IPv6 link address of this adjacency.'
                              ;
                  type ncd:ipv6-address ;
                }
                leaf remote-ipv6 {
                  description 'The remote link IPv6 address of this adjacency.'
                              ;
                  type ncd:ipv6-address ;
                }
              }
              case srv6 {
                description 'SRv6 type segment information.'
                            ;
                leaf srv6-id {
                  description 'SRv6 segment ID.'
                              ;
                  type ncd:ipv6-address ;
                }
              }
              case ids-adjacency {
                description 'ID adjacency type segment information.'
                            ;
                leaf ids-adj-inlabel {
                  description 'The incoming label to this adjacency.'
                              ;
                  type uint32 ;
                }
                leaf front-node-id {
                  description 'The front loopback interface address of this adj'
                            + 'acency.'
                              ;
                  type string {
                    length 1..45 ;
                  }
                }
                leaf front-id {
                  description 'The front loopback interface address of this adj'
                            + 'acency.'
                              ;
                  type uint32 ;
                }
                leaf end-node-id {
                  description 'The remote loopback interface address of this ad'
                            + 'jacency.'
                              ;
                  type string {
                    length 1..45 ;
                  }
                }
                leaf end-id {
                  description 'The remote ID of this adjacency.'
                              ;
                  type uint32 ;
                }
              }
            }
          }
        }
      }
    }
  }
  container configuration {
    description 'Configuration model information.'
                ;
    container lspm {
      description 'LSP management configuration information.'
                  ;
      container static-lsp {
        description 'Static-lsp configuration module.'
                    ;
        presence 'Static-lsp Configuration'
                 ;
        list slsp-inst {
          description 'Configures static-lsp instance.'
                      ;
          key lsp-name ;
          leaf lsp-name {
            description 'Specifies a name of static-lsp instance.'
                        ;
            type string {
              length 1..20 ;
            }
          }
          leaf in-label {
            description 'Specifies a static incoming label of static-lsp instan'
                      + 'ce.'
                        ;
            type uint32 {
              range '0 | 3 | 16..1048575'
                    ;
            }
          }
          choice is-bind {
            description 'Chooses whether to bind static-lsp instance to prefix '
                      + 'or not.'
                        ;
            case bind {
              description 'Case of binding.'
                          ;
              container bind-fec {
                description 'Binds fec to static-lsp instance.'
                            ;
                presence 'Binding FEC'
                         ;
                leaf dest {
                  description 'Specifies a ipv4 prefix to bind to static-lsp in'
                            + 'stance.'
                              ;
                  type ncd:ipv4-address ;
                  mandatory true ;
                }
                leaf mask {
                  description 'Specifies a ipv4 mask to bind to static-lsp inst'
                            + 'ance.'
                              ;
                  type ncd:ipv4-mask ;
                  mandatory true ;
                }
                leaf force-type {
                  description 'Specifies whether forcing to advertise incoming '
                            + 'label to upstream by LDP protocol.'+"\n"
                            + '"force-advertise": means forcing to advertise in'
                            + 'coming label to upstream.'+"\n"
                            + '"unforce-advertise": means not forcing to advert'
                            + 'ise incoming label to upstream.'
                              ;
                  type enumeration {
                    enum unforce-advertise {
                      value 0 ;
                    }
                    enum force-advertise {
                      value 1 ;
                    }
                  }
                  default unforce-advertise ;
                }
              }
            }
          }
          container slsp-outseg-entries {
            description 'Configures forwarding entries of static-lsp instance.'
                        ;
            list slsp-outseg {
              description 'Configures a forwarding entry of static-lsp instance.'
                          ;
              key 'out-interface nexthop'
                  ;
              leaf out-interface {
                description 'Specifies an out-interface of forwarding entry.'
                            ;
                type ncd:ifname {
                  length 1..31 ;
                }
              }
              leaf nexthop {
                description 'Specifies a nexthop of forwarding entry.'
                            ;
                type ncd:ipv4-address {
                  pattern '((([1-9])|([1-9][0-9])|(1[0-9][0-9])|(2[0-4][0-9])|('
                        + '25[0-5]))\.(([0-9])|([1-9][0-9])|(1[0-9][0-9])|(2[0-'
                        + '4][0-9])|(25[0-5]))\.(([0-9])|([1-9][0-9])|(1[0-9][0'
                        + '-9])|(2[0-4][0-9])|(25[0-5]))\.(([0-9])|([1-9][0-9])'
                        + '|(1[0-9][0-9])|(2[0-4][0-9])|(25[0-5])))'
                          ;
                }
              }
              leaf out-label {
                description 'Specifies an outgoing label of forwarding entry.'
                            ;
                type uint32 {
                  range '0 | 3 | 16..1048575'
                        ;
                }
                mandatory true ;
              }
              leaf force-type {
                description 'Specifies whether forcing to use configured label '
                          + 'as outgoing label.'+"\n"
                          + '"force-validation": means forcing to use configure'
                          + 'd label as outgoing label.'+"\n"
                          + '"unforce-validation": means not forcing to use con'
                          + 'figured label as outgoing label.'
                            ;
                type enumeration {
                  enum unforce-validation {
                    value 0 ;
                  }
                  enum force-validation {
                    value 1 ;
                  }
                }
                default unforce-validation ;
              }
            }
            list slsp-outseg-without-interface {
              description 'Configures a forwarding entry of static-lsp instance'
                        + ' without specifying out-interface.'
                          ;
              key nexthop ;
              leaf nexthop {
                description 'Specifies a nexthop of forwarding entry.'
                            ;
                type ncd:ipv4-address ;
              }
              leaf out-label {
                description 'Specifies an outgoing label of forwarding entry.'
                            ;
                type uint32 {
                  range '0 | 3 | 16..1048575'
                        ;
                }
                mandatory true ;
              }
              leaf force-type {
                description 'Specifies whether forcing to use configured label '
                          + 'as outgoing label.'+"\n"
                          + '"force-validation": means forcing to use configure'
                          + 'd label as outgoing label.'+"\n"
                          + '"unforce-validation": means not forcing to use con'
                          + 'figured label as outgoing label.'
                            ;
                type enumeration {
                  enum unforce-validation {
                    value 0 ;
                  }
                  enum force-validation {
                    value 1 ;
                  }
                }
                default unforce-validation ;
              }
            }
            list slsp-outseg-without-nexthop {
              description 'Configures a forwarding entry of static-lsp instance'
                        + ' without specifying nexthop.'
                          ;
              key out-interface ;
              leaf out-interface {
                description 'Specifies an out-interface of forwarding entry.'
                            ;
                type ncd:ifname {
                  length 1..31 ;
                }
              }
              leaf out-label {
                description 'Specifies an outgoing label of forwarding entry.'
                            ;
                type uint32 {
                  range '0 | 3 | 16..1048575'
                        ;
                }
                mandatory true ;
              }
              leaf force-type {
                description 'Specifies whether forcing to use configured label '
                          + 'as outgoing label.'+"\n"
                          + '"force-validation": means forcing to use configure'
                          + 'd label as outgoing label.'+"\n"
                          + '"unforce-validation": means not forcing to use con'
                          + 'figured label as outgoing label.'
                            ;
                type enumeration {
                  enum unforce-validation {
                    value 0 ;
                  }
                  enum force-validation {
                    value 1 ;
                  }
                }
                default unforce-validation ;
              }
            }
          }
        }
      }
      container graceful-restart {
        description 'Graceful-restart configuration module.'
                    ;
        presence Gr ;
        leaf operation-type {
          description 'Specifies whether to enable graceful-restart or not.'
                      ;
          type enumeration {
            enum disable {
              value 0 ;
            }
            enum enable {
              value 1 ;
            }
          }
          mandatory true ;
        }
      }
      container lsp-select-sequence {
        description 'Multi-Protocol LSP select sequence configuration.'
                    ;
        presence 'LSP Select Sequence'
                 ;
        leaf ldp-sequence {
          description 'LDP LSP select sequence configuration.'
                      ;
          type lsp-select-sequence ;
          mandatory true ;
        }
        leaf bgp-sequence {
          description 'BGP LSP select sequence configuration.'
                      ;
          type lsp-select-sequence ;
          mandatory true ;
        }
        leaf sr-sequence {
          description 'SR LSP select sequence configuration.'
                      ;
          type lsp-select-sequence ;
          mandatory true ;
        }
      }
      container segment-routing {
        description 'Segment-routing configuration.'
                    ;
        presence 'SR configuration'
                 ;
        container adjacency {
          description 'SR Adjacency configuration.'
                      ;
          presence 'Adjacency configuration'
                   ;
          leaf backup-sid-hold-time {
            description 'Backup SID hold time in minutes.'
                        ;
            type uint16 {
              range 1..10080 ;
            }
            default 5 ;
          }
        }
        container encapsulation {
          description 'Encapsulation source information.'
                      ;
          presence 'Encapsulation source'
                   ;
          leaf source-address {
            description 'Source IPv6 address.'
                        ;
            type ncd:ipv6-address ;
          }
        }
        container srv6-local-repair {
          description 'SRv6 local repair headend behavior mode configuration.'
                      ;
          presence 'SRv6 local repair headend behavior mode'
                   ;
          leaf headend-behavior {
            description 'Use insert or encaps to configure headend behavior mod'
                      + 'e.'
                        ;
            type enumeration {
              enum insert {
                value 1 ;
              }
              enum encaps {
                value 2 ;
              }
            }
            mandatory true ;
          }
          ncd:revise-date 2021-06-24 ;
        }
        container srv6-srh-reduce {
          description 'SRv6 SRH reduce configuration.'
                      ;
          presence 'SRv6 SRH reduce configuration'
                   ;
          leaf operation-type {
            description 'Specifies whether to enable SRH reduce or not.'
                        ;
            type enumeration {
              enum enable {
                value 1 ;
              }
              enum disable {
                value 2 ;
              }
            }
            mandatory true ;
          }
          ncd:revise-date 2021-12-17 ;
        }
        container srv6-srh-local-end.x-reduce {
          description 'SRv6 SRH local End.X reduce configuration.'
                      ;
          presence 'SRv6 SRH local End.X reduce configuration'
                   ;
          leaf operation-type {
            description 'Specifies whether to enable SRH local End.X reduce or '
                      + 'not.'
                        ;
            type enumeration {
              enum enable {
                value 1 ;
              }
              enum disable {
                value 2 ;
              }
            }
            mandatory true ;
          }
          ncd:revise-date 2021-12-17 ;
        }
        container srv6-te-frr {
          description 'SRv6 traffic engineering fast-reroute configuration.'
                      ;
          presence 'SRv6 traffic engineering fast-reroute'
                   ;
          leaf operation-type {
            description 'Specifies whether to enable or not.'
                        ;
            type enumeration {
              enum disable {
                value 0 ;
              }
              enum enable {
                value 1 ;
              }
            }
            mandatory true ;
          }
          leaf downgrade {
            description 'Specifies whether to downgrade or not.'
                        ;
            type enumeration {
              enum enable {
                value 1 ;
              }
              enum disable {
                value 0 ;
              }
            }
            default disable ;
            ncd:revise-date 2022-06-15 ;
          }
        }
        container srv6-ttl-mode {
          description 'SRv6 TTL mode configuration.'
                      ;
          presence 'SRv6 TTL mode'
                   ;
          leaf ttl-mode {
            description 'Use uniform or pipe to configure TTL mode.'
                        ;
            type enumeration {
              enum uniform {
                value 1 ;
              }
              enum pipe {
                value 2 ;
              }
            }
            mandatory true ;
          }
        }
      }
    }
  }
}
