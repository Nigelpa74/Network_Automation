module zte-an-interface-eth-perf {
    namespace 'http://www.zte.com.cn/zxr10/netconf/schema/rosng/zx-eth-pm';
    prefix zx-eth-pm;

    organization "ZTE Corporation";
    contact " Zhang Weiping   ZTE Corporation
                         Mail: zhang.weiping@zte.com.cn
                         Tel : 021-68896470";
    description "The MIB module for the Performance Management of ZTE 
                 Access Node interface.";
    revision 2017-06-21 {
        description "Support ethernet interface minutes performance table.";
    }
    revision 2017-03-21 {
        description "Add some historical performance objects.";
    }
    revision 2011-09-13 {
        description "Modify this mib according to standard.";
    }
    revision 2011-09-10 {
        description "Modify the description.";
    }
    revision 2011-07-02 {
        description "Initial version of this MIB module.";
    }
    container zxAnInterfaceEthPerf {
        description "";
        container zxAnEthIfPerfObjects {
            description "";
            container zxAnEthIfCurr15MinPerfTable {
                description "The 15 minutes interval performance data table of the 
                             ethernet interfaces.";
                list zxAnEthIfCurr15MinPerfEntry {
                    description "The 15 minutes interval performance data entry of the 
                                 ethernet interfaces.";
                    max-elements 100;
                    key "ifIndex";
                    leaf ifIndex {
                        description "A unique value, greater than zero, for each interface.  It
                                     is recommended that values are assigned contiguously
                                     starting from 1.  The value for each interface sub-layer
                                     must remain constant at least from one re-initialization of
                                     the entity's network management system to the next re-
                                     initialization.";
                        type int32 {
                            range 1..2147483647;
                        }
                    }
                    leaf ethIfC15MTimeElapsed {
                        config false;
                        description "Number of seconds that have elapsed since the beginning of the 
                                     current 15 minutes interval.";
                        type uint32 {
                            range 0..899;
                        }
                    }
                    leaf ethIfC15MInOctets {
                        config false;
                        description "The total number of octets received on the interface,
                                     including framing characters in current 15 minutes interval.";
                        type uint64;
                    }
                    leaf ethIfC15MInPkts {
                        config false;
                        description "The total number of packets received on the interface,
                                     including framing characters in current 15 minutes interval.";
                        type uint64;
                    }
                    leaf ethIfC15MInUcastPkts {
                        config false;
                        description "The number of packets, delivered by this sub-layer to a
                                     higher (sub-)layer, which were not addressed to a multicast
                                     or broadcast address at this sub-layer in current 15 minutes
                                     interval.";
                        type uint64;
                    }
                    leaf ethIfC15MInMcastPkts {
                        config false;
                        description "The number of packets, delivered by this sub-layer to a
                                     higher (sub-)layer, which were addressed to a multicast
                                     address at this sub-layer in current 15 minutes interval.
                                     For a MAC layer protocol, this includes both Group and 
                                     Functional addresses.";
                        type uint64;
                    }
                    leaf ethIfC15MInBcastPkts {
                        config false;
                        description "The number of packets, delivered by this sub-layer to a
                                     higher (sub-)layer, which were addressed to a broadcast
                                     address at this sub-layer in current 15 minutes interval.";
                        type uint64;
                    }
                    leaf ethIfC15MInOversizedPkts {
                        config false;
                        description "The number of packets,whick above the configured MTU-size,
                                     e.g.mtu = 2000 (frames >2000 are discarded) in current 15
                                     minutes interval.";
                        type uint64;
                    }
                    leaf ethIfC15MInUndersizedPkts {
                        config false;
                        description "The number of packets,whick above the min port size,
                                     the value is 64 in current 15 minutes interval.";
                        type uint64;
                    }
                    leaf ethIfC15MOutOctets {
                        config false;
                        description "The total number of octets transmitted out of the interface, 
                                     including framing characters in current 15 minutes interval.";
                        type uint64;
                    }
                    leaf ethIfC15MOutPkts {
                        config false;
                        description "The total number of packets transmitted out of the interface, 
                                     including framing characters in current 15 minutes interval.";
                        type uint64;
                    }
                    leaf ethIfC15MOutUcastPkts {
                        config false;
                        description "The total number of packets that higher-level protocols
                                     requested be transmitted, and which were not addressed to a
                                     multicast or broadcast address at this sub-layer, including
                                     those that were discarded or not sent in current 15 minutes
                                     interval.";
                        type uint64;
                    }
                    leaf ethIfC15MOutMcastPkts {
                        config false;
                        description "The total number of packets that higher-level protocols
                                     requested be transmitted, and which were addressed to a
                                     multicast address at this sub-layer, including those that
                                     were discarded or not sent in current 15 minutes interval.
                                     For a MAC layer protocol, this includes both Group and 
                                     Functional addresses.";
                        type uint64;
                    }
                    leaf ethIfC15MOutBcastPkts {
                        config false;
                        description "The total number of packets that higher-level protocols
                                     requested be transmitted, and which were addressed to a
                                     broadcast address at this sub-layer, including those that
                                     were discarded or not sent in current 15 minutes interval.";
                        type uint64;
                    }
                    leaf ethIfC15MOutPausePkts {
                        config false;
                        description "A count of MAC Control frames transmitted on
                                     this interface with an opcode indicating the
                                     PAUSE operation in current 15 minutes interval.";
                        type uint64;
                    }
                    leaf ethIfC15MOutDiscardPkts {
                        config false;
                        description "The number of outbound packets which were chosen to be
                                     discarded even though no errors had been detected to prevent
                                     their being transmitted in current 15 minutes interval.";
                        type uint64;
                    }
                    leaf ethIfC15MOutCollisions {
                        config false;
                        description "A count of frames that are involved in out collision and 
                                     are subsequently transmitted successfully in current 15 
                                     minutes interval.";
                        type uint64;
                    }
                    leaf ethIfC15MSingleCollisions {
                        config false;
                        description "A count of frames that are involved in a single
                                     collision, and are subsequently transmitted
                                     successfully in current 15 minutes interval.";
                        type uint64;
                    }
                    leaf ethIfC15MMultipleCollisions {
                        config false;
                        description "A count of frames that are involved in more
                                     than one collision and are subsequently
                                     transmitted successfully in current 15 minutes
                                     interval.";
                        type uint64;
                    }
                    leaf ethIfC15MFcsErrors {
                        config false;
                        description "A count of frames received on a particular
                                     interface that are an integral number of octets
                                     in length but do not pass the FCS check.  This
                                     count does not include frames received with
                                     frame-too-long or frame-too-short error in current
                                     15 minutes interval.";
                        type uint64;
                    }
                    leaf ethIfC15MAlignmentErrors {
                        config false;
                        description "A count of frames received on a particular
                                     interface that are not an integral number of
                                     octets in length and do not pass the FCS check
                                     in current 15 minutes interval.";
                        type uint64;
                    }
                    leaf ethIfC15MInCrcErrPkts {
                        config false;
                        description "The total number of CRC errored packets received on the interface
                                     in current 15-minute interval.";
                        type uint64;
                    }
                    leaf ethIfC15MInDiscardPkts {
                        config false;
                        description "The total number of discarded packets received on the interface
                                     in current 15-minute interval.";
                        type uint64;
                    }
                    leaf ethIfC15MInErrPkts {
                        config false;
                        description "The total number of errored packets received on the interface
                                     in current 15-minute interval.";
                        type uint64;
                    }
                    leaf ethIfC15MOutErrPkts {
                        config false;
                        description "The total number of errored packets that could not be transmitted 
                                     from the interface because of errors in current 15-minute 
                                     interval.";
                        type uint64;
                    }
                    leaf ethIfC15MInDropEvents {
                        config false;
                        description "The total number of events in which packets received were 
                                     dropped by the probe due to lack of resources in current 
                                     15-minute interval.
                                     Note that this number is not necessarily the number of packets 
                                     dropped; it is just the number of times this condition has been 
                                     detected.";
                        type uint64;
                    }
                    leaf ethIfC15MOutDropEvents {
                        config false;
                        description "The total number of events in which packets transmitted were 
                                     dropped by the probe due to lack of resources in current 
                                     15-minute interval.
                                     Note that this number is not necessarily the number of packets 
                                     dropped; it is just the number of times this condition has been 
                                     detected.";
                        type uint64;
                    }
                    leaf ethIfC15MOutCrcErrPkts {
                        config false;
                        description "The total number of CRC errored packets transmitted out of the 
                                     interface in current 15-minute interval.";
                        type uint64;
                    }
                    leaf ethIfC15MOutOversizedPkts {
                        config false;
                        description "The total number of packets transmitted that were longer than 
                                     1518 octets (excluding framing bits, but including FCS octets) 
                                     and were otherwise well formed in current 15-minute interval.";
                        type uint64;
                    }
                    leaf ethIfC15MOutUndersizedPkts {
                        config false;
                        description "The total number of packets transmitted that were less than 
                                     64 octets long (excluding framing bits, but including FCS 
                                     octets) and were otherwise well formed in current 15-minute 
                                     interval.";
                        type uint64;
                    }
                    leaf ethIfC15MInFragments {
                        config false;
                        description "The total number of packets received that were less than 64 
                                     octets in length (excluding framing bits but including FCS 
                                     octets) and had either a bad Frame Check Sequence (FCS) with 
                                     an integral number of octets (FCS Error) or a bad FCS with a 
                                     non-integral number of octets (Alignment Error) in current 
                                     15-minute interval.";
                        type uint64;
                    }
                    leaf ethIfC15MOutFragments {
                        config false;
                        description "The total number of packets transmitted that were less than 64 
                                     octets in length (excluding framing bits but including FCS 
                                     octets) and had either a bad Frame Check Sequence (FCS) with an 
                                     integral number of octets (FCS Error) or a bad FCS with a 
                                     non-integral number of octets (Alignment Error) in current 
                                     15-minute interval.";
                        type uint64;
                    }
                    leaf ethIfC15MInJabbers {
                        config false;
                        description "The total number of packets received that were longer than 
                                     1518 octets (excluding framing bits, but including FCS octets), 
                                     and had either a bad Frame Check Sequence (FCS) with an integral 
                                     number of octets (FCS Error) or a bad FCS with a non-integral
                                     number of octets (Alignment Error) in current 15-minute 
                                     interval.
                                     
                                     Note that this definition of jabber is different than the 
                                     definition in IEEE-802.3 section 8.2.1.5 (10BASE5) and section 
                                     10.3.1.4 (10BASE2). These documents define jabber as the 
                                     condition where any packet exceeds 20 ms. The allowed range to 
                                     detect jabber is between 20 ms and 150 ms.";
                        type uint64;
                    }
                    leaf ethIfC15MOutJabbers {
                        config false;
                        description "The total number of packets transmitted that were longer than 
                                     1518 octets (excluding framing bits, but including FCS octets), 
                                     and had either a bad Frame Check Sequence (FCS) with an integral 
                                     number of octets (FCS Error) or a bad FCS with a non-integral
                                     number of octets (Alignment Error) in current 15-minute 
                                     interval.
                                     
                                     Note that this definition of jabber is different than the 
                                     definition in IEEE-802.3 section 8.2.1.5 (10BASE5) and section 
                                     10.3.1.4 (10BASE2). These documents define jabber as the 
                                     condition where any packet exceeds 20 ms. The allowed range to 
                                     detect jabber is between 20 ms and 150 ms.";
                        type uint64;
                    }
                    leaf ethIfC15MInPkts64Octets {
                        config false;
                        description "The total number of packets (including bad packets) received 
                                     that were 64 octets in length (excluding framing bits but 
                                     including FCS octets) in current 15-minute interval.";
                        type uint64;
                    }
                    leaf ethIfC15MOutPkts64Octets {
                        config false;
                        description "The total number of packets (including bad packets) transmitted 
                                     that were 64 octets in length (excluding framing bits but 
                                     including FCS octets) in current 15-minute interval.";
                        type uint64;
                    }
                    leaf ethIfC15MInPkts65to127Octs {
                        config false;
                        description "The total number of packets (including bad packets) received 
                                     that were between 65 and 127 octets in length (excluding 
                                     framing bits but including FCS octets) in current 15-minute 
                                     interval.";
                        type uint64;
                    }
                    leaf ethIfC15MOutPkts65to127Octs {
                        config false;
                        description "The total number of packets (including bad packets) transmitted 
                                     that were between 65 and 127 octets in length (excluding 
                                     framing bits but including FCS octets) in current 15-minute 
                                     interval.";
                        type uint64;
                    }
                    leaf ethIfC15MInPkts128to255Octs {
                        config false;
                        description "The total number of packets (including bad packets) received 
                                     that were between 128 and 255 octets in length (excluding 
                                     framing bits but including FCS octets) in current 15-minute 
                                     interval.";
                        type uint64;
                    }
                    leaf ethIfC15MOutPkts128to255Octs {
                        config false;
                        description "The total number of packets (including bad packets) transmitted 
                                     that were between 128 and 255 octets in length (excluding 
                                     framing bits but including FCS octets) in current 15-minute 
                                     interval.";
                        type uint64;
                    }
                    leaf ethIfC15MInPkts256to511Octs {
                        config false;
                        description "The total number of packets (including bad packets) received 
                                     that were between 256 and 511 octets in length (excluding 
                                     framing bits but including FCS octets) in current 15-minute
                                     interval.";
                        type uint64;
                    }
                    leaf ethIfC15MOutPkts256to511Octs {
                        config false;
                        description "The total number of packets (including bad packets) transmitted 
                                     that were between 256 and 511 octets in length (excluding 
                                     framing bits but including FCS octets) in current 15-minute
                                     interval.";
                        type uint64;
                    }
                    leaf ethIfC15MInPkts512to1023 {
                        config false;
                        description "The total number of packets (including bad packets) received 
                                     that were between 512 and 1023 octets in length (excluding 
                                     framing bits but including FCS octets) in current 15-minute 
                                     interval.";
                        type uint64;
                    }
                    leaf ethIfC15MOutPkts512to1023 {
                        config false;
                        description "The total number of packets (including bad packets) transmitted 
                                     that were between 512 and 1023 octets in length (excluding 
                                     framing bits but including FCS octets) in current 15-minute 
                                     interval.";
                        type uint64;
                    }
                    leaf ethIfC15MInPkts1024to1518 {
                        config false;
                        description "The total number of packets (including bad packets) received 
                                     that were between 1024 and 1518 octets in length (excluding 
                                     framing bits but including FCS octets) in current 15-minute
                                     interval.";
                        type uint64;
                    }
                    leaf ethIfC15MOutPkts1024to1518 {
                        config false;
                        description "The total number of packets (including bad packets) transmitted 
                                     that were between 1024 and 1518 octets in length (excluding 
                                     framing bits but including FCS octets) in current 15-minute 
                                     interval.";
                        type uint64;
                    }
                    leaf ethIfC15MLinkStatusChanges {
                        config false;
                        description "The total number of the link status changes on the interface
                                     in current 15-minute interval.
                                     The total number is increased when the link status changes
                                     from up to down, or from down to up.";
                        type uint32;
                    }
                    leaf ethIfC15MInBwUsingRatio {
                        config false;
                        description "An estimate of the interface's received bandwidth using ratio in 
                                     current 15-minute interval.";
                        type int32 {
                            range 0..100;
                        }
                    }
                    leaf ethIfC15MOutBwUsingRatio {
                        config false;
                        description "An estimate of the interface's transmitted bandwidth using ratio 
                                     in current 15-minute interval.";
                        type int32 {
                            range 0..100;
                        }
                    }
                    leaf ethIfC15MReset {
                        description "Clear all the current 15-minute performance variables.
                                     When get this variable, always return 1.";
                        type enumeration {
                            enum perfReset {
                                value 1;
                                description "";
                            }
                        }
                    }
                }
            }
            container zxAnEthIfCurr1DayPerfTable {
                description "The 1 day interval performance data table of the ethernet 
                             interfaces.";
                list zxAnEthIfCurr1DayPerfEntry {
                    description "The 1 day interval performance data entry of the ethernet 
                                 interfaces.";
                    max-elements 100;
                    key "ifIndex";
                    leaf ifIndex {
                        description "A unique value, greater than zero, for each interface.  It
                                     is recommended that values are assigned contiguously
                                     starting from 1.  The value for each interface sub-layer
                                     must remain constant at least from one re-initialization of
                                     the entity's network management system to the next re-
                                     initialization.";
                        type int32 {
                            range 1..2147483647;
                        }
                    }
                    leaf ethIfC1DTimeElapsed {
                        config false;
                        description "Number of seconds that have elapsed since the beginning of the 
                                     current 1 day interval.";
                        type uint32 {
                            range 0..86399;
                        }
                    }
                    leaf ethIfC1DInOctets {
                        config false;
                        description "The total number of octets received on the interface,
                                     including framing characters in current one day interval.";
                        type uint64;
                    }
                    leaf ethIfC1DInPkts {
                        config false;
                        description "The total number of packets received on the interface,
                                     including framing characters in current one day interval.";
                        type uint64;
                    }
                    leaf ethIfC1DInUcastPkts {
                        config false;
                        description "The number of packets, delivered by this sub-layer to a
                                     higher (sub-)layer, which were not addressed to a multicast
                                     or broadcast address at this sub-layer in current one day
                                     interval.";
                        type uint64;
                    }
                    leaf ethIfC1DInMcastPkts {
                        config false;
                        description "The number of packets, delivered by this sub-layer to a
                                     higher (sub-)layer, which were addressed to a multicast
                                     address at this sub-layer in current one day interval.
                                     For a MAC layer protocol, this includes both Group and 
                                     Functional addresses.";
                        type uint64;
                    }
                    leaf ethIfC1DInBcastPkts {
                        config false;
                        description "The number of packets, delivered by this sub-layer to a
                                     higher (sub-)layer, which were addressed to a broadcast
                                     address at this sub-layer in current one day interval.";
                        type uint64;
                    }
                    leaf ethIfC1DInOversizedPkts {
                        config false;
                        description "The number of packets,whick above the configured MTU-size,
                                     e.g.mtu = 2000 (frames >2000 are discarded) in current one
                                     day interval.";
                        type uint64;
                    }
                    leaf ethIfC1DInUndersizedPkts {
                        config false;
                        description "The number of packets,whick above the min port size,
                                     the value is 64 in current one day interval.";
                        type uint64;
                    }
                    leaf ethIfC1DOutOctets {
                        config false;
                        description "The total number of octets transmitted out of the interface, 
                                     including framing characters in current one day interval.";
                        type uint64;
                    }
                    leaf ethIfC1DOutPkts {
                        config false;
                        description "The total number of packets transmitted out of the interface, 
                                     including framing characters in current one day interval.";
                        type uint64;
                    }
                    leaf ethIfC1DOutUcastPkts {
                        config false;
                        description "The total number of packets that higher-level protocols
                                     requested be transmitted, and which were not addressed to a
                                     multicast or broadcast address at this sub-layer, including
                                     those that were discarded or not sent in current one day
                                     interval.";
                        type uint64;
                    }
                    leaf ethIfC1DOutMcastPkts {
                        config false;
                        description "The total number of packets that higher-level protocols
                                     requested be transmitted, and which were addressed to a
                                     multicast address at this sub-layer, including those that
                                     were discarded or not sent in current one day interval.
                                     For a MAC layer protocol, this includes both Group and 
                                     Functional addresses.";
                        type uint64;
                    }
                    leaf ethIfC1DOutBcastPkts {
                        config false;
                        description "The total number of packets that higher-level protocols
                                     requested be transmitted, and which were addressed to a
                                     broadcast address at this sub-layer, including those that
                                     were discarded or not sent in current one day interval.";
                        type uint64;
                    }
                    leaf ethIfC1DOutPausePkts {
                        config false;
                        description "A count of MAC Control frames transmitted on
                                     this interface with an opcode indicating the
                                     PAUSE operation in current one day interval.";
                        type uint64;
                    }
                    leaf ethIfC1DOutDiscardPkts {
                        config false;
                        description "The number of outbound packets which were chosen to be
                                     discarded even though no errors had been detected to prevent
                                     their being transmitted in current one day interval.";
                        type uint64;
                    }
                    leaf ethIfC1DOutCollisions {
                        config false;
                        description "A count of frames that are involved in out collision and 
                                     are subsequently transmitted successfully in current one 
                                     day interval.";
                        type uint64;
                    }
                    leaf ethIfC1DSingleCollisions {
                        config false;
                        description "A count of frames that are involved in a single
                                     collision, and are subsequently transmitted
                                     successfully in current one day interval.";
                        type uint64;
                    }
                    leaf ethIfC1DMultipleCollisions {
                        config false;
                        description "A count of frames that are involved in more
                                     than one collision and are subsequently
                                     transmitted successfully in current one day
                                     interval.";
                        type uint64;
                    }
                    leaf ethIfC1DFcsErrors {
                        config false;
                        description "A count of frames received on a particular
                                     interface that are an integral number of octets
                                     in length but do not pass the FCS check.  This
                                     count does not include frames received with
                                     frame-too-long or frame-too-short error in current
                                     one day interval.";
                        type uint64;
                    }
                    leaf ethIfC1DAlignmentErrors {
                        config false;
                        description "A count of frames received on a particular
                                     interface that are not an integral number of
                                     octets in length and do not pass the FCS check
                                     in current one day interval.";
                        type uint64;
                    }
                    leaf ethIfC1DInCrcErrPkts {
                        config false;
                        description "The total number of CRC errored packets received on the interface
                                     in current 1-day interval.";
                        type uint64;
                    }
                    leaf ethIfC1DInDiscardPkts {
                        config false;
                        description "The total number of discarded packets received on the interface
                                     in current 1-day interval.";
                        type uint64;
                    }
                    leaf ethIfC1DInErrPkts {
                        config false;
                        description "The total number of errored packets received on the interface
                                     in current 1-day interval.";
                        type uint64;
                    }
                    leaf ethIfC1DOutErrPkts {
                        config false;
                        description "The total number of errored packets that could not be transmitted 
                                     from the interface because of errors in current 1-day interval.";
                        type uint64;
                    }
                    leaf ethIfC1DInDropEvents {
                        config false;
                        description "The total number of events in which packets received were 
                                     dropped by the probe due to lack of resources in current 
                                     1-day interval.
                                     Note that this number is not necessarily the number of packets 
                                     dropped; it is just the number of times this condition has been 
                                     detected.";
                        type uint64;
                    }
                    leaf ethIfC1DOutDropEvents {
                        config false;
                        description "The total number of events in which packets transmitted were 
                                     dropped by the probe due to lack of resources in current 
                                     1-day interval.
                                     Note that this number is not necessarily the number of packets 
                                     dropped; it is just the number of times this condition has been 
                                     detected.";
                        type uint64;
                    }
                    leaf ethIfC1DOutCrcErrPkts {
                        config false;
                        description "The total number of CRC errored packets transmitted out of the 
                                     interface in current 1-day interval.";
                        type uint64;
                    }
                    leaf ethIfC1DOutOversizedPkts {
                        config false;
                        description "The total number of packets transmitted that were longer than 
                                     1518 octets (excluding framing bits, but including FCS octets) 
                                     and were otherwise well formed in current 1-day interval.";
                        type uint64;
                    }
                    leaf ethIfC1DOutUndersizedPkts {
                        config false;
                        description "The total number of packets transmitted that were less than 
                                     64 octets long (excluding framing bits, but including FCS 
                                     octets) and were otherwise well formed in current 1-day
                                     interval.";
                        type uint64;
                    }
                    leaf ethIfC1DInFragments {
                        config false;
                        description "The total number of packets received that were less than 64 
                                     octets in length (excluding framing bits but including FCS 
                                     octets) and had either a bad Frame Check Sequence (FCS) with 
                                     an integral number of octets (FCS Error) or a bad FCS with a 
                                     non-integral number of octets (Alignment Error) in current 
                                     1-day interval.";
                        type uint64;
                    }
                    leaf ethIfC1DOutFragments {
                        config false;
                        description "The total number of packets transmitted that were less than 64 
                                     octets in length (excluding framing bits but including FCS 
                                     octets) and had either a bad Frame Check Sequence (FCS) with an 
                                     integral number of octets (FCS Error) or a bad FCS with a 
                                     non-integral number of octets (Alignment Error) in current 
                                     1-day interval.";
                        type uint64;
                    }
                    leaf ethIfC1DInJabbers {
                        config false;
                        description "The total number of packets received that were longer than 
                                     1518 octets (excluding framing bits, but including FCS octets), 
                                     and had either a bad Frame Check Sequence (FCS) with an integral 
                                     number of octets (FCS Error) or a bad FCS with a non-integral
                                     number of octets (Alignment Error) in current 1-day interval.
                                     
                                     Note that this definition of jabber is different than the 
                                     definition in IEEE-802.3 section 8.2.1.5 (10BASE5) and section 
                                     10.3.1.4 (10BASE2). These documents define jabber as the 
                                     condition where any packet exceeds 20 ms. The allowed range to 
                                     detect jabber is between 20 ms and 150 ms.";
                        type uint64;
                    }
                    leaf ethIfC1DOutJabbers {
                        config false;
                        description "The total number of packets transmitted that were longer than 
                                     1518 octets (excluding framing bits, but including FCS octets), 
                                     and had either a bad Frame Check Sequence (FCS) with an integral 
                                     number of octets (FCS Error) or a bad FCS with a non-integral
                                     number of octets (Alignment Error) in current 1-day interval.
                                     
                                     Note that this definition of jabber is different than the 
                                     definition in IEEE-802.3 section 8.2.1.5 (10BASE5) and section 
                                     10.3.1.4 (10BASE2). These documents define jabber as the 
                                     condition where any packet exceeds 20 ms. The allowed range to 
                                     detect jabber is between 20 ms and 150 ms.";
                        type uint64;
                    }
                    leaf ethIfC1DInPkts64Octets {
                        config false;
                        description "The total number of packets (including bad packets) received 
                                     that were 64 octets in length (excluding framing bits but 
                                     including FCS octets) in current 1-day interval.";
                        type uint64;
                    }
                    leaf ethIfC1DOutPkts64Octets {
                        config false;
                        description "The total number of packets (including bad packets) transmitted 
                                     that were 64 octets in length (excluding framing bits but 
                                     including FCS octets) in current 1-day interval.";
                        type uint64;
                    }
                    leaf ethIfC1DInPkts65to127Octs {
                        config false;
                        description "The total number of packets (including bad packets) received 
                                     that were between 65 and 127 octets in length (excluding 
                                     framing bits but including FCS octets) in current 1-day 
                                     interval.";
                        type uint64;
                    }
                    leaf ethIfC1DOutPkts65to127Octs {
                        config false;
                        description "The total number of packets (including bad packets) transmitted 
                                     that were between 65 and 127 octets in length (excluding 
                                     framing bits but including FCS octets) in current 1-day 
                                     interval.";
                        type uint64;
                    }
                    leaf ethIfC1DInPkts128to255Octs {
                        config false;
                        description "The total number of packets (including bad packets) received 
                                     that were between 128 and 255 octets in length (excluding 
                                     framing bits but including FCS octets) in current 1-day 
                                     interval.";
                        type uint64;
                    }
                    leaf ethIfC1DOutPkts128to255Octs {
                        config false;
                        description "The total number of packets (including bad packets) transmitted 
                                     that were between 128 and 255 octets in length (excluding 
                                     framing bits but including FCS octets) in current 1-day 
                                     interval.";
                        type uint64;
                    }
                    leaf ethIfC1DInPkts256to511Octs {
                        config false;
                        description "The total number of packets (including bad packets) received 
                                     that were between 256 and 511 octets in length (excluding 
                                     framing bits but including FCS octets) in current 1-day
                                     interval.";
                        type uint64;
                    }
                    leaf ethIfC1DOutPkts256to511Octs {
                        config false;
                        description "The total number of packets (including bad packets) transmitted 
                                     that were between 256 and 511 octets in length (excluding 
                                     framing bits but including FCS octets) in current 1-day
                                     interval.";
                        type uint64;
                    }
                    leaf ethIfC1DInPkts512to1023 {
                        config false;
                        description "The total number of packets (including bad packets) received 
                                     that were between 512 and 1023 octets in length (excluding 
                                     framing bits but including FCS octets) in current 1-day 
                                     interval.";
                        type uint64;
                    }
                    leaf ethIfC1DOutPkts512to1023 {
                        config false;
                        description "The total number of packets (including bad packets) transmitted 
                                     that were between 512 and 1023 octets in length (excluding 
                                     framing bits but including FCS octets) in current 1-day 
                                     interval.";
                        type uint64;
                    }
                    leaf ethIfC1DInPkts1024to1518 {
                        config false;
                        description "The total number of packets (including bad packets) received 
                                     that were between 1024 and 1518 octets in length (excluding 
                                     framing bits but including FCS octets) in current 1-day
                                     interval.";
                        type uint64;
                    }
                    leaf ethIfC1DOutPkts1024to1518 {
                        config false;
                        description "The total number of packets (including bad packets) transmitted 
                                     that were between 1024 and 1518 octets in length (excluding 
                                     framing bits but including FCS octets) in current 1-day 
                                     interval.";
                        type uint64;
                    }
                    leaf ethIfC1DLinkStatusChanges {
                        config false;
                        description "The total number of the link status changes on the interface
                                     in current 1-day interval.
                                     The total number is increased when the link status changes
                                     from up to down, or from down to up.";
                        type uint32;
                    }
                    leaf ethIfC1DInBwUsingRatio {
                        config false;
                        description "An estimate of the interface's received bandwidth using ratio in 
                                     current 1-day interval.";
                        type int32 {
                            range 0..100;
                        }
                    }
                    leaf ethIfC1DOutBwUsingRatio {
                        config false;
                        description "An estimate of the interface's transmitted bandwidth using ratio 
                                     in current 1-day interval.";
                        type int32 {
                            range 0..100;
                        }
                    }
                    leaf ethIfC1DReset {
                        description "Clear all the current 1-day performance variables.
                                     When get this variable, always return 1.";
                        type enumeration {
                            enum perfReset {
                                value 1;
                                description "";
                            }
                        }
                    }
                }
            }
            container zxAnEthIfHis15MinPerfTable {
                description "The 15 minutes interval history performance data table of 
                             the ethernet interfaces.";
                list zxAnEthIfHis15MinPerfEntry {
                    config false;
                    description "The 15 minutes interval performance data entry of the 
                                 ethernet interfaces.";
                    max-elements 100;
                    key "ifIndex ethIfH15MIntervalNo";
                    leaf ifIndex {
                        description "A unique value, greater than zero, for each interface.  It
                                     is recommended that values are assigned contiguously
                                     starting from 1.  The value for each interface sub-layer
                                     must remain constant at least from one re-initialization of
                                     the entity's network management system to the next re-
                                     initialization.";
                        type int32 {
                            range 1..2147483647;
                        }
                    }
                    leaf ethIfH15MIntervalNo {
                        description "Performance data interval number 1 is the the most recent 
                                     previous interval; interval 96 is 24 hours ago.  
                                     Intervals 2..96 are optional.";
                        type int32 {
                            range 1..96;
                        }
                    }
                    leaf ethIfH15MIntervalValidData {
                        config false;
                        description "Performance data valid flag. 
                                     true(1) means valid.  
                                     false(2) means invalidm and the performace data is useless.";
                        type int32;
                    }
                    leaf ethIfH15MDateTime {
                        config false;
                        description "The 15 minutes interval performance data generation time.";
                        type binary;
                    }
                    leaf ethIfH15MInOctets {
                        config false;
                        description "The total number of octets received on the interface,
                                     including framing characters in historical 15 minutes interval.";
                        type uint64;
                    }
                    leaf ethIfH15MInPkts {
                        config false;
                        description "The total number of packets received on the interface,
                                     including framing characters in historical 15 minutes interval.";
                        type uint64;
                    }
                    leaf ethIfH15MInUcastPkts {
                        config false;
                        description "The number of packets, delivered by this sub-layer to a
                                     higher (sub-)layer, which were not addressed to a multicast
                                     or broadcast address at this sub-layer in historical 15 minutes
                                     interval.";
                        type uint64;
                    }
                    leaf ethIfH15MInMcastPkts {
                        config false;
                        description "The number of packets, delivered by this sub-layer to a
                                     higher (sub-)layer, which were addressed to a multicast
                                     address at this sub-layer in historical 15 minutes interval.
                                     For a MAC layer protocol, this includes both Group and 
                                     Functional addresses.";
                        type uint64;
                    }
                    leaf ethIfH15MInBcastPkts {
                        config false;
                        description "The number of packets, delivered by this sub-layer to a
                                     higher (sub-)layer, which were addressed to a broadcast
                                     address at this sub-layer in historical 15 minutes interval.";
                        type uint64;
                    }
                    leaf ethIfH15MInOversizedPkts {
                        config false;
                        description "The number of packets,whick above the configured MTU-size,
                                     e.g.mtu = 2000 (frames >2000 are discarded) in historical 15
                                     minutes interval.";
                        type uint64;
                    }
                    leaf ethIfH15MInUndersizedPkts {
                        config false;
                        description "The number of packets,whick above the min port size,
                                     the value is 64 in historical 15 minutes interval.";
                        type uint64;
                    }
                    leaf ethIfH15MOutOctets {
                        config false;
                        description "The total number of octets transmitted out of the interface, 
                                     including framing characters in historical 15 minutes interval.";
                        type uint64;
                    }
                    leaf ethIfH15MOutPkts {
                        config false;
                        description "The total number of packets transmitted out of the interface, 
                                     including framing characters in historical 15 minutes interval.";
                        type uint64;
                    }
                    leaf ethIfH15MOutUcastPkts {
                        config false;
                        description "The total number of packets that higher-level protocols
                                     requested be transmitted, and which were not addressed to a
                                     multicast or broadcast address at this sub-layer, including
                                     those that were discarded or not sent in historical 15 minutes
                                     interval.";
                        type uint64;
                    }
                    leaf ethIfH15MOutMcastPkts {
                        config false;
                        description "The total number of packets that higher-level protocols
                                     requested be transmitted, and which were addressed to a
                                     multicast address at this sub-layer, including those that
                                     were discarded or not sent in historical 15 minutes interval.
                                     For a MAC layer protocol, this includes both Group and 
                                     Functional addresses.";
                        type uint64;
                    }
                    leaf ethIfH15MOutBcastPkts {
                        config false;
                        description "The total number of packets that higher-level protocols
                                     requested be transmitted, and which were addressed to a
                                     broadcast address at this sub-layer, including those that
                                     were discarded or not sent in historical 15 minutes interval.";
                        type uint64;
                    }
                    leaf ethIfH15MOutPausePkts {
                        config false;
                        description "A count of MAC Control frames transmitted on
                                     this interface with an opcode indicating the
                                     PAUSE operation in historical 15 minutes interval.";
                        type uint64;
                    }
                    leaf ethIfH15MOutDiscardPkts {
                        config false;
                        description "The number of outbound packets which were chosen to be
                                     discarded even though no errors had been detected to prevent
                                     their being transmitted in historical 15 minutes interval.";
                        type uint64;
                    }
                    leaf ethIfH15MOutCollisions {
                        config false;
                        description "A count of frames that are involved in out collision and 
                                     are subsequently transmitted successfully in historical 15 
                                     minutes interval.";
                        type uint64;
                    }
                    leaf ethIfH15MSingleCollisions {
                        config false;
                        description "A count of frames that are involved in a single
                                     collision, and are subsequently transmitted
                                     successfully in historical 15 minutes interval.";
                        type uint64;
                    }
                    leaf ethIfH15MMultipleCollisions {
                        config false;
                        description "A count of frames that are involved in more
                                     than one collision and are subsequently
                                     transmitted successfully in historical 15 minutes
                                     interval.";
                        type uint64;
                    }
                    leaf ethIfH15MFcsErrors {
                        config false;
                        description "A count of frames received on a particular
                                     interface that are an integral number of octets
                                     in length but do not pass the FCS check.  This
                                     count does not include frames received with
                                     frame-too-long or frame-too-short error in historical
                                     15 minutes interval.";
                        type uint64;
                    }
                    leaf ethIfH15MAlignmentErrors {
                        config false;
                        description "A count of frames received on a particular
                                     interface that are not an integral number of
                                     octets in length and do not pass the FCS check
                                     in historical 15 minutes interval.";
                        type uint64;
                    }
                    leaf ethIfH15MInCrcErrPkts {
                        config false;
                        description "The total number of CRC errored packets received on the interface
                                     in historical 15-minute interval.";
                        type uint64;
                    }
                    leaf ethIfH15MInDiscardPkts {
                        config false;
                        description "The total number of discarded packets received on the interface
                                     in historical 15-minute interval.";
                        type uint64;
                    }
                    leaf ethIfH15MInErrPkts {
                        config false;
                        description "The total number of errored packets received on the interface
                                     in historical 15-minute interval.";
                        type uint64;
                    }
                    leaf ethIfH15MOutErrPkts {
                        config false;
                        description "The total number of errored packets that could not be transmitted 
                                     from the interface because of errors 
                                     in historical 15-minute interval.";
                        type uint64;
                    }
                    leaf ethIfH15MInDropEvents {
                        config false;
                        description "The total number of events in which packets received were 
                                     dropped by the probe due to lack of resources in historical 
                                     15-minute interval.
                                     Note that this number is not necessarily the number of packets 
                                     dropped; it is just the number of times this condition has been 
                                     detected.";
                        type uint64;
                    }
                    leaf ethIfH15MOutDropEvents {
                        config false;
                        description "The total number of events in which packets transmitted were 
                                     dropped by the probe due to lack of resources in historical 
                                     15-minute interval.
                                     Note that this number is not necessarily the number of packets 
                                     dropped; it is just the number of times this condition has been 
                                     detected.";
                        type uint64;
                    }
                    leaf ethIfH15MOutCrcErrPkts {
                        config false;
                        description "The total number of CRC errored packets transmitted out of the 
                                     interface in historical 15-minute interval.";
                        type uint64;
                    }
                    leaf ethIfH15MOutOversizedPkts {
                        config false;
                        description "The total number of packets transmitted that were longer than 
                                     1518 octets (excluding framing bits, but including FCS octets) 
                                     and were otherwise well formed in historical 15-minute 
                                     interval.";
                        type uint64;
                    }
                    leaf ethIfH15MOutUndersizedPkts {
                        config false;
                        description "The total number of packets transmitted that were less than 
                                     64 octets long (excluding framing bits, but including FCS 
                                     octets) and were otherwise well formed in historical 15-minute 
                                     interval.";
                        type uint64;
                    }
                    leaf ethIfH15MInFragments {
                        config false;
                        description "The total number of packets received that were less than 64 
                                     octets in length (excluding framing bits but including FCS 
                                     octets) and had either a bad Frame Check Sequence (FCS) with 
                                     an integral number of octets (FCS Error) or a bad FCS with a 
                                     non-integral number of octets (Alignment Error) in historical 
                                     15-minute interval.";
                        type uint64;
                    }
                    leaf ethIfH15MOutFragments {
                        config false;
                        description "The total number of packets transmitted that were less than 64 
                                     octets in length (excluding framing bits but including FCS 
                                     octets) and had either a bad Frame Check Sequence (FCS) with an 
                                     integral number of octets (FCS Error) or a bad FCS with a 
                                     non-integral number of octets (Alignment Error) in historical 
                                     15-minute interval.";
                        type uint64;
                    }
                    leaf ethIfH15MInJabbers {
                        config false;
                        description "The total number of packets received that were longer than 
                                     1518 octets (excluding framing bits, but including FCS octets), 
                                     and had either a bad Frame Check Sequence (FCS) with an integral 
                                     number of octets (FCS Error) or a bad FCS with a non-integral
                                     number of octets (Alignment Error) in historical 15-minute 
                                     interval.
                                     
                                     Note that this definition of jabber is different than the 
                                     definition in IEEE-802.3 section 8.2.1.5 (10BASE5) and section 
                                     10.3.1.4 (10BASE2). These documents define jabber as the 
                                     condition where any packet exceeds 20 ms. The allowed range to 
                                     detect jabber is between 20 ms and 150 ms.";
                        type uint64;
                    }
                    leaf ethIfH15MOutJabbers {
                        config false;
                        description "The total number of packets transmitted that were longer than 
                                     1518 octets (excluding framing bits, but including FCS octets), 
                                     and had either a bad Frame Check Sequence (FCS) with an integral 
                                     number of octets (FCS Error) or a bad FCS with a non-integral
                                     number of octets (Alignment Error) in historical 15-minute 
                                     interval.
                                     
                                     Note that this definition of jabber is different than the 
                                     definition in IEEE-802.3 section 8.2.1.5 (10BASE5) and section 
                                     10.3.1.4 (10BASE2). These documents define jabber as the 
                                     condition where any packet exceeds 20 ms. The allowed range to 
                                     detect jabber is between 20 ms and 150 ms.";
                        type uint64;
                    }
                    leaf ethIfH15MInPkts64Octets {
                        config false;
                        description "The total number of packets (including bad packets) received 
                                     that were 64 octets in length (excluding framing bits but 
                                     including FCS octets) in historical 15-minute interval.";
                        type uint64;
                    }
                    leaf ethIfH15MOutPkts64Octets {
                        config false;
                        description "The total number of packets (including bad packets) transmitted 
                                     that were 64 octets in length (excluding framing bits but 
                                     including FCS octets) in historical 15-minute interval.";
                        type uint64;
                    }
                    leaf ethIfH15MInPkts65to127Octs {
                        config false;
                        description "The total number of packets (including bad packets) received 
                                     that were between 65 and 127 octets in length (excluding 
                                     framing bits but including FCS octets) in historical 
                                     15-minute interval.";
                        type uint64;
                    }
                    leaf ethIfH15MOutPkts65to127Octs {
                        config false;
                        description "The total number of packets (including bad packets) transmitted 
                                     that were between 65 and 127 octets in length (excluding 
                                     framing bits but including FCS octets) in historical 15-minute 
                                     interval.";
                        type uint64;
                    }
                    leaf ethIfH15MInPkts128to255Octs {
                        config false;
                        description "The total number of packets (including bad packets) received 
                                     that were between 128 and 255 octets in length (excluding 
                                     framing bits but including FCS octets) in historical 15-minute 
                                     interval.";
                        type uint64;
                    }
                    leaf ethIfH15MOutPkts128to255Octs {
                        config false;
                        description "The total number of packets (including bad packets) transmitted 
                                     that were between 128 and 255 octets in length (excluding 
                                     framing bits but including FCS octets) in historical 15-minute 
                                     interval.";
                        type uint64;
                    }
                    leaf ethIfH15MInPkts256to511Octs {
                        config false;
                        description "The total number of packets (including bad packets) received 
                                     that were between 256 and 511 octets in length (excluding 
                                     framing bits but including FCS octets) in historical 15-minute
                                     interval.";
                        type uint64;
                    }
                    leaf ethIfH15MOutPkts256to511Octs {
                        config false;
                        description "The total number of packets (including bad packets) transmitted 
                                     that were between 256 and 511 octets in length (excluding 
                                     framing bits but including FCS octets) in historical 15-minute
                                     interval.";
                        type uint64;
                    }
                    leaf ethIfH15MInPkts512to1023 {
                        config false;
                        description "The total number of packets (including bad packets) received 
                                     that were between 512 and 1023 octets in length (excluding 
                                     framing bits but including FCS octets) in historical 15-minute 
                                     interval.";
                        type uint64;
                    }
                    leaf ethIfH15MOutPkts512to1023 {
                        config false;
                        description "The total number of packets (including bad packets) transmitted 
                                     that were between 512 and 1023 octets in length (excluding 
                                     framing bits but including FCS octets) in historical 15-minute 
                                     interval.";
                        type uint64;
                    }
                    leaf ethIfH15MInPkts1024to1518 {
                        config false;
                        description "The total number of packets (including bad packets) received 
                                     that were between 1024 and 1518 octets in length (excluding 
                                     framing bits but including FCS octets) in historical 15-minute
                                     interval.";
                        type uint64;
                    }
                    leaf ethIfH15MOutPkts1024to1518 {
                        config false;
                        description "The total number of packets (including bad packets) transmitted 
                                     that were between 1024 and 1518 octets in length (excluding 
                                     framing bits but including FCS octets) in historical 15-minute 
                                     interval.";
                        type uint64;
                    }
                    leaf ethIfH15MLinkStatusChanges {
                        config false;
                        description "The total number of the link status changes on the interface
                                     in historical 15-minute interval.
                                     The total number is increased when the link status changes
                                     from up to down, or from down to up.";
                        type uint32;
                    }
                    leaf ethIfH15MInBwUsingRatio {
                        config false;
                        description "An estimate of the interface's received bandwidth using ratio in 
                                     historical 15-minute interval.";
                        type int32 {
                            range 0..100;
                        }
                    }
                    leaf ethIfH15MOutBwUsingRatio {
                        config false;
                        description "An estimate of the interface's transmitted bandwidth using ratio 
                                     in historical 15-minute interval.";
                        type int32 {
                            range 0..100;
                        }
                    }
                }
            }
            container zxAnEthIfHis1DayPerfTable {
                description "The 1 day interval history performance data table of 
                             the ethernet interfaces.";
                list zxAnEthIfHis1DayPerfEntry {
                    config false;
                    description "The 1 day interval performance data entry of 
                                 the ethernet interfaces.";
                    max-elements 100;
                    key "ifIndex ethIfH1DIntervalNo";
                    leaf ifIndex {
                        description "A unique value, greater than zero, for each interface.  It
                                     is recommended that values are assigned contiguously
                                     starting from 1.  The value for each interface sub-layer
                                     must remain constant at least from one re-initialization of
                                     the entity's network management system to the next re-
                                     initialization.";
                        type int32 {
                            range 1..2147483647;
                        }
                    }
                    leaf ethIfH1DIntervalNo {
                        config false;
                        description "Performance data interval number 1 is the the most recent 
                                     previous interval; interval 7 is 1 week ago.  
                                     Intervals 2..7 are optional.";
                        type int32 {
                            range 1..7;
                        }
                    }
                    leaf ethIfH1DIntervalValidData {
                        config false;
                        description "Performance data valid flag. 
                                     true(1) means valid.  
                                     false(2) means invalidm and the performace data is useless.";
                        type int32;
                    }
                    leaf ethIfH1DDateTime {
                        config false;
                        description "The 1 day interval performance data generation time.";
                        type binary;
                    }
                    leaf ethIfH1DInOctets {
                        config false;
                        description "The total number of octets received on the interface,
                                     including framing characters in historical one day interval.";
                        type uint64;
                    }
                    leaf ethIfH1DInPkts {
                        config false;
                        description "The total number of packets received on the interface,
                                     including framing characters in historical one day interval.";
                        type uint64;
                    }
                    leaf ethIfH1DInUcastPkts {
                        config false;
                        description "The number of packets, delivered by this sub-layer to a
                                     higher (sub-)layer, which were not addressed to a multicast
                                     or broadcast address at this sub-layer in historical one day
                                     interval.";
                        type uint64;
                    }
                    leaf ethIfH1DInMcastPkts {
                        config false;
                        description "The number of packets, delivered by this sub-layer to a
                                     higher (sub-)layer, which were addressed to a multicast
                                     address at this sub-layer in historical one day interval.
                                     For a MAC layer protocol, this includes both Group and 
                                     Functional addresses.";
                        type uint64;
                    }
                    leaf ethIfH1DInBcastPkts {
                        config false;
                        description "The number of packets, delivered by this sub-layer to a
                                     higher (sub-)layer, which were addressed to a broadcast
                                     address at this sub-layer in historical one day interval.";
                        type uint64;
                    }
                    leaf ethIfH1DInOversizedPkts {
                        config false;
                        description "The number of packets,whick above the configured MTU-size,
                                     e.g.mtu = 2000 (frames >2000 are discarded) in current one
                                     day interval.";
                        type uint64;
                    }
                    leaf ethIfH1DInUndersizedPkts {
                        config false;
                        description "The number of packets,whick above the min port size,
                                     the value is 64 in historical one day interval.";
                        type uint64;
                    }
                    leaf ethIfH1DOutOctets {
                        config false;
                        description "The total number of octets transmitted out of the interface, 
                                     including framing characters in historical one day interval.";
                        type uint64;
                    }
                    leaf ethIfH1DOutPkts {
                        config false;
                        description "The total number of packets transmitted out of the interface, 
                                     including framing characters in historical one day interval.";
                        type uint64;
                    }
                    leaf ethIfH1DOutUcastPkts {
                        config false;
                        description "The total number of packets that higher-level protocols
                                     requested be transmitted, and which were not addressed to a
                                     multicast or broadcast address at this sub-layer, including
                                     those that were discarded or not sent in historical one day
                                     interval.";
                        type uint64;
                    }
                    leaf ethIfH1DOutMcastPkts {
                        config false;
                        description "The total number of packets that higher-level protocols
                                     requested be transmitted, and which were addressed to a
                                     multicast address at this sub-layer, including those that
                                     were discarded or not sent in historical one day interval.
                                     For a MAC layer protocol, this includes both Group and 
                                     Functional addresses.";
                        type uint64;
                    }
                    leaf ethIfH1DOutBcastPkts {
                        config false;
                        description "The total number of packets that higher-level protocols
                                     requested be transmitted, and which were addressed to a
                                     broadcast address at this sub-layer, including those that
                                     were discarded or not sent in historical one day interval.";
                        type uint64;
                    }
                    leaf ethIfH1DOutPausePkts {
                        config false;
                        description "A count of MAC Control frames transmitted on
                                     this interface with an opcode indicating the
                                     PAUSE operation in historical one day interval.";
                        type uint64;
                    }
                    leaf ethIfH1DOutDiscardPkts {
                        config false;
                        description "The number of outbound packets which were chosen to be
                                     discarded even though no errors had been detected to prevent
                                     their being transmitted in historical one day interval.";
                        type uint64;
                    }
                    leaf ethIfH1DOutCollisions {
                        config false;
                        description "A count of frames that are involved in out collision and 
                                     are subsequently transmitted successfully in historical one 
                                     day interval.";
                        type uint64;
                    }
                    leaf ethIfH1DSingleCollisions {
                        config false;
                        description "A count of frames that are involved in a single
                                     collision, and are subsequently transmitted
                                     successfully in historical one day interval.";
                        type uint64;
                    }
                    leaf ethIfH1DMultipleCollisions {
                        config false;
                        description "A count of frames that are involved in more
                                     than one collision and are subsequently
                                     transmitted successfully in historical one day
                                     interval.";
                        type uint64;
                    }
                    leaf ethIfH1DFcsErrors {
                        config false;
                        description "A count of frames received on a particular
                                     interface that are an integral number of octets
                                     in length but do not pass the FCS check.  This
                                     count does not include frames received with
                                     frame-too-long or frame-too-short error in historical
                                     one day interval.";
                        type uint64;
                    }
                    leaf ethIfH1DAlignmentErrors {
                        config false;
                        description "A count of frames received on a particular
                                     interface that are not an integral number of
                                     octets in length and do not pass the FCS check
                                     in historical one day interval.";
                        type uint64;
                    }
                    leaf ethIfH1DInCrcErrPkts {
                        config false;
                        description "The total number of CRC errored packets received on the interface
                                     in historical 1-day interval.";
                        type uint64;
                    }
                    leaf ethIfH1DInDiscardPkts {
                        config false;
                        description "The total number of discarded packets received on the interface
                                     in historical 1-day interval.";
                        type uint64;
                    }
                    leaf ethIfH1DInErrPkts {
                        config false;
                        description "The total number of errored packets received on the interface
                                     in historical 1-day interval.";
                        type uint64;
                    }
                    leaf ethIfH1DOutErrPkts {
                        config false;
                        description "The total number of errored packets that could not be transmitted 
                                     from the interface because of errors
                                     in historical 1-day interval.";
                        type uint64;
                    }
                    leaf ethIfH1DInDropEvents {
                        config false;
                        description "The total number of events in which packets received were 
                                     dropped by the probe due to lack of resources in historical 
                                     1-day interval.
                                     Note that this number is not necessarily the number of packets 
                                     dropped; it is just the number of times this condition has been 
                                     detected.";
                        type uint64;
                    }
                    leaf ethIfH1DOutDropEvents {
                        config false;
                        description "The total number of events in which packets transmitted were 
                                     dropped by the probe due to lack of resources in historical 
                                     1-day interval.
                                     Note that this number is not necessarily the number of packets 
                                     dropped; it is just the number of times this condition has been 
                                     detected.";
                        type uint64;
                    }
                    leaf ethIfH1DOutCrcErrPkts {
                        config false;
                        description "The total number of CRC errored packets transmitted out of the 
                                     interface in historical 1-day interval.";
                        type uint64;
                    }
                    leaf ethIfH1DOutOversizedPkts {
                        config false;
                        description "The total number of packets transmitted that were longer than 
                                     1518 octets (excluding framing bits, but including FCS octets) 
                                     and were otherwise well formed in historical 1-day interval.";
                        type uint64;
                    }
                    leaf ethIfH1DOutUndersizedPkts {
                        config false;
                        description "The total number of packets transmitted that were less than 
                                     64 octets long (excluding framing bits, but including FCS 
                                     octets) and were otherwise well formed in historical 1-day
                                     interval.";
                        type uint64;
                    }
                    leaf ethIfH1DInFragments {
                        config false;
                        description "The total number of packets received that were less than 64 
                                     octets in length (excluding framing bits but including FCS 
                                     octets) and had either a bad Frame Check Sequence (FCS) with 
                                     an integral number of octets (FCS Error) or a bad FCS with a 
                                     non-integral number of octets (Alignment Error) in historical 
                                     1-day interval.";
                        type uint64;
                    }
                    leaf ethIfH1DOutFragments {
                        config false;
                        description "The total number of packets transmitted that were less than 64 
                                     octets in length (excluding framing bits but including FCS 
                                     octets) and had either a bad Frame Check Sequence (FCS) with an 
                                     integral number of octets (FCS Error) or a bad FCS with a 
                                     non-integral number of octets (Alignment Error) in historical 
                                     1-day interval.";
                        type uint64;
                    }
                    leaf ethIfH1DInJabbers {
                        config false;
                        description "The total number of packets received that were longer than 
                                     1518 octets (excluding framing bits, but including FCS octets), 
                                     and had either a bad Frame Check Sequence (FCS) with an integral 
                                     number of octets (FCS Error) or a bad FCS with a non-integral
                                     number of octets (Alignment Error) in historical 1-day interval.
                                     
                                     Note that this definition of jabber is different than the 
                                     definition in IEEE-802.3 section 8.2.1.5 (10BASE5) and section 
                                     10.3.1.4 (10BASE2). These documents define jabber as the 
                                     condition where any packet exceeds 20 ms. The allowed range to 
                                     detect jabber is between 20 ms and 150 ms.";
                        type uint64;
                    }
                    leaf ethIfH1DOutJabbers {
                        config false;
                        description "The total number of packets transmitted that were longer than 
                                     1518 octets (excluding framing bits, but including FCS octets), 
                                     and had either a bad Frame Check Sequence (FCS) with an integral 
                                     number of octets (FCS Error) or a bad FCS with a non-integral
                                     number of octets (Alignment Error) in historical 1-day interval.
                                     
                                     Note that this definition of jabber is different than the 
                                     definition in IEEE-802.3 section 8.2.1.5 (10BASE5) and section 
                                     10.3.1.4 (10BASE2). These documents define jabber as the 
                                     condition where any packet exceeds 20 ms. The allowed range to 
                                     detect jabber is between 20 ms and 150 ms.";
                        type uint64;
                    }
                    leaf ethIfH1DInPkts64Octets {
                        config false;
                        description "The total number of packets (including bad packets) received 
                                     that were 64 octets in length (excluding framing bits but 
                                     including FCS octets) in historical 1-day interval.";
                        type uint64;
                    }
                    leaf ethIfH1DOutPkts64Octets {
                        config false;
                        description "The total number of packets (including bad packets) transmitted 
                                     that were 64 octets in length (excluding framing bits but 
                                     including FCS octets) in historical 1-day interval.";
                        type uint64;
                    }
                    leaf ethIfH1DInPkts65to127Octs {
                        config false;
                        description "The total number of packets (including bad packets) received 
                                     that were between 65 and 127 octets in length (excluding 
                                     framing bits but including FCS octets) in historical 1-day 
                                     interval.";
                        type uint64;
                    }
                    leaf ethIfH1DOutPkts65to127Octs {
                        config false;
                        description "The total number of packets (including bad packets) transmitted 
                                     that were between 65 and 127 octets in length (excluding 
                                     framing bits but including FCS octets) in historical 1-day 
                                     interval.";
                        type uint64;
                    }
                    leaf ethIfH1DInPkts128to255Octs {
                        config false;
                        description "The total number of packets (including bad packets) received 
                                     that were between 128 and 255 octets in length (excluding 
                                     framing bits but including FCS octets) in historical 1-day 
                                     interval.";
                        type uint64;
                    }
                    leaf ethIfH1DOutPkts128to255Octs {
                        config false;
                        description "The total number of packets (including bad packets) transmitted 
                                     that were between 128 and 255 octets in length (excluding 
                                     framing bits but including FCS octets) in historical 1-day 
                                     interval.";
                        type uint64;
                    }
                    leaf ethIfH1DInPkts256to511Octs {
                        config false;
                        description "The total number of packets (including bad packets) received 
                                     that were between 256 and 511 octets in length (excluding 
                                     framing bits but including FCS octets) in historical 1-day
                                     interval.";
                        type uint64;
                    }
                    leaf ethIfH1DOutPkts256to511Octs {
                        config false;
                        description "The total number of packets (including bad packets) transmitted 
                                     that were between 256 and 511 octets in length (excluding 
                                     framing bits but including FCS octets) in historical 1-day
                                     interval.";
                        type uint64;
                    }
                    leaf ethIfH1DInPkts512to1023 {
                        config false;
                        description "The total number of packets (including bad packets) received 
                                     that were between 512 and 1023 octets in length (excluding 
                                     framing bits but including FCS octets) in historical 1-day 
                                     interval.";
                        type uint64;
                    }
                    leaf ethIfH1DOutPkts512to1023 {
                        config false;
                        description "The total number of packets (including bad packets) transmitted 
                                     that were between 512 and 1023 octets in length (excluding 
                                     framing bits but including FCS octets) in historical 1-day 
                                     interval.";
                        type uint64;
                    }
                    leaf ethIfH1DInPkts1024to1518 {
                        config false;
                        description "The total number of packets (including bad packets) received 
                                     that were between 1024 and 1518 octets in length (excluding 
                                     framing bits but including FCS octets) in historical 1-day
                                     interval.";
                        type uint64;
                    }
                    leaf ethIfH1DOutPkts1024to1518 {
                        config false;
                        description "The total number of packets (including bad packets) transmitted 
                                     that were between 1024 and 1518 octets in length (excluding 
                                     framing bits but including FCS octets) in historical 1-day 
                                     interval.";
                        type uint64;
                    }
                    leaf ethIfH1DLinkStatusChanges {
                        config false;
                        description "The total number of the link status changes on the interface
                                     in historical 1-day interval.
                                     The total number is increased when the link status changes
                                     from up to down, or from down to up.";
                        type uint32;
                    }
                    leaf ethIfH1DInBwUsingRatio {
                        config false;
                        description "An estimate of the interface's received bandwidth using ratio in 
                                     historical 1-day interval.";
                        type int32 {
                            range 0..100;
                        }
                    }
                    leaf ethIfH1DOutBwUsingRatio {
                        config false;
                        description "An estimate of the interface's transmitted bandwidth using ratio 
                                     in historical 1-day interval.";
                        type int32 {
                            range 0..100;
                        }
                    }
                }
            }
            container zxAnEthIfAlmProfileConfTable {
                description "The performance alarm threshold profile table of the ethernet interfaces.";
                list zxAnEthIfAlmProfileConfEntry {
                    description "The performance alarm threshold profile entry of the ethernet interfaces.These
                                 variables in the profile configuration is optional,if not configured,
                                 it means the correspongding alarm is not reported, but the alarm and
                                 clear alarm threshold configuration is needed to bind.";
                    max-elements 100;
                    key "ethIfAlmProfileName ethIfPerfVariable";
                    leaf ethIfAlmProfileName {
                        description "The profile name.";
                        type string {
                            length 1..32;
                        }
                    }
                    leaf ethIfPerfVariable {
                        description "The object identifier of performance variables.";
                        type binary;
                    }
                    leaf ethIfRiseAlmThresh {
                        description "The threshold for rising alarm.";
                        type uint64;
                    }
                    leaf ethIfClrRiseAlmThresh {
                        description "The threshold for rising alarm restore.";
                        type uint64;
                    }
                    leaf ethIfRiseWarnThresh {
                        description "The threshold for rising warning.";
                        type uint64;
                    }
                    leaf ethIfClrRiseWarnThresh {
                        description "The threshold for rising warning restore.";
                        type uint64;
                    }
                    leaf ethIfFallWarnThresh {
                        description "The threshold for falling warning.";
                        type uint64;
                    }
                    leaf ethIfClrFallWarnThresh {
                        description "The threshold for falling warning restore.";
                        type uint64;
                    }
                    leaf ethIfFallAlmThresh {
                        description "The threshold for falling alarm.";
                        type uint64;
                    }
                    leaf ethIfClrFallAlmThresh {
                        description "The threshold for falling alarm restore.";
                        type uint64;
                    }
                    leaf ethIfThreshUsed {
                        description "The threshold used flag.";
                        type bits {
                            bit riseAlmThresh {
                                description "";
                                reference "";
                            }
                            bit riseAlmClrThresh {
                                description "";
                                reference "";
                            }
                            bit riseWarnThresh {
                                description "";
                                reference "";
                            }
                            bit riseWarnClrThresh {
                                description "";
                                reference "";
                            }
                            bit fallWarnThresh {
                                description "";
                                reference "";
                            }
                            bit fallWarnClrThresh {
                                description "";
                                reference "";
                            }
                            bit fallAlmThresh {
                                description "";
                                reference "";
                            }
                            bit fallAlmClrThresh {
                                description "";
                                reference "";
                            }
                        }
                    }
                }
            }
            container zxAnEthIfAlmProfileApplyTable {
                description "The performance alarm threshold profile configuration table of 
                             the ethernet interfaces.";
                list zxAnEthIfAlmProfileApplyEntry {
                    description "The performance alarm threshold profile configuration entry of 
                                 the ethernet interfaces.";
                    max-elements 100;
                    key "ifIndex";
                    leaf ifIndex {
                        description "A unique value, greater than zero, for each interface.  It
                                     is recommended that values are assigned contiguously
                                     starting from 1.  The value for each interface sub-layer
                                     must remain constant at least from one re-initialization of
                                     the entity's network management system to the next re-
                                     initialization.";
                        type int32 {
                            range 1..2147483647;
                        }
                    }
                    leaf ethIfAlmPrf {
                        description "The performance alarm threshold profile.";
                        type string {
                            length 1..32;
                        }
                    }
                }
            }
            container zxAnEthIfAlmProfileTable {
                description "The performance alarm threshold profile table of the ethernet interfaces.It can be used to
                             delete all of the performance alarm threshold profiles which has the same name configured
                             in 'zxAnEthIfAlmProfileConfTable'.";
                list zxAnEthIfAlmProfileEntry {
                    description "The performance alarm threshold profile entry of the ethernet interfaces.";
                    max-elements 100;
                    key "ethIfAlmProfileName";
                    leaf ethIfAlmProfileName {
                        description "The profile name.";
                        type string {
                            length 1..32;
                        }
                    }
                }
            }
            container zxAnEthIfCurrMinPerfTable {
                description "The minutes interval performance data table of the 
                             ethernet interfaces.";
                list zxAnEthIfCurrMinPerfEntry {
                    description "The minutes interval performance data entry of the 
                                 ethernet interfaces.";
                    max-elements 100;
                    key "ifIndex";
                    leaf ifIndex {
                        description "A unique value, greater than zero, for each interface.  It
                                     is recommended that values are assigned contiguously
                                     starting from 1.  The value for each interface sub-layer
                                     must remain constant at least from one re-initialization of
                                     the entity's network management system to the next re-
                                     initialization.";
                        type int32 {
                            range 1..2147483647;
                        }
                    }
                    leaf ethIfCMinTimeElapsed {
                        config false;
                        description "Number of seconds that have elapsed since the beginning of the 
                                     current minutes interval.";
                        type int32 {
                            range 0..86399;
                        }
                    }
                    leaf ethIfCMinInOctets {
                        config false;
                        description "The total number of octets received on the interface,
                                     including framing characters in current minutes interval.";
                        type uint64;
                    }
                    leaf ethIfCMinInPkts {
                        config false;
                        description "The total number of packets received on the interface,
                                     including framing characters in current minutes interval.";
                        type uint64;
                    }
                    leaf ethIfCMinInUcastPkts {
                        config false;
                        description "The number of packets, delivered by this sub-layer to a
                                     higher (sub-)layer, which were not addressed to a multicast
                                     or broadcast address at this sub-layer in current minutes
                                     interval.";
                        type uint64;
                    }
                    leaf ethIfCMinInMcastPkts {
                        config false;
                        description "The number of packets, delivered by this sub-layer to a
                                     higher (sub-)layer, which were addressed to a multicast
                                     address at this sub-layer in current minutes interval.
                                     For a MAC layer protocol, this includes both Group and 
                                     functional addresses.";
                        type uint64;
                    }
                    leaf ethIfCMinInBcastPkts {
                        config false;
                        description "The number of packets, delivered by this sub-layer to a
                                     higher (sub-)layer, which were addressed to a broadcast
                                     address at this sub-layer in current minutes interval.";
                        type uint64;
                    }
                    leaf ethIfCMinInOversizedPkts {
                        config false;
                        description "The number of packets,whick above the configured MTU-size,
                                     e.g.mtu = 2000 (frames >2000 are discarded) in current
                                     minutes interval.";
                        type uint64;
                    }
                    leaf ethIfCMinInUndersizedPkts {
                        config false;
                        description "The number of packets,whick above the min port size,
                                     the value is 64 in current minutes interval.";
                        type uint64;
                    }
                    leaf ethIfCMinOutOctets {
                        config false;
                        description "The total number of octets transmitted out of the interface, 
                                     including framing characters in current minutes interval.";
                        type uint64;
                    }
                    leaf ethIfCMinOutPkts {
                        config false;
                        description "The total number of packets transmitted out of the interface, 
                                     including framing characters in current minutes interval.";
                        type uint64;
                    }
                    leaf ethIfCMinOutUcastPkts {
                        config false;
                        description "The total number of packets that higher-level protocols
                                     requested be transmitted, and which were not addressed to a
                                     multicast or broadcast address at this sub-layer, including
                                     those that were discarded or not sent in current minutes
                                     interval.";
                        type uint64;
                    }
                    leaf ethIfCMinOutMcastPkts {
                        config false;
                        description "The total number of packets that higher-level protocols
                                     requested be transmitted, and which were addressed to a
                                     multicast address at this sub-layer, including those that
                                     were discarded or not sent in current minutes interval.
                                     For a MAC layer protocol, this includes both Group and 
                                     functional addresses.";
                        type uint64;
                    }
                    leaf ethIfCMinOutBcastPkts {
                        config false;
                        description "The total number of packets that higher-level protocols
                                     requested be transmitted, and which were addressed to a
                                     broadcast address at this sub-layer, including those that
                                     were discarded or not sent in current minutes interval.";
                        type uint64;
                    }
                    leaf ethIfCMinOutPausePkts {
                        config false;
                        description "A count of MAC Control frames transmitted on
                                     this interface with an opcode indicating the
                                     PAUSE operation in current minutes interval.";
                        type uint64;
                    }
                    leaf ethIfCMinOutDiscardPkts {
                        config false;
                        description "The number of outbound packets which were chosen to be
                                     discarded even though no errors had been detected to prevent
                                     their being transmitted in current minutes interval.";
                        type uint64;
                    }
                    leaf ethIfCMinOutCollisions {
                        config false;
                        description "A count of frames that are involved in out collision and 
                                     are subsequently transmitted successfully in current 
                                     minutes interval.";
                        type uint64;
                    }
                    leaf ethIfCMinSingleCollisions {
                        config false;
                        description "A count of frames that are involved in a single
                                     collision, and are subsequently transmitted
                                     successfully in current minutes interval.";
                        type uint64;
                    }
                    leaf ethIfCMinMultipleCollisions {
                        config false;
                        description "A count of frames that are involved in more
                                     than one collision and are subsequently
                                     transmitted successfully in current minutes
                                     interval.";
                        type uint64;
                    }
                    leaf ethIfCMinFcsErrors {
                        config false;
                        description "A count of frames received on a particular
                                     interface that are an integral number of octets
                                     in length but do not pass the FCS check.  This
                                     count does not include frames received with
                                     frame-too-long or frame-too-short error in current
                                     minutes interval.";
                        type uint64;
                    }
                    leaf ethIfCMinAlignmentErrors {
                        config false;
                        description "A count of frames received on a particular
                                     interface that are not an integral number of
                                     octets in length and do not pass the FCS check
                                     in current minutes interval.";
                        type uint64;
                    }
                    leaf ethIfCMinInCrcErrPkts {
                        config false;
                        description "The total number of CRC errored packets received on the interface
                                     in current minutes interval.";
                        type uint64;
                    }
                    leaf ethIfCMinInDiscardPkts {
                        config false;
                        description "The total number of discarded packets received on the interface
                                     in current minutes interval.";
                        type uint64;
                    }
                    leaf ethIfCMinInErrPkts {
                        config false;
                        description "The total number of errored packets received on the interface
                                     in current minutes interval.";
                        type uint64;
                    }
                    leaf ethIfCMinOutErrPkts {
                        config false;
                        description "The total number of errored packets that could not be transmitted 
                                     from the interface because of errors in current minutes 
                                     interval.";
                        type uint64;
                    }
                    leaf ethIfCMinInDropEvents {
                        config false;
                        description "The total number of events in which packets received were 
                                     dropped by the probe due to lack of resources.
                                     Note that this number is not necessarily the number of packets 
                                     dropped; it is just the number of times this condition has been 
                                     detected in current minutes interval.";
                        type uint64;
                    }
                    leaf ethIfCMinOutDropEvents {
                        config false;
                        description "The total number of events in which packets transmitted were 
                                     dropped by the probe due to lack of resources.
                                     Note that this number is not necessarily the number of packets 
                                     dropped; it is just the number of times this condition has been 
                                     detected in current minutes interval.";
                        type uint64;
                    }
                    leaf ethIfCMinOutCrcErrPkts {
                        config false;
                        description "The total number of CRC errored packets transmitted out of the 
                                     interface in current minutes interval.";
                        type uint64;
                    }
                    leaf ethIfCMinOutOversizedPkts {
                        config false;
                        description "The total number of packets transmitted that were longer than 
                                     1518 octets (excluding framing bits, but including FCS octets) 
                                     and were otherwise well formed in current minutes interval.";
                        type uint64;
                    }
                    leaf ethIfCMinOutUndersizedPkts {
                        config false;
                        description "The total number of packets transmitted that were less than 
                                     64 octets long (excluding framing bits, but including FCS 
                                     octets) and were otherwise well formed in current minutes 
                                     interval.";
                        type uint64;
                    }
                    leaf ethIfCMinInFragments {
                        config false;
                        description "The total number of packets received that were less than 64 
                                     octets in length (excluding framing bits but including FCS 
                                     octets) and had either a bad Frame Check Sequence (FCS) with 
                                     an integral number of octets (FCS Error) or a bad FCS with a 
                                     non-integral number of octets (Alignment Error) in current 
                                     minutes interval.";
                        type uint64;
                    }
                    leaf ethIfCMinOutFragments {
                        config false;
                        description "The total number of packets transmitted that were less than 64 
                                     octets in length (excluding framing bits but including FCS 
                                     octets) and had either a bad Frame Check Sequence (FCS) with an 
                                     integral number of octets (FCS Error) or a bad FCS with a 
                                     non-integral number of octets (Alignment Error) in current 
                                     minutes interval.";
                        type uint64;
                    }
                    leaf ethIfCMinInJabbers {
                        config false;
                        description "The total number of packets received that were longer than 
                                     1518 octets (excluding framing bits, but including FCS octets), 
                                     and had either a bad Frame Check Sequence (FCS) with an integral 
                                     number of octets (FCS Error) or a bad FCS with a non-integral
                                     number of octets (Alignment Error).
                                     
                                     Note that this definition of jabber is different than the 
                                     definition in IEEE-802.3 section 8.2.1.5 (10BASE5) and section 
                                     10.3.1.4 (10BASE2). These documents define jabber as the 
                                     condition where any packet exceeds 20 ms. The allowed range to 
                                     detect jabber is between 20 ms and 150 ms in current minutes 
                                     interval.";
                        type uint64;
                    }
                    leaf ethIfCMinOutJabbers {
                        config false;
                        description "The total number of packets transmitted that were longer than 
                                     1518 octets (excluding framing bits, but including FCS octets), 
                                     and had either a bad Frame Check Sequence (FCS) with an integral 
                                     number of octets (FCS Error) or a bad FCS with a non-integral
                                     number of octets (Alignment Error).
                                     
                                     Note that this definition of jabber is different than the 
                                     definition in IEEE-802.3 section 8.2.1.5 (10BASE5) and section 
                                     10.3.1.4 (10BASE2). These documents define jabber as the 
                                     condition where any packet exceeds 20 ms. The allowed range to 
                                     detect jabber is between 20 ms and 150 ms in current minutes 
                                     interval.";
                        type uint64;
                    }
                    leaf ethIfCMinInPkts64Octets {
                        config false;
                        description "The total number of packets (including bad packets) received 
                                     that were 64 octets in length (excluding framing bits but 
                                     including FCS octets) in current minutes interval.";
                        type uint64;
                    }
                    leaf ethIfCMinOutPkts64Octets {
                        config false;
                        description "The total number of packets (including bad packets) transmitted 
                                     that were 64 octets in length (excluding framing bits but 
                                     including FCS octets) in current minutes interval.";
                        type uint64;
                    }
                    leaf ethIfCMinInPkts65to127Octs {
                        config false;
                        description "The total number of packets (including bad packets) received 
                                     that were between 65 and 127 octets in length (excluding 
                                     framing bits but including FCS octets) in current minutes 
                                     interval.";
                        type uint64;
                    }
                    leaf ethIfCMinOutPkts65to127Octs {
                        config false;
                        description "The total number of packets (including bad packets) transmitted 
                                     that were between 65 and 127 octets in length (excluding 
                                     framing bits but including FCS octets) in current minutes 
                                     interval.";
                        type uint64;
                    }
                    leaf ethIfCMinInPkts128to255Octs {
                        config false;
                        description "The total number of packets (including bad packets) received 
                                     that were between 128 and 255 octets in length (excluding 
                                     framing bits but including FCS octets) in current minutes 
                                     interval.";
                        type uint64;
                    }
                    leaf ethIfCMinOutPkts128to255Octs {
                        config false;
                        description "The total number of packets (including bad packets) transmitted 
                                     that were between 128 and 255 octets in length (excluding 
                                     framing bits but including FCS octets) in current minutes 
                                     interval.";
                        type uint64;
                    }
                    leaf ethIfCMinInPkts256to511Octs {
                        config false;
                        description "The total number of packets (including bad packets) received 
                                     that were between 256 and 511 octets in length (excluding 
                                     framing bits but including FCS octets) in current minutes
                                     interval.";
                        type uint64;
                    }
                    leaf ethIfCMinOutPkts256to511Octs {
                        config false;
                        description "The total number of packets (including bad packets) transmitted 
                                     that were between 256 and 511 octets in length (excluding 
                                     framing bits but including FCS octets) in current minutes
                                     interval.";
                        type uint64;
                    }
                    leaf ethIfCMinInPkts512to1023 {
                        config false;
                        description "The total number of packets (including bad packets) received 
                                     that were between 512 and 1023 octets in length (excluding 
                                     framing bits but including FCS octets) in current minutes 
                                     interval.";
                        type uint64;
                    }
                    leaf ethIfCMinOutPkts512to1023 {
                        config false;
                        description "The total number of packets (including bad packets) transmitted 
                                     that were between 512 and 1023 octets in length (excluding 
                                     framing bits but including FCS octets) in current minutes 
                                     interval.";
                        type uint64;
                    }
                    leaf ethIfCMinInPkts1024to1518 {
                        config false;
                        description "The total number of packets (including bad packets) received 
                                     that were between 1024 and 1518 octets in length (excluding 
                                     framing bits but including FCS octets) in current minutes
                                     interval.";
                        type uint64;
                    }
                    leaf ethIfCMinOutPkts1024to1518 {
                        config false;
                        description "The total number of packets (including bad packets) transmitted 
                                     that were between 1024 and 1518 octets in length (excluding 
                                     framing bits but including FCS octets) in current minutes 
                                     interval.";
                        type uint64;
                    }
                    leaf ethIfCMinLinkStatusChanges {
                        config false;
                        description "The total number of the link status changes on the interface
                                     in in current minutes interval.
                                     The total number is increased when the link status changes
                                     from up to down, or from down to up.";
                        type uint32;
                    }
                    leaf ethIfCMinInBwUsingRatio {
                        config false;
                        description "An estimate of the interface's received bandwidth using ratio in 
                                     current minutes interval.";
                        type int32 {
                            range 0..100;
                        }
                    }
                    leaf ethIfCMinOutBwUsingRatio {
                        config false;
                        description "An estimate of the interface's transmitted bandwidth using ratio 
                                     in current minutes interval.";
                        type int32 {
                            range 0..100;
                        }
                    }
                    leaf ethIfCMinReset {
                        description "Clear all the current minutes performance variables.
                                     When get this variable, always return 1.";
                        type enumeration {
                            enum perfReset {
                                value 1;
                                description "";
                            }
                        }
                    }
                }
            }
            container zxAnEthIfHisMinPerfTable {
                description "The minutes interval history performance data table of 
                             the ethernet interfaces.";
                list zxAnEthIfHisMinPerfEntry {
                    config false;
                    description "The minutes interval performance data entry of the 
                                 ethernet interfaces.";
                    max-elements 100;
                    key "ifIndex ethIfHMinIntervalNo";
                    leaf ifIndex {
                        description "A unique value, greater than zero, for each interface.  It
                                     is recommended that values are assigned contiguously
                                     starting from 1.  The value for each interface sub-layer
                                     must remain constant at least from one re-initialization of
                                     the entity's network management system to the next re-
                                     initialization.";
                        type int32 {
                            range 1..2147483647;
                        }
                    }
                    leaf ethIfHMinIntervalNo {
                        config false;
                        description "The performance data interval number.";
                        type int32;
                    }
                    leaf ethIfHMinIntervalValidData {
                        config false;
                        description "Performance data valid flag. 
                                     true(1) means valid.  
                                     false(2) means invalidm and the performace data is useless.";
                        type int32;
                    }
                    leaf ethIfHMinDateTime {
                        config false;
                        description "The minutes interval performance data generation time.";
                        type binary;
                    }
                    leaf ethIfHMinInOctets {
                        config false;
                        description "The total number of octets received on the interface,
                                     including framing characters in historical minutes interval.";
                        type uint64;
                    }
                    leaf ethIfHMinInPkts {
                        config false;
                        description "The total number of packets received on the interface,
                                     including framing characters in historical minutes interval.";
                        type uint64;
                    }
                    leaf ethIfHMinInUcastPkts {
                        config false;
                        description "The number of packets, delivered by this sub-layer to a
                                     higher (sub-)layer, which were not addressed to a multicast
                                     or broadcast address at this sub-layer in historical minutes
                                     interval.";
                        type uint64;
                    }
                    leaf ethIfHMinInMcastPkts {
                        config false;
                        description "The number of packets, delivered by this sub-layer to a
                                     higher (sub-)layer, which were addressed to a multicast
                                     address at this sub-layer in historical minutes interval.
                                     For a MAC layer protocol, this includes both Group and 
                                     Functional addresses.";
                        type uint64;
                    }
                    leaf ethIfHMinInBcastPkts {
                        config false;
                        description "The number of packets, delivered by this sub-layer to a
                                     higher (sub-)layer, which were addressed to a broadcast
                                     address at this sub-layer in historical minutes interval.";
                        type uint64;
                    }
                    leaf ethIfHMinInOversizedPkts {
                        config false;
                        description "The number of packets,whick above the configured MTU-size,
                                     e.g.mtu = 2000 (frames >2000 are discarded) in historical
                                     minutes interval.";
                        type uint64;
                    }
                    leaf ethIfHMinInUndersizedPkts {
                        config false;
                        description "The number of packets,whick above the min port size,
                                     the value is 64 in historical minutes interval.";
                        type uint64;
                    }
                    leaf ethIfHMinOutOctets {
                        config false;
                        description "The total number of octets transmitted out of the interface, 
                                     including framing characters in historical minutes interval.";
                        type uint64;
                    }
                    leaf ethIfHMinOutPkts {
                        config false;
                        description "The total number of packets transmitted out of the interface, 
                                     including framing characters in historical minutes interval.";
                        type uint64;
                    }
                    leaf ethIfHMinOutUcastPkts {
                        config false;
                        description "The total number of packets that higher-level protocols
                                     requested be transmitted, and which were not addressed to a
                                     multicast or broadcast address at this sub-layer, including
                                     those that were discarded or not sent in historical minutes
                                     interval.";
                        type uint64;
                    }
                    leaf ethIfHMinOutMcastPkts {
                        config false;
                        description "The total number of packets that higher-level protocols
                                     requested be transmitted, and which were addressed to a
                                     multicast address at this sub-layer, including those that
                                     were discarded or not sent in historical minutes interval.
                                     For a MAC layer protocol, this includes both Group and 
                                     functional addresses.";
                        type uint64;
                    }
                    leaf ethIfHMinOutBcastPkts {
                        config false;
                        description "The total number of packets that higher-level protocols
                                     requested be transmitted, and which were addressed to a
                                     broadcast address at this sub-layer, including those that
                                     were discarded or not sent in historical minutes interval.";
                        type uint64;
                    }
                    leaf ethIfHMinOutPausePkts {
                        config false;
                        description "A count of MAC Control frames transmitted on
                                     this interface with an opcode indicating the
                                     PAUSE operation in historical minutes interval.";
                        type uint64;
                    }
                    leaf ethIfHMinOutDiscardPkts {
                        config false;
                        description "The number of outbound packets which were chosen to be
                                     discarded even though no errors had been detected to prevent
                                     their being transmitted in historical minutes interval.";
                        type uint64;
                    }
                    leaf ethIfHMinOutCollisions {
                        config false;
                        description "A count of frames that are involved in out collision and 
                                     are subsequently transmitted successfully in historical 
                                     minutes interval.";
                        type uint64;
                    }
                    leaf ethIfHMinSingleCollisions {
                        config false;
                        description "A count of frames that are involved in a single
                                     collision, and are subsequently transmitted
                                     successfully in historical minutes interval.";
                        type uint64;
                    }
                    leaf ethIfHMinMultipleCollisions {
                        config false;
                        description "A count of frames that are involved in more
                                     than one collision and are subsequently
                                     transmitted successfully in historical minutes
                                     interval.";
                        type uint64;
                    }
                    leaf ethIfHMinFcsErrors {
                        config false;
                        description "A count of frames received on a particular
                                     interface that are an integral number of octets
                                     in length but do not pass the FCS check.  This
                                     count does not include frames received with
                                     frame-too-long or frame-too-short error in historical
                                     minutes interval.";
                        type uint64;
                    }
                    leaf ethIfHMinAlignmentErrors {
                        config false;
                        description "A count of frames received on a particular
                                     interface that are not an integral number of
                                     octets in length and do not pass the FCS check
                                     in historical minutes interval.";
                        type uint64;
                    }
                    leaf ethIfHMinInCrcErrPkts {
                        config false;
                        description "The total number of CRC errored packets received on the interface
                                     in historical minutes interval.";
                        type uint64;
                    }
                    leaf ethIfHMinInDiscardPkts {
                        config false;
                        description "The total number of discarded packets received on the interface
                                     in historical minutes interval.";
                        type uint64;
                    }
                    leaf ethIfHMinInErrPkts {
                        config false;
                        description "The total number of errored packets received on the interface
                                     in historical minutes interval.";
                        type uint64;
                    }
                    leaf ethIfHMinOutErrPkts {
                        config false;
                        description "The total number of errored packets that could not be transmitted 
                                     from the interface because of errors 
                                     in historical minutes interval.";
                        type uint64;
                    }
                    leaf ethIfHMinInDropEvents {
                        config false;
                        description "The total number of events in which packets received were 
                                     dropped by the probe due to lack of resources.
                                     Note that this number is not necessarily the number of packets 
                                     dropped; it is just the number of times this condition has been 
                                     detected in historical minutes interval.";
                        type uint64;
                    }
                    leaf ethIfHMinOutDropEvents {
                        config false;
                        description "The total number of events in which packets transmitted were 
                                     dropped by the probe due to lack of resources.
                                     Note that this number is not necessarily the number of packets 
                                     dropped; it is just the number of times this condition has been 
                                     detected in historical minutes interval.";
                        type uint64;
                    }
                    leaf ethIfHMinOutCrcErrPkts {
                        config false;
                        description "The total number of CRC errored packets transmitted out of the 
                                     interface in historical minutes interval.";
                        type uint64;
                    }
                    leaf ethIfHMinOutOversizedPkts {
                        config false;
                        description "The total number of packets transmitted that were longer than 
                                     1518 octets (excluding framing bits, but including FCS octets) 
                                     and were otherwise well formed in historical minutes 
                                     interval.";
                        type uint64;
                    }
                    leaf ethIfHMinOutUndersizedPkts {
                        config false;
                        description "The total number of packets transmitted that were less than 
                                     64 octets long (excluding framing bits, but including FCS 
                                     octets) and were otherwise well formed in historical minutes 
                                     interval.";
                        type uint64;
                    }
                    leaf ethIfHMinInFragments {
                        config false;
                        description "The total number of packets received that were less than 64 
                                     octets in length (excluding framing bits but including FCS 
                                     octets) and had either a bad Frame Check Sequence (FCS) with 
                                     an integral number of octets (FCS Error) or a bad FCS with a 
                                     non-integral number of octets (Alignment Error) in historical 
                                     minutes interval.";
                        type uint64;
                    }
                    leaf ethIfHMinOutFragments {
                        config false;
                        description "The total number of packets transmitted that were less than 64 
                                     octets in length (excluding framing bits but including FCS 
                                     octets) and had either a bad Frame Check Sequence (FCS) with an 
                                     integral number of octets (FCS Error) or a bad FCS with a 
                                     non-integral number of octets (Alignment Error) in historical 
                                     minutes interval.";
                        type uint64;
                    }
                    leaf ethIfHMinInJabbers {
                        config false;
                        description "The total number of packets received that were longer than 
                                     1518 octets (excluding framing bits, but including FCS octets), 
                                     and had either a bad Frame Check Sequence (FCS) with an integral 
                                     number of octets (FCS Error) or a bad FCS with a non-integral
                                     number of octets (Alignment Error).
                                     
                                     Note that this definition of jabber is different than the 
                                     definition in IEEE-802.3 section 8.2.1.5 (10BASE5) and section 
                                     10.3.1.4 (10BASE2). These documents define jabber as the 
                                     condition where any packet exceeds 20 ms. The allowed range to 
                                     detect jabber is between 20 ms and 150 ms in historical
                                     minutes interval.";
                        type uint64;
                    }
                    leaf ethIfHMinOutJabbers {
                        config false;
                        description "The total number of packets transmitted that were longer than 
                                     1518 octets (excluding framing bits, but including FCS octets), 
                                     and had either a bad Frame Check Sequence (FCS) with an integral 
                                     number of octets (FCS Error) or a bad FCS with a non-integral
                                     number of octets (Alignment Error).
                                     
                                     Note that this definition of jabber is different than the 
                                     definition in IEEE-802.3 section 8.2.1.5 (10BASE5) and section 
                                     10.3.1.4 (10BASE2). These documents define jabber as the 
                                     condition where any packet exceeds 20 ms. The allowed range to 
                                     detect jabber is between 20 ms and 150 ms in historical
                                     minutes interval.";
                        type uint64;
                    }
                    leaf ethIfHMinInPkts64Octets {
                        config false;
                        description "The total number of packets (including bad packets) received 
                                     that were 64 octets in length (excluding framing bits but 
                                     including FCS octets) in historical minutes interval.";
                        type uint64;
                    }
                    leaf ethIfHMinOutPkts64Octets {
                        config false;
                        description "The total number of packets (including bad packets) transmitted 
                                     that were 64 octets in length (excluding framing bits but 
                                     including FCS octets) in historical minutes interval.";
                        type uint64;
                    }
                    leaf ethIfHMinInPkts65to127Octs {
                        config false;
                        description "The total number of packets (including bad packets) received 
                                     that were between 65 and 127 octets in length (excluding 
                                     framing bits but including FCS octets) in historical 
                                     minutes interval.";
                        type uint64;
                    }
                    leaf ethIfHMinOutPkts65to127Octs {
                        config false;
                        description "The total number of packets (including bad packets) transmitted 
                                     that were between 65 and 127 octets in length (excluding 
                                     framing bits but including FCS octets) in historical minutes 
                                     interval.";
                        type uint64;
                    }
                    leaf ethIfHMinInPkts128to255Octs {
                        config false;
                        description "The total number of packets (including bad packets) received 
                                     that were between 128 and 255 octets in length (excluding 
                                     framing bits but including FCS octets) in historical minutes 
                                     interval.";
                        type uint64;
                    }
                    leaf ethIfHMinOutPkts128to255Octs {
                        config false;
                        description "The total number of packets (including bad packets) transmitted 
                                     that were between 128 and 255 octets in length (excluding 
                                     framing bits but including FCS octets) in historical minutes 
                                     interval.";
                        type uint64;
                    }
                    leaf ethIfHMinInPkts256to511Octs {
                        config false;
                        description "The total number of packets (including bad packets) received 
                                     that were between 256 and 511 octets in length (excluding 
                                     framing bits but including FCS octets) in historical minutes
                                     interval.";
                        type uint64;
                    }
                    leaf ethIfHMinOutPkts256to511Octs {
                        config false;
                        description "The total number of packets (including bad packets) transmitted 
                                     that were between 256 and 511 octets in length (excluding 
                                     framing bits but including FCS octets) in historical minutes
                                     interval.";
                        type uint64;
                    }
                    leaf ethIfHMinInPkts512to1023 {
                        config false;
                        description "The total number of packets (including bad packets) received 
                                     that were between 512 and 1023 octets in length (excluding 
                                     framing bits but including FCS octets) in historical minutes 
                                     interval.";
                        type uint64;
                    }
                    leaf ethIfHMinOutPkts512to1023 {
                        config false;
                        description "The total number of packets (including bad packets) transmitted 
                                     that were between 512 and 1023 octets in length (excluding 
                                     framing bits but including FCS octets) in historical minutes 
                                     interval.";
                        type uint64;
                    }
                    leaf ethIfHMinInPkts1024to1518 {
                        config false;
                        description "The total number of packets (including bad packets) received 
                                     that were between 1024 and 1518 octets in length (excluding 
                                     framing bits but including FCS octets) in historical minutes
                                     interval.";
                        type uint64;
                    }
                    leaf ethIfHMinOutPkts1024to1518 {
                        config false;
                        description "The total number of packets (including bad packets) transmitted 
                                     that were between 1024 and 1518 octets in length (excluding 
                                     framing bits but including FCS octets) in historical minutes 
                                     interval.";
                        type uint64;
                    }
                    leaf ethIfHMinLinkStatusChanges {
                        config false;
                        description "The total number of the link status changes on the interface
                                     in historical minutes interval.
                                     The total number is increased when the link status changes
                                     from up to down, or from down to up.";
                        type uint32;
                    }
                    leaf ethIfHMinInBwUsingRatio {
                        config false;
                        description "An estimate of the interface's received bandwidth using ratio in 
                                     historical minutes interval.";
                        type int32 {
                            range 0..100;
                        }
                    }
                    leaf ethIfHMinOutBwUsingRatio {
                        config false;
                        description "An estimate of the interface's transmitted bandwidth using ratio 
                                     in historical minutes interval.";
                        type int32 {
                            range 0..100;
                        }
                    }
                }
            }
            container zxAnEthIfMinPerfTable {
                description "";
                list zxAnEthIfMinPerfEntry {
                    config false;
                    description " ";
                    max-elements 1;
                    key "ifIndex";
                    leaf ifIndex {
                        description "A unique value, greater than zero, for each interface.  It
                                     is recommended that values are assigned contiguously
                                     starting from 1.  The value for each interface sub-layer
                                     must remain constant at least from one re-initialization of
                                     the entity's network management system to the next re-
                                     initialization.";
                        type int32 {
                            range 1..2147483647;
                        }
                    }
                    leaf numberOfMinIntervals {
                        config false;
                        description "The total number of 15-minute PM intervals for which data was collected.";
                        type int32 {
                            range 0..96;
                        }
                    }
                    leaf nonValidMinIntervals {
                        config false;
                        description "The number of 15-minute PM intervals for which the data is considered to be invalid or incomplete.";
                        type int32 {
                            range 0..96;
                        }
                    }
                }
            }
            container zxAnEthIf1DayPerfTable {
                description "";
                list zxAnEthIf1DayPerfEntry {
                    config false;
                    description "";
                    max-elements 1;
                    key "ifIndex";
                    leaf ifIndex {
                        description "A unique value, greater than zero, for each interface.  It
                                     is recommended that values are assigned contiguously
                                     starting from 1.  The value for each interface sub-layer
                                     must remain constant at least from one re-initialization of
                                     the entity's network management system to the next re-
                                     initialization.";
                        type int32 {
                            range 1..2147483647;
                        }
                    }
                    leaf numberOf1DayIntervals {
                        config false;
                        description "The total number of 15-minute PM intervals for which data was collected.";
                        type int32 {
                            range 0..7;
                        }
                    }
                    leaf nonValid1DayIntervals {
                        config false;
                        description "The number of 15-minute PM intervals for which the data is considered to be invalid or incomplete.";
                        type int32 {
                            range 0..7;
                        }
                    }
                }
            }
        }
    }
}
