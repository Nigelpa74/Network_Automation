module zte-an-mac {
    namespace 'http://www.zte.com.cn/zxr10/netconf/schema/rosng/msmac';
    prefix msmac;
    import zxr10-netconf-defs {
        prefix ncd;
        revision-date 2017-08-15;
    }
    organization "ZTE Corporation";
    contact "Huang XuRui  ZTE Corporation
                         Mail: huang.xurui@zte.com.cn
                         Tel : +86-21-68897477
                  
                         Kong WenHui ZTE Corporation
                         Mail: kong.wenhui@zte.com.cn
                         Tel : +86-21-68897477";
    description "This MIB defines MAC forwarding managed objects of zte
                 Access Node.";
    revision 2014-04-09 {
        description "The modification of this mib file is following:
                     - add the mac type 'static(3)' for zxAnMacFwdAddrStatus.";
    }
    revision 2011-09-17 {
        description "The modification of this mib file is following:
                     - modify the description of some variables.";
    }
    revision 2011-08-17 {
        description "Initial version of this MIB module.";
    }
    container zxAnMac {
        description "";
        container zxAnMacObjects {
            description "";
            container zxAnMacTableObjects {
                description "";
                container zxAnMacFwdVlanConfTable {
                    description "A table containing MAC forwarding configuration based on VLAN.";
                    list zxAnMacFwdVlanConfEntry {
                        description "Entry for zxAnMacFwdVlanConfTable.";
                        max-elements 4094;
                        key "zxAnMacFwdVlanConfVid";
                        leaf zxAnMacFwdVlanConfVid {
                            description "The VLAN ID of MAC forwarding configuration.";
                            type int32 {
                                range 1..4094;
                            }
                        }
                        leaf zxAnMacFwdVlanConfAgingTime {
                            description "The MAC aging time based on VLAN.";
                            type int32 {
                                range 10..1000000;
                            }
                            default 300;
                        }
                    }
                }
            }
        }
    }
}
