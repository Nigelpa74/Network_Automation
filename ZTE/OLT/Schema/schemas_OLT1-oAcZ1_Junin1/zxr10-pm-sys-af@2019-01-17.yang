module zxr10-pm-sys-af {
  namespace 'http://www.zte.com.cn/zxr10/netconf/schema/rosng/pm-sys-af'
            ;
  prefix pm-sys-af ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  revision 2019-01-17 {
    description 'shelf range 0-255.slot range 0-255.'
                ;
  }
  revision 2018-01-31 {
    description 'Add leaf af-node for contain ports.'
                ;
  }
  revision 2018-01-28 {
    description 'Initialize version.'
                ;
  }
  container state {
    config false ;
    container sys {
      container ports {
        list port {
          key 'shelf slot subslot portno'
              ;
          leaf shelf {
            description 'Shelf number.'
                        ;
            type uint8 {
              range 0..255 {
                description 'shelf range.'
                            ;
              }
            }
          }
          leaf slot {
            description 'Slot number.'
                        ;
            type uint8 {
              range 0..255 {
                description 'slot range.'
                            ;
              }
            }
          }
          leaf subslot {
            description 'Subslot number.'
                        ;
            type uint8 ;
          }
          leaf portno {
            description 'Port number.'
                        ;
            type uint32 ;
          }
          leaf porttype {
            description 'Port type.'
                        ;
            type uint16 ;
          }
          leaf portname {
            description 'Port name.'
                        ;
            type string ;
          }
          leaf portphystatus {
            description 'Port physical status.'
                        ;
            type uint8 ;
          }
          leaf porteoproperty {
            description 'Port electric optical property.'
                        ;
            type uint8 ;
          }
          leaf portspeed {
            description 'Port speed.'
                        ;
            type uint32 ;
          }
          leaf af-node {
            description 'Port af-node.'
                        ;
            type ncd:af-name {
              length 1..32 ;
            }
          }
          ncd:select 'shelf slot subslot portno'
                     ;
        }
      }
    }
  }
}
