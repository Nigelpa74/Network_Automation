module zxr10-multicast-action {
  namespace 'http://www.zte.com.cn/zxr10/netconf/schema/rosng/multicast-action'
            ;
  prefix zx_mcast_action ;
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The Netconf module  to describe mcast operation.'
              ;
  revision 2020-05-26 ;
  container operation {
    description 'Mcast operation commands'
                ;
    config false ;
    container mcast {
      description 'Mcast operation commands'
                  ;
      container clear {
        container igmp {
          description 'Igmp operation commands'
                      ;
          container zxAnIgmpStatsObjects {
            container zxAnIgmpPktStatsTable {
              description 'A table that contains IGMP packet statistics informa'
                        + 'tion.'
                          ;
              list zxAnIgmpPktStatsEntry {
                description "The action object to reset the statistics values.W"
                          + "hen reset the statistics, it must be set to '1', a"
                          + "ssociated with corresponding index.When be queried"
                          + ", it always returns '0'."
                            ;
                key 'zxAnIgmpMVid ifIndex zxAnSubIfIndex'
                    ;
                max-elements 1 ;
                leaf zxAnIgmpMVid {
                  description 'Multicast VLAN ID.'
                              ;
                  type int32 {
                    range 1..4094 ;
                  }
                }
                leaf ifIndex {
                  description "A unique value, greater than zero, for each inte"
                            + "rface.  It is recommended that values are assign"
                            + "ed contiguously starting from 1.  The value for "
                            + "each interface sub-layer must remain constant at"
                            + " least from one re-initialization of the entity'"
                            + "s network management system to the next re-initi"
                            + "alization."
                              ;
                  type int32 {
                    range 0..2147483647 ;
                  }
                }
                leaf zxAnSubIfIndex {
                  description 'Sub-interface index at this interface.'
                              ;
                  type int32 ;
                }
              }
            }
          }
        }
        container mld {
          container zxAnMldStatsObjects {
            container zxAnMldPktStatsTable {
              list zxAnMldPktStatsEntry {
                description "The action object to reset the statistics values.W"
                          + "hen reset the statistics, it must be set to '1', a"
                          + "ssociated with corresponding index.When be queried"
                          + ", it always returns '0'."
                            ;
                key 'zxAnMldMVid ifIndex zxAnSubIfIndex'
                    ;
                max-elements 1 ;
                leaf zxAnMldMVid {
                  description 'Multicast VLAN ID.'
                              ;
                  type int32 {
                    range 1..4094 ;
                  }
                }
                leaf ifIndex {
                  description "A unique value, greater than zero, for each inte"
                            + "rface.  It is recommended that values are assign"
                            + "ed contiguously starting from 1.  The value for "
                            + "each interface sub-layer must remain constant at"
                            + " least from one re-initialization of the entity'"
                            + "s network management system to the next re-initi"
                            + "alization."
                              ;
                  type int32 {
                    range 0..2147483647 ;
                  }
                }
                leaf zxAnSubIfIndex {
                  description 'Sub-interface index at this interface.'
                              ;
                  type int32 ;
                }
              }
            }
          }
        }
      }
    }
  }
}
