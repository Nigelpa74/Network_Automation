module zxr10-ssh {
  namespace 'http://www.zte.com.cn/zxr10/netconf/schema/rosng/ssh'
            ;
  prefix ssh ;
  yang-version 1 ;
  import zxr10-netconf-defs {
    prefix ncd ;
    revision-date 2019-07-16 ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The netconf module to describe the SSH(Secure Shell).'
              ;
  revision 2022-02-28 {
    description "1.Add leaf-list '/configuration/ssh/ssh-server/recognize-packe"
              + "t/recognize-packet-type'
\n2.Add leaf key node '/configuration"
              + "/ssh/ssh-server/recognize-packet/recognize-packet-type/type'"
                ;
  }
  revision 2021-12-16 {
    description "1.Add leaf node '/configuration/ssh/ssh-client/first-time/stat"
              + "us'
\n2.Add leaf node '/configuration/ssh/ssh-client/signature"
              + "-authen/status'
\n3.Add list node '/state/ssh/ssh-client/peer-"
              + "public-key/ipv4'
\n4.Add list node '/state/ssh/ssh-client/peer"
              + "-public-key/ipv6'
\n5.Add rpc leaf node '/rpc/client-import-pe"
              + "er-public-key/ipv4-addr'
\n6.Add rpc leaf node '/rpc/client-im"
              + "port-peer-public-key/ipv6-addr'
\n7.Add rpc leaf node '/rpc/cl"
              + "ient-import-peer-public-key/key-file'
\n8.Add rpc leaf node '/"
              + "rpc/client-clear-peer-public-key/ipv4-addr'
\n9.Add rpc leaf n"
              + "ode '/rpc/client-clear-peer-public-key/ipv6-addr'
\n10.Add rpc"
              + " leaf node '/rpc/client-clear-peer-public-key/key-type'"
                ;
  }
  revision 2021-03-04 {
    description "1.Add container node '/configuration/ssh/ssh-server/algorithm-"
              + "mng', add container node '/configuration/ssh/ssh-server/algori"
              + "thm-mng/diffie-hellman-algorithms', add list node '/configurat"
              + "ion/ssh/ssh-server/algorithm-mng/diffie-hellman-algorithms/dif"
              + "fie-hellman-algorithm', add leaf node '/configuration/ssh/ssh-"
              + "server/algorithm-mng/diffie-hellman-algorithms/diffie-hellman-"
              + "algorithm/diffie-hellman-algorithm'
\n2.Add container node '/c"
              + "onfiguration/ssh/ssh-client', add container node '/configurati"
              + "on/ssh/ssh-client/algorithm-mng', add container node '/configu"
              + "ration/ssh/ssh-client/algorithm-mng/diffie-hellman-algorithms'"
              + ", add list node '/configuration/ssh/ssh-client/algorithm-mng/d"
              + "iffie-hellman-algorithms/diffie-hellman-algorithm', add leaf n"
              + "ode '/configuration/ssh/ssh-client/algorithm-mng/diffie-hellma"
              + "n-algorithms/diffie-hellman-algorithm/diffie-hellman-algorithm"
              + "'"
                ;
  }
  revision 2020-08-27 {
    description "1.Add container node '/configuration/ssh/ssh-server/hmac', add"
              + " list node '/configuration/ssh/ssh-server/hmac/hmac-algorithm-"
              + "disabled' add leaf node '/configuration/ssh/ssh-server/hmac/hm"
              + "ac-algorithm-disabled/hmac-algorithm'
\n2.Add container node '"
              + "/configuration/ssh/ssh-server/encryption', add list node '/con"
              + "figuration/ssh/ssh-server/encryption/encryption-algorithm-disa"
              + "bled' add leaf node '/configuration/ssh/ssh-server/encryption/"
              + "encryption-algorithm-disabled/encryption-algorithm'
\n3.Add co"
              + "ntainer node '/configuration/ssh/ssh-server/diffie-hellman', a"
              + "dd list node '/configuration/ssh/ssh-server/diffie-hellman/dif"
              + "fie-hellman-algorithm-disabled' add leaf node '/configuration/"
              + "ssh/ssh-server/diffie-hellman/diffie-hellman-algorithm-disable"
              + "d/diffie-hellman-algorithm'
\n4.Add container node '/configura"
              + "tion/ssh/ssh-server/host-key', add list node '/configuration/s"
              + "sh/ssh-server/host-key/host-key-algorithm-disabled' add leaf n"
              + "ode '/configuration/ssh/ssh-server/host-key/host-key-algorithm"
              + "-disabled/host-key-algorithm'"
                ;
  }
  revision 2019-01-28 {
    description "1.Add container node '/state/ssh/host-key/rsa', add leaf node "
              + "'/state/ssh/host-key/rsa/key-modulus' and '/state/ssh/host-key"
              + "/rsa/key-code'
\n2.Add list node '/state/ssh/host-key/ecc', ad"
              + "d leaf node '/state/ssh/host-key/ecc/curve-name', '/state/ssh/"
              + "host-key/ecc/key-modulus' and '/state/ssh/host-key/ecc/key-cod"
              + "e'
\n3.Add choice node '/operation/ssh/generate/host-key', add"
              + " case node '/operation/ssh/generate/host-key/rsa' and '/operat"
              + "ion/ssh/generate/host-key/ecc', add leaf node '/operation/ssh/"
              + "generate/host-key/rsa/rsa' and '/operation/ssh/generate/host-k"
              + "ey/rsa/key-modulus' and '/operation/ssh/generate/host-key/ecc'"
              + " and '/operation/ssh/generate/host-key/ecc/curve-name'
\n4.Add"
              + " feature node 'weak-host-key-algorithm' and 'strong-host-key-a"
              + "lgorithm'"
                ;
  }
  revision 2019-01-23 {
    description 'Support keyboard-interactive authentication.'
                ;
  }
  revision 2014-05-06 {
    description 'Modify the default value of dscp.'
                ;
  }
  revision 2014-01-24 {
    description '1.Modified configuration/ssh/ssh-server/authentication/user/us'
              + 'ername node maximum length from 32 to 65.'
                ;
  }
  revision 2013-11-01 {
    description '1.Modified state/ssh/publick-key/key-code node maximum length '
              + 'from 512 to 2048.'+"\n"
              + '2.Remove mandatory attribute of configuration/ssh/ssh-server/s'
              + 'erver-valid/enable/enable node.'
                ;
  }
  revision 2013-10-15 {
    description '1.Add state for supporting get user authentication public-key '
              + 'information.'+"\n"
              + '2.Modified configuration/ssh/ssh-server/authentication/user/au'
              + 'th-type node and operation/ssh/generate/key/key-type node type'
              + ' from uint8 to enumeration.'+"\n"
              + '3.Add length range for string node.'
                ;
  }
  revision 2013-09-25 {
    description 'Move the listen-port node to enable case.'
                ;
  }
  revision 2013-07-17 {
    description 'Modified according to the specification, e.g. adding some desc'
              + 'riptions and deleting capital letter of entity names.'
                ;
  }
  revision 2013-06-19 {
    description 'Initial version'
                ;
  }
  feature strong-host-key-algorithm ;
  feature weak-host-key-algorithm {
    description 'Only RSA is supported, The modulus of the RSA key pair is 1024.'
                ;
  }
  container configuration {
    description 'The configuration model of SSH.'
                ;
    container ssh {
      description 'Configure the SSH parameters.'
                  ;
      container ssh-server {
        description 'Configure the SSH server parameters.'
                    ;
        choice server-valid {
          description 'To configure the SSH server enable or disable.'
                      ;
          default disable ;
          case disable {
            description 'To configure the SSH server disable.'
                        ;
            leaf disable {
              description 'Disable the SSH server. After disable the snetconf s'
                        + 'erver, then the SSH server can be disabled.'
                          ;
              type empty ;
            }
          }
          case enable {
            description 'To configure the SSH server enable.'
                        ;
            leaf enable {
              description 'Enable the SSH server. After enable the SSH server, '
                        + 'then the snetconf server can be enabled.'
                          ;
              type empty ;
            }
            leaf listen-port {
              description 'The listenning port of the SSH server. It can be con'
                        + 'figured as 22 or any integer between 49152 and 65535'
                        + '. It cannot be changed while SSH server has been ena'
                        + 'bled.'
                          ;
              type uint16 {
                range '22 | 49152..65535'
                      ;
              }
              default 22 ;
            }
          }
        }
        container acl {
          description 'The ACL name which is binded to the SSH server.'
                      ;
          leaf ipv4-acl {
            description 'The IPv4 ACL name which is binded to the SSH server.'
                        ;
            type string {
              length 1..31 {
                description 'The ACL name length must be between 1 and 31 chara'
                          + 'cters.'
                            ;
              }
            }
          }
          leaf ipv6-acl {
            description 'The IPv6 ACL name which is binded to the SSH server.'
                        ;
            type string {
              length 1..31 {
                description 'The ACL name length must be between 1 and 31 chara'
                          + 'cters.'
                            ;
              }
            }
          }
        }
        leaf dscp {
          description 'The DSCP value is used in packets of the SSH server. It '
                    + 'can be configured any integer between 0 and 63.'
                      ;
          type uint8 {
            range 0..63 ;
          }
        }
        leaf version {
          description 'The protocol version of the SSH server. The value is 1 o'
                    + 'r 2. '+"\n"
                    + '1 : SSH version 1; '+"\n"
                    + '2 : SSH version 2.'
                      ;
          type uint8 {
            range 1..2 ;
          }
          default 2 ;
        }
        container authentication {
          description 'Configure the authentication type of SSH server.'
                      ;
          list user {
            description 'Configure the authentication type of specified SSH use'
                      + 'r. SSH user should be configured on ADM_MGR at first.
'
                      + ''+"\n"
                      + '  If the SSH user only need password authentication, t'
                      + 'his node may be not configured. '+"\n"
                      + '  If the SSH user need public-key authentication, this'
                      + ' node must be configured.'
                        ;
            key username ;
            leaf username {
              description 'The name of a user.'
                          ;
              type string {
                length 1..65 {
                  description 'The user name length must be between 1 and 65 ch'
                            + 'aracters.'
                              ;
                }
              }
              mandatory true ;
            }
            leaf auth-type {
              description 'The authentication type of the SSH server. Include: '
                        + 'password authentication, pubblic-key authentication,'
                        + ' password and public-key authentication, password or'
                        + ' public-key authentication.'
                          ;
              type enumeration {
                enum password {
                  value 1 ;
                  description 'Password authentication.'
                              ;
                }
                enum publickey {
                  value 2 ;
                  description 'Public-key authentication.'
                              ;
                }
                enum password-publickey {
                  value 3 ;
                  description 'Password and public-key authentication.'
                              ;
                }
                enum any {
                  value 4 ;
                  description 'Password or public-key or keyboard-interactive a'
                            + 'uthentication;'
                              ;
                }
                enum keyboard-interactive {
                  value 7 ;
                  description 'Keyboard-interactive authentication.'
                              ;
                }
              }
              mandatory true ;
            }
            leaf key-name {
              description 'The key name used by public-key authentication.'
                          ;
              type string {
                length 1..31 {
                  description 'The public-key name length must be between 1 and'
                            + ' 31 characters.'
                              ;
                }
              }
            }
          }
        }
        container rekey {
          description 'Configure the parameters of regenerate server key.'
                      ;
          leaf interval {
            description 'The interval of regenerate server key. The valid value'
                      + ' is any integer between 0 and 720. '+"\n"
                      + 'The value of 0 means no regeneration.'
                        ;
            type uint16 {
              range 0..720 ;
            }
            units hour ;
            default 1 ;
          }
        }
        container hmac {
          description 'shield SSH hmac algorithm'
                      ;
          list hmac-algorithm-disabled {
            description 'hmac algorithm disabled'
                        ;
            key hmac-algorithm ;
            leaf hmac-algorithm {
              description 'hmac algorithm'
                          ;
              type enumeration {
                enum none {
                  value 1 ;
                  description 'none algorithm'
                              ;
                }
                enum md5 {
                  value 2 ;
                  description 'md5 algorithm'
                              ;
                }
                enum sha1 {
                  value 11 ;
                  description 'sha1 algorithm'
                              ;
                }
              }
            }
          }
          ncd:revise-date 2020-08-27 ;
        }
        container encryption {
          description 'shield SSH encryption algorithm'
                      ;
          list encryption-algorithm-disabled {
            description 'encryption algorithm disabled'
                        ;
            key encryption-algorithm ;
            leaf encryption-algorithm {
              description 'encryption algorithm'
                          ;
              type enumeration {
                enum none {
                  value 3 ;
                  description 'none algorithm'
                              ;
                }
                enum aes128-cbc {
                  value 5 ;
                  description 'aes128-cbc algorithm'
                              ;
                }
                enum blowfish-cbc {
                  value 6 ;
                  description 'blowfish-cbc algorithm'
                              ;
                }
                enum 3des-cbc {
                  value 7 ;
                  description '3des-cbc algorithm'
                              ;
                }
                enum aes192-cbc {
                  value 8 ;
                  description 'aes192-cbc algorithm'
                              ;
                }
                enum aes256-cbc {
                  value 9 ;
                  description 'aes256-cbc algorithm'
                              ;
                }
              }
            }
          }
          ncd:revise-date 2020-08-27 ;
        }
        container diffie-hellman {
          description 'shield SSH diffie-hellman algorithm'
                      ;
          list diffie-hellman-algorithm-disabled {
            description 'diffie-hellman algorithm disabled'
                        ;
            key diffie-hellman-algorithm ;
            leaf diffie-hellman-algorithm {
              description 'diffie-hellman algorithm'
                          ;
              type enumeration {
                enum group1-sha1 {
                  value 4 ;
                  description 'group1-sha1 algorithm'
                              ;
                }
                enum group-exchange-sha1 {
                  value 13 ;
                  description 'group-exchange-sha1 algorithm'
                              ;
                }
                enum group-exchange-sha256 {
                  value 23 ;
                  description 'group-exchange-sha256 algorithm'
                              ;
                }
              }
            }
          }
          ncd:revise-date 2020-08-27 ;
        }
        container host-key {
          description 'shield SSH host-key algorithm'
                      ;
          list host-key-algorithm-disabled {
            description 'host-key algorithm disabled'
                        ;
            key host-key-algorithm ;
            leaf host-key-algorithm {
              description 'host-key algorithm'
                          ;
              type enumeration {
                enum dsa {
                  value 28 ;
                  description 'dsa algorithm'
                              ;
                }
              }
            }
          }
          ncd:revise-date 2020-08-27 ;
        }
        container algorithm-mng {
          description 'SSH algorithm management of server'
                      ;
          container diffie-hellman-algorithms {
            description 'diffie-hellman algorithm management of server'
                        ;
            list diffie-hellman-algorithm {
              description 'Add or remove diffie-hellman algorithms of server'
                          ;
              key diffie-hellman-algorithm ;
              leaf diffie-hellman-algorithm {
                description 'diffie-hellman algorithm of server'
                            ;
                type enumeration {
                  enum group16-sha512 {
                    value 38 ;
                  }
                }
              }
            }
          }
          ncd:revise-date 2021-03-04 ;
        }
        container recognize-packet {
          description 'Set SSH server recognize specific type of packet.'+"\n"
                    + 'If the configuration is deleted or not configured, the p'
                    + 'acket of the specific type cannot be recognized.'
                      ;
          list recognize-packet-type {
            description 'Set SSH server recognize packet type.'
                        ;
            key type ;
            leaf type {
              description 'SSH packet type'
                          ;
              type enumeration {
                enum global-request {
                  value 80 ;
                  description 'SSH_MSG_GLOBAL_REQUEST packet type'
                              ;
                }
              }
            }
          }
          ncd:revise-date 2022-02-28 ;
        }
      }
      container ssh-client {
        description 'Configure the SSH client parameters.'
                    ;
        container algorithm-mng {
          description 'SSH algorithm management of client'
                      ;
          container diffie-hellman-algorithms {
            description 'diffie-hellman algorithm management of client'
                        ;
            list diffie-hellman-algorithm {
              description 'Add or remove diffie-hellman algorithms of client'
                          ;
              key diffie-hellman-algorithm ;
              leaf diffie-hellman-algorithm {
                description 'diffie-hellman algorithm of client'
                            ;
                type enumeration {
                  enum group16-sha512 {
                    value 38 ;
                  }
                }
              }
            }
          }
        }
        container first-time {
          description 'The authentication function status of first time access'
                      ;
          leaf status {
            description 'The authentication function status of first time access'
                        ;
            type enumeration {
              enum enable {
                value 1 ;
              }
              enum disable {
                value 2 ;
              }
            }
            default disable ;
          }
          ncd:revise-date 2021-12-16 ;
        }
        container signature-authen {
          description 'The status of signature authentication function'
                      ;
          leaf status {
            description 'The status of signature authentication function'
                        ;
            type enumeration {
              enum enable {
                value 1 ;
              }
              enum disable {
                value 2 ;
              }
            }
            default disable ;
          }
          ncd:revise-date 2021-12-16 ;
        }
        ncd:revise-date 2021-03-04 ;
      }
    }
  }
  container state {
    config false ;
    container ssh {
      description 'SSH state parameters'
                  ;
      list public-key {
        description 'The the detail information of public-key.'
                    ;
        key key-name ;
        leaf key-name {
          description 'The name of public key.'
                      ;
          type string {
            length 1..31 ;
          }
        }
        leaf key-type {
          description 'The type of public key.'
                      ;
          type enumeration {
            enum RSA {
              value 1 ;
              description 'RSA type'
                          ;
            }
            enum DSA {
              value 2 ;
              description 'DSA type'
                          ;
            }
          }
        }
        leaf key-module {
          description 'The module of public key.'
                      ;
          type uint16 {
            range 512..2048 ;
          }
        }
        leaf key-code {
          description 'The code of public key.'
                      ;
          type string {
            length 1..2048 ;
          }
        }
      }
      container host-key {
        description 'The host key information'
                    ;
        container rsa {
          description 'RSA (Revest-Shamir-Adleman Algorithm) host key.'
                      ;
          leaf key-modulus {
            description 'The modulus of the RSA key pair, in bits.'
                        ;
            type uint32 {
              range 256..2048 ;
            }
          }
          leaf key-code {
            description 'RSA host public key information.'
                        ;
            type string {
              length 1..2048 ;
            }
          }
        }
        list ecc {
          description 'ECC (Elliptic Curves Cryptography) host key.'
                      ;
          key curve-name ;
          leaf curve-name {
            description 'Elliptic curve name.'
                        ;
            type enumeration {
              enum nistp256 {
                value 1 ;
                description 'NISTP256 algorithm'
                            ;
              }
              enum nistp384 {
                value 2 ;
                description 'NISTP384 algorithm'
                            ;
              }
              enum nistp521 {
                value 3 ;
                description 'NISTP521 algorithm'
                            ;
              }
              enum ed25519 {
                value 4 ;
                description 'ED25519 algorithm'
                            ;
              }
            }
          }
          leaf key-modulus {
            description 'The modulus of the ECC key pair, in bits.'
                        ;
            type uint32 {
              range 256..2048 ;
            }
          }
          leaf key-code {
            description 'ECC host public key information.'
                        ;
            type string {
              length 1..2048 ;
            }
          }
        }
      }
      container ssh-client {
        description 'SSH client state parameters'
                    ;
        container peer-public-key {
          description 'Peer public key information'
                      ;
          list ipv4 {
            description 'Peer public key information bind with IPv4 address'
                        ;
            key 'ipv4-addr key-type'
                ;
            leaf ipv4-addr {
              description 'IPv4 address'
                          ;
              type ncd:ipv4-address ;
            }
            leaf key-type {
              description 'The type of public key'
                          ;
              type enumeration {
                enum RSA {
                  value 1 ;
                  description 'RSA type'
                              ;
                }
                enum DSA {
                  value 2 ;
                  description 'DSA type'
                              ;
                }
                enum ECC {
                  value 3 ;
                  description 'ECC type'
                              ;
                }
              }
            }
            leaf curve-name {
              description 'Elliptic curve name(This node has a value only when '
                        + 'the key-type is ECC).'
                          ;
              type enumeration {
                enum nistp256 {
                  value 1 ;
                  description 'NISTP256 algorithm'
                              ;
                }
                enum nistp384 {
                  value 2 ;
                  description 'NISTP384 algorithm'
                              ;
                }
                enum nistp521 {
                  value 3 ;
                  description 'NISTP521 algorithm'
                              ;
                }
                enum ed25519 {
                  value 4 ;
                  description 'ED25519 algorithm'
                              ;
                }
              }
            }
            leaf key-module {
              description 'The module of public key'
                          ;
              type uint16 {
                range 256..8192 ;
              }
            }
            leaf key-code {
              description 'The code of public key'
                          ;
              type ncd:long-text {
                length 1..4095 ;
              }
            }
            ncd:select ipv4-addr ;
            ncd:select 'ipv4-addr key-type'
                       ;
          }
          list ipv6 {
            description 'Peer public key information bind with IPv6 address'
                        ;
            key 'ipv6-addr key-type'
                ;
            leaf ipv6-addr {
              description 'IPv6 address'
                          ;
              type ncd:ipv6-address ;
            }
            leaf key-type {
              description 'The type of public key'
                          ;
              type enumeration {
                enum RSA {
                  value 1 ;
                  description 'RSA type'
                              ;
                }
                enum DSA {
                  value 2 ;
                  description 'DSA type'
                              ;
                }
                enum ECC {
                  value 3 ;
                  description 'ECC type'
                              ;
                }
              }
            }
            leaf curve-name {
              description 'Elliptic curve name(This node has a value only when '
                        + 'the key-type is ECC).'
                          ;
              type enumeration {
                enum nistp256 {
                  value 1 ;
                  description 'NISTP256 algorithm'
                              ;
                }
                enum nistp384 {
                  value 2 ;
                  description 'NISTP384 algorithm'
                              ;
                }
                enum nistp521 {
                  value 3 ;
                  description 'NISTP521 algorithm'
                              ;
                }
                enum ed25519 {
                  value 4 ;
                  description 'ED25519 algorithm'
                              ;
                }
              }
            }
            leaf key-module {
              description 'The module of public key'
                          ;
              type uint16 {
                range 256..8192 ;
              }
            }
            leaf key-code {
              description 'The code of public key'
                          ;
              type ncd:long-text {
                length 1..4095 ;
              }
            }
            ncd:select ipv6-addr ;
            ncd:select 'ipv6-addr key-type'
                       ;
          }
        }
        ncd:revise-date 2021-12-16 ;
      }
    }
  }
  container operation {
    config false ;
    description 'The operation model of SSH.'
                ;
    container ssh {
      description 'The parameters of SSH operation.'
                  ;
      container import {
        description 'The importing operation of SSH.'
                    ;
        container public-key {
          description 'Import public-key file to SSH.'
                      ;
          presence 'The parameter key-name and key-file should be set at the sa'
                 + 'me time.'
                   ;
          leaf key-name {
            description 'The name of public key.'
                        ;
            type string {
              length 1..31 ;
            }
            mandatory true ;
          }
          leaf key-file {
            description 'The key file and path that to be imported.'
                        ;
            type string {
              length 1..159 ;
            }
            mandatory true ;
          }
        }
      }
      container clear {
        description 'The clearing operation of SSH.'
                    ;
        container public-key {
          description 'Clear public-key of SSH.'
                      ;
          leaf key-name {
            description 'The public-key name that to be cleared.'
                        ;
            type string {
              length 1..31 ;
            }
          }
        }
      }
      container generate {
        description 'The generating operation of SSH.'
                    ;
        container key {
          if-feature weak-host-key-algorithm ;
          description 'Generate or update public/private key pairs of SSH.'
                      ;
          leaf key-type {
            description 'The type of public/private key pairs. Only RSA is supp'
                      + 'orted now.'
                        ;
            type enumeration {
              enum RSA {
                value 1 ;
                description 'RSA type.'
                            ;
              }
            }
          }
        }
        choice host-key {
          if-feature strong-host-key-algorithm ;
          description 'Generate or update public/private key pairs of SSH.'
                      ;
          case rsa {
            description 'RSA (Revest-Shamir-Adleman Algorithm) host key.'
                        ;
            leaf rsa {
              description 'RSA algorithm.'
                          ;
              type empty ;
              mandatory true ;
            }
            leaf key-modulus {
              description 'The modulus of the RSA key pair, in bits. default is'
                        + ' 1024.'
                          ;
              type enumeration {
                enum 1024 {
                  value 1024 ;
                  description 'The number of RSA modulus bits is 1024.'
                              ;
                }
                enum 2048 {
                  value 2048 ;
                  description 'The number of RSA modulus bits is 2048.'
                              ;
                }
              }
              default 1024 ;
            }
          }
          case ecc {
            description 'ECC (Elliptic Curves Cryptography) host key.'
                        ;
            leaf ecc {
              description 'ECC algorithm.'
                          ;
              type empty ;
              mandatory true ;
            }
            leaf curve-name {
              description 'Elliptic curve name.Default is nistp521.'
                          ;
              type enumeration {
                enum nistp256 {
                  value 1 ;
                  description 'nistp256 algorithm.'
                              ;
                }
                enum nistp384 {
                  value 2 ;
                  description 'nistp384 algorithm.'
                              ;
                }
                enum nistp521 {
                  value 3 ;
                  description 'nistp521 algorithm.'
                              ;
                }
                enum ed25519 {
                  value 4 ;
                  description 'ed25519 algorithm.'
                              ;
                }
              }
              default nistp521 ;
            }
          }
        }
      }
    }
  }
  rpc client-import-peer-public-key {
    description 'The SSH client imports the peer public key file.'
                ;
    input {
      choice ip-addr {
        description 'Peer IP address.'
                    ;
        mandatory true ;
        case ipv4 {
          description 'Peer IPv4 address.'
                      ;
          leaf ipv4-addr {
            description 'Peer IPv4 address.'
                        ;
            type ncd:ipv4-address ;
          }
        }
        case ipv6 {
          description 'Peer IPv6 address'
                      ;
          leaf ipv6-addr {
            description 'Peer IPv6 address'
                        ;
            type ncd:ipv6-address ;
          }
        }
      }
      leaf key-file {
        description 'Public key file name to be imported (including path)'
                    ;
        type string {
          length 1..159 ;
        }
        mandatory true ;
      }
    }
    ncd:revise-date 2021-12-16 ;
  }
  rpc client-clear-peer-public-key {
    description 'The SSH client clears the peer public key.'
                ;
    input {
      choice ip-addr {
        description 'Peer IP address.'
                    ;
        mandatory true ;
        case ipv4 {
          description 'Peer IPv4 address.'
                      ;
          leaf ipv4-addr {
            description 'Peer IPv4 address.'
                        ;
            type ncd:ipv4-address ;
          }
        }
        case ipv6 {
          description 'Peer IPv6 address.'
                      ;
          leaf ipv6-addr {
            description 'Peer IPv6 address.'
                        ;
            type ncd:ipv6-address ;
          }
        }
      }
      leaf key-type {
        description 'The type of public key'
                    ;
        type enumeration {
          enum RSA {
            value 1 ;
          }
          enum DSA {
            value 2 ;
          }
          enum ECC {
            value 3 ;
          }
        }
        mandatory true ;
      }
    }
    ncd:revise-date 2021-12-16 ;
  }
}
