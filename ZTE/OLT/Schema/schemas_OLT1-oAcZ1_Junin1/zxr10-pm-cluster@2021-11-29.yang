module zxr10-pm-cluster {
  namespace 'http://www.zte.com.cn/zxr10/netconf/schema/rosng/pm-cluster'
            ;
  prefix pm-cluster ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  revision 2021-11-29 {
    description 'add leaf plane-mode and enum 2.4t/4t of run-mode.'
                ;
  }
  revision 2021-05-18 {
    description 'Change vendor Length to 24.'
                ;
  }
  revision 2019-01-17 {
    description 'shelf range 0-255.slot range 0-255.'
                ;
  }
  revision 2017-07-01 {
    description 'delete the mode below mode of node run mode  '+"\n"
              + '  1+2     LCC shelf number:1-2, CFC shelf number:1, CSFU numbe'
              + 'r:8'+"\n"
              + '  1+4     LCC shelf number:1-4, CFC shelf number:1, CSFU numbe'
              + 'r:16'+"\n"
              + '  2+8     LCC shelf number:1-8, CFC shelf number:2, CSFU numbe'
              + 'r:32'+"\n"
              + '  4+16    LCC shelf number:1-16, CFC shelf number:4, CSFU numb'
              + 'er:64'
                ;
  }
  revision 2017-01-24 {
    description 'delete 2+2 enum of run-mode.'
                ;
  }
  revision 2015-05-20 ;
  container state {
    config false ;
    container cluster {
      container cplink-topologys {
        list cplink-topology {
          key 'source-shelf source-slot source-subslot source-port'
              ;
          leaf source-shelf {
            description 'Source shelf number'
                        ;
            type uint8 {
              range 0..79 ;
            }
          }
          leaf source-slot {
            description 'Source slot number'
                        ;
            type uint8 {
              range 0..27 ;
            }
          }
          leaf source-subslot {
            description 'Source subslot number'
                        ;
            type uint8 ;
          }
          leaf source-port {
            description 'Source port number'
                        ;
            type uint8 ;
          }
          leaf source-restype {
            description 'Source resource type'
                        ;
            type uint16 ;
          }
          leaf source-ifname {
            description 'Source interface name'
                        ;
            type string ;
          }
          leaf dest-shelf {
            description 'Destination shelf number'
                        ;
            type uint8 ;
          }
          leaf dest-slot {
            description 'Destination slot number'
                        ;
            type uint8 ;
          }
          leaf dest-subslot {
            description 'Destination subslot number'
                        ;
            type uint8 ;
          }
          leaf dest-port {
            description 'Destination port number'
                        ;
            type uint8 ;
          }
          leaf dest-restype {
            description 'Destination resource type'
                        ;
            type uint16 ;
          }
          leaf dest-ifname {
            description 'Destination interface name'
                        ;
            type string ;
          }
        }
      }
      container cplink-statistics {
        list cplink-statistic {
          key 'shelf slot cpu'
              ;
          leaf shelf {
            description 'Shelf number'
                        ;
            type uint8 {
              range 0..255 {
                description 'shelf range.'
                            ;
              }
            }
          }
          leaf slot {
            description 'Slot number'
                        ;
            type uint8 {
              range 0..255 {
                description 'slot range.'
                            ;
              }
            }
          }
          leaf cpu {
            description 'CPU number'
                        ;
            type uint8 ;
          }
          list cplink {
            key 'source-shelf source-slot source-port'
                ;
            leaf source-shelf {
              description 'Source shelf number'
                          ;
              type uint8 {
                range 0..255 {
                  description 'shelf range.'
                              ;
                }
              }
            }
            leaf source-slot {
              description 'Source slot number'
                          ;
              type uint8 {
                range 0..255 {
                  description 'slot range.'
                              ;
                }
              }
            }
            leaf source-port {
              description 'Source port number'
                          ;
              type uint8 ;
            }
            leaf source-port-status {
              description 'Source port status'
                          ;
              type ncd:string-all ;
            }
            leaf source-pkg-send {
              description 'Source port send package'
                          ;
              type uint32 ;
            }
            leaf source-pkg-receive {
              description 'Source port receive package'
                          ;
              type uint32 ;
            }
            leaf source-pkg-senddrop {
              description 'Source port send package of drop'
                          ;
              type uint32 ;
            }
            leaf source-pkg-receivedrop {
              description 'Source port receive package of drop'
                          ;
              type uint32 ;
            }
            leaf source-pkg-crcdrop {
              description 'Source port crc package of drop'
                          ;
              type uint32 ;
            }
            leaf source-stp {
              description 'Source stp'
                          ;
              type ncd:string-all ;
            }
            leaf source-block-count {
              description 'Source port block count'
                          ;
              type uint32 ;
            }
            leaf dest-shelf {
              description 'Destination shelf number'
                          ;
              type uint8 {
                range 0..255 {
                  description 'shelf range.'
                              ;
                }
              }
            }
            leaf dest-slot {
              description 'Destination slot number'
                          ;
              type uint8 {
                range 0..255 {
                  description 'slot range.'
                              ;
                }
              }
            }
            leaf dest-port {
              description 'Destination port number'
                          ;
              type uint8 ;
            }
            leaf dest-port-status {
              description 'Destination port status'
                          ;
              type ncd:string-all ;
            }
            leaf dest-pkg-send {
              description 'Destination port send package'
                          ;
              type uint32 ;
            }
            leaf dest-pkg-receive {
              description 'Destination port receive package'
                          ;
              type uint32 ;
            }
            leaf dest-pkg-senddrop {
              description 'Destination port send package of drop'
                          ;
              type uint32 ;
            }
            leaf dest-pkg-receivedrop {
              description 'Destination port receive package of drop'
                          ;
              type uint32 ;
            }
            leaf dest-pkg-crcdrop {
              description 'Destination port crc package of drop'
                          ;
              type uint32 ;
            }
            leaf dest-stp {
              description 'Destination stp'
                          ;
              type ncd:string-all ;
            }
            leaf dest-block-count {
              description 'Destination port block count'
                          ;
              type uint32 ;
            }
          }
        }
      }
      container cp-opticals {
        list cp-optical {
          key 'shelf slot'
              ;
          leaf shelf {
            description 'Shelf number'
                        ;
            type uint8 {
              range 0..255 {
                description 'shelf range.'
                            ;
              }
            }
          }
          leaf slot {
            description 'Slot number'
                        ;
            type uint8 {
              range 0..255 {
                description 'slot range.'
                            ;
              }
            }
          }
          list optical {
            key if-name ;
            leaf if-name {
              description 'Interface name'
                          ;
              type string ;
            }
            leaf opt-type {
              type ncd:string-all ;
            }
            leaf vendor {
              type ncd:string-all ;
            }
            leaf wavelength {
              type uint16 ;
            }
            leaf transfer-distance {
              type ncd:string-all ;
            }
            leaf receive-power {
              type ncd:string-all ;
            }
            leaf send-power {
              type ncd:string-all ;
            }
            leaf bias-current {
              type ncd:string-all ;
            }
            leaf temperature {
              type ncd:string-all ;
            }
          }
        }
      }
      container dplink-topologys {
        list dplink-topology {
          key 'source-shelf source-slot source-subslot source-port'
              ;
          leaf source-shelf {
            description 'Source shelf number'
                        ;
            type uint8 {
              range 0..255 {
                description 'shelf range.'
                            ;
              }
            }
          }
          leaf source-slot {
            description 'Source slot number'
                        ;
            type uint8 {
              range 0..255 {
                description 'slot range.'
                            ;
              }
            }
          }
          leaf source-subslot {
            description 'Source subslot number'
                        ;
            type uint8 ;
          }
          leaf source-port {
            description 'Source port number'
                        ;
            type uint8 ;
          }
          leaf source-restype {
            description 'Source resource type'
                        ;
            type uint16 ;
          }
          leaf source-ifname {
            description 'Source interface name'
                        ;
            type string ;
          }
          leaf dest-shelf {
            description 'Destination shelf number'
                        ;
            type uint8 {
              range 0..255 {
                description 'shelf range.'
                            ;
              }
            }
          }
          leaf dest-slot {
            description 'Destination slot number'
                        ;
            type uint8 {
              range 0..255 {
                description 'slot range.'
                            ;
              }
            }
          }
          leaf dest-subslot {
            description 'Destination subslot number'
                        ;
            type uint8 ;
          }
          leaf dest-port {
            description 'Destination port number'
                        ;
            type uint8 ;
          }
          leaf dest-restype {
            description 'Destination resource type'
                        ;
            type uint16 ;
          }
          leaf dest-ifname {
            description 'Destination interface name'
                        ;
            type string ;
          }
          leaf down-number {
            description 'Number of down serdes'
                        ;
            type uint32 ;
          }
          leaf error-number {
            description 'Number of up serdes which have errors'
                        ;
            type uint32 ;
          }
          leaf connect-flag {
            description 'Connect flag'
                        ;
            type enumeration {
              enum no {
                value 0 ;
              }
              enum yes {
                value 1 ;
              }
            }
          }
          leaf expect-shelf {
            description 'Expect shelf number'
                        ;
            type uint8 {
              range 0..255 {
                description 'shelf range.'
                            ;
              }
            }
          }
          leaf expect-slot {
            description 'Expect slot number'
                        ;
            type uint8 {
              range 0..255 {
                description 'slot range.'
                            ;
              }
            }
          }
          leaf expect-subslot {
            description 'Expect subslot number'
                        ;
            type uint8 ;
          }
          leaf expect-port {
            description 'Expect port number'
                        ;
            type uint8 ;
          }
          leaf expect-restype {
            description 'Expect resource type'
                        ;
            type uint16 ;
          }
          leaf expect-ifname {
            description 'Expect interface name'
                        ;
            type string ;
          }
        }
      }
      container dplink-statistics {
        list dplink-statistic {
          key 'source-shelf source-slot source-subslot source-port'
              ;
          leaf source-shelf {
            description 'Source shelf number'
                        ;
            type uint8 {
              range 0..255 {
                description 'shelf range.'
                            ;
              }
            }
          }
          leaf source-slot {
            description 'Source slot number'
                        ;
            type uint8 {
              range 0..255 {
                description 'slot range.'
                            ;
              }
            }
          }
          leaf source-subslot {
            description 'Source subslot number'
                        ;
            type uint8 ;
          }
          leaf source-port {
            description 'Source port number'
                        ;
            type uint8 ;
          }
          leaf source-restype {
            description 'Source resource type'
                        ;
            type uint16 ;
          }
          leaf source-ifname {
            description 'Source interface name'
                        ;
            type string ;
          }
          leaf dest-shelf {
            description 'Destination shelf number'
                        ;
            type uint8 {
              range 0..255 {
                description 'shelf range.'
                            ;
              }
            }
          }
          leaf dest-slot {
            description 'Destination slot number'
                        ;
            type uint8 {
              range 0..255 {
                description 'slot range.'
                            ;
              }
            }
          }
          leaf dest-subslot {
            description 'Destination subslot number'
                        ;
            type uint8 ;
          }
          leaf dest-port {
            description 'Destination port number'
                        ;
            type uint8 ;
          }
          leaf dest-restype {
            description 'Destination resource type'
                        ;
            type uint16 ;
          }
          leaf dest-ifname {
            description 'Destination interface name'
                        ;
            type string ;
          }
          leaf chip-id {
            description 'Chip id'
                        ;
            type uint8 ;
          }
          leaf down-flag {
            description 'Flag of autodown'
                        ;
            type uint8 ;
          }
          leaf serdes-number {
            description 'Serial number up serdes which have errors'
                        ;
            type uint8 ;
          }
          leaf error-number {
            description 'Errors number'
                        ;
            type uint32 ;
          }
        }
      }
    }
  }
  container operation {
    config false ;
    container cluster {
      container update-sfu {
        leaf shelf {
          description 'Shelf number.'
                      ;
          type uint8 {
            range 0..255 {
              description 'Shelf range.'
                          ;
            }
          }
        }
        leaf slot {
          description 'Slot number.'
                      ;
          type uint8 {
            range 0..255 {
              description 'Slot range.'
                          ;
            }
          }
        }
      }
    }
  }
  container configuration {
    container cluster {
      leaf run-mode {
        description 'Run mode'
                    ;
        type enumeration {
          enum single {
            value 0 ;
            description 'LCC shelf number:1, CFC shelf number:0, CSFU number:0'
                        ;
          }
          enum 2+4 {
            value 4 ;
            description 'LCC shelf number:1-4, CFC shelf number:2, CSFU number:'
                      + '16'
                        ;
          }
          enum b2b {
            value 8 ;
            description 'LCC shelf number:1-2, CFC shelf number:0, CSFU number:0'
                        ;
          }
          enum 2.4t {
            value 9 ;
            description 'LCC shelf number: 1-6, CFC shelf number: 2, CSFU numbe'
                      + 'r: 16-32, for 2.4T Cluster system'
                        ;
          }
          enum 4t {
            value 10 ;
            description 'LCC shelf number: 1-4, CFC shelf number: 2, CSFU numbe'
                      + 'r: 16-32, for 4T Cluster system'
                        ;
          }
        }
        default single ;
      }
      leaf plane-mode {
        description 'Plane mode'
                    ;
        type enumeration {
          enum 2c {
            value 1 ;
            description 'LCC shelf number: 1-3(2.4t) or 1-2(4t), CFC shelf numb'
                      + 'er: 2, CSFU number:16'
                        ;
          }
          enum 3c {
            value 2 ;
            description 'LCC shelf number: 1-5(2.4t) or 1-3(4t), CFC shelf numb'
                      + 'er: 2, CSFU number:24'
                        ;
          }
          enum 4c {
            value 3 ;
            description 'LCC shelf number: 1-6(2.4t) or 1-4(4t), CFC shelf numb'
                      + 'er: 2, CSFU number:32'
                        ;
          }
          enum none {
            value 0 ;
            description 'None plane mode.'
                        ;
          }
        }
        ncd:revise-date 2021-11-29 ;
      }
      leaf fiber-length-all {
        description 'Fiber length'
                    ;
        type enumeration {
          enum 10 {
            value 10 ;
            description 'Fiber length is 10 meter'
                        ;
          }
          enum 30 {
            value 30 ;
            description 'Fiber length is 30 meter'
                        ;
          }
          enum 100 {
            value 100 ;
            description 'Fiber length is 100 meter'
                        ;
          }
        }
      }
      container fiber-lengths {
        list fiber-length {
          key shelf ;
          leaf shelf {
            description 'Shelf number'
                        ;
            type uint8 {
              range 0..255 {
                description 'LCC shelf'
                            ;
              }
            }
          }
          leaf length {
            description 'Fiber length'
                        ;
            type enumeration {
              enum 10 {
                value 10 ;
                description 'Fiber length is 10 meter'
                            ;
              }
              enum 30 {
                value 30 ;
                description 'Fiber length is 30 meter'
                            ;
              }
              enum 100 {
                value 100 ;
                description 'Fiber length is 100 meter'
                            ;
              }
            }
          }
        }
      }
    }
  }
}
