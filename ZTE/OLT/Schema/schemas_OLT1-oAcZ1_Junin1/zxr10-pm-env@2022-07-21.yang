module zxr10-pm-env {
  namespace 'http://www.zte.com.cn/zxr10/netconf/schema/rosng/pm-env'
            ;
  prefix pm-env ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  revision 2022-07-21 {
    description 'add 400G optical FEC state and PreFec BER.'
                ;
  }
  revision 2022-07-09 {
    description 'add list:power-inputline'
                ;
  }
  revision 2022-05-15 {
    description 'add leafs:current-power current-voltage current-current power-'
              + 'status run-status output-voltage output-current module-online-'
              + 'nums'
                ;
  }
  revision 2022-03-23 {
    description 'Add 5960M to feature optical-module-config.optical total-send-'
              + 'power and total-recv-power support 5960M.'
                ;
  }
  revision 2022-03-07 {
    description 'obsolete ipmb'
                ;
  }
  revision 2022-02-16 {
    reference 'add configuration env optical'
              ;
  }
  revision 2022-02-09 {
    description 'add 5960M.'
                ;
  }
  revision 2022-01-04 {
    reference 'add optical laser stat'
              ;
  }
  revision 2021-11-11 {
    reference 'add optical copper multi'
              ;
  }
  revision 2021-10-22 {
    description 'add pc label in feature shelf-15k2.'
                ;
  }
  revision 2021-10-20 {
    description 'add temperature major-threshold.'
                ;
  }
  revision 2021-10-15 {
    description 'Add outdoor fan speed curve set.'
                ;
  }
  revision 2021-10-14 {
    description 'Change the range of slot minor-threshold-slot value to 1~255.'
                ;
  }
  revision 2021-09-16 {
    description 'Add env state opticals leaf length-om4 length-om5 and version'
                ;
  }
  revision 2021-09-14 {
    description "Change almtype's value range to 0~65535."
                ;
  }
  revision 2021-08-11 {
    description 'add slot temperature minor-threshold.'
                ;
  }
  revision 2021-06-08 {
    description 'add redundancy slot function.'
                ;
  }
  revision 2021-05-19 {
    description 'fit netconf fan config'
                ;
  }
  revision 2021-05-18 {
    description 'Change vendor-name,vendor-pn,vendor-sn,vendor-rev Length to 24.'
                ;
  }
  revision 2021-04-26 {
    description 'add leafs:sensitivity,overload,power-range-tx.'
                ;
  }
  revision 2021-02-26 {
    description 'delete unnecessary if-feature.'
                ;
  }
  revision 2021-02-05 {
    description 'add leaf optical-stand.'
                ;
  }
  revision 2020-12-18 {
    description 'add leaf panel of boards and board-powers.'
                ;
  }
  revision 2020-10-15 {
    description 'add container delete-offline-afnode.'
                ;
  }
  revision 2020-06-22 {
    description 'add show ipmb function'
                ;
  }
  revision 2020-06-04 {
    description 'add card-plug-event'
                ;
  }
  revision 2020-05-23 {
    description 'add fan-pid'
                ;
  }
  revision 2020-04-27 {
    description 'add more fan node'
                ;
  }
  revision 2020-04-17 {
    description 'add temper protect function.'
                ;
  }
  revision 2020-04-10 {
    description 'add leafs:voltage3.3,voltage5,current,high-warning-threshold-r'
              + 'x,low-warning-threshold-rx,high-warning-threshold-tx,low-warni'
              + 'ng-threshold-tx.'
                ;
  }
  revision 2020-03-31 {
    description 'add set fan shift'
                ;
  }
  revision 2020-03-27 {
    description 'Set temper minor and shutdown threshold Node.'
                ;
  }
  revision 2020-03-13 {
    description 'Set Fan Temper-stand Node'
                ;
  }
  revision 2020-03-05 {
    description 'Change Monitor Msf Length to 40.'
                ;
  }
  revision 2020-03-01 {
    description 'add board temperature and power info'
                ;
  }
  revision 2020-02-28 {
    description 'add leafs for reload system slot and add reload-shelf.'
                ;
  }
  revision 2020-02-27 {
    description 'add utilizations'
                ;
  }
  revision 2020-02-15 {
    description 'add show fan-switch'
                ;
  }
  revision 2019-08-29 {
    description 'add link-detect'
                ;
  }
  revision 2019-07-15 {
    description 'add total-recv-power'
                ;
  }
  revision 2019-04-04 {
    description 'add status enum value: maintenance in list board-start'
                ;
  }
  revision 2019-03-18 {
    description 'add extern alarm input and output switch'
                ;
  }
  revision 2019-03-12 {
    description 'add switch state'
                ;
  }
  revision 2019-03-07 {
    description 'add total-send-power and fec-mode'
                ;
  }
  revision 2019-02-28 {
    description 'add forbidons in configuration and state.'
                ;
  }
  revision 2019-01-17 {
    description 'shelf range 0-255.slot range 0-255.'
                ;
  }
  revision 2018-09-13 {
    description 'add temperature-control-mode'
                ;
  }
  revision 2018-09-10 {
    description 'add leaf node sync-total-status'
                ;
  }
  revision 2018-07-04 {
    description 'add connector-type'
                ;
  }
  revision 2018-05-08 {
    description 'add channel-number'
                ;
  }
  revision 2017-10-26 {
    description 'add authentication, authentication-code, product-serial-number'
              + ' and product-date'
                ;
  }
  revision 2016-12-05 {
    description 'add optical status, online or offline.'
                ;
  }
  revision 2016-05-04 {
    description 'modify send-power/receive-power/temperature length of optical;'
              + ''+"\n"
              + 'add leaf supply-division of power-source'
                ;
  }
  revision 2016-04-18 {
    description 'Add contain dustproof, dustproof-statuss, reset-dustproof'
                ;
  }
  revision 2016-03-28 {
    description 'Modify data type of the leaf node current-temperature from uin'
              + 't 32 to int32'
                ;
  }
  revision 2015-09-06 {
    description 'Add contain boards'
                ;
  }
  feature shelf-15k2 ;
  feature optical-module-config ;
  feature switch ;
  feature switch-temperature ;
  feature temperature-major {
    ncd:revise-date 2021-10-20 ;
  }
  feature spn {
    ncd:revise-date 2022-01-04 ;
  }
  container configuration {
    container env {
      container alarm-ring {
        leaf ring {
          description 'Alarm ring on/off.'
                      ;
          type enumeration {
            enum off {
              value 0 ;
              description 'Alarm-ring off.'
                          ;
            }
            enum on {
              value 1 ;
              description 'Alarm-ring on.'
                          ;
            }
          }
          default off ;
        }
      }
      container alarm-tandems {
        list alarm-tandem {
          description 'Configure the tandem mode of alarm in.'
                      ;
          key 'shelf slot'
              ;
          leaf shelf {
            description 'Number of shelf.'
                        ;
            type uint8 {
              range 0..255 {
                description 'Shelf range.'
                            ;
              }
            }
          }
          leaf slot {
            description 'Number of slot.'
                        ;
            type uint8 {
              range 0..255 {
                description 'Slot range.'
                            ;
              }
            }
          }
        }
      }
      container extern-alarms {
        list extern-alarm {
          description 'Configure the voltage of extern alarm.'
                      ;
          key 'shelf slot line'
              ;
          leaf shelf {
            description 'Number of shelf.'
                        ;
            type uint8 {
              range 0..255 {
                description 'Shelf range.'
                            ;
              }
            }
          }
          leaf slot {
            description 'Number of slot.'
                        ;
            type uint8 {
              range 0..255 {
                description 'Slot range.'
                            ;
              }
            }
          }
          leaf line {
            description 'Line number.'
                        ;
            type enumeration {
              enum 1 {
                value 1 ;
                description 'Alarm line 1.'
                            ;
              }
              enum 2 {
                value 2 ;
                description 'Alarm line 2.'
                            ;
              }
              enum 3 {
                value 3 ;
                description 'Alarm line 3.'
                            ;
              }
              enum 4 {
                value 4 ;
                description 'Alarm line 4.'
                            ;
              }
            }
          }
          leaf voltage {
            description 'The voltage.'
                        ;
            type enumeration {
              enum off {
                value 0 ;
                description 'The alarm line is off.'
                            ;
              }
              enum low {
                value 1 ;
                description 'The alarm line is low voltage.'
                            ;
              }
              enum high {
                value 2 ;
                description 'The alarm line is high voltage.'
                            ;
              }
            }
            default off ;
          }
        }
      }
      container fans {
        leaf fan-speed {
          description 'The fan speed mode.'
                      ;
          type enumeration {
            enum auto {
              value 0 ;
              description 'Auto speed.'
                          ;
            }
            enum full {
              value 1 ;
              description 'Full speed.'
                          ;
            }
          }
          default auto ;
        }
        leaf fan-temper-stand {
          description 'The fan temper stand.'
                      ;
          type int32 {
            range 0..95 ;
          }
          default 0 ;
          ncd:revise-date 2020-03-13 ;
        }
        list fan {
          key shelf ;
          leaf shelf {
            description 'Shelf number'
                        ;
            type uint8 {
              range 0..255 {
                description 'shelf range.'
                            ;
              }
            }
          }
          leaf percent {
            description 'Percentage of fan speed'
                        ;
            type union {
              type enumeration {
                enum auto {
                  value 128 ;
                }
                enum full {
                  value 100 ;
                }
                enum 50-percent {
                  value 50 ;
                }
                enum 60-percent {
                  value 60 ;
                }
                enum 70-percent {
                  value 70 ;
                }
                enum 80-percent {
                  value 80 ;
                }
                enum 90-percent {
                  value 90 ;
                }
              }
              type uint8 {
                range 50..100 ;
              }
            }
          }
          leaf temperature-control-mode {
            description 'The mode of temperature-control-mode.'
                        ;
            type enumeration {
              enum strict {
                value 0 ;
                description 'The temperature-control-mode is strict.'
                            ;
              }
              enum normal {
                value 1 ;
                description 'The temperature-control-mode is normal.'
                            ;
              }
            }
            default strict ;
          }
        }
        list fan-pid-strategy {
          key shelf ;
          leaf shelf {
            description 'Shelf number'
                        ;
            type uint8 {
              range 0..255 {
                description 'shelf range.'
                            ;
              }
            }
          }
          leaf pid-strategy {
            description 'fan pid-strategy'
                        ;
            type uint8 {
              range 1..3 ;
            }
          }
          ncd:revise-date 2020-05-23 ;
        }
      }
      container powers {
        list power {
          key shelf ;
          leaf shelf {
            description 'Shelf number'
                        ;
            type uint8 {
              range 0..255 {
                description 'shelf range.'
                            ;
              }
            }
          }
          leaf budget-policy {
            description 'Power budgeting policy'
                        ;
            type enumeration {
              enum normal {
                value 0 ;
                description 'Normal policy'
                            ;
              }
              enum control {
                value 1 ;
                description 'Control policy'
                            ;
              }
              enum decontrol {
                value 2 ;
                description 'Decontrol policy'
                            ;
              }
            }
            default normal ;
          }
          leaf reserve-status {
            description 'Power reserve status'
                        ;
            type enumeration {
              enum enable {
                value 0 ;
              }
              enum disable {
                value 1 ;
              }
            }
            default enable ;
          }
        }
        list power-inputline {
          key shelf ;
          leaf shelf {
            description 'Shelf number'
                        ;
            type uint8 {
              range 0..255 {
                description 'shelf range.'
                            ;
              }
            }
          }
          leaf power-inputline {
            description 'power inputline number'
                        ;
            type enumeration {
              enum single {
                value 1 ;
              }
              enum double {
                value 2 ;
              }
            }
            default single ;
          }
          ncd:revise-date 2022-07-09 ;
        }
      }
      container board-starts {
        list board-start {
          key 'shelf slot'
              ;
          leaf shelf {
            description 'Shelf number'
                        ;
            type uint8 {
              range 0..255 {
                description 'shelf range.'
                            ;
              }
            }
          }
          leaf slot {
            description 'Slot number'
                        ;
            type uint8 {
              range 0..255 {
                description 'slot range.'
                            ;
              }
            }
          }
          leaf status {
            description 'Board start status'
                        ;
            type enumeration {
              enum offline {
                value 0 ;
              }
              enum online {
                value 1 ;
              }
              enum maintenance {
                value 2 ;
              }
            }
            ncd:revise-date 2019-04-04 ;
          }
        }
      }
      container cpu-cirs {
        list cpu-cir {
          key cpuname ;
          leaf cpuname {
            description 'CPU name'
                        ;
            type string ;
          }
          leaf speed {
            description 'CPU speed'
                        ;
            type uint32 {
              range 100..1000000 {
                description 'speed range'
                            ;
              }
            }
          }
        }
      }
      container outdoor {
        if-feature shelf-15k2 ;
        leaf lines-function {
          type enumeration {
            enum alarm-out {
              value 0 ;
            }
            enum rs485 {
              value 1 ;
            }
          }
          default alarm-out ;
        }
        leaf power-type {
          type enumeration {
            enum DC {
              value 0 ;
            }
            enum AC {
              value 1 ;
            }
          }
          default DC ;
        }
        leaf fan {
          type enumeration {
            enum auto {
              value 0 ;
            }
            enum 25 {
              value 1 ;
            }
            enum 50 {
              value 2 ;
            }
            enum 75 {
              value 3 ;
            }
            enum 100 {
              value 4 ;
            }
          }
          default auto ;
        }
        leaf fan-curve {
          type enumeration {
            enum low-noise {
              value 0 ;
              description 'low-noise curve'
                          ;
            }
            enum low-temperature {
              value 1 ;
              description 'low-temperature curve'
                          ;
            }
          }
          default low-noise ;
          ncd:revise-date 2021-10-15 ;
        }
        leaf update-data-period {
          type uint8 {
            range 0..255 ;
          }
          default 2 ;
        }
        list temperature-threshold {
          reference 'set temperature-threshold.'
                    ;
          key check-point ;
          leaf check-point {
            reference 'temperature check-point.'
                      ;
            type uint8 {
              range 0..3 ;
            }
          }
          leaf max {
            reference temperature-threshold. ;
            type int32 {
              range 50..100 ;
            }
            default 64 ;
          }
        }
      }
      container dustproof {
        list dustproof-cleancycle {
          description 'Configure the clean cycle of dust proof.'
                      ;
          key shelf ;
          leaf shelf {
            description 'Shelf number.'
                        ;
            type uint8 {
              range 0..255 {
                description 'shelf range.'
                            ;
              }
            }
          }
          leaf day {
            description 'Clean cycle.'
                        ;
            type uint16 {
              range 0..10000 ;
            }
            default 90 ;
          }
        }
        ncd:revise-date 2016-04-18 ;
      }
      container forbidons {
        list forbidon {
          key 'shelf slot'
              ;
          leaf shelf {
            description 'Number of shelf.'
                        ;
            type uint8 {
              range 0..127 {
                description 'Shelf range.'
                            ;
              }
            }
          }
          leaf slot {
            description 'Number of slot.'
                        ;
            type uint8 {
              range 0..253 {
                description 'Slot range.'
                            ;
              }
            }
          }
          leaf forbidon-status {
            description 'forbidon status'
                        ;
            type enumeration {
              enum permit {
                value 1 ;
              }
              enum forbid {
                value 2 ;
              }
            }
            default permit ;
          }
        }
        ncd:revise-date 2019-02-28 ;
      }
      container exalminputs {
        description 'Setting external input alarm command'
                    ;
        list exalminput {
          key 'shelf slot line'
              ;
          leaf shelf {
            description 'Number of shelf.'
                        ;
            type uint8 {
              range 0..127 {
                description 'Shelf range.'
                            ;
              }
            }
          }
          leaf slot {
            description 'Number of slot.'
                        ;
            type uint8 {
              range 0..253 {
                description 'Slot range.'
                            ;
              }
            }
          }
          leaf line {
            description 'Line number.'
                        ;
            type uint8 {
              range 1..8 ;
            }
          }
          leaf voltage {
            description 'The voltage.'
                        ;
            type enumeration {
              enum high {
                value 0 ;
                description 'The alarm line is high voltage.'
                            ;
              }
              enum low {
                value 1 ;
                description 'The alarm line is low voltage.'
                            ;
              }
            }
            mandatory true ;
          }
          leaf almtype {
            description 'alarm type'
                        ;
            type uint16 {
              range 0..65535 {
                description 'extern alarm type range'
                            ;
              }
            }
            mandatory true ;
          }
        }
        ncd:revise-date 2019-03-18 ;
      }
      container link-detect {
        description 'Set link detect'
                    ;
        presence link-detect ;
        leaf dscp {
          description 'Dscp value'
                      ;
          type uint8 {
            range 0..63 {
              description 'Dscp range'
                          ;
            }
          }
          mandatory true ;
        }
        ncd:revise-date 2019-08-29 ;
      }
      container outputswitchs {
        description 'Set output switch'
                    ;
        list outputswitch {
          key 'shelf slot portno'
              ;
          leaf shelf {
            description 'Number of shelf.'
                        ;
            type uint8 {
              range 0..127 {
                description 'Shelf range.'
                            ;
              }
            }
          }
          leaf slot {
            description 'Number of slot.'
                        ;
            type uint8 {
              range 0..253 {
                description 'Slot range.'
                            ;
              }
            }
          }
          leaf portno {
            description 'Line number.'
                        ;
            type uint8 {
              range 1..8 ;
            }
          }
          leaf outputswitchtype {
            description 'output switch type'
                        ;
            type enumeration {
              enum not-output-alarm {
                value 1 ;
                description 'Do not output alarm of this network element.'
                            ;
              }
              enum severe-alarm {
                value 2 ;
                description 'as the output of severe alarm;'
                            ;
              }
              enum main-alarm {
                value 3 ;
                description 'used as the main alarm for output.'
                            ;
              }
              enum secondary-alarm {
                value 4 ;
                description 'used as secondary alarm for output'
                            ;
              }
              enum alarm-bell {
                value 5 ;
                description 'used as output alarm bell; used only for UPP devic'
                          + 'es'
                            ;
              }
              enum user-control-port {
                value 6 ;
                description 'used as a user control port; used only for UPP dev'
                          + 'ices'
                            ;
              }
            }
            default not-output-alarm ;
          }
          leaf almvoltleveltype {
            description 'alarm voltlevel type'
                        ;
            type enumeration {
              enum on {
                value 1 ;
                description '1 open alarm'
                            ;
              }
              enum off {
                value 2 ;
                description '2 close alarm'
                            ;
              }
            }
            default on ;
          }
          leaf enableoutput {
            description 'enble disable output'
                        ;
            type enumeration {
              enum enable-output {
                value 1 ;
                description 'enable output'
                            ;
              }
              enum disable-output {
                value 2 ;
                description 'disable output'
                            ;
              }
            }
            default enable-output ;
          }
          leaf usrctloutputvoltlevel {
            description 'user control output voltlevel'
                        ;
            type enumeration {
              enum output-on-state {
                value 1 ;
                description 'output on state'
                            ;
              }
              enum output-off-state {
                value 2 ;
                description 'output off state'
                            ;
              }
            }
            default output-off-state ;
          }
        }
        ncd:revise-date 2019-03-18 ;
      }
      container temperature {
        list shutdown-threshold {
          key shelf ;
          leaf shelf {
            description 'Shelf number'
                        ;
            type uint8 {
              range 0..255 {
                description 'shelf range.'
                            ;
              }
            }
            mandatory true ;
          }
          leaf threshold-value {
            description 'shutdown threshold value.'
                        ;
            type uint8 {
              range 115..125 ;
            }
          }
        }
        list minor-threshold {
          key shelf ;
          leaf shelf {
            description 'Shelf number'
                        ;
            type uint8 {
              range 0..255 {
                description 'shelf range.'
                            ;
              }
            }
            mandatory true ;
          }
          leaf bardtype {
            description 'board tye.'
                        ;
            type enumeration {
              enum mpu {
                value 1 ;
              }
              enum pfu {
                value 3 ;
              }
              enum sfu {
                value 4 ;
              }
            }
            mandatory true ;
          }
          leaf cputype {
            description 'temperature point type.'
                        ;
            type empty ;
          }
          leaf panelno {
            description 'board panel id.'
                        ;
            type uint8 ;
            mandatory true ;
          }
          leaf cpuvalue {
            description 'temper point threshold value.'
                        ;
            type uint8 {
              range 1..127 ;
            }
            default 85 ;
          }
          leaf oattype {
            description 'temperature point type.'
                        ;
            type empty ;
          }
          leaf oatvalue {
            description 'temper point threshold value.'
                        ;
            type uint8 {
              range 1..127 ;
            }
            default 85 ;
          }
          leaf iattype {
            description 'temperature point type.'
                        ;
            type empty ;
          }
          leaf iatvalue {
            description 'temper point threshold value.'
                        ;
            type uint8 {
              range 1..127 ;
            }
            default 85 ;
          }
          leaf chiptype {
            description 'temperature point type.'
                        ;
            type empty ;
          }
          leaf chipvalue {
            description 'temper point threshold value.'
                        ;
            type uint8 {
              range 1..127 ;
            }
            default 105 ;
          }
        }
        list minor-threshold-slot {
          if-feature switch-temperature ;
          description 'Configure the minor threshold'
                      ;
          key 'shelf slot addr'
              ;
          leaf shelf {
            description 'Shelf number'
                        ;
            type uint8 {
              range 0..255 {
                description 'shelf range.'
                            ;
              }
            }
          }
          leaf slot {
            description 'Slot number'
                        ;
            type uint8 {
              range 0..255 ;
            }
          }
          leaf addr {
            description 'Temperature point address'
                        ;
            type uint32 {
              range 0..255 ;
            }
          }
          leaf value {
            description 'Configure the minor threshold'
                        ;
            type uint32 {
              range 1..255 ;
            }
          }
          ncd:revise-date 2021-08-11 ;
        }
        list major-threshold {
          if-feature temperature-major ;
          description 'Configure the major threshold'
                      ;
          key 'shelf slot addr'
              ;
          leaf shelf {
            description 'Shelf number'
                        ;
            type uint8 {
              range 0..255 {
                description 'shelf range.'
                            ;
              }
            }
          }
          leaf slot {
            description 'Slot number'
                        ;
            type uint8 {
              range 0..255 ;
            }
          }
          leaf addr {
            description 'Temperature point address'
                        ;
            type uint32 {
              range 0..255 ;
            }
          }
          leaf value {
            description 'Configure the major threshold'
                        ;
            type uint32 {
              range 0..255 ;
            }
          }
          ncd:revise-date 2021-10-20 ;
        }
      }
      container temper-protect {
        list fan-offline {
          key shelf ;
          leaf shelf {
            description 'Shelf number'
                        ;
            type uint8 {
              range 0..255 {
                description 'shelf range.'
                            ;
              }
            }
            mandatory true ;
          }
          leaf enable {
            description 'enable all fan offline protect function.'
                        ;
            type enumeration {
              enum enable {
                value 1 ;
              }
              enum disable {
                value 0 ;
              }
            }
          }
          leaf delay-time {
            description 'fan offline delay time.'
                        ;
            type uint8 {
              range 1..10 ;
            }
          }
        }
        list board {
          key shelf ;
          leaf shelf {
            description 'Shelf number'
                        ;
            type uint8 {
              range 0..255 {
                description 'shelf range.'
                            ;
              }
            }
            mandatory true ;
          }
          leaf enable {
            description 'enable board temper protect function.'
                        ;
            type enumeration {
              enum enable {
                value 1 ;
              }
              enum disable {
                value 0 ;
              }
            }
          }
        }
        ncd:revise-date 2020-04-17 ;
      }
      container optical {
        list optical-property {
          if-feature spn ;
          key if-name ;
          leaf if-name {
            type ncd:ifname ;
          }
          leaf lanenum {
            type uint8 ;
            mandatory true ;
          }
          leaf perfcode {
            type enumeration {
              enum powerrx {
                value 50 ;
                description 'Receive signal power threshold of optical module(d'
                          + 'Bm)'
                            ;
              }
              enum bias {
                value 239 ;
                description 'Bias current threshold of optical module(mA)'
                            ;
              }
              enum temperature {
                value 240 ;
                description 'Temperature threshold of optical module(degree(s) '
                          + 'Celsius)'
                            ;
              }
              enum powertx {
                value 241 ;
                description 'Transmit signal power threshold of optical module('
                          + 'dBm)'
                            ;
              }
              enum supplyvoltage2 {
                value 757 ;
                description 'Supply voltage2 threshold of optical module(V)'
                            ;
              }
              enum supplyvoltage1 {
                value 760 ;
                description 'Supply voltage1 threshold of optical module(V)'
                            ;
              }
            }
            mandatory true ;
          }
          leaf low-alarm {
            type string ;
          }
          leaf pre-low-alarm {
            type string ;
          }
          leaf pre-high-alarm {
            type string ;
          }
          leaf high-alarm {
            type string ;
          }
        }
        ncd:revise-date 2022-02-16 ;
      }
    }
  }
  container state {
    config false ;
    container env {
      container fan-status {
        list fans {
          key 'shelf group-num'
              ;
          leaf shelf {
            description 'Shelf number.'
                        ;
            type uint8 {
              range 0..255 {
                description 'Shelf range.'
                            ;
              }
            }
          }
          leaf group-num {
            description 'Group number.'
                        ;
            type uint8 {
              range 0..255 {
                description 'Group range.'
                            ;
              }
            }
          }
          leaf fan-div-num {
            description 'Fan div number.'
                        ;
            type uint8 ;
            ncd:revise-date 2020-04-27 ;
          }
          leaf fan-div-sumnum {
            description 'Fan div sum number.'
                        ;
            type uint8 ;
            ncd:revise-date 2020-02-15 ;
          }
          leaf fan-module-sumnum {
            description 'Fan module sum number.'
                        ;
            type uint8 ;
            ncd:revise-date 2020-02-15 ;
          }
          leaf fan-name {
            description 'Fan name.'
                        ;
            type ncd:string-all ;
          }
          leaf fan-present {
            description 'Fan online status.'
                        ;
            type enumeration {
              enum online {
                value 0 ;
                description 'Fan online.'
                            ;
              }
              enum offline {
                value 1 ;
                description 'Fan offline.'
                            ;
              }
            }
            ncd:revise-date 2020-02-15 ;
          }
          leaf physical-status {
            description 'Fan physical status.'
                        ;
            type enumeration {
              enum online {
                value 0 ;
                description 'Fan status normal.'
                            ;
              }
              enum offline {
                value 1 ;
                description 'Fan status warning.'
                            ;
              }
              enum normal {
                value 3 ;
              }
              enum warning {
                value 4 ;
              }
              enum N/A {
                value 2 ;
              }
            }
          }
          leaf fan-shift {
            description 'Fan run speed level.'
                        ;
            type uint8 ;
            ncd:revise-date 2020-02-15 ;
          }
          leaf fan-speed-rpm {
            description 'Fan Rmp.'
                        ;
            type uint32 ;
            ncd:revise-date 2020-02-15 ;
          }
          leaf fan-mode {
            description 'Fan speed mode.'
                        ;
            type enumeration {
              enum auto {
                value 0 ;
                description 'Auto speed mode.'
                            ;
              }
              enum full {
                value 1 ;
                description 'Full speed mode.'
                            ;
              }
              enum manual {
                value 2 ;
                description 'Manual speed mode.'
                            ;
              }
              enum N/A {
                value 3 ;
              }
            }
            ncd:revise-date 2020-02-15 ;
          }
          leaf version-number {
            description 'Fan version-number.'
                        ;
            type ncd:string-all ;
            ncd:revise-date 2020-02-15 ;
          }
          leaf serial-number {
            description 'Fan serial-number.'
                        ;
            type ncd:string-all ;
            ncd:revise-date 2020-02-15 ;
          }
          leaf manufacture-date {
            description 'Fan manufacture-date.'
                        ;
            type ncd:string-all ;
            ncd:revise-date 2020-02-15 ;
          }
          leaf board-name {
            description 'Fan board name.'
                        ;
            type ncd:string-all ;
            ncd:revise-date 2020-02-15 ;
          }
          leaf board-version {
            description 'Fan board-version.'
                        ;
            type ncd:string-all ;
            ncd:revise-date 2020-02-15 ;
          }
          leaf fan-all-power-w {
            description 'Fan total power.'
                        ;
            type ncd:string-all ;
            ncd:revise-date 2020-02-15 ;
          }
          leaf fan-single-power-w {
            description 'Fan power.'
                        ;
            type ncd:string-all ;
            ncd:revise-date 2020-02-15 ;
          }
          leaf fan-max-speed-rpm {
            description 'Fan max Rmp.'
                        ;
            type uint32 ;
            ncd:revise-date 2020-02-15 ;
          }
          leaf fan-stand-speed-rpm {
            description 'Fan stand Rmp.'
                        ;
            type uint32 ;
            ncd:revise-date 2020-02-15 ;
          }
          leaf fan-local-temp {
            description 'Fan local temp.'
                        ;
            type int32 ;
            ncd:revise-date 2020-02-15 ;
          }
          leaf fan-remote-temp {
            description 'Fan remote temp.'
                        ;
            type int32 ;
            ncd:revise-date 2020-02-15 ;
          }
          leaf fan-stand-temp {
            description 'Fan stand temp.'
                        ;
            type int32 ;
            ncd:revise-date 2020-02-15 ;
          }
          leaf fan-env-temp {
            description 'Fan env temp.'
                        ;
            type int32 ;
            ncd:revise-date 2020-02-15 ;
          }
          leaf pwd {
            description 'Fan pwd.'
                        ;
            type uint16 ;
            ncd:revise-date 2020-04-27 ;
          }
          leaf fan-type {
            description 'Fan type.'
                        ;
            type ncd:string-all ;
            ncd:revise-date 2020-04-27 ;
          }
          leaf fan-hwver {
            description 'Fan hardware version.'
                        ;
            type ncd:string-all ;
            ncd:revise-date 2020-04-27 ;
          }
          leaf current-power {
            description 'Current power'
                        ;
            type ncd:string-all ;
            ncd:revise-date 2022-05-15 ;
          }
          leaf current-voltage {
            description 'Current voltage'
                        ;
            type ncd:string-all ;
            ncd:revise-date 2022-05-15 ;
          }
          leaf current-current {
            description 'Current current'
                        ;
            type ncd:string-all ;
            ncd:revise-date 2022-05-15 ;
          }
          container fan-iipma-offline-msg {
            leaf fan-iipma-offline-msg {
              description fan-iipma-offline-msg ;
              type ncd:string-all ;
            }
            ncd:revise-date 2020-02-15 ;
          }
          list fan {
            key fan-num ;
            leaf fan-num {
              description 'Fan number in the group.'
                          ;
              type uint8 ;
            }
            leaf work-status {
              description 'Fan work status.'
                          ;
              type enumeration {
                enum fail-to-work {
                  value 0 ;
                  description 'Fail to work.'
                              ;
                }
                enum work-normally {
                  value 1 ;
                  description 'Work normally.'
                              ;
                }
              }
            }
            leaf level {
              description 'Fan run speed.'
                          ;
              type uint8 ;
            }
          }
        }
      }
      container power-source {
        list power-group {
          key 'shelf group-num'
              ;
          leaf shelf {
            description 'Shelf number'
                        ;
            type uint8 {
              range 0..255 {
                description 'Shelf range.'
                            ;
              }
            }
          }
          leaf group-num {
            description 'Group number'
                        ;
            type uint8 ;
          }
          leaf group-name {
            description 'Group name'
                        ;
            type ncd:string-all ;
          }
          list power-module {
            key module-num ;
            leaf module-num {
              type uint8 ;
            }
            leaf power-type {
              type enumeration {
                enum DC {
                  value 1 ;
                }
                enum AC {
                  value 2 ;
                }
              }
            }
            leaf power-name {
              type ncd:string-all ;
            }
            leaf supply-division {
              type uint8 ;
              ncd:revise-date 2016-05-04 ;
            }
            leaf phy-status {
              type enumeration {
                enum online {
                  value 0 ;
                }
                enum offline {
                  value 1 ;
                }
                enum unknown {
                  value 255 ;
                }
              }
            }
            leaf power-status {
              type enumeration {
                enum normal {
                  value 0 ;
                }
                enum abnormal {
                  value 1 ;
                }
                enum unknown {
                  value 255 ;
                }
              }
              ncd:revise-date 2022-05-15 ;
            }
            leaf com-status {
              type enumeration {
                enum normal {
                  value 0 ;
                }
                enum abnormal {
                  value 1 ;
                }
                enum unknown {
                  value 255 ;
                }
              }
            }
            leaf run-status {
              type enumeration {
                enum normal {
                  value 0 ;
                }
                enum abnormal {
                  value 1 ;
                }
                enum unknown {
                  value 255 ;
                }
              }
              ncd:revise-date 2022-05-15 ;
            }
            leaf power-capacity {
              type ncd:string-all ;
            }
            leaf power-used {
              type ncd:string-all ;
            }
            leaf power-available {
              type ncd:string-all ;
            }
            list division {
              key division-num ;
              leaf division-num {
                type uint8 ;
              }
              leaf rating-power {
                type uint32 ;
              }
            }
            leaf outputorInput1-voltage {
              description 'Output or input voltage.'
                          ;
              type uint32 ;
            }
            leaf outputorInput1-current {
              description 'Output or input current.'
                          ;
              type uint32 ;
            }
            leaf inputorInput2-voltage {
              description 'Input or output voltage.'
                          ;
              type uint32 ;
            }
            leaf inputorInput2-current {
              description 'Input or output current.'
                          ;
              type uint32 ;
            }
            leaf version-number {
              description 'Version number.'
                          ;
              type string ;
            }
            leaf temperature {
              description 'Power temperature.'
                          ;
              type string ;
            }
            leaf manufacture-date {
              description 'Power manufacture date.'
                          ;
              type string ;
            }
            leaf serial-number {
              description 'Power serial number.'
                          ;
              type string ;
            }
            leaf output-voltage {
              description 'Output voltage.'
                          ;
              type ncd:string-all ;
              ncd:revise-date 2022-05-15 ;
            }
            leaf output-current {
              description 'Output current.'
                          ;
              type ncd:string-all ;
              ncd:revise-date 2022-05-15 ;
            }
            container monitor-offline-msg {
              leaf no-rcv-msg {
                description 'Monitor board offline message.'
                            ;
                type ncd:string-with-blank ;
              }
              ncd:revise-date 2019-08-29 ;
            }
          }
        }
      }
      container opticals {
        list optical {
          key if-name ;
          leaf if-name {
            type string ;
          }
          leaf optical-status {
            type enumeration {
              enum offline {
                value 0 ;
                description 'The optical is offline.'
                            ;
              }
              enum online {
                value 1 ;
                description 'The optical is online.'
                            ;
              }
            }
            default offline ;
            ncd:revise-date 2016-12-05 ;
          }
          leaf optical-electric-mode {
            type uint8 ;
          }
          leaf transceiver-type {
            type ncd:string-all ;
          }
          leaf single-fiber-double-orient {
            type uint8 ;
          }
          leaf distance-mode {
            type uint8 ;
          }
          leaf work-speed {
            type uint32 ;
          }
          leaf media-type {
            type uint8 ;
          }
          leaf send-wavelength {
            type uint32 ;
          }
          leaf recv-wavelength {
            type uint32 ;
          }
          leaf length-9um-smf {
            type uint32 ;
          }
          leaf length-50um-om2 {
            type uint32 ;
          }
          leaf length-62um-om1 {
            type uint32 ;
          }
          leaf length-50um-om3 {
            type uint32 ;
          }
          leaf length-om4 {
            type uint32 ;
            ncd:revise-date 2021-09-16 ;
          }
          leaf length-om5 {
            type uint32 ;
            ncd:revise-date 2021-09-16 ;
          }
          leaf length-50um-ebw {
            type uint32 ;
          }
          leaf copper-line {
            type uint32 ;
          }
          leaf sonet-codes {
            type ncd:string-all ;
          }
          leaf ethernet-codes {
            type ncd:string-all ;
          }
          leaf vendor-name {
            type ncd:string-all ;
          }
          leaf vendor-pn {
            type ncd:string-all ;
          }
          leaf vendor-sn {
            type ncd:string-all ;
          }
          leaf vendor-rev {
            type ncd:string-all ;
          }
          leaf send-waveband-scope {
            type ncd:string-all ;
          }
          leaf recv-waveband-scope {
            type ncd:string-all ;
          }
          leaf send-power {
            type ncd:string-all ;
          }
          leaf receive-power {
            type ncd:string-all ;
          }
          leaf temperature {
            type ncd:string-all ;
          }
          leaf authentication {
            type ncd:string-all ;
            ncd:revise-date 2017-10-26 ;
          }
          leaf authentication-code {
            type ncd:string-all ;
            ncd:revise-date 2017-10-26 ;
          }
          leaf product-serial-number {
            type ncd:string-all ;
            ncd:revise-date 2017-10-26 ;
          }
          leaf product-date {
            type ncd:string-all ;
            ncd:revise-date 2017-10-26 ;
          }
          leaf channel-number {
            type uint8 ;
            ncd:revise-date 2018-05-08 ;
          }
          leaf connector-type {
            type ncd:string-all ;
            ncd:revise-date 2018-07-04 ;
          }
          leaf total-send-power {
            if-feature optical-module-config ;
            type ncd:string-all ;
            ncd:revise-date 2019-03-07 ;
          }
          leaf fec-mode {
            if-feature optical-module-config ;
            type ncd:string-all ;
            ncd:revise-date 2019-03-07 ;
          }
          leaf total-recv-power {
            if-feature optical-module-config ;
            type ncd:string-all ;
            ncd:revise-date 2019-07-15 ;
          }
          leaf voltage3.3 {
            type ncd:string-all ;
            ncd:revise-date 2020-04-10 ;
          }
          leaf voltage5 {
            type ncd:string-all ;
            ncd:revise-date 2020-04-10 ;
          }
          leaf current {
            type ncd:string-all ;
            ncd:revise-date 2020-04-10 ;
          }
          leaf high-warning-threshold-rx {
            type ncd:string-all ;
            ncd:revise-date 2020-04-10 ;
          }
          leaf low-warning-threshold-rx {
            type ncd:string-all ;
            ncd:revise-date 2020-04-10 ;
          }
          leaf high-warning-threshold-tx {
            type ncd:string-all ;
            ncd:revise-date 2020-04-10 ;
          }
          leaf low-warning-threshold-tx {
            type ncd:string-all ;
            ncd:revise-date 2020-04-10 ;
          }
          leaf optical-stand {
            type uint8 ;
            ncd:revise-date 2021-02-05 ;
          }
          leaf sensitivity {
            type ncd:string-all ;
            ncd:revise-date 2021-05-19 ;
          }
          leaf overload {
            type ncd:string-all ;
            ncd:revise-date 2021-05-19 ;
          }
          leaf power-range-tx {
            type ncd:string-all ;
            ncd:revise-date 2021-05-19 ;
          }
          leaf version {
            type string ;
            ncd:revise-date 2021-09-16 ;
          }
          leaf copper-multi {
            type uint32 ;
            ncd:revise-date 2021-11-11 ;
          }
          leaf laser-stat {
            if-feature spn ;
            type uint32 ;
            ncd:revise-date 2022-01-04 ;
          }
          leaf fec-state {
            type string ;
            ncd:revise-date 2022-07-21 ;
          }
          leaf prefec-ber {
            type string ;
            ncd:revise-date 2022-07-21 ;
          }
        }
      }
      container temperatures {
        list temperature {
          key 'shelf slot'
              ;
          leaf shelf {
            description 'Shelf number.'
                        ;
            type uint8 {
              range 0..255 {
                description 'shelf range.'
                            ;
              }
            }
          }
          leaf slot {
            description 'Slot number.'
                        ;
            type uint8 {
              range 0..255 {
                description 'slot range.'
                            ;
              }
            }
          }
          leaf boardtype {
            type string ;
          }
          leaf i2c {
            type uint32 ;
          }
          leaf address {
            type uint32 ;
          }
          leaf status {
            type enumeration {
              enum normal {
                value 0 ;
                description 'temperature normal'
                            ;
              }
              enum abnormal {
                value 1 ;
                description 'temperature abnormal'
                            ;
              }
            }
          }
          leaf current-temperature {
            type int32 ;
          }
          leaf minor-threshold {
            type uint32 ;
          }
          leaf major-threshold {
            type uint32 ;
          }
          leaf fatal-threshold {
            type uint32 ;
          }
          leaf board-panel-id {
            if-feature switch ;
            description 'Board panel ID.'
                        ;
            type string ;
          }
          leaf cpu-temperature {
            description 'CPU temperature.'
                        ;
            type int16 ;
          }
          leaf iat-temperature {
            description 'Inlet air temperature.'
                        ;
            type int16 ;
          }
          leaf oat-temperature {
            description 'Outlet air temperature.'
                        ;
            type int16 ;
          }
          leaf chip1-temperature {
            description 'Chip1 temperature.'
                        ;
            type int16 ;
          }
          leaf chip2-temperature {
            description 'Chip2 temperature.'
                        ;
            type int16 ;
          }
          leaf chip3-temperature {
            description 'Chip3 temperature.'
                        ;
            type int16 ;
          }
          leaf chip4-temperature {
            description 'Chip4 temperature.'
                        ;
            type int16 ;
          }
          leaf chip5-temperature {
            description 'Chip5 temperature.'
                        ;
            type int16 ;
          }
          leaf chip6-temperature {
            description 'Chip6 temperature.'
                        ;
            type int16 ;
          }
          ncd:select shelf ;
          ncd:select 'shelf slot'
                     ;
          ncd:select 'shelf board-panel-id'
                     ;
        }
      }
      container board-powers {
        list board-power {
          key 'shelf slot'
              ;
          leaf shelf {
            description 'Shelf number'
                        ;
            type uint8 {
              range 0..255 {
                description 'shelf range.'
                            ;
              }
            }
          }
          leaf slot {
            description 'Slot number'
                        ;
            type uint8 {
              range 0..255 {
                description 'slot range.'
                            ;
              }
            }
          }
          leaf phy-status {
            description 'Physical status'
                        ;
            type ncd:string-all ;
          }
          leaf board-name {
            description 'Board name'
                        ;
            type ncd:string-all ;
          }
          leaf admin-status {
            description 'Admin status'
                        ;
            type ncd:string-all ;
          }
          leaf current-status {
            description 'Current status'
                        ;
            type ncd:string-all ;
          }
          leaf current-power {
            description 'Current power'
                        ;
            type ncd:string-all ;
          }
          leaf current-voltage {
            description 'Current voltage'
                        ;
            type ncd:string-all ;
          }
          leaf current-current {
            description 'Current current'
                        ;
            type ncd:string-all ;
          }
          leaf panel {
            if-feature switch ;
            description 'Panel number'
                        ;
            type ncd:string-with-blank {
              length 1..8 ;
            }
          }
          ncd:select shelf ;
          ncd:select 'shelf slot'
                     ;
          ncd:select 'shelf panel'
                     ;
        }
      }
      container power-modes {
        list power-mode {
          key shelf ;
          leaf shelf {
            description 'Shelf number'
                        ;
            type uint8 {
              range 0..255 {
                description 'shelf range.'
                            ;
              }
            }
          }
          leaf module-nums {
            description 'Module numbers'
                        ;
            type uint8 ;
          }
          leaf module-online-nums {
            description 'Module online numbers.'
                        ;
            type uint8 ;
            ncd:revise-date 2022-05-15 ;
          }
          leaf total-rating-power {
            description 'Rating power of shelf'
                        ;
            type ncd:string-all ;
          }
          leaf total-used-power {
            description 'Used power of shelf'
                        ;
            type ncd:string-all ;
          }
          leaf redundancy-type {
            description 'Redundancy type'
                        ;
            type ncd:string-all ;
          }
          leaf budget-policy {
            description 'Power budget policy'
                        ;
            type ncd:string-all ;
          }
          leaf reserve-power {
            description 'Power reserve power'
                        ;
            type ncd:string-all ;
          }
          leaf power-type {
            description 'Power type.'
                        ;
            type enumeration {
              enum N/A {
                value 0 ;
              }
              enum DC {
                value 1 ;
              }
              enum AC {
                value 2 ;
              }
            }
          }
          leaf group-nums {
            description 'Power power type.'
                        ;
            type uint8 ;
          }
        }
      }
      container synchronizations {
        leaf sync-total-status {
          type enumeration {
            enum unknown {
              value 0 ;
            }
            enum finished {
              value 1 ;
            }
            enum unfinished {
              value 2 ;
            }
          }
          ncd:revise-date 2018-09-10 ;
        }
        list synchronization {
          description 'Overall status of LE synchronization'
                      ;
          key location ;
          leaf location {
            description 'Location of logic entity'
                        ;
            type ncd:string-all ;
          }
          leaf le-type {
            description 'Type of logic entity'
                        ;
            type ncd:string-all ;
          }
          leaf ms-status {
            description 'Master slave status of logic entity'
                        ;
            type ncd:string-all ;
          }
          leaf sync-status {
            description 'Synchronized status of logic entity'
                        ;
            type ncd:string-all ;
          }
        }
      }
      container outdoor-statuss {
        if-feature shelf-15k2 ;
        list outdoor-status {
          key group-number ;
          leaf group-number {
            description 'Fan group number'
                        ;
            type uint8 ;
          }
          leaf fan-speed {
            description 'Fan speed'
                        ;
            type uint16 ;
          }
        }
      }
      container boards {
        list board {
          key 'shelf slot subslot'
              ;
          leaf shelf {
            description 'Shelf number'
                        ;
            type uint8 {
              range 0..255 {
                description 'shelf range.'
                            ;
              }
            }
          }
          leaf slot {
            description 'Slot number'
                        ;
            type uint8 {
              range 0..255 {
                description 'slot range.'
                            ;
              }
            }
          }
          leaf subslot {
            description 'Subslot number'
                        ;
            type uint8 ;
          }
          leaf board-status {
            description 'Board status'
                        ;
            type enumeration {
              enum online-work {
                value 0 ;
              }
              enum online-poweroff {
                value 1 ;
              }
              enum offline {
                value 2 ;
              }
              enum abnormal {
                value 3 ;
              }
            }
          }
          leaf panel {
            if-feature switch ;
            description 'Panel number'
                        ;
            type ncd:string-with-blank {
              length 1..8 ;
            }
          }
          ncd:select shelf ;
          ncd:select 'shelf slot'
                     ;
          ncd:select 'shelf slot subslot'
                     ;
          ncd:select 'shelf panel'
                     ;
          ncd:select 'shelf subslot panel'
                     ;
        }
        ncd:revise-date 2015-09-06 ;
      }
      container dustproof-statuss {
        list dustproof-status {
          key shelf ;
          leaf shelf {
            description 'Shelf number.'
                        ;
            type uint8 {
              range 0..255 {
                description 'shelf range.'
                            ;
              }
            }
          }
          leaf clean-cycle {
            description 'Dust proof clean cycle.'
                        ;
            type uint16 ;
          }
          leaf clean-time {
            description 'Last clean time.'
                        ;
            type ncd:string-all ;
          }
          leaf clean-days {
            description 'Up to last clean days.'
                        ;
            type uint16 ;
          }
          leaf alarm-days {
            description 'Alarm existence days.'
                        ;
            type uint16 ;
          }
        }
        ncd:revise-date 2016-04-18 ;
      }
      container forbidons {
        list forbidon {
          key 'shelf slot'
              ;
          leaf shelf {
            description 'Number of shelf.'
                        ;
            type uint8 {
              range 0..255 ;
            }
          }
          leaf slot {
            description 'Number of slot.'
                        ;
            type uint8 {
              range 0..255 ;
            }
          }
          leaf forbidon-status {
            description 'forbidon status'
                        ;
            type enumeration {
              enum permit {
                value 1 ;
              }
              enum forbid {
                value 2 ;
              }
            }
            default permit ;
          }
        }
        ncd:revise-date 2019-02-28 ;
      }
      container wavelengths {
        if-feature optical-module-config ;
        list wavelength {
          key if-name ;
          leaf if-name {
            type string ;
          }
          leaf port-dir {
            type uint16 {
              range 0..65535 ;
            }
          }
          leaf center-freq {
            type string ;
          }
          leaf base-freq {
            type string ;
          }
          leaf band {
            type uint32 ;
          }
          leaf wave-spacing {
            type uint32 ;
          }
          leaf wave-num {
            type uint32 ;
          }
          leaf translation-mode {
            type uint8 ;
          }
          leaf spectralwidth {
            type uint8 ;
          }
        }
        ncd:revise-date 2019-03-07 ;
      }
      container switch-states {
        list switch-state {
          key 'shelf slot cpu'
              ;
          leaf shelf {
            description 'Shelf number'
                        ;
            type uint8 {
              range 0..127 ;
            }
          }
          leaf slot {
            description 'Slot number'
                        ;
            type uint8 {
              range 0..253 ;
            }
          }
          leaf cpu {
            description 'mpu number'
                        ;
            type uint8 ;
          }
          leaf board-state {
            description 'Board state'
                        ;
            type enumeration {
              enum offline {
                value 0 ;
              }
              enum online-work {
                value 1 ;
              }
              enum online-poweroff {
                value 2 ;
              }
              enum not-ready {
                value 3 ;
              }
              enum abnormal {
                value 255 ;
              }
            }
          }
          leaf switch-state {
            description 'switch state'
                        ;
            type enumeration {
              enum service-in-work-unit-no-request {
                value 0 ;
              }
              enum service-in-work-unit-lockout {
                value 1 ;
              }
              enum service-in-protect-unit-forced-switch {
                value 2 ;
              }
              enum service-in-protect-unit-auto-switch {
                value 4 ;
              }
              enum service-in-protect-unit-manual-switch {
                value 6 ;
              }
              enum service-in-protect-unit-wait-to-restore {
                value 7 ;
              }
              enum service-in-protect-unit-no-request {
                value 8 ;
              }
              enum service-in-work-unit-forced-switch {
                value 9 ;
              }
              enum service-in-work-unit-auto-switch {
                value 10 ;
              }
              enum service-in-work-unit-manual-switch {
                value 11 ;
              }
            }
          }
        }
        ncd:revise-date 2019-03-12 ;
      }
      container utilizations {
        list utilization {
          key shelf ;
          leaf shelf {
            type uint8 {
              range 0..1 ;
            }
          }
          leaf cpu-current-low-utilization {
            type uint8 ;
          }
          leaf cpu-current-middle-utilization {
            type uint8 ;
          }
          leaf cpu-current-high-utilization {
            type uint8 ;
          }
          leaf cpu-default-utilization {
            type uint8 ;
          }
          leaf mem-current-low-utilization {
            type uint8 ;
          }
          leaf mem-current-middle-utilization {
            type uint8 ;
          }
          leaf mem-current-high-utilization {
            type uint8 ;
          }
          leaf mem-default-utilization {
            type uint8 ;
          }
          leaf flashorsata-current-low-utilization {
            type uint8 ;
          }
          leaf flashorsata-current-middle-utilization {
            type uint8 ;
          }
          leaf flashorsata-current-high-utilization {
            type uint8 ;
          }
          leaf flashorsata-default-utilization {
            type uint8 ;
          }
          leaf sd-current-low-utilization {
            type uint8 ;
          }
          leaf sd-current-middle-utilization {
            type uint8 ;
          }
          leaf sd-current-high-utilization {
            type uint8 ;
          }
          leaf sd-default-utilization {
            type uint8 ;
          }
          leaf usb-current-low-utilization {
            type uint8 ;
          }
          leaf usb-current-middle-utilization {
            type uint8 ;
          }
          leaf usb-current-high-utilization {
            type uint8 ;
          }
          leaf usb-default-utilization {
            type uint8 ;
          }
        }
      }
      container ipmb {
        status obsolete {
          ncd:revise-date 2022-03-07 ;
        }
        list ipmb-info {
          description 'Query IPMB information'
                      ;
          key 'shelf board-type ipmc-id'
              ;
          leaf shelf {
            description 'Shelf number'
                        ;
            type uint8 {
              range 0..255 {
                description 'Shelf range.'
                            ;
              }
            }
          }
          leaf ipmc-modules-numbers {
            description 'IPMC module numbers'
                        ;
            type uint8 ;
          }
          leaf board-type {
            description 'Board type'
                        ;
            type ncd:string-all ;
          }
          leaf ipmc-id {
            description 'IPMC id'
                        ;
            type uint8 ;
          }
          leaf ipmc-present {
            description 'IPMC present'
                        ;
            type ncd:string-all ;
          }
          leaf ipmc-version {
            description 'IPMC verson information'
                        ;
            type ncd:string-all ;
          }
          leaf ipmc-power-state {
            description 'IPMC state of power supply'
                        ;
            type ncd:string-all ;
          }
          leaf ipmc-power {
            description 'IPMC power(W)'
                        ;
            type uint32 ;
          }
          leaf ipmc-voltage {
            description 'IPMC voltage(mV)'
                        ;
            type uint32 ;
          }
          leaf ipmc-power-down-reason {
            description 'Reason of IPMC power down'
                        ;
            type ncd:string-all ;
          }
        }
        container monitor-offline-msg {
          leaf no-rcv-msg {
            description 'Monitor board offline message'
                        ;
            type ncd:string-with-blank ;
          }
        }
        ncd:revise-date 2020-06-22 ;
      }
    }
  }
  container operation {
    config false ;
    container env {
      container reload-system {
        leaf reload-mode {
          type enumeration {
            enum force {
              value 0 ;
            }
            enum grace {
              value 1 ;
            }
          }
        }
        choice timectrl {
          case at {
            leaf time {
              description 'The format is hh:mm:ss.'
                          ;
              type ncd:time {
                length 1..9 ;
              }
            }
          }
          case delay {
            leaf minutes {
              description 'The unit is minutes.'
                          ;
              type uint32 {
                range 0..6000 ;
              }
            }
          }
          ncd:revise-date 2020-02-28 ;
        }
        leaf cancel {
          type enumeration {
            enum 1 {
              value 1 ;
            }
          }
          ncd:revise-date 2020-02-28 ;
        }
      }
      container reload-slot {
        leaf shelf {
          type uint8 {
            range 0..255 {
              description 'shelf range.'
                          ;
            }
          }
        }
        leaf slot {
          type uint8 {
            range 0..255 {
              description 'slot range.'
                          ;
            }
          }
        }
        leaf reload-mode {
          type enumeration {
            enum force {
              value 0 ;
            }
            enum grace {
              value 1 ;
            }
          }
        }
        choice boardctrl {
          case mpu {
            leaf mpupanel {
              description 'Panel number.'
                          ;
              type ncd:string-with-blank {
                length 1..8 ;
              }
            }
          }
          case pfu {
            leaf pfupanel {
              description 'Panel number.'
                          ;
              type ncd:string-with-blank {
                length 1..8 ;
              }
            }
          }
          case sfu {
            leaf sfupanel {
              description 'Panel number.'
                          ;
              type ncd:string-with-blank {
                length 1..8 ;
              }
            }
          }
          ncd:revise-date 2020-02-28 ;
        }
        choice timectrl {
          case at {
            leaf time {
              description 'The format is hh:mm:ss.'
                          ;
              type ncd:time {
                length 1..9 ;
              }
            }
          }
          case delay {
            leaf minutes {
              description 'The unit is minutes.'
                          ;
              type uint32 {
                range 0..6000 ;
              }
            }
          }
          ncd:revise-date 2020-02-28 ;
        }
        leaf cancel {
          type enumeration {
            enum 1 {
              value 1 ;
            }
          }
          ncd:revise-date 2020-02-28 ;
        }
      }
      container reload-ssc {
        leaf reload-mode {
          type enumeration {
            enum force {
              value 0 ;
            }
            enum grace {
              value 1 ;
            }
          }
        }
      }
      container redundancy {
        leaf mode {
          type enumeration {
            enum force {
              value 0 ;
            }
            enum grace {
              value 1 ;
            }
          }
        }
        choice granularityctrl {
          case board {
            leaf shelf {
              type uint8 {
                range 0..255 {
                  description 'shelf range.'
                              ;
                }
              }
            }
            leaf slot {
              type uint8 {
                range 0..255 ;
              }
            }
          }
          case netelement {
            leaf name {
              type enumeration {
                enum sc {
                  value 1 ;
                }
              }
            }
          }
          ncd:revise-date 2021-06-08 ;
        }
      }
      container power-on-off {
        leaf shelf {
          type uint8 {
            range 0..255 {
              description 'shelf range.'
                          ;
            }
          }
        }
        leaf slot {
          type uint8 {
            range 0..255 {
              description 'slot range.'
                          ;
            }
          }
        }
        choice power-mode {
          case board-on {
            leaf board-power-on {
              type enumeration {
                enum on {
                  value 1 ;
                }
              }
            }
          }
          case board-off {
            leaf board-power-off {
              type enumeration {
                enum off {
                  value 0 ;
                }
              }
            }
            leaf set-mode {
              type enumeration {
                enum force {
                  value 0 ;
                }
                enum grace {
                  value 1 ;
                }
              }
            }
          }
          case sub-board {
            leaf subslot {
              type uint8 {
                range 0..3 ;
              }
            }
            leaf power-status {
              type enumeration {
                enum off {
                  value 0 ;
                }
                enum on {
                  value 1 ;
                }
              }
            }
          }
        }
      }
      container delete-offline {
        leaf shelf {
          description 'Shelf number'
                      ;
          type uint8 {
            range 0..255 {
              description 'shelf range.'
                          ;
            }
          }
        }
        leaf slot {
          description 'Slot number'
                      ;
          type uint8 {
            range 0..255 {
              description 'slot range.'
                          ;
            }
          }
        }
        leaf subslot {
          description 'Subslot number'
                      ;
          type uint8 ;
        }
      }
      container reset-dustproof {
        leaf shelf {
          description 'Shelf number.'
                      ;
          type uint8 {
            range 0..255 {
              description 'shelf range.'
                          ;
            }
          }
        }
        ncd:revise-date 2016-04-18 ;
      }
      container delete-offline-afnode {
        leaf af-node {
          description 'Application forwarder node name.'
                      ;
          type ncd:af-name ;
        }
        leaf shelf {
          description 'Shelf number'
                      ;
          type uint8 {
            range 0..255 {
              description 'shelf range.'
                          ;
            }
          }
        }
        leaf slot {
          description 'Slot number'
                      ;
          type uint8 {
            range 0..254 {
              description 'slot range.'
                          ;
            }
          }
        }
        leaf subslot {
          description 'Subslot number'
                      ;
          type uint8 {
            range 0..3 ;
          }
        }
        ncd:revise-date 2020-10-15 ;
      }
    }
  }
  rpc reload-shelf {
    description 'Reload the shelf'
                ;
    input {
      leaf shelf {
        config false ;
        description 'Shelf number'
                    ;
        type uint8 {
          range 0..255 {
            description 'Shelf range.'
                        ;
          }
        }
      }
      leaf reload-mode {
        config false ;
        description 'The reload type'
                    ;
        type enumeration {
          enum force {
            value 0 ;
          }
          enum grace {
            value 1 ;
          }
        }
      }
      choice timectrl {
        config false ;
        description 'Reload time control'
                    ;
        case at {
          leaf time {
            description 'The format is hh:mm:ss.'
                        ;
            type ncd:time {
              length 1..9 ;
            }
          }
        }
        case delay {
          leaf minutes {
            description 'The unit is minutes.'
                        ;
            type uint32 {
              range 0..6000 ;
            }
          }
        }
      }
      leaf cancel {
        config false ;
        description 'Cancel reload'
                    ;
        type enumeration {
          enum 1 {
            value 1 ;
          }
        }
      }
    }
    output {
      leaf result {
        config false ;
        description result ;
        type ncd:string-all ;
        mandatory true ;
      }
    }
  }
  rpc fan-shift {
    description 'set fan shift'
                ;
    input {
      leaf shelf {
        config false ;
        description 'Shelf number'
                    ;
        type uint8 {
          range 0..255 {
            description 'shelf range.'
                        ;
          }
        }
        mandatory true ;
      }
      choice fanrange {
        case groupnum {
          leaf group {
            config false ;
            type uint8 {
              range 0..255 {
                description 'slot range.'
                            ;
              }
            }
          }
        }
        case fanidnum {
          leaf fanid {
            config false ;
            type uint8 {
              range 0..255 {
                description 'slot range.'
                            ;
              }
            }
          }
        }
      }
      leaf shift {
        config false ;
        description 'fan shift'
                    ;
        type union {
          type enumeration {
            enum auto {
              value 0 ;
            }
          }
          type uint8 {
            range 1..14 ;
          }
        }
        mandatory true ;
      }
    }
  }
  notification event {
    container card_event {
      config false ;
      description card_event ;
      leaf shelf {
        description 'Shelf number'
                    ;
        type uint8 {
          range 0..255 ;
        }
      }
      leaf slot {
        description 'Slot number'
                    ;
        type uint8 {
          range 0..255 ;
        }
      }
      leaf subslot {
        description 'Subslot number'
                    ;
        type uint8 {
          range '0..3 | 255'
                ;
        }
      }
      leaf status {
        description Status ;
        type string ;
      }
    }
    container card-plug-event {
      config false ;
      leaf cardname {
        description 'card name'
                    ;
        type string ;
      }
      leaf funcid {
        description 'functional id'
                    ;
        type uint32 {
          range 0..4294967295 {
            description 'netconfig functional id'
                        ;
          }
        }
      }
      leaf event-type {
        description 'event type'
                    ;
        type enumeration {
          enum online {
            value 0 ;
            description 'status of physical board,online.'
                        ;
          }
          enum offline {
            value 1 ;
            description 'status of physical board,offline.'
                        ;
          }
          enum create {
            value 2 ;
            description 'status of offcfg board,create.'
                        ;
          }
          enum delete {
            value 3 ;
            description 'status of offcfg board,delete'
                        ;
          }
        }
      }
      ncd:revise-date 2020-06-04 ;
    }
  }
}
