module zxr10-pm-sys {
  namespace 'http://www.zte.com.cn/zxr10/netconf/schema/rosng/pm-sys'
            ;
  prefix pm-sys ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  revision 2022-07-01 {
    description 'add leaf item and description in list rack and shelf.'
                ;
  }
  revision 2022-02-20 {
    description 'add obsolete tag to nvram boot-strong-password.'
                ;
  }
  revision 2022-01-21 {
    description 'add obsolete tag to nvram boot-password.'
                ;
  }
  revision 2021-10-26 {
    description 'add performance parameter with default min value of CPU load.'
                ;
  }
  revision 2021-09-14 {
    description 'add obsolete tag to nsr.'
                ;
  }
  revision 2021-08-16 {
    description 'Modify string length of banner-login.'
                ;
  }
  revision 2021-07-22 {
    description 'add state banner login.'
                ;
  }
  revision 2021-07-16 {
    description 'Modify the length of leaf old-passwd, new-passwd and new-confi'
              + 'rm to 1-128 in rpc container enable-passwd.'
                ;
  }
  revision 2021-07-12 {
    description 'add device application role invalid value.'
                ;
  }
  revision 2021-06-30 {
    description 'Add cpu-threshold-brd and memory-threshold-brd'
                ;
  }
  revision 2021-05-27 {
    description 'add enumeration value UNKNOWN for the leaf board-logictype.'
                ;
  }
  revision 2021-05-25 {
    description 'add switch-method.'
                ;
  }
  revision 2021-05-08 {
    description 'add device application role.'
                ;
  }
  revision 2021-04-30 {
    description 'Add leaf boot-strong-passwd for supporting boot server passwor'
              + 'd configuration.'
                ;
  }
  revision 2021-02-07 {
    description 'The system name supports Chinese characters.'
                ;
  }
  revision 2021-02-05 {
    description 'Add leaf mssc-info and cpudes for processor-usage.'
                ;
  }
  revision 2020-12-18 {
    description 'Add leaf panel for virtual-boards and cards.'
                ;
  }
  revision 2020-10-30 {
    description 'Modify unit of boot-time from seconds to nanoseconds.'
                ;
  }
  revision 2020-09-04 {
    description 'Add leaf for neid, and the logic type of board, and the softwa'
              + 're-version of board, and the hardware-version of board.'
                ;
  }
  revision 2020-09-03 {
    description 'Add leaf for system uptime.'
                ;
  }
  revision 2020-08-08 {
    description 'Add leaf for non-authenticated optical module.'
                ;
  }
  revision 2020-07-06 {
    description 'Add imgfile-name length 1~79'
                ;
  }
  revision 2020-06-15 {
    description 'Add nvram information'
                ;
  }
  revision 2020-05-30 {
    description 'Add banner login'
                ;
  }
  revision 2020-05-26 {
    description 'Add select for cpus and periphrals.'
                ;
  }
  revision 2020-04-17 {
    description 'Add rpc leafs to modify nvram enable-password, and obsolete nv'
              + 'ram enable-password in configuration.'
                ;
  }
  revision 2020-02-11 {
    description 'Add some leafs and container board-info.'
                ;
  }
  revision 2020-01-15 {
    description 'Add leafs such as status, funcid-conf and enumeration value em'
              + 'pty-slot for the leaf brdstate.'
                ;
  }
  revision 2019-11-07 {
    description 'Add container all-cards.'
                ;
  }
  revision 2019-10-18 {
    description 'Add enumeration value mini-txt and mini-txt-reload for the lea'
              + 'f load-mode.'
                ;
  }
  revision 2019-10-10 {
    description 'Add container manage-element.'
                ;
  }
  revision 2019-08-28 {
    description 'add leaf'
                ;
  }
  revision 2019-08-23 {
    description 'add hardware version.'
                ;
  }
  revision 2019-05-10 {
    description 'add rpc reboot.'
                ;
  }
  revision 2019-01-28 {
    description 'Add container board-event.'
                ;
  }
  revision 2019-01-17 {
    description 'shelf range 0-255.slot range 0-255.'
                ;
  }
  revision 2018-11-30 {
    description 'Add leaf of component attributes.'
                ;
  }
  revision 2018-08-01 {
    description 'Add leaf user-configuration.'
                ;
  }
  revision 2018-06-14 {
    description 'Add containers of all-ports.'
                ;
  }
  revision 2018-06-06 {
    description 'Add leaf installstate ,software-version and mc-version for con'
              + 'tainer rack.'
                ;
  }
  revision 2018-05-17 {
    description 'Add containers of boards for state/sys node.'
                ;
  }
  revision 2018-02-01 {
    description 'Add containers of basic-card-maintains.'
                ;
  }
  revision 2018-01-24 {
    description 'modify the range of shelf and slot to 0-255'
                ;
  }
  revision 2018-01-13 {
    description 'Add leaf system-image for contain system.'
                ;
  }
  revision 2018-01-08 {
    description 'Add a container of spi-ports.'
                ;
  }
  revision 2017-10-16 {
    description 'add harddisk and cpucorenum'
                ;
  }
  revision 2017-07-12 {
    description 'Delete select of peripherals'
                ;
  }
  revision 2017-01-05 {
    description 'Delete select property of cpus node in state'
                ;
  }
  revision 2016-12-07 {
    description "1.Change nvram enable-passwd children node's property from ALL"
              + " to IN.
\n2.Add OUT property to nvram enable-passwd children n"
              + "ode."
                ;
  }
  revision 2016-11-04 {
    description 'Add select attribute to state child nodes.'
                ;
  }
  revision 2016-05-25 {
    description 'expand hostname to 64 byte'
                ;
  }
  revision 2016-02-23 {
    description 'Add leaf cpu for contain cards.'
                ;
  }
  revision 2015-12-02 {
    description 'Add leaf bgp isis rip ospf service for contain nsr.'
                ;
  }
  feature switch ;
  container configuration {
    container sys {
      leaf hostname {
        description "Configure system's network name."
                    ;
        type ncd:string-all-with-chinese {
          length 1..64 {
            description 'Length range.'
                        ;
          }
        }
        default ZXR10 ;
      }
      leaf contact {
        description "Configure system administrator's contact information."
                    ;
        type ncd:string-with-blank {
          length 1..200 {
            description 'Length range.'
                        ;
          }
        }
      }
      leaf location {
        description "Configure system's location information."
                    ;
        type ncd:string-with-blank {
          length 1..200 {
            description 'Length range.'
                        ;
          }
        }
      }
      leaf cpu-isolate {
        description 'Configure CPU isolate enable or disable.'
                    ;
        type enumeration {
          enum enable {
            value 0 ;
            description 'Cpu isolate enable.'
                        ;
          }
          enum disable {
            value 1 ;
            description 'Cpu isolate disable.'
                        ;
          }
        }
        default enable ;
      }
      leaf login-authorized {
        description 'Configure console authentication.'
                    ;
        type empty ;
      }
      leaf load-mode {
        description 'Configure load mode of data.'
                    ;
        type enumeration {
          enum zdb {
            value 1 ;
            description 'Load configuration from binary database file.'
                        ;
          }
          enum txt {
            value 2 ;
            description 'Load configuration from command-line txt file.'
                        ;
          }
          enum noload {
            value 3 ;
            description 'Start up with no configuration.'
                        ;
          }
          enum mini-txt {
            value 6 ;
            description 'Trigger the minimum set txt file generation, and load '
                      + 'configuration from command-line txt file.'
                        ;
          }
          enum mini-txt-reload {
            value 7 ;
            description 'Trigger the minimum set txt file generation, and autom'
                      + 'atically load configuration from command-line txt file'
                      + '.'
                        ;
          }
        }
        default zdb ;
      }
      leaf serdes-check-argument {
        description 'This command configures the alarm threshold of switching c'
                  + 'hips.'
                    ;
        type uint32 {
          range 12..4294967295 ;
        }
      }
      leaf autoplug-card {
        description 'Configure automatically plugging card enable or disable.'
                    ;
        type enumeration {
          enum enable {
            value 1 ;
            description 'Automatically plugging card enable.'
                        ;
          }
          enum disable {
            value 2 ;
            description 'Automatically plugging card disable.'
                        ;
          }
        }
      }
      leaf opt-non-certified-alarm-switch {
        description 'Configure the alarm switch for non-authenticated optical m'
                  + 'odule.'
                    ;
        type enumeration {
          enum disable {
            value 0 ;
            description 'Disable the alarm switch.'
                        ;
          }
          enum enable {
            value 1 ;
            description 'Enable the alarm switch.'
                        ;
          }
        }
        default disable ;
        ncd:revise-date 2020-08-08 ;
      }
      container nvram {
        container boot-server {
          leaf v4addr {
            description 'IPv4 server IP.'
                        ;
            type ncd:ipv4-address ;
          }
          leaf v6addr {
            description 'IPv6 server IP.'
                        ;
            type ncd:ipv6-address ;
          }
        }
        container default-gateway {
          leaf v4-addr {
            description 'IPv4 gateway.'
                        ;
            type ncd:ipv4-address ;
          }
          leaf v6-addr {
            description 'IPv6 gateway.'
                        ;
            type ncd:ipv6-address ;
          }
        }
        leaf boot-username {
          description 'Configure ftp username for boot server.'
                      ;
          type string {
            length 1..19 {
              description 'Ftp username.'
                          ;
            }
          }
        }
        leaf boot-passwd {
          status obsolete {
            ncd:revise-date 2022-01-21 ;
          }
          description 'Configure ftp password for boot server.'
                      ;
          type string {
            length 1..19 {
              description 'Ftp password.'
                          ;
            }
          }
        }
        leaf ftp-path {
          description 'Configure ftp path for boot server.'
                      ;
          type ncd:string-with-blank {
            length 1..79 {
              description 'Ftp path.'
                          ;
            }
          }
        }
        container enable-passwd {
          status obsolete {
            ncd:revise-date 2020-04-17 ;
          }
          description 'Configure enable password.'
                      ;
          leaf old-passwd {
            status obsolete {
              ncd:revise-date 2020-04-17 ;
            }
            description 'Enable password.'
                        ;
            type string {
              length 3..15 {
                description 'Old password.'
                            ;
              }
            }
          }
          leaf new-passwd {
            status obsolete {
              ncd:revise-date 2020-04-17 ;
            }
            description 'New enable password.'
                        ;
            type string {
              length 3..15 {
                description 'New password.'
                            ;
              }
            }
          }
          leaf new-confirm {
            status obsolete {
              ncd:revise-date 2020-04-17 ;
            }
            description 'New enable password confirm.'
                        ;
            type string {
              length 3..15 {
                description 'New password again.'
                            ;
              }
            }
          }
        }
        leaf boot-from {
          description 'Configure boot server type.'
                      ;
          type enumeration {
            enum ipv4-server {
              value 0 ;
            }
            enum ipv6-server {
              value 1 ;
            }
          }
          ncd:revise-date 2020-06-15 ;
        }
        leaf boot-strong-passwd {
          status obsolete {
            ncd:revise-date 2022-02-20 ;
          }
          description 'Configure ftp password for boot server.'
                      ;
          type string {
            length 8..128 {
              description 'Ftp password.'
                          ;
            }
          }
          ncd:revise-date 2021-04-30 ;
        }
      }
      container nsr {
        leaf status {
          status obsolete {
            ncd:revise-date 2021-09-14 ;
          }
          description 'Enable or disable NSR.'
                      ;
          type enumeration {
            enum enable {
              value 1 ;
              description 'Enable NSR.'
                          ;
            }
            enum disable {
              value 2 ;
              description 'Disable NSR.'
                          ;
            }
          }
          default disable ;
        }
        leaf name {
          status obsolete {
            ncd:revise-date 2021-09-14 ;
          }
          description 'NSR service name.'
                      ;
          type enumeration {
            enum all {
              value 1 ;
              description 'All the NSR service.'
                          ;
            }
          }
          default all ;
        }
        leaf all {
          description 'All service'
                      ;
          type empty ;
        }
        leaf route {
          description 'Router service'
                      ;
          type empty ;
        }
        leaf ldp {
          description 'LDP service'
                      ;
          type empty ;
        }
        leaf mplste {
          description 'MPLS-TE service'
                      ;
          type empty ;
        }
        leaf multicast {
          description 'Multicast service'
                      ;
          type empty ;
        }
        leaf bgp {
          description 'BGP service'
                      ;
          type empty ;
        }
        leaf isis {
          description 'ISIS service'
                      ;
          type empty ;
        }
        leaf rip {
          description 'RIP service'
                      ;
          type empty ;
        }
        leaf ospf {
          status obsolete {
            ncd:revise-date 2021-09-14 ;
          }
          description 'OSPF service'
                      ;
          type empty ;
        }
        leaf ospf2 {
          description 'OSPF2 service'
                      ;
          type empty ;
          ncd:revise-date 2021-09-14 ;
        }
        leaf ospf3 {
          description 'OSPF3 service'
                      ;
          type empty ;
          ncd:revise-date 2021-09-14 ;
        }
      }
      container cpu-thresholds {
        list cpu-threshold {
          key level ;
          leaf level {
            description 'The alarm level of the CPU usage rate'
                        ;
            type enumeration {
              enum low {
                value 0 ;
                description 'The low level of alarm update'
                            ;
              }
              enum middle {
                value 1 ;
                description 'The middle level of alarm update'
                            ;
              }
              enum high {
                value 2 ;
                description 'The high level of alarm update'
                            ;
              }
            }
          }
          leaf cpu-usage {
            description 'The threshold of the CPU usage rate'
                        ;
            type uint8 {
              range 50..100 ;
            }
            default 95 ;
          }
        }
        list cpu-threshold-brd {
          key cpu_name ;
          leaf cpu_name {
            description 'MPU information'
                        ;
            type string {
              length 1..27 ;
            }
          }
          leaf cpu_threshold_value {
            description 'The threshold of the CPU load usage rate'
                        ;
            type uint8 {
              range 50..100 ;
            }
          }
          ncd:revise-date 2021-06-30 ;
        }
      }
      container mem-thresholds {
        list mem-threshold {
          key level ;
          leaf level {
            description 'The alarm level of the memory usage rate'
                        ;
            type enumeration {
              enum low {
                value 0 ;
                description 'The low level of alarm update'
                            ;
              }
              enum middle {
                value 1 ;
                description 'The middle level of alarm update'
                            ;
              }
              enum high {
                value 2 ;
                description 'The high level of alarm update'
                            ;
              }
            }
          }
          leaf mem-usage {
            description 'The threshold of the memory usage rate'
                        ;
            type uint8 {
              range 1..100 ;
            }
            default 60 ;
          }
        }
        list memory-threshold-brd {
          key cpu_name ;
          leaf cpu_name {
            description 'MPU information'
                        ;
            type string {
              length 1..27 ;
            }
          }
          leaf memory_threshold_value {
            description 'The threshold of the memory usage rate'
                        ;
            type uint8 {
              range 1..100 ;
            }
          }
          ncd:revise-date 2021-06-30 ;
        }
      }
      container storage-thresholds {
        list storage-threshold {
          key level ;
          leaf level {
            description 'The alarm level of the storage usage rate'
                        ;
            type enumeration {
              enum low {
                value 0 ;
                description 'The low level of alarm update'
                            ;
              }
              enum middle {
                value 1 ;
                description 'The middle level of alarm update'
                            ;
              }
              enum high {
                value 2 ;
                description 'The high level of alarm update'
                            ;
              }
            }
          }
          leaf storage-usage {
            description 'The threshold of the storage usage rate'
                        ;
            type uint8 {
              range 50..100 ;
            }
            default 90 ;
          }
        }
      }
      container load-sharing-hash-templates {
        list load-sharing-hash-template {
          key item ;
          leaf item {
            description 'The item'
                        ;
            type enumeration {
              enum srcmac {
                value 0 ;
              }
              enum dstmac {
                value 1 ;
              }
              enum srcip {
                value 2 ;
              }
              enum dstip {
                value 3 ;
              }
              enum port {
                value 4 ;
              }
              enum vlan {
                value 5 ;
              }
              enum label {
                value 6 ;
              }
              enum vpnsrcip {
                value 8 ;
              }
              enum vpndstip {
                value 9 ;
              }
              enum l2vpn {
                value 10 ;
              }
            }
          }
          leaf status {
            description 'The status'
                        ;
            type enumeration {
              enum enable {
                value 1 ;
              }
              enum disable {
                value 0 ;
              }
            }
          }
        }
      }
      container basic-card-maintains {
        list basic-card-maintain {
          description basic-card-maintain ;
          key 'shelf slot subslot'
              ;
          leaf shelf {
            description 'Shelf Number'
                        ;
            type uint8 {
              range 0..255 {
                description 'shelf range.'
                            ;
              }
            }
          }
          leaf slot {
            description 'Slot Number'
                        ;
            type uint8 {
              range 0..255 {
                description 'slot range'
                            ;
              }
            }
          }
          leaf subslot {
            description 'Subslot Number'
                        ;
            type uint8 {
              range 0..255 ;
            }
          }
          list ports {
            description ports ;
            key 'resno restpye'
                ;
            leaf resno {
              description 'Port Number'
                          ;
              type uint32 {
                range 0..200 ;
              }
            }
            leaf restpye {
              description ResType ;
              type string {
                length 1..31 ;
              }
            }
          }
          leaf funcid {
            description 'Funcid of the insert card'
                        ;
            type uint32 {
              range 1..4294967295 ;
            }
          }
          leaf resnum {
            description 'Maximum port number of the insert card'
                        ;
            type uint32 {
              range 0..20000 ;
            }
          }
          leaf version {
            description 'Version of the insert card'
                        ;
            type string {
              length 0..80 ;
            }
          }
          leaf description {
            description 'Description of the insert card'
                        ;
            type string {
              length 0..512 ;
            }
          }
        }
      }
      leaf banner {
        description "These characters's ASCII unicode must be between 0x21-0x3E"
                  + " / 0x40-0x5F / 0x61-0x7E."
                    ;
        type ncd:long-text ;
      }
      leaf banner-login {
        description "These characters's ASCII unicode must be between 0x20-0x7E."
                    ;
        type ncd:long-text {
          length 1..1023 ;
        }
        ncd:revise-date 2020-05-30 ;
      }
      leaf domain-name {
        description 'Specifies the domain name used to form fully qualified nam'
                  + 'e for unqualified hostnames.'
                    ;
        type string ;
      }
      leaf device-application-role {
        description 'Device application role'
                    ;
        type enumeration {
          enum core {
            value 3 ;
          }
          enum aggregation {
            value 2 ;
          }
          enum access {
            value 1 ;
          }
          enum core-aggregation {
            value 4 ;
          }
          enum aggregation-access {
            value 5 ;
          }
          enum core-edge {
            value 6 ;
          }
          enum access-edge {
            value 7 ;
          }
          enum province-trunk {
            value 8 ;
          }
          enum national-trunk {
            value 9 ;
          }
          enum backbone {
            value 10 ;
          }
          enum first-backbone {
            value 11 ;
          }
          enum second-backbone {
            value 12 ;
          }
          enum unknown {
            value 13 ;
          }
          enum invalid {
            value 0 ;
          }
        }
        ncd:revise-date 2021-05-08 ;
      }
    }
  }
  container operation {
    config false ;
    container sys {
      container set-recover-enable-remind {
        leaf original-passwd {
          description 'Original password.'
                      ;
          type string {
            length 1..15 ;
          }
        }
        leaf new-question {
          description 'New question.'
                      ;
          type string {
            length 1..50 ;
          }
        }
        leaf new-passwd {
          description 'New password.'
                      ;
          type string {
            length 1..50 ;
          }
        }
      }
      container recover-enable {
        leaf question {
          description 'Question of recover enable.'
                      ;
          type string {
            length 1..50 ;
          }
        }
        leaf answer {
          description 'Answer of recover enable.'
                      ;
          type string {
            length 1..50 ;
          }
        }
      }
      leaf user-configuration {
        description 'Manually download finish'
                    ;
        type enumeration {
          enum enable {
            value 1 ;
            description 'Manually enable the user configration'
                        ;
          }
          enum finish {
            value 2 ;
            description 'Manually finish the command download'
                        ;
          }
        }
      }
      container nvram {
        container imgfile-location {
          description 'Set location for bootup imaging file'
                      ;
          leaf type {
            description 'Boot file type'
                        ;
            type enumeration {
              enum local {
                value 0 ;
              }
              enum network {
                value 1 ;
              }
            }
          }
          leaf imgfile-name {
            description 'Remote bootup file name'
                        ;
            type ncd:string-all {
              length 1..79 ;
            }
          }
        }
        ncd:revise-date 2020-06-15 ;
      }
    }
  }
  container state {
    config false ;
    container sys {
      container racks {
        list rack {
          key 'shelf slot'
              ;
          leaf shelf {
            description 'Shelf number.'
                        ;
            type uint8 {
              range 0..255 {
                description 'shelf range.'
                            ;
              }
            }
          }
          leaf slot {
            description 'Slot number.'
                        ;
            type uint8 {
              range 0..255 {
                description 'slot range.'
                            ;
              }
            }
          }
          leaf subslot {
            description 'Subslot number.'
                        ;
            type uint8 {
              range '0..15 | 255'
                    {
                description 'subslot range.'
                            ;
              }
            }
          }
          leaf character {
            type string {
              length 1..28 ;
            }
          }
          leaf boardtype {
            type uint32 ;
          }
          leaf portnum {
            type uint8 ;
          }
          leaf pcb {
            type ncd:string-with-blank {
              length 1..80 ;
            }
          }
          leaf fpga {
            type ncd:string-all ;
          }
          leaf epld {
            type ncd:string-all ;
          }
          leaf sn {
            type ncd:string-all ;
          }
          leaf manufacture {
            description 'The Manufacture Date of the card'
                        ;
            type ncd:string-all ;
          }
          leaf boardname {
            description 'The card name'
                        ;
            type ncd:string-all ;
          }
          leaf assemblysn {
            type ncd:string-all ;
          }
          leaf harddisk {
            type uint32 ;
          }
          leaf installstate {
            description 'The install state of real board'
                        ;
            type enumeration {
              enum down {
                value 0 ;
                description 'The board is down.'
                            ;
              }
              enum up {
                value 1 ;
                description 'The board is up.'
                            ;
              }
            }
          }
          leaf software-version {
            description 'software version'
                        ;
            type ncd:string-with-blank {
              length 1..80 ;
            }
          }
          leaf mc-version {
            description 'Mc version'
                        ;
            type ncd:string-with-blank {
              length 1..80 ;
            }
          }
          leaf panel {
            if-feature switch ;
            description 'Panel number'
                        ;
            type ncd:string-with-blank {
              length 1..8 ;
            }
            ncd:revise-date 2020-02-11 ;
          }
          leaf baud {
            description 'System baud'
                        ;
            type uint32 ;
            ncd:revise-date 2020-02-11 ;
          }
          leaf type {
            if-feature switch ;
            description 'Board logic type'
                        ;
            type enumeration {
              enum MPU {
                value 1 ;
                description 'The board is MPU.'
                            ;
              }
              enum PFU {
                value 3 ;
                description 'The board is PFU.'
                            ;
              }
              enum SFU {
                value 4 ;
                description 'The board is SFU.'
                            ;
              }
            }
            ncd:revise-date 2020-02-11 ;
          }
          leaf item {
            description 'Board sales code.'
                        ;
            type ncd:string-all ;
            ncd:revise-date 2022-07-01 ;
          }
          leaf description {
            description 'Board description.'
                        ;
            type ncd:string-all ;
            ncd:revise-date 2022-07-01 ;
          }
          ncd:select 'shelf slot'
                     ;
          ncd:select 'shelf panel'
                     ;
        }
      }
      container ports {
        list port {
          key 'shelf slot subslot portno'
              ;
          leaf shelf {
            description 'Shelf number.'
                        ;
            type uint8 {
              range 0..255 {
                description 'shelf range.'
                            ;
              }
            }
          }
          leaf slot {
            description 'Slot number.'
                        ;
            type uint8 {
              range 0..255 {
                description 'slot range.'
                            ;
              }
            }
          }
          leaf subslot {
            description 'Subslot number.'
                        ;
            type uint8 ;
          }
          leaf portno {
            description 'Port number.'
                        ;
            type uint32 ;
          }
          leaf porttype {
            description 'Port type.'
                        ;
            type uint16 ;
          }
          leaf portname {
            description 'Port name.'
                        ;
            type string ;
          }
          leaf portphystatus {
            description 'Port physical status.'
                        ;
            type uint8 ;
          }
          leaf porteoproperty {
            description 'Port electric optical property.'
                        ;
            type uint8 ;
          }
          leaf portspeed {
            description 'Port speed.'
                        ;
            type uint32 ;
          }
          ncd:select 'shelf slot subslot portno'
                     ;
        }
      }
      container special-ports {
        list special-port {
          key 'shelf slot'
              ;
          leaf shelf {
            description 'Shelf number.'
                        ;
            type uint8 {
              range 0..255 {
                description 'shelf range.'
                            ;
              }
            }
          }
          leaf slot {
            description 'Slot number.'
                        ;
            type uint8 {
              range 0..255 {
                description 'slot range.'
                            ;
              }
            }
          }
          leaf subslot {
            description 'Subslot number.'
                        ;
            type uint8 ;
          }
          leaf portno {
            description 'The number of the special port.'
                        ;
            type uint32 ;
          }
          leaf porttype {
            description 'The type of the special port.'
                        ;
            type uint16 ;
          }
          leaf portname {
            description 'Interface name.'
                        ;
            type string ;
          }
          leaf port-runstatus {
            description 'The running status of the special port.'
                        ;
            type uint8 ;
          }
          leaf slotboardtype {
            description 'The type of slotboard where the special port located.'
                        ;
            type uint32 ;
          }
          ncd:select 'shelf slot'
                     ;
        }
      }
      container system {
        leaf system-version {
          type ncd:string-all ;
        }
        leaf system-uptime {
          type ncd:string-all ;
        }
        leaf system-mac {
          type ncd:string-all ;
        }
        leaf device-version {
          description 'Network management version'
                      ;
          type ncd:string-all ;
        }
        leaf device-type {
          description 'Device type'
                      ;
          type ncd:string-all ;
        }
        leaf system-image {
          type ncd:string-all ;
        }
        leaf hostname {
          type ncd:string-all-with-chinese ;
        }
        leaf banner {
          type ncd:long-text ;
        }
        leaf boot-time {
          type uint64 ;
        }
        leaf domain-name {
          description 'Specifies the domain name used to form fully qualified n'
                    + 'ame for unqualified hostnames.'
                      ;
          type string ;
        }
        leaf hardware-version {
          description 'Device hardware version.'
                      ;
          type ncd:string-all ;
        }
        leaf machine {
          type ncd:string-all ;
        }
        leaf os-name {
          type ncd:string-all ;
        }
        leaf os-release {
          type ncd:string-all ;
        }
        leaf os-version {
          type ncd:string-all ;
        }
        leaf version-path {
          description 'Version path'
                      ;
          type ncd:string-all ;
          ncd:revise-date 2020-02-11 ;
        }
        leaf copyright {
          description copyRight ;
          type ncd:string-all ;
          ncd:revise-date 2020-02-11 ;
        }
        leaf compile-time {
          type ncd:string-all ;
          ncd:revise-date 2020-02-11 ;
        }
        leaf system-objectid {
          type ncd:string-all ;
          ncd:revise-date 2020-02-11 ;
        }
        leaf rosng-version {
          type ncd:string-all ;
          ncd:revise-date 2020-02-11 ;
        }
        leaf service-num {
          type uint32 ;
          ncd:revise-date 2020-02-11 ;
        }
        leaf mng-mac {
          type ncd:string-all ;
          ncd:revise-date 2020-02-11 ;
        }
        leaf mng-mac-num {
          type int16 ;
          ncd:revise-date 2020-02-11 ;
        }
        leaf system-mac-num {
          type uint16 ;
          ncd:revise-date 2020-02-11 ;
        }
        leaf uptime-seconds {
          type uint32 ;
          ncd:revise-date 2020-09-03 ;
        }
        leaf neid {
          type string ;
          ncd:revise-date 2020-09-04 ;
        }
        leaf switch-method {
          description 'Master and slave switch method.'
                      ;
          type string ;
          ncd:revise-date 2021-05-25 ;
        }
        leaf banner-login {
          type ncd:long-text ;
          ncd:revise-date 2021-07-22 ;
        }
      }
      container cpus {
        list cpu {
          key 'shelf slot cpu'
              ;
          leaf shelf {
            description 'Shelf number.'
                        ;
            type uint8 {
              range 0..255 {
                description 'shelf range'
                            ;
              }
            }
          }
          leaf slot {
            description 'Slot number.'
                        ;
            type uint8 {
              range 0..255 {
                description 'slot range.'
                            ;
              }
            }
          }
          leaf cpu {
            type uint8 {
              range 0..15 ;
            }
          }
          leaf cputype {
            description 'CPU type'
                        ;
            type uint8 ;
          }
          leaf cpuname {
            description 'CPU name'
                        ;
            type string ;
          }
          leaf memory {
            type uint32 ;
          }
          leaf flash {
            type uint32 ;
          }
          leaf nvram {
            type uint32 ;
          }
          leaf processor {
            type ncd:string-with-blank ;
          }
          leaf bootver {
            type ncd:string-with-blank {
              length 1..20 ;
            }
          }
          leaf cpucorenum {
            type uint8 ;
          }
          leaf cpucardver {
            description 'CPU card version'
                        ;
            type ncd:string-with-blank {
              length 1..20 ;
            }
            ncd:revise-date 2020-02-11 ;
          }
          leaf panel {
            if-feature switch ;
            description 'Panel number'
                        ;
            type ncd:string-with-blank {
              length 1..8 ;
            }
            ncd:revise-date 2020-02-11 ;
          }
          ncd:select 'shelf slot'
                     ;
          ncd:select 'shelf slot cpu'
                     ;
          ncd:select 'shelf panel'
                     ;
          ncd:select 'shelf cpu panel'
                     ;
        }
      }
      container peripherals {
        list peripheral {
          key 'shelf slot peripheral-type'
              ;
          leaf shelf {
            description 'Shelf number.'
                        ;
            type uint8 {
              range 0..255 {
                description 'shelf range.'
                            ;
              }
            }
          }
          leaf slot {
            description 'Slot number.'
                        ;
            type uint8 {
              range 0..255 {
                description 'slot range.'
                            ;
              }
            }
          }
          leaf peripheral-type {
            type enumeration {
              enum flash {
                value 128 ;
              }
              enum harddisk {
                value 131 ;
              }
              enum cfcard {
                value 156 ;
              }
              enum sdcard {
                value 157 ;
              }
              enum usb1 {
                value 158 ;
              }
              enum usb2 {
                value 159 ;
              }
            }
          }
          leaf total-size {
            type uint32 ;
          }
          leaf free-size {
            type uint32 ;
          }
          leaf panel {
            if-feature switch ;
            description 'Panel number'
                        ;
            type ncd:string-with-blank {
              length 1..8 ;
            }
            ncd:revise-date 2020-02-11 ;
          }
          leaf boardtype {
            if-feature switch ;
            description 'Board logic type'
                        ;
            type enumeration {
              enum MPU {
                value 1 ;
                description 'The board is MPU.'
                            ;
              }
              enum PFU {
                value 3 ;
                description 'The board is PFU.'
                            ;
              }
              enum SFU {
                value 4 ;
                description 'The board is SFU.'
                            ;
              }
            }
            ncd:revise-date 2020-02-11 ;
          }
          ncd:select 'shelf slot'
                     ;
          ncd:select 'shelf slot peripheral-type'
                     ;
          ncd:select 'shelf panel boardtype'
                     ;
          ncd:select 'shelf peripheral-type panel boardtype'
                     ;
        }
      }
      container shelfs {
        list shelf {
          key shelfno ;
          leaf shelfno {
            description 'Shelf number'
                        ;
            type uint8 {
              range 0..255 {
                description 'shelf range.'
                            ;
              }
            }
          }
          leaf shelfattr {
            description 'Shelf attribute'
                        ;
            type enumeration {
              enum CFC {
                value 0 ;
              }
              enum LCC {
                value 1 ;
              }
            }
          }
          leaf shelftype {
            description 'Shelf type: value 4 is shelf -18, value 5 is shelf -3,'
                      + ' value 6 is shelf -5, value 7 is shelf -8'
                        ;
            type uint32 ;
          }
          leaf slotnum {
            description 'Slot number'
                        ;
            type uint8 ;
          }
          leaf manufacture {
            description 'Manufacture date'
                        ;
            type ncd:string-all ;
          }
          leaf shelfsn {
            description 'Shelf series number'
                        ;
            type ncd:string-all ;
          }
          leaf shelfname {
            description 'Shelf name'
                        ;
            type ncd:string-with-blank {
              length 1..80 ;
            }
            ncd:revise-date 2020-02-11 ;
          }
          leaf item {
            description 'Shelf sales code.'
                        ;
            type ncd:string-all ;
            ncd:revise-date 2022-07-01 ;
          }
          leaf description {
            description 'Shelf description.'
                        ;
            type ncd:string-all ;
            ncd:revise-date 2022-07-01 ;
          }
        }
      }
      container virtual-boards {
        list virtual-board {
          key 'shelf slot'
              ;
          leaf shelf {
            description 'Shelf number.'
                        ;
            type uint8 {
              range 0..255 {
                description 'shelf range.'
                            ;
              }
            }
          }
          leaf slot {
            description 'Slot number.'
                        ;
            type uint8 {
              range 0..255 {
                description 'slot range.'
                            ;
              }
            }
          }
          leaf subslot {
            description 'Subslot number.'
                        ;
            type uint8 ;
          }
          leaf portnum {
            description 'Port number.'
                        ;
            type uint8 ;
          }
          leaf boardtype {
            description 'Virtual board type.'
                        ;
            type uint32 ;
          }
          leaf panel {
            if-feature switch ;
            description 'Panel number'
                        ;
            type ncd:string-with-blank {
              length 1..8 ;
            }
          }
          ncd:select 'shelf slot'
                     ;
          ncd:select 'shelf panel'
                     ;
        }
      }
      container cards {
        list card {
          key 'shelf slot'
              ;
          leaf shelf {
            description 'Shelf number'
                        ;
            type uint8 {
              range 0..255 {
                description 'shelf range.'
                            ;
              }
            }
          }
          leaf slot {
            description 'Slot number'
                        ;
            type uint8 {
              range 0..255 {
                description 'slot range.'
                            ;
              }
            }
          }
          leaf subslot {
            description 'Subslot number'
                        ;
            type uint8 ;
          }
          leaf cpu {
            description 'Cpu number'
                        ;
            type uint8 ;
          }
          leaf run-time {
            description 'Run time'
                        ;
            type ncd:string-all {
              length 1..40 ;
            }
          }
          leaf panel {
            if-feature switch ;
            description 'Panel number'
                        ;
            type ncd:string-with-blank {
              length 1..8 ;
            }
          }
          ncd:select 'shelf slot'
                     ;
          ncd:select 'shelf panel'
                     ;
        }
      }
      container processor-usages {
        list processor-usage {
          key 'shelf slot'
              ;
          leaf shelf {
            description 'Shelf number'
                        ;
            type uint8 {
              range 0..255 {
                description 'shelf range.'
                            ;
              }
            }
          }
          leaf slot {
            description 'Slot number'
                        ;
            type uint8 {
              range 0..255 {
                description 'slot range.'
                            ;
              }
            }
          }
          leaf cpu {
            description 'CPU number'
                        ;
            type uint8 ;
          }
          leaf cpu-usage-5s {
            description 'CPU usage ratio measured in 5 seconds'
                        ;
            type ncd:string-all ;
          }
          leaf cpu-usage-1m {
            description 'CPU usage ratio measured in 1 minute'
                        ;
            type ncd:string-all ;
          }
          leaf cpu-usage-5m {
            description 'CPU usage ratio measured in 5 minute'
                        ;
            type ncd:string-all ;
          }
          leaf cpu-peak {
            description 'CPU peak usage ratio measured in 1 minute'
                        ;
            type ncd:string-all ;
          }
          leaf mem-usage {
            description 'Memory usage ratio'
                        ;
            type ncd:string-all ;
          }
          leaf mem-physical {
            description 'Physical memory'
                        ;
            type uint32 ;
            ncd:revise-date 2020-02-11 ;
          }
          leaf mem-free {
            description 'Free memory'
                        ;
            type uint32 ;
            ncd:revise-date 2020-02-11 ;
          }
          leaf panel {
            if-feature switch ;
            description 'Panel number'
                        ;
            type ncd:string-with-blank {
              length 1..8 ;
            }
            ncd:revise-date 2020-02-11 ;
          }
          leaf boardtype {
            if-feature switch ;
            description 'Board logic type'
                        ;
            type enumeration {
              enum MPU {
                value 1 ;
                description 'The board is MPU.'
                            ;
              }
              enum PFU {
                value 3 ;
                description 'The board is PFU.'
                            ;
              }
              enum SFU {
                value 4 ;
                description 'The board is SFU.'
                            ;
              }
            }
            ncd:revise-date 2020-02-11 ;
          }
          leaf mssc-info {
            description 'SC master/slave information.'
                        ;
            type ncd:string-all ;
            ncd:revise-date 2021-02-05 ;
          }
          leaf cpudes {
            description 'CPU description.'
                        ;
            type ncd:string-all ;
            ncd:revise-date 2021-02-05 ;
          }
          ncd:select 'shelf slot'
                     ;
          ncd:select 'shelf panel'
                     ;
        }
      }
      container components {
        list component {
          key id ;
          leaf id {
            type ncd:string-all ;
          }
        }
      }
      container spi-ports {
        list spi-ports {
          key 'shelf slot'
              ;
          leaf shelf {
            description 'Shelf number.'
                        ;
            type uint8 {
              range 0..255 {
                description 'shelf range.'
                            ;
              }
            }
          }
          leaf slot {
            description 'Slot number.'
                        ;
            type uint8 {
              range 0..255 {
                description 'slot range.'
                            ;
              }
            }
          }
          leaf subslot {
            description 'Subslot number.'
                        ;
            type uint8 ;
          }
          leaf portno {
            description 'The number of the spi port.'
                        ;
            type uint32 ;
          }
          leaf porttype {
            description 'The type of the spi port.'
                        ;
            type uint16 ;
          }
          leaf portname {
            description 'Interface name.'
                        ;
            type string ;
          }
          leaf channelno {
            description 'The number of the spi-ports channel.'
                        ;
            type uint32 ;
          }
          ncd:select 'shelf slot'
                     ;
        }
      }
      container boards {
        list board {
          description board ;
          key 'shelf slot subslot'
              ;
          leaf shelf {
            description 'Shelf Number'
                        ;
            type uint8 {
              range 0..255 {
                description 'shelf range.'
                            ;
              }
            }
          }
          leaf slot {
            description 'Slot Number'
                        ;
            type uint8 {
              range 0..255 {
                description 'slot range.'
                            ;
              }
            }
          }
          leaf subslot {
            description 'Subslot Number'
                        ;
            type uint8 {
              range 0..255 ;
            }
          }
          leaf brdstate {
            description 'Board consistent state'
                        ;
            type enumeration {
              enum unknown {
                value 0 ;
                description Unknown. ;
              }
              enum matching {
                value 1 ;
                description 'The emsboard matchs the realboard.'
                            ;
              }
              enum no-matching {
                value 2 ;
                description 'The emsboard do not match the realboard.'
                            ;
              }
              enum no-emsbrd {
                value 3 ;
                description 'The emsboard is inexistent.'
                            ;
              }
              enum no-realbrd {
                value 4 ;
                description 'The realboard is inexistent.'
                            ;
              }
              enum empty-slot {
                value 5 ;
                description 'Current slot is empty.'
                            ;
              }
            }
          }
          container ems-board {
            description emsboard ;
            leaf brd-type {
              description 'Funcid of the insert card'
                          ;
              type uint32 {
                range 0..4294967295 ;
              }
            }
            leaf version {
              description 'Version of the insert card'
                          ;
              type ncd:string-with-blank {
                length 0..80 ;
              }
            }
            leaf memo {
              description 'Description of the insert card'
                          ;
              type ncd:string-with-blank {
                length 0..512 ;
              }
            }
            leaf max-port-num {
              description 'Maximum port number of the insert card'
                          ;
              type uint32 {
                range 0..4294967295 ;
              }
            }
            list ports {
              description ports ;
              key 'port-no port-type'
                  ;
              leaf port-no {
                description 'Port Number'
                            ;
                type uint32 {
                  range 0..4294967295 ;
                }
              }
              leaf port-type {
                description 'Port Type'
                            ;
                type string {
                  length 0..32 ;
                }
              }
            }
          }
          container real-board {
            description realboard ;
            leaf brd-type {
              description 'Funcid of the insert card'
                          ;
              type uint32 {
                range 0..4294967295 ;
              }
            }
            leaf version {
              description 'Version of the insert card'
                          ;
              type ncd:string-with-blank {
                length 0..80 ;
              }
            }
            leaf memo {
              description 'Description of the insert card'
                          ;
              type ncd:string-with-blank {
                length 0..512 ;
              }
            }
            leaf max-port-num {
              description 'Maximum port number of the insert card'
                          ;
              type uint32 {
                range 0..4294967295 ;
              }
            }
            list ports {
              description ports ;
              key 'port-no port-type'
                  ;
              leaf port-no {
                description 'Port Number'
                            ;
                type uint32 {
                  range 0..4294967295 ;
                }
              }
              leaf port-type {
                description 'Port Type'
                            ;
                type string {
                  length 0..32 ;
                }
              }
            }
          }
        }
      }
      container all-ports {
        list port {
          key 'shelf slot subslot portno'
              ;
          leaf shelf {
            description 'Shelf number.'
                        ;
            type uint8 {
              range 0..255 {
                description 'shelf range.'
                            ;
              }
            }
          }
          leaf slot {
            description 'Slot number.'
                        ;
            type uint8 {
              range 0..255 {
                description 'slot range.'
                            ;
              }
            }
          }
          leaf subslot {
            description 'Subslot number.'
                        ;
            type uint8 ;
          }
          leaf portno {
            description 'Port number.'
                        ;
            type uint32 ;
          }
          leaf porttype {
            description 'Port type.'
                        ;
            type uint16 ;
          }
          leaf portname {
            description 'Port name.'
                        ;
            type string ;
          }
          leaf portphystatus {
            description 'Port physical status.'
                        ;
            type uint8 ;
          }
          leaf porteoproperty {
            description 'Port electric optical property.'
                        ;
            type uint8 ;
          }
          leaf portspeed {
            description 'Port speed.'
                        ;
            type uint32 ;
          }
          leaf vnd-name {
            description 'Port vnd-name.'
                        ;
            type string ;
          }
          ncd:select 'shelf slot subslot portno'
                     ;
        }
      }
      container processes {
        list process {
          key pid ;
          leaf pid {
            description 'The process pid'
                        ;
            type uint64 ;
            mandatory true ;
          }
          leaf name {
            description 'The process name'
                        ;
            type ncd:string-all ;
          }
          leaf start-time {
            description 'The time at which this process started, reported as na'
                      + 'noseconds since the UNIX epoch.  The system must be sy'
                      + 'nchronized such that the start-time can be reported ac'
                      + 'curately, otherwise it should not be reported.'
                        ;
            type uint64 ;
          }
          leaf uptime {
            description 'Amount of time elapsed since this process started.'
                        ;
            type uint64 ;
          }
          leaf cpu-usage-user {
            description 'CPU time consumed by this process in user mode.'
                        ;
            type uint64 ;
          }
          leaf cpu-usage-system {
            description 'CPU time consumed by this process in kernel mode.'
                        ;
            type uint64 ;
          }
          leaf cpu-utilization {
            description 'The percentage of CPU that is being used by the proces'
                      + 's.'
                        ;
            type uint8 ;
          }
          leaf memory-usage {
            description 'Bytes allocated and still in use by the process'
                        ;
            type uint64 ;
          }
          leaf memory-utilization {
            description 'The percentage of RAM that is being used by the proces'
                      + 's.'
                        ;
            type uint8 ;
          }
        }
      }
      container manage-element {
        description ME. ;
        leaf me-status {
          description 'ME status'
                      ;
          type enumeration {
            enum unknown {
              value 0 ;
              description 'The status of ME is unknown.'
                          ;
            }
            enum installing {
              value 1 ;
              description 'The status of ME is installing.'
                          ;
            }
            enum running {
              value 2 ;
              description 'The status of ME is running.'
                          ;
            }
            enum maintenance {
              value 3 ;
              description 'The status of ME is maintenance.'
                          ;
            }
          }
        }
        ncd:revise-date 2019-10-10 ;
      }
      container memory {
        description 'Top-level container for system memory data.'
                    ;
        leaf physical {
          description 'Reports the total physical memory available on the syste'
                    + 'm.'
                      ;
          type uint64 ;
          units bytes ;
        }
        leaf reserved {
          description 'Memory reserved for system use'
                      ;
          type uint64 ;
          units bytes ;
        }
        leaf utilization {
          description 'Memory utilization for system'
                      ;
          type uint8 {
            range 0..100 ;
          }
        }
      }
      container all-cards {
        list all-card {
          key 'shelf slot'
              ;
          leaf shelf {
            description 'Shelf number'
                        ;
            type uint8 ;
          }
          leaf slot {
            description 'Slot number'
                        ;
            type uint8 ;
          }
          leaf subslot {
            description 'Subslot number'
                        ;
            type uint8 ;
          }
          leaf status {
            description 'The status of real card'
                        ;
            type enumeration {
              enum online {
                value 0 ;
                description 'The real card is online.'
                            ;
              }
              enum offline {
                value 1 ;
                description 'The real card is offline.'
                            ;
              }
            }
            ncd:revise-date 2020-01-15 ;
          }
          leaf sub-type {
            description Sub-type ;
            type uint8 ;
          }
          leaf back-board-type {
            description Back-board-type ;
            type uint8 ;
          }
          leaf cfg-type {
            description Cfg-type ;
            type uint8 ;
          }
          leaf funcid {
            description 'Funcid of real card'
                        ;
            type uint32 ;
          }
          leaf funcid-conf {
            description 'Funcid of insert-card'
                        ;
            type uint32 ;
            ncd:revise-date 2020-01-15 ;
          }
          leaf board-logictype {
            description 'The logic type of board'
                        ;
            type enumeration {
              enum UNKNOWN {
                value 0 ;
                description 'The logictype of board is unknown'
                            ;
              }
              enum MPU {
                value 1 ;
                description 'The MPU'
                            ;
              }
              enum PFU {
                value 3 ;
                description 'The PFU'
                            ;
              }
              enum SFU {
                value 4 ;
                description 'The SFU'
                            ;
              }
              enum MPSFU {
                value 17 ;
                description 'The mpsfu'
                            ;
              }
            }
            ncd:revise-date 2021-05-27 ;
          }
          leaf software-version {
            description 'The software-version of board'
                        ;
            type ncd:string-all ;
            ncd:revise-date 2020-09-04 ;
          }
          leaf hardware-version {
            description 'The hardware-version of board'
                        ;
            type ncd:string-all ;
            ncd:revise-date 2020-09-04 ;
          }
        }
        ncd:revise-date 2019-11-07 ;
      }
      container board-info {
        list board-info {
          key 'shelf slot'
              ;
          leaf shelf {
            description 'Shelf number'
                        ;
            type uint8 {
              range 0..255 {
                description 'shelf range.'
                            ;
              }
            }
          }
          leaf slot {
            description 'Slot number'
                        ;
            type uint8 {
              range 0..255 {
                description 'slot range.'
                            ;
              }
            }
          }
          leaf panel {
            if-feature switch ;
            description 'Panel number'
                        ;
            type ncd:string-with-blank {
              length 1..8 ;
            }
          }
          leaf boardtype {
            if-feature switch ;
            description 'Board logic type'
                        ;
            type enumeration {
              enum MPU {
                value 1 ;
                description 'The board is MPU.'
                            ;
              }
              enum PFU {
                value 3 ;
                description 'The board is PFU.'
                            ;
              }
              enum SFU {
                value 4 ;
                description 'The board is SFU.'
                            ;
              }
            }
          }
          leaf online {
            description 'Board status'
                        ;
            type ncd:string-all ;
          }
          leaf lastestuptime {
            description 'Lastest up time'
                        ;
            type uint32 ;
          }
          leaf lastestdowntime {
            description 'Lastest down time'
                        ;
            type uint32 ;
          }
          leaf currenttime {
            description 'Current time'
                        ;
            type uint32 ;
          }
          leaf blocknum {
            description 'Block number'
                        ;
            type uint32 ;
          }
          leaf role {
            description 'Master slave status'
                        ;
            type ncd:string-all ;
          }
          ncd:select 'shelf slot'
                     ;
          ncd:select 'shelf panel'
                     ;
        }
        ncd:revise-date 2020-02-11 ;
      }
      container nvram {
        leaf imgfile-location {
          type ncd:string-all ;
        }
        leaf mng-ip-address {
          type ncd:ipv4-address ;
        }
        leaf mng-ip-mask {
          type ncd:ipv4-address ;
        }
        leaf boot-server {
          type ncd:ipv4-address ;
        }
        leaf default-gateway {
          type ncd:ipv4-address ;
        }
        leaf boot-username {
          type string ;
        }
        leaf ftp-path {
          type ncd:string-all ;
        }
        leaf mng-ipv6-address {
          type ncd:string-all ;
        }
        leaf boot-ipv6-server {
          type ncd:string-all ;
        }
        leaf def-ipv6-gateway {
          type ncd:string-all ;
        }
        leaf mng-ipv6-enable {
          type enumeration {
            enum enable {
              value 1 ;
            }
            enum disable {
              value 0 ;
            }
          }
        }
        leaf boot-from {
          type enumeration {
            enum ipv4-server {
              value 0 ;
            }
            enum ipv6-server {
              value 1 ;
            }
          }
        }
        ncd:revise-date 2020-06-15 ;
      }
    }
  }
  rpc reboot {
    description 'RPC Operation'
                ;
    input {
      leaf name {
        config false ;
        description 'card name'
                    ;
        type string ;
        mandatory true ;
      }
      leaf reboot-type {
        config false ;
        description 'Type of the reboot type'
                    ;
        type enumeration {
          enum NO_COMMAND {
            value 0 ;
            description 'do nothing'
                        ;
          }
          enum WARM_RESET {
            value 1 ;
            description 'warm reboot'
                        ;
          }
          enum COLD_RESET {
            value 2 ;
            description 'cold reboot'
                        ;
          }
        }
        default NO_COMMAND ;
      }
    }
    output {
      leaf result {
        config false ;
        description result ;
        type ncd:string-all ;
        mandatory true ;
      }
    }
  }
  rpc nvram {
    description 'Nvram Operation'
                ;
    input {
      container enable-passwd {
        description 'Modify enable password.'
                    ;
        leaf old-passwd {
          config false ;
          description 'Enable password.'
                      ;
          type string {
            length 1..128 {
              description 'Old password.'
                          ;
            }
          }
        }
        leaf new-passwd {
          config false ;
          description 'New enable password.'
                      ;
          type string {
            length 8..128 {
              description 'New enable password.'
                          ;
            }
          }
        }
        leaf new-confirm {
          config false ;
          description 'New enable password confirm.'
                      ;
          type string {
            length 8..128 {
              description 'New enable password confirm.'
                          ;
            }
          }
        }
      }
    }
  }
  notification event {
    description 'hostname banner boot-time domain-name'
                ;
    container sys {
      leaf hostname {
        type ncd:string-all-with-chinese ;
      }
      leaf banner {
        type ncd:long-text ;
      }
      leaf boot-time {
        type uint64 ;
      }
      leaf domain-name {
        type string ;
      }
    }
    container board-event {
      config false ;
      description 'board event'
                  ;
      leaf shelf {
        description 'Shelf Number'
                    ;
        type uint8 {
          range 0..255 ;
        }
      }
      leaf slot {
        description 'Slot Number'
                    ;
        type uint8 {
          range 0..255 ;
        }
      }
      leaf subslot {
        description 'Subslot Number'
                    ;
        type uint8 {
          range 0..255 ;
        }
      }
      leaf brdstate {
        description 'Board consistent state'
                    ;
        type enumeration {
          enum unknown {
            value 0 ;
            description Unknown. ;
          }
          enum matching {
            value 1 ;
            description 'The emsboard matchs the realboard.'
                        ;
          }
          enum no-matching {
            value 2 ;
            description 'The emsboard do not match the realboard.'
                        ;
          }
          enum no-emsbrd {
            value 3 ;
            description 'The emsboard is inexistent.'
                        ;
          }
          enum no-realbrd {
            value 4 ;
            description 'The realboard is inexistent.'
                        ;
          }
          enum empty-slot {
            value 5 ;
            description 'Current slot is empty.'
                        ;
          }
        }
      }
      container ems-board {
        description emsboard ;
        leaf brd-type {
          description 'Funcid of the insert card'
                      ;
          type uint32 {
            range 0..4294967295 ;
          }
        }
        leaf version {
          description 'Version of the insert card'
                      ;
          type ncd:string-with-blank {
            length 0..80 ;
          }
        }
        leaf description {
          description 'Description of the insert card'
                      ;
          type ncd:string-with-blank {
            length 0..512 ;
          }
        }
        leaf max-port-num {
          description 'Maximum port number of the insert card'
                      ;
          type uint32 {
            range 0..4294967295 ;
          }
        }
        list ports {
          description port ;
          key 'port-no port-type'
              ;
          leaf port-no {
            description 'Port Number'
                        ;
            type uint32 {
              range 0..4294967295 ;
            }
          }
          leaf port-type {
            description 'Port Type'
                        ;
            type string {
              length 0..32 ;
            }
          }
        }
      }
      container real-board {
        description realboard ;
        leaf brd-type {
          description 'Funcid of the insert card'
                      ;
          type uint32 {
            range 0..4294967295 ;
          }
        }
        leaf version {
          description 'Version of the insert card'
                      ;
          type ncd:string-with-blank {
            length 0..80 ;
          }
        }
        leaf description {
          description 'Description of the insert card'
                      ;
          type ncd:string-with-blank {
            length 0..512 ;
          }
        }
        leaf max-port-num {
          description 'Maximum port number of the insert card'
                      ;
          type uint32 {
            range 0..4294967295 ;
          }
        }
        list ports {
          description ports ;
          key 'port-no port-type'
              ;
          leaf port-no {
            description 'Port Number'
                        ;
            type uint32 {
              range 0..4294967295 ;
            }
          }
          leaf port-type {
            description 'Port Type'
                        ;
            type string {
              length 0..32 ;
            }
          }
        }
      }
    }
  }
}
