module zxr10-pm-lr {
  namespace 'http://www.zte.com.cn/zxr10/netconf/schema/rosng/pm-lr'
            ;
  prefix pm-lr ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  revision 2020-10-19 {
    description 'Change description leaf parameter type from string to string-a'
              + 'll'
                ;
  }
  revision 2019-01-17 {
    description 'shelf range 0-255.slot range 0-255.'
                ;
  }
  revision 2018-04-21 {
    description 'add assign-flexe function'
                ;
  }
  revision 2017-10-19 {
    description 'add delete-assigned-offline-card'
                ;
  }
  revision 2017-04-05 {
    description 'logic-router -> virtual-network-device
lr -> vnd'
                ;
  }
  revision 2016-02-29 ;
  container configuration {
    container virtual-network-device {
      container virtual-network-device-config-vnd0 {
        list undeploy-mpu {
          description 'vnd0 undeploy MPU'
                      ;
          key mpu ;
          leaf mpu {
            description 'MPU information'
                        ;
            type string {
              length 1..28 ;
            }
          }
        }
      }
      list virtual-network-device-config-vndx {
        key vndx-name ;
        leaf vndx-name {
          description 'vndx name'
                      ;
          type string {
            length 1..31 ;
          }
        }
        list deploy-mpu {
          description 'deploy MPU'
                      ;
          key mpu ;
          leaf mpu {
            description 'MPU information'
                        ;
            type string {
              length 1..28 ;
            }
          }
        }
        list assign-interface {
          description 'vndx assign interface'
                      ;
          key interface-name ;
          leaf interface-name {
            description 'interface name'
                        ;
            type string {
              length 1..31 ;
            }
          }
        }
        container vndx-attribute {
          leaf description {
            description 'description of vndx'
                        ;
            type ncd:string-all {
              length 1..127 ;
            }
          }
          leaf status {
            description 'disable or enable vndx'
                        ;
            type enumeration {
              enum enable {
                value 1 ;
              }
              enum disable {
                value 2 ;
              }
            }
          }
        }
        list assign-flexe {
          key 'flexe_client flexe_group calendar phy-interface'
              ;
          leaf flexe_client {
            description 'flexe_client ifname'
                        ;
            type string ;
          }
          leaf flexe_group {
            description 'flexe_group ifname'
                        ;
            type string ;
          }
          leaf calendar {
            description 'calendar template'
                        ;
            type enumeration {
              enum A {
                value 1 ;
                description 'calendar-template A'
                            ;
              }
              enum B {
                value 2 ;
                description 'calendar-template B'
                            ;
              }
            }
          }
          leaf phy-interface {
            description 'physical interface'
                        ;
            type string ;
          }
          leaf timeslots {
            description 'timeslots range'
                        ;
            type ncd:range ;
          }
          ncd:revise-date 2018-04-21 ;
        }
      }
      container delete-assigned-offline-interface {
        leaf shelf {
          type uint8 {
            range 0..255 {
              description 'shelf range.'
                          ;
            }
          }
        }
        leaf slot {
          type uint8 {
            range 0..255 {
              description 'slot range.'
                          ;
            }
          }
        }
        leaf subslot {
          type uint8 {
            range 0..3 ;
          }
        }
      }
      container delete-assigned-offline-card {
        leaf shelf {
          type uint8 {
            range 0..255 {
              description 'shelf range.'
                          ;
            }
          }
        }
        leaf slot {
          type uint8 {
            range 0..255 {
              description 'slot range.'
                          ;
            }
          }
        }
        ncd:revise-date 2017-10-19 ;
      }
      ncd:revise-date 2017-04-05 ;
    }
  }
  container operation {
    config false ;
    container virtual-network-device {
      container restart-vnd {
        leaf vnd-name {
          type string {
            length 1..31 ;
          }
        }
      }
      ncd:revise-date 2017-04-05 ;
    }
  }
  container state {
    config false ;
    container virtual-network-device {
      container show-virtual-network-device {
        list show-virtual-network-device-list {
          key vnd-name ;
          leaf vnd-name {
            type string {
              length 1..31 ;
            }
          }
          leaf vnd-id {
            type uint32 {
              range 0..255 ;
            }
          }
          leaf vnd-status {
            type enumeration {
              enum running {
                value 1 ;
              }
              enum stop {
                value 2 ;
              }
              enum no-license {
                value 3 ;
              }
            }
          }
          leaf description {
            type ncd:string-all {
              length 1..127 ;
            }
          }
          list deploy-mpu {
            key mpu ;
            leaf mpu {
              type string {
                length 1..28 ;
              }
            }
          }
          list assign-interface {
            key interface-name ;
            leaf interface-name {
              type string {
                length 1..31 ;
              }
            }
          }
        }
      }
      ncd:revise-date 2017-04-05 ;
    }
  }
}
