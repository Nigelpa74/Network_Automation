module zxr10-tacplus {
  namespace 'http://www.zte.com.cn/zxr10/netconf/schema/rosng/tacplus'
            ;
  prefix tacplus ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'This module describes the netconf model about TACPLUS.'
              ;
  revision 2020-07-22 {
    description '1.Requirment DES to AES,Configure length and type of global ke'
              + 'y.host key .host6 key'
                ;
  }
  revision 2020-02-06 {
    description '1 Add leaf under the server-group/group.Tacplus server group a'
              + 'lgorithm'
                ;
  }
  revision 2018-10-24 {
    description '1. Add leaf under the zxr10-tacplus/configuration/tacplus/glob'
              + 'al/'
                ;
  }
  revision 2015-07-30 {
    description '1.changed the config label of state container from true into f'
              + 'alse.'
                ;
  }
  revision 2015-03-30 {
    description "1. Modefied the zxr10-tacplus/configuration/tacplus/global/ mo"
              + "dels.
\n     (1) change choice type node en-disable into a lea"
              + "f type node,and its vuale 0 as disable,128 as enable.
\n  2. M"
              + "odefied the zxr10-tacplus/configuration/tacplus/ models and th"
              + "e zxr10-tacplus/configuration/tacplus/server-group/group.
\n  "
              + "   (1)Move the zxr10-tacplus/configuration/tacplus/group-serve"
              + "r4 into thezxr10-tacplus/configuration/tacplus/server-group/gr"
              + "oup,
\n        delete the  group-name  leaf node and change th"
              + "e type of  master leaf node in  enumeration  in  those list :
"
              + "\n                zxr10-tacplus/configuration/tacplus/server-g"
              + "roup/group/group-server4/groupv4s/groupv4,
\n        zxr10-tac"
              + "plus/configuration/tacplus/server-group/group/group-server4/gr"
              + "oupv4-mngs/groupv4-mng,                
\n            zxr10-ta"
              + "cplus/configuration/tacplus/server-group/group/group-server4/g"
              + "roupv4-vrfs/groupv4-vrf.                   
\n     (2)Move the"
              + " zxr10-tacplus/configuration/tacplus/group-server6 into the zx"
              + "r10-tacplus/configuration/tacplus/server-group/group 
\n      "
              + "      delete the  group-name  leaf node and change the type of"
              + "  master leaf node in  enumeration  in  those list :
\n       "
              + "    zxr10-tacplus/configuration/tacplus/server-group/group/gro"
              + "up-server6/groupv6s/groupv6,
\n           zxr10-tacplus/config"
              + "uration/tacplus/server-group/group/group-server6/groupv6-mngs/"
              + "groupv6-mng,
\n           zxr10-tacplus/configuration/tacplus/"
              + "server-group/group/group-server6/groupv6-vrfs/groupv6-vrf.    "
              + "
\n   3. changed those name which contain '_' into '-':pkt"
              + "_max_len,ip_if,host_mngs,host_mng,host_vrfs,host_vrf,vrf_name,"
              + "host6_mngs,host6_mng,host6_vrfs,host6_vrf,   vrf_name,group_na"
              + "me . 
\n   4. add the value of max-elements in those list node"
              + ".
\n     (1)make the value of max-elements in those list are 2"
              + "56:
\n           the zxr10-tacplus/configuration/tacplus/hostv"
              + "4/hosts/host,
\n           the zxr10-tacplus/configuration/tac"
              + "plus/hostv4/host-mngs/host_mng,
\n           the zxr10-tacplus"
              + "/configuration/tacplus/hostv4/host-vrfs/host_vrf,
\n          "
              + " the zxr10-tacplus/configuration/tacplus/hostv6/host6s/host6,
"
              + "\n           the zxr10-tacplus/configuration/tacplus/hostv6/ho"
              + "st6-mngs/host6-mng,
\n   the zxr10-tacplus/configurati"
              + "on/tacplus/hostv6/host6-vrfs/host6-vrf,
\n           the zxr10"
              + "-tacplus/configuration/tacplus/server-group/group.
\n         "
              + "(2) make the value of max-elements in those list are 4:
\n    "
              + "       the zxr10-tacplus/configuration/tacplus/server-group/gr"
              + "oup/group-server4/groupv4s/groupv4,
\n           the zxr10-tac"
              + "plus/configuration/tacplus/server-group/group/group-server4/gr"
              + "oupv4-mngs/groupv4-mng,
\n           thezxr10-tacplus/configu"
              + "ration/tacplus/server-group/group/group-server4/groupv4-vrfs/g"
              + "roupv4-vrf,
\n           the zxr10-tacplus/configuration/tacpl"
              + "us/server-group/group/group-server6/groupv6s/groupv6,
\n"
              + "     the zxr10-tacplus/configuration/tacplus/server-group/grou"
              + "p/group-server6/groupv6-mngs/groupv6-mng,
\n           the zxr"
              + "10-tacplus/configuration/tacplus/server-group/group/group-serv"
              + "er6/groupv6-vrfs/groupv6-vrf."
                ;
  }
  revision 2015-03-06 {
    description '1. Modefied the zxr10-tacplus/configuration/tacplus/global/ mo'
              + 'dels.'+"\n"
              + '     (1) changed the key leaf nod rang from 0 to 63 into rang '
              + 'from 1 to 63.'+"\n"
              + ' 2. Modefied the zxr10-tacplus/configuration/tacplus/hostv4/ho'
              + 'sts/host/ models.'+"\n"
              + '     (1) changed the key leaf nod rang from 0 to 63 into rang '
              + 'from 1 to 63.'+"\n"
              + '     (2) changed the timeout leaf nod rang from 0 to 1000 into'
              + ' rang from 1 to 1000,and delete defual value 0.'+"\n"
              + ' 3. Modefied the zxr10-tacplus/configuration/tacplus/hostv4/ho'
              + 'st_mngs/host_mng/ models.'+"\n"
              + '     (1) changed the key leaf nod rang from 0 to 63 into rang '
              + 'from 1 to 63.'+"\n"
              + '     (2) changed the timeout leaf nod rang from 0 to 1000 into'
              + ' rang from 1 to 1000,and delete defual value 0.'+"\n"
              + ' 4. Modefied the zxr10-tacplus/configuration/tacplus/hostv4/ho'
              + 'st_vrfs/host_vrf/ models.'+"\n"
              + '     (1) changed the key leaf nod rang from 0 to 63 into rang '
              + 'from 1 to 63.'+"\n"
              + '     (2) changed the vrf-name  leaf nod rang from 1 to 35 into'
              + ' rang from 1 to 32.'+"\n"
              + '     (3) changed the timeout leaf nod rang from 0 to 1000 into'
              + ' rang from 1 to 1000,and delete defual value 0.'+"\n"
              + ' 5. Modefied the zxr10-tacplus/configuration/tacplus/hostv6/ho'
              + 'st6s/host6/ models.'+"\n"
              + '     (1) changed the key leaf nod rang from 0 to 63 into rang '
              + 'from 1 to 63.'+"\n"
              + '     (2) changed the timeout leaf nod rang from 0 to 1000 into'
              + ' rang from 1 to 1000,and delete defual value 0.'+"\n"
              + ' 6. Modefied the zxr10-tacplus/configuration/tacplus/hostv6/ho'
              + 'st6_mngs/host6_mng/ models.'+"\n"
              + '     (1) changed the key leaf nod rang from 0 to 63 into rang '
              + 'from 1 to 63.'+"\n"
              + '     (2) changed the timeout leaf nod rang from 0 to 1000 into'
              + ' rang from 1 to 1000,and delete defual value 0.'+"\n"
              + ' 7. Modefied the zxr10-tacplus/configuration/tacplus/hostv6/ho'
              + 'st6_vrfs/host6_vrf/ models.'+"\n"
              + '     (1) changed the key leaf nod rang from 0 to 63 into rang '
              + 'from 1 to 63.'+"\n"
              + '     (2) changed the vrf-name  leaf nod rang from 1 to 35 into'
              + ' rang from 1 to 32.'+"\n"
              + '     (3) changed the timeout leaf nod rang from 0 to 1000 into'
              + ' rang from 1 to 1000,and delete defual value 0.	 '+"\n"
              + ' 8. Modefied the zxr10-tacplus/configuration/tacplus/group-ser'
              + 'ver4/groupv4_vrfs/groupv4_vrf/ models.'+"\n"
              + '     (1) changed the vrf-name  leaf nod rang from 1 to 35 into'
              + ' rang from 1 to 32.'+"\n"
              + ' 9. Modefied the zxr10-tacplus/configuration/tacplus/group-ser'
              + 'ver6/groupv6_vrfs/groupv6_vrf/ models.'+"\n"
              + '     (1) changed the vrf-name  leaf nod rang from 1 to 35 into'
              + ' rang from 1 to 32.'+"\n"
              + '10.  Modefied the zxr10-tacplus/configuration/tacplus/global/t'
              + 'acacs-client models.'+"\n"
              + '     (1) add the description of the choice node ip_if,and enab'
              + 'le mandatory as true.'+"\n"
              + '     (2) changed the description of those leaf nodes:if,ip,por'
              + 't.'+"\n"
              + '11.  Modefied the zxr10-tacplus/configuration/tacplus/global/t'
              + 'acacs-client6 models.'+"\n"
              + '     (1) add the description of the choice node ip_if,and enab'
              + 'le mandatory as true.'+"\n"
              + '     (2) changed the description of those leaf nodes:if,ip,por'
              + 't.'+"\n"
              + '     (3) add the length rang of the type of if leaf node.'
                ;
  }
  revision 2015-02-10 {
    description "1.Modefied zxr10-tacplus/configuration/tacplus/global/tacacs-c"
              + "lient model.
\n  1)Add source-interface leaf node.
\n  2)Chang"
              + "ed the raw node into choice node,add cases ip and if,put ip-ad"
              + "dressleaf node into the ip case,and add the source-interface i"
              + "nto ifcase.
\n  3)Remove the port node's default value 49,and "
              + "change the range of this leaf node.  
\n2.Modefied zxr10-tacpl"
              + "us/configuration/tacplus/global/tacacs-client6 model.
\n  1)Ad"
              + "d source-interface leaf node.
\n  2)Changed the raw node into "
              + "choice node,add cases ip and if,put ipv6-address leaf node int"
              + "o the ip case,and add the source-interfaceinto if case.
\n  3)"
              + "Remove the port node's default value 49,andchange the range of"
              + " this leaf node.
\n  4)Move the ipv6-addressleaf node in the f"
              + "ront of the port leaf node."
                ;
  }
  revision 2014-03-14 {
    description 'Initial version.'
                ;
  }
  typedef authen-type {
    type enumeration {
      enum none {
        value 0 ;
        description 'Authentication type value:NONE.'
                    ;
      }
      enum ascii {
        value 1 ;
        description 'Authentication type value:ASCII.'
                    ;
      }
      enum pap {
        value 2 ;
        description 'Authentication type value:PAP.'
                    ;
      }
      enum chap {
        value 3 ;
        description 'Authentication type value:CHAP.'
                    ;
      }
      enum arap {
        value 4 ;
        description 'Authentication type value:ARAP.'
                    ;
      }
      enum mschap {
        value 5 ;
        description 'Authentication type value:MSCHAP.'
                    ;
      }
      enum unknown {
        value 255 ;
        description 'NO authentication type value.'
                    ;
      }
    }
    description 'Configure TACPLUS packet authentication type.'
                ;
  }
  typedef authen-method {
    type enumeration {
      enum notset {
        value 0 ;
        description 'Authentication method value:NOTSET.'
                    ;
      }
      enum none {
        value 1 ;
        description 'Authentication method value:NONE.'
                    ;
      }
      enum krb5 {
        value 2 ;
        description 'Authentication method value:KRB5.'
                    ;
      }
      enum line {
        value 3 ;
        description 'Authentication method value:LINE.'
                    ;
      }
      enum enable {
        value 4 ;
        description 'Authentication method value:ENABLE.'
                    ;
      }
      enum local {
        value 5 ;
        description 'Authentication method value:LOCAL.'
                    ;
      }
      enum tacplus {
        value 6 ;
        description 'Authentication method value:TACPLUS.'
                    ;
      }
      enum guest {
        value 8 ;
        description 'Authentication method value:GUEST.'
                    ;
      }
      enum radius {
        value 16 ;
        description 'Authentication method value:RADIUS.'
                    ;
      }
      enum krb4 {
        value 17 ;
        description 'Authentication method value:KRB4.'
                    ;
      }
      enum rcmd {
        value 32 ;
        description 'Authentication method value:RCMD.'
                    ;
      }
      enum unknown {
        value 255 ;
        description 'No authentication method value.'
                    ;
      }
    }
    description 'Configure TACPLUS authorization packet authentication method.'
                ;
  }
  typedef authen-service {
    type enumeration {
      enum none {
        value 0 ;
        description 'Authentication service value:NONE.'
                    ;
      }
      enum login {
        value 1 ;
        description 'Authentication service value:LOGIN.'
                    ;
      }
      enum enable {
        value 2 ;
        description 'Authentication service value:ENABLE.'
                    ;
      }
      enum ppp {
        value 3 ;
        description 'Authentication service value:PPP.'
                    ;
      }
      enum arap {
        value 4 ;
        description 'Authentication service value:ARAP.'
                    ;
      }
      enum pt {
        value 5 ;
        description 'Authentication service value:PT.'
                    ;
      }
      enum rcmd {
        value 6 ;
        description 'Authentication service value:RCMD.'
                    ;
      }
      enum x25 {
        value 7 ;
        description 'Authentication service value:X25.'
                    ;
      }
      enum nasi {
        value 8 ;
        description 'Authentication service value:NASI.'
                    ;
      }
      enum fwproxy {
        value 9 ;
        description 'Authentication service value:FWPROXY.'
                    ;
      }
      enum unknown {
        value 255 ;
        description 'No authentication service value.'
                    ;
      }
    }
    default unknown ;
    description 'Configure TACPLUS  authorization packet authentication service.'
                ;
  }
  typedef group-state {
    type enumeration {
      enum active {
        value 0 ;
        description 'Tacplus group state:active.'
                    ;
      }
      enum dead {
        value 1 ;
        description 'Tacplus group state:dead.'
                    ;
      }
    }
    description 'Tacplus group state.'
                ;
  }
  container configuration {
    description 'TACPLUS configuration.'
                ;
    container tacplus {
      description 'Tacplus info.'
                  ;
      container global {
        description 'Tacplus global configuration.'
                    ;
        leaf enable-state {
          description 'Enable or disable TACPLUS.'
                      ;
          type enumeration {
            enum disable {
              value 0 ;
              description 'Disable TACPLUS.'
                          ;
            }
            enum enable {
              value 128 ;
              description 'Enable TACPLUS.'
                          ;
            }
          }
          default disable ;
          ncd:revise-date 2015-03-30 ;
        }
        leaf pkt-max-len {
          description 'Max packet size (default: 1024 bytes).'
                      ;
          type uint32 {
            range 1024..4096 {
              description 'Max packet size (default: 1024 bytes).'
                          ;
            }
          }
          units byte ;
          default 1024 ;
          ncd:revise-date 2015-03-30 ;
        }
        leaf timeout {
          description 'Time to wait for TACPLUS server to reply(second).'
                      ;
          type uint32 {
            range 1..1000 {
              description 'Timeout value (default: 5 seconds).'
                          ;
              reference 'Timeout value (default: 5 seconds)'
                        ;
            }
          }
          units second ;
          default 5 ;
        }
        leaf min-key-len {
          description 'Min TACPLUS key length.(default: 0).'
                      ;
          type uint32 {
            range 0..63 {
              description 'Min TACPLUS key length.(default: 0).'
                          ;
              reference 'Min TACPLUS key length.(default: 0).'
                        ;
            }
          }
          units byte ;
          default 0 ;
          ncd:revise-date 2018-10-24 ;
        }
        leaf key {
          description 'Set TACPLUS  encryption key.'
                      ;
          type string {
            length '1..63 | 64..128'
                   {
              description 'Key string (1-63 characters)'+"\n"
                        + 'Encrypted key(64 - 128characters).'
                          ;
            }
          }
        }
        leaf deadtime {
          description 'Deadtime(default:5 minutes).'
                      ;
          type uint32 {
            range 0..65535 {
              description 'Deadtime(default:5 minutes).'
                          ;
              reference 'Deadtime(default:5 minutes)'
                        ;
            }
          }
          units minute ;
          default 5 ;
        }
        container tacacs-client {
          description 'Configure TACPLUS  V4 client.'
                      ;
          presence tacacs-client ;
          choice ip-if {
            description 'IPv4 address or source-interface configuration of TACP'
                      + 'LUS  client.'
                        ;
            mandatory true ;
            case ip {
              description 'IP address of TACPLUS  client.'
                          ;
              leaf ip-address {
                description 'IP address of TACPLUS  client.'
                            ;
                type ncd:ipv4-address ;
                mandatory true ;
              }
            }
            case if {
              description 'TACACS client source-interface name.'
                          ;
              leaf source-interface {
                description 'TACACS client source-interface name.'
                            ;
                type ncd:ifname {
                  length 1..31 {
                    description 'interface name length.'
                                ;
                  }
                }
                mandatory true ;
              }
            }
            ncd:revise-date 2015-03-30 ;
          }
          leaf port {
            description 'Port number of TACPLUS  client for IPV4.'
                        ;
            type uint16 {
              range 1025..65535 {
                description 'Port number value.'
                            ;
                reference 'Port number value'
                          ;
              }
            }
          }
        }
        container tacacs-client6 {
          description 'IPv6 TACPLUS  client.'
                      ;
          presence tacacs-client6 ;
          choice ip-if {
            description 'IPv6 address or source-interface configuration of TACP'
                      + 'LUS  client.'
                        ;
            mandatory true ;
            case ip {
              description 'IPv6 address of TACPLUS  client.'
                          ;
              leaf ipv6-address {
                description 'IPv6 address of TACPLUS  client.'
                            ;
                type ncd:ipv6-address ;
                mandatory true ;
              }
            }
            case if {
              description 'TACACS client6 source-interface name.'
                          ;
              leaf source-interface {
                description 'TACACS client6 source-interface name.'
                            ;
                type ncd:ifname {
                  length 1..31 {
                    description 'source-interface name length.'
                                ;
                  }
                }
                mandatory true ;
              }
            }
            ncd:revise-date 2015-03-30 ;
          }
          leaf port {
            description 'Port number of TACPLUS  client for IPV6.'
                        ;
            type uint16 {
              range 1025..65535 {
                description 'Port number value.'
                            ;
              }
            }
          }
        }
        container enable-packet {
          description 'Configure TACPLUS  enable packet authentication type.'
                      ;
          leaf authen-type {
            description 'Configure TACPLUS  enable packet authentication type.'
                        ;
            type authen-type ;
            default unknown ;
          }
        }
        container author-packet {
          description 'Configure TACPLUS  authorization packet attribute.'
                      ;
          leaf authen-type {
            description 'Configure TACPLUS authorization packet authentication '
                      + 'type.'
                        ;
            type authen-type ;
            default unknown ;
          }
          leaf authen-method {
            description 'Configure TACPLUS authorization packet authentication '
                      + 'method.'
                        ;
            type authen-method ;
            default unknown ;
          }
          leaf authen-service {
            description 'Configure TACPLUS authorization packet authentication '
                      + 'service.'
                        ;
            type authen-service ;
            default unknown ;
          }
        }
      }
      container hostv4 {
        description 'Specify a TACPLUS server.'
                    ;
        container hosts {
          description 'Specify a TACPLUS server.'
                      ;
          list host {
            description 'Specify a TACPLUS server.'
                        ;
            max-elements 256 ;
            key 'ip-address port'
                ;
            leaf ip-address {
              description 'A.B.C.D  IP address of TACPLUS server.'
                          ;
              type ncd:ipv4-address ;
            }
            leaf port {
              description 'Port number of TACPLUS server.'
                          ;
              type uint16 {
                range '49 | 1025..65535'
                      {
                  description 'Port number value.'
                              ;
                }
              }
            }
            leaf timeout {
              description 'Time to wait for TACPLUS server to reply(second).'
                          ;
              type uint32 {
                range 1..1000 {
                  description 'Timeout value (second).'
                              ;
                }
              }
              units second ;
            }
            leaf key {
              description 'Set TACPLUS encryption key.'
                          ;
              type string {
                length '1..63 | 64..128'
                       {
                  description 'WORD       Key string (1-63 characters)'+"\n"
                            + 'Encrypted  Set TACACS+ encrypted key(64-128 char'
                            + 'acters).'
                              ;
                }
              }
            }
          }
        }
        container host-mngs {
          description 'Specify a TACPLUS server.'
                      ;
          list host-mng {
            description 'Specify a TACPLUSserver.'
                        ;
            max-elements 256 ;
            key 'ip-address port'
                ;
            leaf ip-address {
              description 'IP address of TACPLUS server.'
                          ;
              type ncd:ipv4-address ;
            }
            leaf port {
              description 'Port number of TACPLUS server.'
                          ;
              type uint16 {
                range '49 | 1025..65535'
                      {
                  description 'Port number value.'
                              ;
                }
              }
            }
            leaf timeout {
              description 'Time to wait for TACPLUS server to reply(second).'
                          ;
              type uint32 {
                range 1..1000 {
                  description 'Timeout value (second).'
                              ;
                }
              }
              units second ;
            }
            leaf key {
              description 'Set TACPLUS encryption key.'
                          ;
              type string {
                length '1..63 | 64..128'
                       {
                  description 'Key string (1-63 characters)'+"\n"
                            + 'Encrypted key (64 - 128 characters).'
                              ;
                }
              }
            }
          }
          ncd:revise-date 2015-03-30 ;
        }
        container host-vrfs {
          description 'Specify a TACPLUS server.'
                      ;
          list host-vrf {
            description 'Specify a TACPLUSserver.'
                        ;
            max-elements 256 ;
            key 'ip-address vrf-name port'
                ;
            leaf ip-address {
              description 'IP address of TACPLUS server.'
                          ;
              type ncd:ipv4-address ;
            }
            leaf vrf-name {
              description 'VPN Routing/Forwarding instance.'
                          ;
              type string {
                length 1..32 {
                  description 'VPN Routing/Forwarding instance name (1-32 chara'
                            + 'cters).'
                              ;
                }
              }
            }
            leaf port {
              description 'Port number of TACPLUS server.'
                          ;
              type uint16 {
                range '49 | 1025..65535'
                      {
                  description 'Port number value.'
                              ;
                }
              }
            }
            leaf timeout {
              description 'Time to wait for TACPLUS server to reply(second).'
                          ;
              type uint32 {
                range 1..1000 {
                  description 'Timeout value (second).'
                              ;
                }
              }
              units second ;
            }
            leaf key {
              description 'Set TACPLUS encryption key.'
                          ;
              type string {
                length '1..63 | 64..128'
                       {
                  description 'Key string (1-63 characters)'+"\n"
                            + 'Encrypted key (64 - 128 characters).'
                              ;
                }
              }
            }
          }
          ncd:revise-date 2015-03-30 ;
        }
      }
      container hostv6 {
        description 'Specify an IPv6 TACPLUS server.'
                    ;
        container host6s {
          description 'Specify an IPv6 TACPLUS server.'
                      ;
          list host6 {
            description 'Specify an IPv6 TACPLUS server.'
                        ;
            max-elements 256 ;
            key 'ipv6-address port'
                ;
            leaf ipv6-address {
              description 'IPv6 address of TACPLUS client.'
                          ;
              type ncd:ipv6-address ;
            }
            leaf port {
              description 'Port number of TACPLUS server.'
                          ;
              type uint16 {
                range '49 | 1025..65535'
                      {
                  description 'Port number value.'
                              ;
                }
              }
            }
            leaf timeout {
              description 'Time to wait for TACPLUS server to reply(second).'
                          ;
              type uint32 {
                range 1..1000 {
                  description 'Timeout value (second).'
                              ;
                }
              }
              units second ;
            }
            leaf key {
              description 'Set TACPLUS encryption key.'
                          ;
              type string {
                length '1..63 | 64..128'
                       {
                  description 'Key string (1-63 characters)'+"\n"
                            + 'Encrypted key (64 -128 characters).'
                              ;
                }
              }
            }
          }
        }
        container host6-mngs {
          description 'Specify an IPv6 TACPLUS server.'
                      ;
          list host6-mng {
            description 'Specify an IPv6 TACPLUS server.'
                        ;
            max-elements 256 ;
            key 'ipv6-address port'
                ;
            leaf ipv6-address {
              description 'IPv6 address of TACPLUS client.'
                          ;
              type ncd:ipv6-address ;
            }
            leaf port {
              description 'Port number of TACPLUS server.'
                          ;
              type uint16 {
                range '49 | 1025..65535'
                      {
                  description 'Port number value.'
                              ;
                }
              }
            }
            leaf timeout {
              description 'Time to wait for TACPLUS server to reply(second).'
                          ;
              type uint32 {
                range 1..1000 {
                  description 'Timeout value (second).'
                              ;
                }
              }
              units second ;
            }
            leaf key {
              description 'Set TACPLUS encryption key.'
                          ;
              type string {
                length '1..63 | 64..128'
                       {
                  description 'Key string (1-63 characters)'+"\n"
                            + 'Encrypted key (64 - 128 characters).'
                              ;
                }
              }
            }
          }
          ncd:revise-date 2015-03-30 ;
        }
        container host6-vrfs {
          description 'Specify an IPv6 TACPLUS server.'
                      ;
          list host6-vrf {
            description 'Specify an IPv6 TACPLUS server.'
                        ;
            max-elements 256 ;
            key 'ipv6-address port vrf-name'
                ;
            leaf ipv6-address {
              description 'IPv6 address of TACPLUS client.'
                          ;
              type ncd:ipv6-address ;
            }
            leaf port {
              description 'Port number of TACPLUS server.'
                          ;
              type uint16 {
                range '49 | 1025..65535'
                      {
                  description 'Port number value.'
                              ;
                }
              }
            }
            leaf vrf-name {
              description 'VPN Routing/Forwarding instance.'
                          ;
              type string {
                length 1..32 {
                  description 'VPN Routing/Forwarding instance name (1-32 chara'
                            + 'cters).'
                              ;
                }
              }
            }
            leaf timeout {
              description 'Time to wait for TACPLUS server to reply(second).'
                          ;
              type uint32 {
                range 1..1000 {
                  description 'Timeout value (second).'
                              ;
                }
              }
              units second ;
            }
            leaf key {
              description 'Set TACPLUS encryption key.'
                          ;
              type string {
                length '1..63 | 64..128'
                       {
                  description 'Key string (1-63 characters)'+"\n"
                            + 'Encrypted key (64 - 128 characters).'
                              ;
                }
              }
            }
          }
          ncd:revise-date 2015-03-30 ;
        }
      }
      container server-group {
        description 'Name of server group (1-31 characters).'
                    ;
        list group {
          description 'Name of server group (1-31 characters).'
                      ;
          max-elements 256 ;
          key group-name ;
          leaf group-name {
            description 'Name of server group (1-31 characters).'
                        ;
            type string {
              length 1..31 {
                description 'Name of server group (1-31 characters).'
                            ;
              }
            }
          }
          leaf algorithm {
            description 'tacplus server select style'
                        ;
            type enumeration {
              enum first {
                value 0 ;
                description 'Master server is always queried first'
                            ;
              }
              enum rollover-on-reject {
                value 1 ;
                description 'Servers are queried in rollover-on-reject'
                            ;
              }
            }
            default first ;
            ncd:revise-date 2020-02-06 ;
          }
          container group-server4 {
            description 'Configure server group.'
                        ;
            container groupv4s {
              description 'Configure server group.'
                          ;
              list groupv4 {
                description 'Configure server group.'
                            ;
                max-elements 4 ;
                key 'ip-address port'
                    ;
                leaf ip-address {
                  description 'IP address of TACPLUS host.'
                              ;
                  type ncd:ipv4-address ;
                }
                leaf port {
                  description 'Port number of TACPLUS host.'
                              ;
                  type uint16 {
                    range '49 | 1025..65535'
                          {
                      description 'Port number value.'
                                  ;
                    }
                  }
                }
                leaf master {
                  description 'Set this server as master.'
                              ;
                  type enumeration {
                    enum slave {
                      value 0 ;
                      description 'server as slave.'
                                  ;
                    }
                    enum master {
                      value 1 ;
                    }
                  }
                  default slave ;
                }
              }
            }
            container groupv4-mngs {
              description 'Configure server group.'
                          ;
              list groupv4-mng {
                description 'Configure server group.'
                            ;
                max-elements 4 ;
                key 'ip-address port'
                    ;
                leaf ip-address {
                  description 'IP address of TACPLUS host.'
                              ;
                  type ncd:ipv4-address ;
                }
                leaf port {
                  description 'Port number of TACPLUS host.'
                              ;
                  type uint16 {
                    range '49 | 1025..65535'
                          {
                      description 'Port number value.'
                                  ;
                    }
                  }
                }
                leaf master {
                  description 'Set this server as master.'
                              ;
                  type enumeration {
                    enum slave {
                      value 0 ;
                      description 'slave server.'
                                  ;
                    }
                    enum master {
                      value 1 ;
                      description 'master server.'
                                  ;
                    }
                  }
                  default slave ;
                }
              }
            }
            container groupv4-vrfs {
              description 'Configure server group.'
                          ;
              list groupv4-vrf {
                description 'Configure server group.'
                            ;
                max-elements 4 ;
                key 'vrf-name ip-address port'
                    ;
                leaf vrf-name {
                  description 'VPN Routing/Forwarding instance.'
                              ;
                  type string {
                    length 1..32 {
                      description 'VPN Routing/Forwarding instance name (1-32 c'
                                + 'haracters).'
                                  ;
                    }
                  }
                }
                leaf ip-address {
                  description 'IP address of TACPLUS host.'
                              ;
                  type ncd:ipv4-address ;
                }
                leaf port {
                  description 'Port number of TACPLUS host.'
                              ;
                  type uint16 {
                    range '49 | 1025..65535'
                          {
                      description 'Port number value.'
                                  ;
                    }
                  }
                }
                leaf master {
                  description 'Set this server as master.'
                              ;
                  type enumeration {
                    enum slave {
                      value 0 ;
                      description 'slave server.'
                                  ;
                    }
                    enum master {
                      value 1 ;
                      description 'master server.'
                                  ;
                    }
                  }
                  default slave ;
                }
              }
            }
            ncd:revise-date 2015-03-30 ;
          }
          container group-server6 {
            description 'Configure server group.'
                        ;
            container groupv6s {
              description 'Configure server group.'
                          ;
              list groupv6 {
                description 'Configure server group.'
                            ;
                max-elements 4 ;
                key 'ipv6-address port'
                    ;
                leaf ipv6-address {
                  description 'TACPLUS IPv6 host.'
                              ;
                  type ncd:ipv6-address ;
                }
                leaf port {
                  description 'Port number of TACPLUS host.'
                              ;
                  type uint16 {
                    range '49 | 1025..65535'
                          {
                      description 'Port number value.'
                                  ;
                    }
                  }
                }
                leaf master {
                  description 'Set this server as master.'
                              ;
                  type enumeration {
                    enum slave {
                      value 0 ;
                      description 'slave server.'
                                  ;
                    }
                    enum master {
                      value 1 ;
                      description 'master server.'
                                  ;
                    }
                  }
                  default slave ;
                }
              }
            }
            container groupv6-mngs {
              description 'Configure server group.'
                          ;
              list groupv6-mng {
                description 'Configure server group.'
                            ;
                max-elements 4 ;
                key 'ipv6-address port'
                    ;
                leaf ipv6-address {
                  description 'TACPLUS IPv6 host.'
                              ;
                  type ncd:ipv6-address ;
                }
                leaf port {
                  description 'Port number of TACPLUS host.'
                              ;
                  type uint16 {
                    range '49 | 1025..65535'
                          {
                      description 'Port number value.'
                                  ;
                    }
                  }
                }
                leaf master {
                  description 'Set this server as master.'
                              ;
                  type enumeration {
                    enum slave {
                      value 0 ;
                      description 'slave server.'
                                  ;
                    }
                    enum master {
                      value 1 ;
                      description 'master sever.'
                                  ;
                    }
                  }
                  default slave ;
                }
              }
            }
            container groupv6-vrfs {
              description 'Configure server group.'
                          ;
              list groupv6-vrf {
                description 'Configure server group.'
                            ;
                max-elements 4 ;
                key 'vrf-name ipv6-address port'
                    ;
                leaf vrf-name {
                  description 'VPN Routing/Forwarding instance.'
                              ;
                  type string {
                    length 1..32 {
                      description 'VPN Routing/Forwarding instance name (1-32 c'
                                + 'haracters).'
                                  ;
                    }
                  }
                }
                leaf ipv6-address {
                  description 'TACPLUS IPv6 host.'
                              ;
                  type ncd:ipv6-address ;
                }
                leaf port {
                  description 'Port number of TACPLUS host.'
                              ;
                  type uint16 {
                    range '49 | 1025..65535'
                          {
                      description 'Port number value.'
                                  ;
                    }
                  }
                }
                leaf master {
                  description 'Set this server as master.'
                              ;
                  type enumeration {
                    enum slave {
                      value 0 ;
                      description 'slave server.'
                                  ;
                    }
                    enum master {
                      value 1 ;
                      description 'master server.'
                                  ;
                    }
                  }
                  default slave ;
                }
              }
            }
            ncd:revise-date 2015-03-30 ;
          }
        }
      }
    }
  }
  container state {
    config false ;
    description 'TACPLUS state info.'
                ;
    container tacplus {
      description 'TACPLUS state info.'
                  ;
      container group-state {
        description 'TACPLUS group state info.'
                    ;
        list server-group-state {
          description 'Show TACPLUS group state.'
                      ;
          key group-name ;
          leaf group-name {
            description 'Name of server group (1-31 characters).'
                        ;
            type string {
              length 1..31 {
                description 'Name of server group (1-31 characters).'
                            ;
              }
            }
            ncd:revise-date 2015-03-30 ;
          }
          leaf state {
            description 'Tacplus group-server state.'
                        ;
            type group-state ;
          }
        }
      }
    }
  }
}
