module zxr10-adm-mgr {
  namespace 'http://www.zte.com.cn/zxr10/netconf/schema/rosng/adm-mgr'
            ;
  prefix adm-mgr ;
  yang-version 1 ;
  import zxr10-netconf-defs {
    prefix ncd ;
    revision-date 2013-11-22 ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The netconf module to describe the ADM_MGR.'
              ;
  revision 2022-09-25 {
    description 'Support enable password same consecutive check.'+"\n"
              + '(1)Add a container node.  path:/configuration/adm-mgr/global-c'
              + 'onfiguration/enable/enable-strong-password'+"\n"
              + '(1)Add a leaf node. path:/configuration/adm-mgr/global-configu'
              + 'ration/enable/enable-strong-password/same-consecutive-length'
                ;
  }
  revision 2022-09-09 {
    description 'Add the projects SWITCH(59/89/99/5960/99X/5960X/5960M) support'
              + 'ed by feature node "local-user-offline".'
                ;
  }
  revision 2022-08-01 {
    description 'Support password dictionary.'+"\n"
              + '(1)Add a container node. path:/configuration/adm-mgr/global-co'
              + 'nfiguration/password/password-dictionary.'+"\n"
              + '(2)Add a list node. path:/configuration/adm-mgr/global-configu'
              + 'ration/password/password-dictionary/password.'+"\n"
              + '(3)Add a leaf node. path:/configuration/adm-mgr/global-configu'
              + 'ration/password/password-dictionary/password/password.'+"\n"
              + '(4)Add a leaf node. path:/configuration/adm-mgr/global-configu'
              + 'ration/password/strong-password/dictionary.'
                ;
  }
  revision 2022-07-22 {
    description '(1)Add container node. path:/adm-mgr:configuration/adm-mgr:adm'
              + '-mgr/adm-mgr:usernames/adm-mgr:username/adm-mgr:access-time-ra'
              + 'nge '+"\n"
              + '(2)Add a leaf node. path:/adm-mgr:configuration/adm-mgr:adm-mg'
              + 'r/adm-mgr:usernames/adm-mgr:username/adm-mgr:access-time-range'
              + '/adm-mgr:time-range-name'
                ;
  }
  revision 2022-06-16 {
    description "(1)Add the projects PC(MSE) supported by feature node \"unlock"
              + "-root-user\".
\n(2)Add feature node 'show-root-user' and delet"
              + "e all projects except MSR(ASR,ZSRV2),SWITCH(59) and PC(MSE)."
                ;
  }
  revision 2022-06-06 {
    description 'Support username dictionary.'+"\n"
              + '(1)Add a container node. path:/configuration/adm-mgr/global-co'
              + 'nfiguration/username-dictionary.'+"\n"
              + '(2)Add a list node. path:/configuration/adm-mgr/global-configu'
              + 'ration/username-dictionary/username.'+"\n"
              + '(3)Add a leaf node. path:/configuration/adm-mgr/global-configu'
              + 'ration/username-dictionary/username/name.'+"\n"
              + '(4)Add a leaf node. path:/configuration/adm-mgr/global-configu'
              + 'ration/strong-username/dictionary.'
                ;
  }
  revision 2022-05-27 {
    description 'Add the projects HighEndRouter(T8000),HighEndPacket(15K) and M'
              + 'SE(M6000) supported by feature node "local-user-offline"'
                ;
  }
  revision 2022-05-10 {
    description 'Add the projects OTN(7000/M721) and PC(MSE) supported by featu'
              + 're node "root-user"'
                ;
  }
  revision 2022-04-22 {
    description 'Add the project FN(C89E) supported by feature node "password-d'
              + 'uration"'
                ;
  }
  revision 2022-04-18 {
    description 'Add the projects FN(C89E) supported by feature node "local-use'
              + 'r-offline"'
                ;
  }
  revision 2022-02-22 {
    description "(1)Add feature node 'unlock-root-user' and delete all projects"
              + " except MSR and SWITCH(59).
\n(2)Delete all projects except MS"
              + "R and SWITCH(59) supported by feature node 'root-user'."
                ;
  }
  revision 2022-01-10 {
    description '(1)Add a new leaf node.Path:/configuration/adm-mgr/authorizati'
              + 'on-templates/author-template/login-type-allowed/grpc'+"\n"
              + '(2)Add Enum Item.Path:/operation/adm-mgr/clear-online-user/cle'
              + 'ar-user/user-access-info/access-type'
                ;
  }
  revision 2021-12-14 {
    description 'Add the projects SWITCH(59E) supported by feature node "clear-'
              + 'online-user" and "local-user-offline"'
                ;
  }
  revision 2021-10-21 {
    description 'Support to control whether the FTP AAA authentication function'
              + ' is enabled.'+"\n"
              + 'Add container node. path:/configuration/adm-mgr/global-configu'
              + 'ration/ftp-aaa-authentication.'+"\n"
              + 'Add leaf node. path:/configuration/adm-mgr/global-configuratio'
              + 'n/ftp-aaa-authentication/enabled.'
                ;
  }
  revision 2021-10-20 {
    description '99X project no longer supports container "access-only" and its'
              + ' leafs by feature node "access-only"'
                ;
  }
  revision 2021-10-18 {
    description 'Add the projects T8000,15K,V6000(vBras/vRouter/CDB),MSE(M6000/'
              + 'M6000-S) supported by feature node "remind-before-expire"'
                ;
  }
  revision 2021-09-21 {
    description "Modifiy the type of '/configuration/adm-mgr/global-configurati"
              + "on/enable/enable-level-secret/enable-secret/password' length r"
              + "ange  from '3-200' to '8-200'."
                ;
  }
  revision 2021-06-28 {
    description '(1)support configuring the expiration policy for the enable se'
              + 'cret by netconf.'+"\n"
              + '(2)Add container node. path:/configuration/adm_mgr/global-conf'
              + 'igurationenable/enable/enable-secret-expire.'
                ;
  }
  revision 2021-05-07 {
    description '(1)All projects support the feature node "global-user-aging"'+"\n"
              + '(2)All projects support the feature node "user-aging"'
                ;
  }
  revision 2021-04-06 {
    description '(1)Support remote server user continuous authentication failur'
              + 'e lock. Add leaf node. path:/configuration/adm-mgr/global-conf'
              + 'iguration/login-restriction/user-authen-restriction/period.'+"\n"
              + '(2)Add a new leaf node.Path:/configuration/adm-mgr/usernames/u'
              + 'sername/user-authen-restriction/period.'
                ;
  }
  revision 2021-03-10 {
    description '(1) Add the projects PTN(61V5_1) supported by feature node "us'
              + 'er-authen-restriction"'
                ;
  }
  revision 2021-02-08 {
    description '(1) Add container node. path:/configuration/adm_mgr/authentica'
              + 'tion-templates/authen-template/authentication-method/ascii.'+"\n"
              + '(2) Add leaf node. path:/configuration/adm_mgr/authentication-'
              + 'templates/authen-template/authentication-method/ascii/pap.'+"\n"
              + '(3) Add leaf node. path:/configuration/adm_mgr/authentication-'
              + 'templates/authen-template/authentication-method/ascii/chap.'
                ;
  }
  revision 2021-02-07 {
    description '(1)Change the description of node path:/state/adm-mgr/rootuser'
              + '-info/encrypt-password.'
                ;
  }
  revision 2021-01-28 {
    description '(1) Add the projects PTN(65V5/6700/61-SSP) OTN(7000/8700/9700)'
              + ' supported by feature node "clear-online-user"'+"\n"
              + '(2) Add the projects PTN(61-SSP)  supported by feature node "r'
              + 'emind-before-expire"'
                ;
  }
  revision 2020-11-26 {
    description "(1)Add container node path:/configuration/adm-mgr/usernames/us"
              + "ername/change-password.
\n(2)Add leaf node. path:/configuratio"
              + "n/adm-mgr/usernames/username/change-password/min-period.
\n(3)"
              + "Extend the length range of node '/configuration/adm-mgr/global"
              + "-configuration/password/root-user/password' from 6-200 to 6-25"
              + "4."
                ;
  }
  revision 2020-11-17 {
    description "(1) Change the projects supported by feature node \"maxlen-len"
              + "gth\"
\n(2)Extend the length range of node '/configuration/adm"
              + "-mgr/global-configuration/enable/enable-level-secret/enable-se"
              + "cret/password' from 3-16,24-200 to 3-200.
\n(3)Extend the leng"
              + "th range of node '/configuration/adm-mgr/global-configuration/"
              + "user-groups/user-group/encrypted-password' from 64-200 to 64-2"
              + "54.
\n(4)Extend the length range of node '/configuration/adm-m"
              + "gr/global-configuration/user-groups/user-group/unencrypted-pas"
              + "sword' from 3-32 to 3-128.
\n(5)Change the range of node '/con"
              + "figuration/adm-mgr/global-configuration/password/strong-passwo"
              + "rd/length' from 6-64 to 6-128.
\n(6)Change the range of node '"
              + "/configuration/adm-mgr/global-configuration/password/strong-pa"
              + "ssword/max-length' from 8-64 to 8-128.
\n(7)Extend the length "
              + "range of node'/configuration/adm-mgr/global-configuration/loca"
              + "l-user-change-password/old-password'from 3-64 to 3-128.
\n(8)E"
              + "xtend the length range of node'/configuration/adm-mgr/global-c"
              + "onfiguration/local-user-change-password/new-password'from 3-64"
              + " to 3-128.
\n(9)Extend the length of node '/configuration/adm-"
              + "mgr/usernames/username/cleartext-password' from 3-64 to 3-128."
              + "
\n(10)Extend the length of node '/configuration/adm-mgr/usern"
              + "ames/username/encrypted-password' from 64-200 to 64-254.
\n(11"
              + ")Extend the length of node '/configuration/adm-mgr/usernames/u"
              + "sername/irreversible-cleartext-password' from 3-64 to 3-128.
\n"
              + "(12)Extend the length of node '/configuration/adm-mgr/username"
              + "s/username/irreversible-encrypted-password' from 63-200 to 63-"
              + "254."
                ;
  }
  revision 2020-11-13 {
    description "(1) C600 project does not support 'root-user' and 'rootuser-in"
              + "fo'"
                ;
  }
  revision 2020-11-02 {
    description "(1)Change the node '/configuration/adm-mgr/usernames/username/"
              + "cleartext-password' datatype from 'plaintext' to \"chars\"
\n("
              + "2)Change the node '/configuration/adm-mgr/usernames/username/i"
              + "rreversible-cleartext-password' datatype from 'plaintext' to \""
              + "chars\"
\n(3)Change the node '/configuration/adm-mgr/usernames"
              + "/username/encrypted-password' datatype from 'ciphertext' to \""
              + "chars\"
\n(4)Change the node '/configuration/adm-mgr/usernames"
              + "/username/irreversible-encrypted-password' datatype from 'ciph"
              + "ertext' to \"chars\""
                ;
  }
  revision 2020-10-14 {
    description "(1)Add container node path:/configuration/adm-mgr/global-confi"
              + "guration/password/password-duration.
\n(2)Add leaf node. path:"
              + "/configuration/adm-mgr/global-configuration/password/password-"
              + "duration/password-duration.
\n(3)Add leaf node. path:/configur"
              + "ation/adm-mgr/global-configuration/password/password-duration/"
              + "remind-before-expire.
\n(4)Add feature node 'password-duration"
              + "'."
                ;
  }
  revision 2020-09-21 {
    description '(1)node path: /state/adm-mgr/user-info/encrypt-password,The ci'
              + 'phertext of the password is changed from ciphertext character '
              + 'string to ******.&#xD;'+"\n"
              + '(2)node path: /state/adm-mgr/rootuser-info/encrypt-password,Th'
              + 'e ciphertext of the password is changed from ciphertext charac'
              + 'ter string to ******.'
                ;
  }
  revision 2020-08-31 {
    description '(1)Add container node path:/configuration/adm-mgr/global-confi'
              + 'guration/change-password.'+"\n"
              + '(2)Add leaf node. path:/configuration/adm-mgr/global-configura'
              + 'tion/change-password/max-times-per-day.'
                ;
  }
  revision 2020-08-17 {
    description "(1)Add container node path:/configuration/adm-mgr/global-confi"
              + "guration/local-user-offline.
\n(2)Add leaf node. path:/configu"
              + "ration/adm-mgr/global-configuration/local-user-offline/passwor"
              + "d-changed.
\n(3)Add leaf node. path:/configuration/adm-mgr/glo"
              + "bal-configuration/local-user-offline/locked.
\n(4)Add feature "
              + "node 'local-user-offline'."
                ;
  }
  revision 2020-07-07 {
    description "(1)Change the node '/configuration/adm-mgr/usernames/username/"
              + "cleartext-password' datatype from 'chars' to \"plaintext\"
\n("
              + "2)Change the node '/configuration/adm-mgr/usernames/username/i"
              + "rreversible-cleartext-password' datatype from 'chars' to \"pla"
              + "intext\"
\n(3)Change the node '/configuration/adm-mgr/username"
              + "s/username/encrypted-password' datatype from 'chars' to \"ciph"
              + "ertext\"
\n(4)Change the node '/configuration/adm-mgr/username"
              + "s/username/irreversible-encrypted-password' datatype from 'cha"
              + "rs' to \"ciphertext\"
\n(5)Change the node '/configuration/adm"
              + "-mgr/global-configuration/user-groups/user-group/unencrypted-p"
              + "assword' datatype from 'chars' to \"plaintext\"
\n(6)Change th"
              + "e node '/configuration/adm-mgr/global-configuration/user-group"
              + "s/user-group/encrypted-password' datatype from 'chars' to \"pl"
              + "aintext\"
\n(7)Extend the length range of node '/configuration"
              + "/adm-mgr/global-configuration/user-groups/user-group/encrypted"
              + "-password' from 64-67 to 64-200"
                ;
  }
  revision 2020-07-03 {
    description "(1)Add feature node 'chmode-access'
\n(2)Add a new container n"
              + "ode. Path:/configuration/adm-mgr/authorization-templates/autho"
              + "r-template/chmode-access
\n(3)Add list node. Path:/configurati"
              + "on/adm-mgr/authorization-templates/author-template/chmode-acce"
              + "ss/chmode
\n(4)Add leaf node. Path:/configuration/adm-mgr/auth"
              + "orization-templates/author-template/chmode-access/chmode/absol"
              + "ute-path
\n(5)Add leaf node. Path:/configuration/adm-mgr/autho"
              + "rization-templates/author-template/chmode-access/chmode/operat"
              + "ion-mode"
                ;
  }
  revision 2020-06-10 {
    description "(1)Add feature node for '/configuration/adm-mgr/usernames/user"
              + "name/password-recover-remind'
\n(2) 9900 and 5960 project does"
              + " not support 'password-recover-remind'"
                ;
  }
  revision 2019-10-31 {
    description "(1)Add RPC node 'unlock-local-user/input/username'
\n(2)Add RP"
              + "C node 'unlock-root-user'
\n(3)Add a new container node.Path:/"
              + "configuration/adm-mgr/usernames/username/user-authen-restricti"
              + "on.
\n(4)Add a new leaf node.Path:/configuration/adm-mgr/usern"
              + "ames/username/user-authen-restriction/fail-times.
\n(5)Add a n"
              + "ew leaf node.Path:/configuration/adm-mgr/usernames/username/us"
              + "er-authen-restriction/lock-time.
\n(6)Change the range of node"
              + " 'configuration/adm-mgr/global-configuration/login-restriction"
              + "/user-authen-restriction/fail-times' from 3-16 to 0-16.
\n(7)A"
              + "dd a default value for node 'configuration/adm-mgr/global-conf"
              + "iguration/login-restriction/user-authen-restriction/fail-times"
              + "'. 
\n(8)Add a default value for node 'configuration/adm-mgr/g"
              + "lobal-configuration/login-restriction/user-authen-restriction/"
              + "lock-time'.
\n(9)Delete presence for node 'configuration/adm-m"
              + "gr/global-configuration/login-restriction/user-authen-restrict"
              + "ion'."
                ;
  }
  revision 2019-09-11 {
    description "(1)Add container node '/configuration/adm-mgr/global-configura"
              + "tion/local-user-change-password'.
\n(2)Add leaf node. path:/co"
              + "nfiguration/adm-mgr/global-configuration/local-user-change-pas"
              + "sword/old-password.
\n(3)Add leaf node. path:/configuration/ad"
              + "m-mgr/global-configuration/local-user-change-password/new-pass"
              + "word."
                ;
  }
  revision 2019-08-20 {
    description 'Add a new leaf node.Path:/configuration/adm-mgr/usernames/user'
              + 'name/change-password-expired.'
                ;
  }
  revision 2019-08-12 {
    description "(1)Extend the length range of node '/configuration/adm-mgr/glo"
              + "bal-configuration/enable/enable-level-secret/enable-secret/pas"
              + "sword' from 24,63 to 24-200.
\n(2)Extend the length range of n"
              + "ode '/configuration/adm-mgr/global-configuration/user-groups/u"
              + "ser-group/encrypted-password' from 64 to 64-67.
\n(3)Extend th"
              + "e length range of node '/configuration/adm-mgr/global-configur"
              + "ation/password/root-user/password' from 6-64 to 6-200.
\n(4)Ex"
              + "tend the length range of node '/configuration/adm-mgr/username"
              + "s/username/encrypted-password' from 64-128 to 64-200.
\n(5)Ext"
              + "end the length range of node '/configuration/adm-mgr/usernames"
              + "/username/irreversible-encrypted-password' from 63-64 to 63-20"
              + "0.
\n(6)Extend the length range of node '/configuration/adm-mg"
              + "r/usernames/username/password-recover-remind/answer' from 1-50"
              + " to 1-200.
\n(7)Extend the length range of node '/state/adm-mg"
              + "r/user-info/encrypt-password' from 1-128 to 1-200.
\n(8)Extend"
              + " the length range of node '/state/adm-mgr/rootuser-info/encryp"
              + "t-password' from 63-64 to 1-200."
                ;
  }
  revision 2019-06-28 {
    description "Add the length value 63 for leaf node '/configuration/adm-mgr/"
              + "global-configuration/enable/enable-level-secret/enable-secret/"
              + "password'"
                ;
  }
  revision 2019-05-27 {
    description "(1)Change the range of node '/configuration/adm-mgr/global-con"
              + "figuration/password/strong-password/length' from 6-32 to 6-64."
              + "
\n(2)Change the range of node '/configuration/adm-mgr/global-"
              + "configuration/password/strong-password/max-length' from 8-32 t"
              + "o 8-64.
\n(3)Change the length of node '/configuration/adm-mgr"
              + "/usernames/username/cleartext-password' from 3-32 to 3-64.
\n("
              + "4)Change the length of node '/configuration/adm-mgr/usernames/"
              + "username/encrypted-password' from 64 to 64 or 128.
\n(5)Change"
              + " the length of node '/configuration/adm-mgr/usernames/username"
              + "/irreversible-cleartext-password' from 3-32 to 3-64.
\n(6)Chan"
              + "ge the length of node '/state/adm-mgr/user-info/encrypt-passwo"
              + "rd' from 1-64 to 1-128."
                ;
  }
  revision 2019-05-16 {
    description "Change the length of node '/state/adm-mgr/rootuser-info/encryp"
              + "t-password' from 64 to 63-64."
                ;
  }
  revision 2019-04-09 {
    description "1)Change the length of node '/configuration/adm-mgr/usernames/"
              + "username/irreversible-encrypted-password' from 64 to 63-64
\n2"
              + ")Change the length of node '/configuration/adm-mgr/global-conf"
              + "iguration/password/root-user/password' from 64 to 63-64"
                ;
  }
  revision 2019-01-03 {
    description "(1)Add feature node 'remind-before-expire'
\n(2)Add leaf node "
              + "'/configuration/adm-mgr/usernames/username/remind-before-expir"
              + "e'"
                ;
  }
  revision 2018-10-08 {
    description "(1)Add feature node 'max-length'
\n(2)Add leaf node '/configur"
              + "ation/adm-mgr/global-configuration/password/strong-password/ma"
              + "x-length'"
                ;
  }
  revision 2018-07-23 {
    description "(1)Add leaf node '/configuration/adm-mgr/authorization-templat"
              + "es/author-template/login-type-allowed/console'
\n(2)Add leaf n"
              + "ode '/configuration/adm-mgr/authorization-templates/author-tem"
              + "plate/login-type-allowed/only-telnet'"
                ;
  }
  revision 2018-07-17 {
    description "(1)Obsolete container node '/configuration/adm-mgr/global-conf"
              + "iguration/password/strong-password/character' 
\n(2)Add choice"
              + " node '/configuration/adm-mgr/global-configuration/password/st"
              + "rong-password/character-strategy',
\nAdd container node '/conf"
              + "iguration/adm-mgr/global-configuration/password/strong-passwor"
              + "d/character-type',
\nAdd container node '/configuration/adm-mg"
              + "r/global-configuration/password/strong-password/character-set-"
              + "num',
\nAdd leaf node '/configuration/adm-mgr/global-configura"
              + "tion/password/strong-password/character-set/min-num'"
                ;
  }
  revision 2018-05-19 {
    description "The feature node 'date-check' surpport switch project 99 and 5"
              + "960.
\nAdd container node '/configuration/adm-mgr/global-confi"
              + "guration/global-user-aging'.
\nAdd leaf node '/configuration/a"
              + "dm-mgr/global-configuration/global-user-aging/day'.
\nAdd cont"
              + "ainer node '/configuration/adm-mgr/usernames/username/user-agi"
              + "ng'.
\nAdd leaf node '/configuration/adm-mgr/usernames/usernam"
              + "e/user-aging/day'.
\nAdd leaf node '/state/adm-mgr/user-info/u"
              + "ser-aging-state'.
\nAdd leaf node '/state/adm-mgr/user-info/lo"
              + "cked-state'.
\nAdd container node '/operation/adm-mgr/activate"
              + "-user'.
\nAdd leaf node '/operation/adm-mgr/activate-user/user"
              + "name'.
\nAdd feature node 'global-user-aging'.
\nAdd feature n"
              + "ode 'user-aging'.
\nAdd feature node 'activate-user'."
                ;
  }
  revision 2018-04-17 {
    description "Add leaf nodes 'configuration/adm_mgr/global-configuration/pas"
              + "sword/strong-password/date-check' and feature node 'date-check"
              + "'"
                ;
  }
  revision 2018-03-29 {
    description "Add container node 'global-configuration/strong-username' and "
              + "leaf node 'global-configuration/strong-username/min-length'"
                ;
  }
  revision 2018-03-14 {
    description "Add leaf node 'protocol-type','authentication-method' and 'aut"
              + "horization-method' for 'state/adm-mgr/online-user'"
                ;
  }
  revision 2018-01-31 {
    description "Add container node '/configuration/adm_mgr/global-configuratio"
              + "n/password/strong-password/username-related-check'"
                ;
  }
  revision 2017-11-25 {
    description "Add leaf nodes 'configuration/adm_mgr/global-configuration/pas"
              + "sword/strong-password-check/status/enable/enable' and 'configu"
              + "ration/adm_mgr/global-configuration/password/strong-password-c"
              + "heck/status/disable/disable'"
                ;
  }
  revision 2017-10-13 {
    description "Add leaf nodes 'irreversible-cleartext-password' and 'irrevers"
              + "ible-encrypted-password' for choice node '/adm-mgr:configurati"
              + "on/adm-mgr:adm-mgr/adm-mgr:usernames/adm-mgr:username/adm-mgr:"
              + "password/'"
                ;
  }
  revision 2017-06-01 {
    description "Modifiy the type of '/adm-mgr:state/adm-mgr:adm-mgr/adm-mgr:lo"
              + "gin-fail-response-info/adm-mgr:username' length range  from '1"
              + "-65' to '0-65'."
                ;
  }
  revision 2017-01-04 {
    description "Cancel Mandatory of 'configuration/adm_mgr/global-configuratio"
              + "n/login-ascii/authortication-template'"
                ;
  }
  revision 2015-03-10 {
    description "Modifiy the type of '/adm-mgr:state/adm-mgr:adm-mgr/adm-mgr:us"
              + "er-info/adm-mgr:username','/adm-mgr:state/adm-mgr:adm-mgr/adm-"
              + "mgr:authen-restriction-info/adm-mgr:username','/adm-mgr:state/"
              + "adm-mgr:adm-mgr/adm-mgr:online-user/adm-mgr:username','/adm-mg"
              + "r:state/adm-mgr:adm-mgr/adm-mgr:login-fail-response-info/adm-m"
              + "gr:username', and '/adm-mgr:state/adm-mgr:adm-mgr/adm-mgr:root"
              + "user-info/adm-mgr:username' from 'string' to 'ncd:string-all'."
                ;
  }
  revision 2015-02-28 {
    description "Add container node of state type '/adm-mgr:state/adm-mgr:adm-m"
              + "gr/adm-mgr:rootuser-info'"
                ;
  }
  revision 2015-02-10 {
    description "(1)Add the description of '/operation/adm-mgr/clear-online-use"
              + "r/access-type/' enumeration items 'cli','qx','tl1','xml' and '"
              + "web'.
\n(2)Modify feature name from 'clear-on-line-user' to 'c"
              + "lear-online-user'"
                ;
  }
  revision 2015-01-14 {
    description "(1)Delete default value of 'configuration/adm-mgr/global-confi"
              + "guration/login-restriction/login-failure-alarm/' leaf 'every-t"
              + "imes'
\n(2)Modify the mandatory value of 'configuration/adm-mg"
              + "r/global-configuration/login-restriction/login-failure-alarm/'"
              + " leaf 'every-times' from false to true.
\n(3)Modify word spell"
              + "ing error,replace word 'leafs' for 'leaves'."
                ;
  }
  revision 2014-08-04 {
    description "(1)Modify the mandatory value of 'configuration/adm-mgr/userna"
              + "mes/username/enable-type/authen-type/aaa/' leaf 'aaa-authentic"
              + "ation' from false to true.
\n(2)Modify the mandatory value of "
              + "'configuration/adm-mgr/usernames/username/enable-type/authen-t"
              + "ype/aaa/' leaf 'authentication-template' from false to true."
                ;
  }
  revision 2014-06-30 {
    description "(1)Modify the length range of 'configuration/adm-mgr/state/log"
              + "in-fail-response-info/' leaf 'login-time' from 1 to 40."
                ;
  }
  revision 2014-06-06 {
    description "(1)Add Presence value of 'configuration/adm-mgr/global-configu"
              + "ration/login-restriction/user-authen-restriction' Container wi"
              + "th 'Mandatory leaves are included.',
\n(2)Modify Mandatory val"
              + "ue of 'configuration/adm-mgr/global-configuration/login-restri"
              + "ction/user-authen-restriction/' leaf 'fail-times' and 'lock-ti"
              + "me' with true.
\n(3)Modify the Type value of 'configuration/ad"
              + "m-mgr/state/login-fail-response-info/' leaf 'terminal-type' fr"
              + "om unit8 to enumeration.
\n(4)Delete the enum value 'normal-mo"
              + "de' of 'state/adm-mgr/login-state-info/' leaf 'current-mode', "
              + "change enum value 'monitor-mode' to 'watch-mode' of this leaf."
                ;
  }
  revision 2014-05-15 {
    description "(1)Modify default value of 'configuration\adm-mgr\usernames\us"
              + "ername' leaf 'once-password'and 'lock',
\n(2)Modify default va"
              + "lue of 'configuration\adm-mgr\authorization-templates\author-t"
              + "emplate' leaf 'local-cmdgroup-mode'."
                ;
  }
  revision 2014-04-18 {
    description 'Initial version.'
                ;
  }
  feature clear-online-user {
    description 'Clear the online user.'
                ;
  }
  feature root-user {
    description 'Configure root user password.'
                ;
  }
  feature date-check {
    description 'Set password date-related check'
                ;
  }
  feature activate-user {
    description 'Activate local user.'
                ;
  }
  feature global-user-aging {
    description 'The configuration of global user-aging.'
                ;
  }
  feature user-aging {
    description "The configuration of user's user-aging."
                ;
  }
  feature max-length {
    description 'Set the maximum length of the password'
                ;
  }
  feature remind-before-expire ;
  feature password-recover-remind {
    description 'Configure the question and answer for password recovery.'
                ;
  }
  feature user-authen-restriction {
    description "The configuration of user's user-authen-restriction."
                ;
  }
  feature chmode-access ;
  feature local-user-offline ;
  feature password-duration ;
  feature access-only {
    ncd:revise-date 2021-10-20 ;
  }
  feature unlock-root-user {
    ncd:revise-date 2022-02-22 ;
  }
  feature show-root-user {
    ncd:revise-date 2022-06-16 ;
  }
  feature access-time-range {
    description 'The Access time range of user.'
                ;
    ncd:revise-date 2022-07-22 ;
  }
  container configuration {
    description 'The configuration model of ADM_MGR.'
                ;
    container adm-mgr {
      description 'The configuration model of ADM_MGR.'
                  ;
      container global-configuration {
        description 'The global configuration of ADM_MGR.'
                    ;
        container account-switch {
          description 'Account switch.'
                      ;
          choice switch {
            description 'To configure the command account swith.'
                        ;
            default switch-off ;
            case switch-on {
              description 'To open command account function.'
                          ;
              leaf on {
                description 'To open account function.'
                            ;
                type empty ;
                mandatory true ;
              }
              leaf accounting-template {
                description 'To bind AAA account template'
                            ;
                type uint16 {
                  range 2001..2128 ;
                }
                mandatory true ;
              }
            }
            case switch-off {
              description 'To close command account function.'
                          ;
              leaf off {
                description 'To close account function.'
                            ;
                type empty ;
              }
            }
          }
        }
        container login-ascii {
          description 'To configure ASCII authentication type.'
                      ;
          presence 'Mandatory leaves are included.'
                   ;
          leaf ascii {
            description 'To configure ASCII authentication type.'
                        ;
            type empty ;
            mandatory true ;
          }
          leaf authentication-template {
            description 'To configure the global authentication template number.'
                        ;
            type uint8 {
              range 1..128 ;
            }
            mandatory true ;
          }
          leaf authortication-template {
            description 'To configure the global authorization template number.'
                        ;
            type uint8 {
              range 1..128 ;
            }
          }
        }
        container enable {
          description 'To configure enable authentication type.'
                      ;
          container global-enable-type {
            description 'To configure global enable authentication type.'
                        ;
            choice authen-type {
              description 'The global enable authentication type.'
                          ;
              default local ;
              case local {
                description 'Local authentication.'
                            ;
                leaf local-authentication {
                  description 'Local authentication.'
                              ;
                  type empty ;
                }
              }
              case aaa {
                description 'AAA authentication.'
                            ;
                leaf aaa-authentication {
                  description 'AAA authentication.'
                              ;
                  type empty ;
                  mandatory true ;
                }
                leaf authentication-template {
                  description 'To Configure authentication template.'
                              ;
                  type uint8 {
                    range 1..128 ;
                  }
                  mandatory true ;
                }
              }
            }
          }
          container enable-level-secret {
            description 'To configure enable password and privilege level.'
                        ;
            list enable-secret {
              description 'To configure enable password and privilege level.'
                          ;
              max-elements 18 ;
              key level ;
              leaf level {
                description 'The privilege level.'
                            ;
                type uint32 {
                  range 1..18 ;
                }
              }
              choice password-type {
                description 'The password type'
                            ;
                mandatory true ;
                case encrypted {
                  description 'The encrypted password.'
                              ;
                  leaf encrypted-password {
                    description 'The encrypted password.'
                                ;
                    type empty ;
                  }
                }
                case unencrypted {
                  description 'The unencrypted password.'
                              ;
                  leaf unencrypted-password {
                    description 'The unencrypted password.'
                                ;
                    type empty ;
                  }
                }
              }
              leaf password {
                description 'Set the password for enable authentication. The le'
                          + 'ngth of cleartext is 8~128 characters, the length '
                          + 'of ciphertext is 24 or 63 characters.'
                            ;
                type string {
                  length 8..200 ;
                }
                mandatory true ;
              }
            }
          }
          container enable-secret-expire {
            description 'Set the expiration policy for the enable secret, inclu'
                      + 'ding the expire day(s) and the prompt day(s).'
                        ;
            presence 'enable-secret expire prompt'
                     ;
            choice expire {
              description 'Set the expire day(s) and the prompt day(s) of the e'
                        + 'xpiration policy.'
                          ;
              case never-expire {
                description 'Set the expiration policy to never expire.'
                            ;
                leaf never-expire {
                  description 'Never expire.'
                              ;
                  type empty ;
                  mandatory true ;
                }
              }
              case expire-days {
                description 'Set the expiration policy.'
                            ;
                leaf expire-days {
                  description 'The expire day(s).'
                              ;
                  type uint32 {
                    range 1..360 ;
                  }
                  mandatory true ;
                }
                leaf prompt-days {
                  description 'The prompt day(s).'
                              ;
                  type uint32 {
                    range 1..180 ;
                  }
                  mandatory true ;
                }
              }
            }
            ncd:revise-date 2021-06-28 ;
          }
          container enable-strong-password {
            description 'To config enable password same consecutive character m'
                      + 'ax length.'
                        ;
            presence enable-strong-password ;
            leaf same-consecutive-length {
              description 'Enable password same consecutive character max lengt'
                        + 'h.'
                          ;
              type uint8 {
                range 3..5 {
                  description 'Same consecutive max length'
                              ;
                }
              }
              mandatory true ;
            }
            ncd:revise-date 2022-09-25 ;
          }
        }
        leaf default-privilege-level {
          description 'To configure default privilege level.'
                      ;
          type uint8 {
            range 0..15 ;
          }
          default 0 ;
        }
        container default-user {
          description 'The default configuration'
                      ;
          leaf bind-authentication-template {
            description 'To configure default user authentication template numb'
                      + 'er.'
                        ;
            type uint8 {
              range 1..128 ;
            }
          }
          leaf bind-authortication-template {
            description 'To configure default user authortication template numb'
                      + 'er.'
                        ;
            type uint8 {
              range 1..128 ;
            }
          }
          container enable-type {
            description 'To configure default enable authentication type.'
                        ;
            choice authen-type {
              description 'To configure default enable authentication type.'
                          ;
              default local ;
              case local {
                description 'Default user local authentication.'
                            ;
                leaf local-authentication {
                  description 'Default user local authentication.'
                              ;
                  type empty ;
                }
              }
              case aaa {
                description 'Default user AAA authentication.'
                            ;
                leaf aaa-authentication {
                  description 'Default user AAA authentication.'
                              ;
                  type empty ;
                  mandatory true ;
                }
                leaf authentication-template {
                  description 'To Configure default user authentication templat'
                            + 'e.'
                              ;
                  type uint8 {
                    range 1..128 ;
                  }
                  mandatory true ;
                }
              }
            }
          }
        }
        container user-groups {
          description 'To configure user group'
                      ;
          list user-group {
            description 'Configure user group information for PPP authenticatio'
                      + 'n.'
                        ;
            key 'group-name username'
                ;
            leaf group-name {
              description 'Configure user group name.'
                          ;
              type string {
                length 1..15 ;
              }
            }
            leaf username {
              description 'Configure the user name in the group.'
                          ;
              type string {
                length 1..16 ;
              }
            }
            choice password-type {
              description 'To configure the password.'
                          ;
              case encrypted {
                description 'To configure the encrypted password.'
                            ;
                leaf encrypted-password {
                  description 'Configure the encrypted password of a user in a '
                            + 'group.'
                              ;
                  type string {
                    length 64..254 ;
                  }
                }
              }
              case unencryted {
                description 'To configure the unencrypted password.'
                            ;
                leaf unencrypted-password {
                  description 'Configure the unencrypted password of a user in '
                            + 'a group.'
                              ;
                  type string {
                    length 3..128 ;
                  }
                }
              }
            }
          }
        }
        container password {
          description 'The configuration of password-related.'
                      ;
          container root-user {
            description 'Configuring the Password of the root User, The root pa'
                      + 'ssword cannot be deleted.'
                        ;
            leaf password {
              if-feature root-user ;
              description 'To configure root user password. The length of clear'
                        + 'text is 6~128 characters.'
                          ;
              type string {
                length 6..254 ;
              }
            }
          }
          container strong-password {
            description 'Set the strong password strategy'
                        ;
            leaf length {
              description 'set the minimum length of strong password'
                          ;
              type uint8 {
                range 6..128 ;
              }
            }
            choice character-strategy {
              description 'Set the character strategy of strong password.'
                          ;
              case character-type {
                description 'Set the character combination of strong password.'
                            ;
                container character-type {
                  description 'Set the character combination of strong password.'
                              ;
                  leaf number {
                    description 'The number'
                                ;
                    type empty ;
                  }
                  leaf capital {
                    description 'The capital'
                                ;
                    type empty ;
                  }
                  leaf lowercase {
                    description 'The lowercase'
                                ;
                    type empty ;
                  }
                  leaf special {
                    description 'The special character'
                                ;
                    type empty ;
                  }
                }
              }
              case character-set-num {
                description 'Set the number of character sets that must be incl'
                          + 'uded in the password.'
                            ;
                container character-set-num {
                  description 'Set the number of character types that must be i'
                            + 'ncluded in the password.'
                              ;
                  leaf min-num {
                    description 'The minimum number of character sets'
                                ;
                    type uint8 {
                      range 2..4 ;
                    }
                  }
                }
              }
              ncd:revise-date 2018-07-17 ;
            }
            container character {
              status obsolete {
                ncd:revise-date 2018-07-17 ;
              }
              description 'set the character combination of strong password'
                          ;
              leaf number {
                description 'The number'
                            ;
                type empty ;
              }
              leaf capital {
                description 'The capital'
                            ;
                type empty ;
              }
              leaf lowercase {
                description 'The lowercase'
                            ;
                type empty ;
              }
              leaf special {
                description 'The special character'
                            ;
                type empty ;
              }
            }
            container username-related-check {
              description 'Set username-related check in password'
                          ;
              container substring {
                description 'Check the substring'
                            ;
                presence 'check substring'
                         ;
                leaf substring {
                  description 'Check the substring associated with username(cas'
                            + 'e insensitive)'
                              ;
                  type enumeration {
                    enum enable {
                      value 1 ;
                      description 'Enable substring check'
                                  ;
                    }
                    enum disable {
                      value 2 ;
                      description 'Disable substring check'
                                  ;
                    }
                  }
                  mandatory true ;
                }
              }
              leaf inverse {
                description 'Check the inverse substring associated with userna'
                          + 'me'
                            ;
                type enumeration {
                  enum enable {
                    value 1 ;
                    description 'Enable inverse check'
                                ;
                  }
                  enum disable {
                    value 2 ;
                    description 'Disable inverse check'
                                ;
                  }
                }
                default disable ;
              }
              ncd:revise-date 2018-01-31 ;
            }
            leaf date-check {
              if-feature date-check ;
              description 'Set password date-related check. Any date ranging fr'
                        + 'om 1 January 1970 to 31 December 2037 is not allowed'
                        + '. The date formats include: YYYYMMDD, MMDDYYYY, DDMM'
                        + 'YYYY, YYYY-MM-DD, MM-DD-YYYY, DD-MM-YYYY'
                          ;
              type enumeration {
                enum enable {
                  value 1 ;
                  description 'Enable date-related check in password'
                              ;
                }
                enum disable {
                  value 2 ;
                  description 'Disable date-related check in password'
                              ;
                }
              }
              default disable ;
              ncd:revise-date 2018-04-17 ;
            }
            leaf max-length {
              if-feature max-length ;
              description 'Set the maximum length of the password'
                          ;
              type uint8 {
                range 8..128 ;
              }
              ncd:revise-date 2018-10-08 ;
            }
            leaf dictionary {
              description 'Enable password dictionary check.'
                          ;
              type empty ;
              ncd:revise-date 2022-08-01 ;
            }
          }
          container strong-password-check {
            description 'The status of strong password check'
                        ;
            choice status {
              description 'The status of strong password check'
                          ;
              default enable ;
              case enable {
                description 'Open strong password check'
                            ;
                leaf enable {
                  description 'Open strong password check'
                              ;
                  type empty ;
                }
              }
              case disable {
                description 'Close strong password check'
                            ;
                leaf disable {
                  description 'Close strong password check'
                              ;
                  type empty ;
                }
              }
            }
            ncd:revise-date 2017-11-25 ;
          }
          leaf duplicated-password {
            description 'To configure the interval times of last same passwords.'
                        ;
            type uint8 {
              range 2..10 ;
            }
            default 5 ;
          }
          container password-duration {
            if-feature password-duration ;
            description 'The configuration of password duration related.'
                        ;
            presence password-duration ;
            leaf password-duration {
              description 'Set the number of days the password is valid.'
                          ;
              type uint16 {
                range 1..360 ;
              }
              units day ;
              mandatory true ;
            }
            leaf remind-before-expire {
              description 'Set the number of days to remind before the password'
                        + ' expires. The default is 3 days. Allows you to set t'
                        + 'he reminder days to be greater than the number of da'
                        + 'ys the password is valid.'
                          ;
              type uint16 {
                range 1..360 ;
              }
              default 3 ;
            }
            ncd:revise-date 2020-10-14 ;
          }
          container password-dictionary {
            description 'The Configuration of password dictionary.'
                        ;
            list password {
              description 'Establish password.'
                          ;
              max-elements 128 ;
              key password ;
              leaf password {
                description 'Password in the password dictionary.'
                            ;
                type string {
                  length 3..128 ;
                }
              }
            }
            ncd:revise-date 2022-08-01 ;
          }
        }
        container login-restriction {
          description 'The configuration of restrict login.'
                      ;
          container login-block {
            description 'This command configures and activates the anti-attack '
                      + 'monitoring function for remote login.'
                        ;
            reference 'show login'
                      ;
            presence 'All the leaves of this container should be mandatory'
                     ;
            leaf block-time {
              description 'The time of block login.'
                          ;
              type uint16 {
                range 1..65535 {
                  description 'range from 1 to 65535'
                              ;
                }
              }
              units second ;
              mandatory true ;
            }
            leaf attemp-times {
              description 'The max try times of login failure.'
                          ;
              type uint16 {
                range 1..65535 {
                  description 'range from 1 to 65535'
                              ;
                }
              }
              mandatory true ;
            }
            leaf watch-period {
              description 'The period of watch.'
                          ;
              type uint16 {
                range 1..65535 {
                  description 'range from 1 to 65535'
                              ;
                }
              }
              units second ;
              mandatory true ;
            }
          }
          container login-failure-alarm {
            description 'This command configure the system to create the log in'
                      + 'formation or TRAP information when a login attempt fai'
                      + 'led.'
                        ;
            reference 'show login failure'
                      ;
            presence 'Mandatory leaf is included.'
                     ;
            leaf every-times {
              description 'Set failure try times when alarm'
                          ;
              type uint8 {
                range 1..100 {
                  description 'range from 1 to 100'
                              ;
                }
              }
              mandatory true ;
            }
          }
          container login-quiet-mode-acl {
            description 'To configure login quiet mode acl.'
                        ;
            leaf ipv4-acl {
              description 'To configure ipv4 acl.'
                          ;
              type string {
                length 1..31 ;
              }
            }
            leaf ipv6-acl {
              description 'To configure ipv6 acl.'
                          ;
              type string {
                length 1..31 ;
              }
            }
          }
          container user-authen-restriction {
            description 'Set the maximum number of consecutive authentication f'
                      + 'ailures and locking times for users.'
                        ;
            leaf fail-times {
              description 'Set the consecutive failure times (0: means no limit'
                        + ').'
                          ;
              type uint8 {
                range 0..16 ;
              }
              default 5 ;
            }
            leaf lock-time {
              description 'Set the lock time.'
                          ;
              type uint16 {
                range 1..1440 ;
              }
              units minute ;
              default 5 ;
            }
            leaf period {
              description 'Set the time length of continuous authentication fai'
                        + 'lures. The user will be locked automatically after t'
                        + 'he specified number of times of continuous authentic'
                        + 'ation failures within period.'
                          ;
              type uint16 {
                range 1..120 ;
              }
              units minute ;
              ncd:revise-date 2021-04-06 ;
            }
          }
        }
        container strong-username {
          description 'Set the username strategy'
                      ;
          leaf min-length {
            description 'Set the minimum length of the username'
                        ;
            type uint8 {
              range 1..65 ;
            }
          }
          leaf dictionary {
            description 'Enable(1) or disable(0) username dictionary.'
                        ;
            type uint8 {
              range 0..1 ;
            }
            ncd:revise-date 2022-06-06 ;
          }
          ncd:revise-date 2018-03-29 ;
        }
        container global-user-aging {
          if-feature global-user-aging ;
          description 'The configuration of global user-aging.'
                      ;
          leaf day {
            description 'Set the local user aging period. If the local user is '
                      + 'not used continuously for a period of time that reache'
                      + 's the aging period,the user is disabled.'
                        ;
            type uint16 {
              range 1..365 ;
            }
            units day ;
          }
          ncd:revise-date 2018-05-19 ;
        }
        container local-user-change-password {
          description 'A user that has passed local authentication modifies its'
                    + ' password.'
                      ;
          presence 'Mandatory leaves are included.'
                   ;
          leaf old-password {
            description 'Old password'
                        ;
            type string {
              length 3..128 ;
            }
            mandatory true ;
          }
          leaf new-password {
            description 'New password'
                        ;
            type string {
              length 3..128 ;
            }
            mandatory true ;
          }
          ncd:revise-date 2019-09-11 ;
        }
        container local-user-offline {
          if-feature local-user-offline ;
          description 'Local user configuration changes kick users offline.'
                      ;
          leaf password-changed {
            description 'Set change the local user password and kick the user o'
                      + 'ffline.'
                        ;
            type empty ;
          }
          leaf locked {
            description 'Set lock the local user and kick the user offline.'
                        ;
            type empty ;
          }
          ncd:revise-date 2020-08-17 ;
        }
        container change-password {
          description 'The restriction policy of changing password.'
                      ;
          presence change-password ;
          leaf max-times-per-day {
            description 'Maximum number of changing password within a day.'
                        ;
            type uint16 {
              range 1..10 ;
            }
            mandatory true ;
          }
          ncd:revise-date 2020-08-31 ;
        }
        container ftp-aaa-authentication {
          description 'FTP AAA authentication.'
                      ;
          leaf enabled {
            description 'Enables or disables FTP AAA authentication.'+"\n"
                      + 'By default, FTP only supports local authentication. Th'
                      + 'at is, users can upload and download files through FTP'
                      + ' without using the AAA authentication template.'+"\n"
                      + 'After FTP AAA authentication is enabled, an authentica'
                      + 'tion template must be configured to support local and '
                      + 'remote authentication.'
                        ;
            type boolean ;
            default false ;
          }
          ncd:revise-date 2021-10-21 ;
        }
        container username-dictionary {
          description 'The Configuration of username dictionary.'
                      ;
          list username {
            description 'Establish username.'
                        ;
            max-elements 128 ;
            key name ;
            leaf name {
              description 'Username in the username dictionary.'
                          ;
              type string {
                length 1..65 ;
              }
            }
          }
          ncd:revise-date 2022-06-06 ;
        }
      }
      container usernames {
        description 'The configuration of username-related.'
                    ;
        list username {
          description 'Establish user name'
                      ;
          max-elements 128 ;
          key name ;
          leaf name {
            description 'System username.'
                        ;
            type string {
              length 1..65 ;
            }
          }
          choice password {
            description 'Set user password'
                        ;
            case cleartext {
              description 'The unencrypted password'
                          ;
              leaf cleartext-password {
                description 'The UNENCRYPTED (cleartext) user password'
                            ;
                type string {
                  length 3..128 ;
                }
              }
            }
            case encrypted {
              description 'The encrypted password'
                          ;
              leaf encrypted-password {
                description 'The encrypted user password'
                            ;
                type string {
                  length 64..254 ;
                }
              }
            }
            case irreversible-cleartext {
              description 'The unencrypted password'
                          ;
              leaf irreversible-cleartext-password {
                description 'The UNENCRYPTED (cleartext) user password'
                            ;
                type string {
                  length 3..128 ;
                }
              }
              ncd:revise-date 2017-10-13 ;
            }
            case irreversible-encrypted {
              description 'The encrypted password'
                          ;
              leaf irreversible-encrypted-password {
                description 'The irreversible encrypted password'
                            ;
                type string {
                  length 63..254 ;
                }
              }
              ncd:revise-date 2017-10-13 ;
            }
          }
          leaf bind-authen-template {
            description 'Bind authentication template number'
                        ;
            type uint32 {
              range 1..128 ;
            }
          }
          leaf bind-author-template {
            description 'Bind authorization template number'
                        ;
            type uint32 {
              range 1..128 ;
            }
          }
          leaf password-duration {
            description 'Set the number of days the password is valid. If set t'
                      + 'o 0, the password never expires.'
                        ;
            type uint16 {
              range '0 | 90..360'
                    ;
            }
          }
          leaf remind-before-expire {
            if-feature remind-before-expire ;
            description 'Set the number of days to remind before the password e'
                      + 'xpires. The default is 3 days. Allows you to set the r'
                      + 'eminder days to be greater than the number of days the'
                      + ' password is valid. When the password never expires, t'
                      + 'he reminder days is invalid.'
                        ;
            type uint16 {
              range 1..360 ;
            }
            ncd:revise-date 2019-01-03 ;
          }
          leaf once-password {
            description 'Must modify password when first login.'
                        ;
            type enumeration {
              enum off {
                value 0 ;
                description "Needn't modify password when first login."
                            ;
              }
              enum on {
                value 1 ;
                description 'Must modify password when first login.'
                            ;
              }
            }
            default off ;
          }
          leaf lock {
            description 'Lock or unlock a local user. Locked user is not allowe'
                      + 'd to login device.'
                        ;
            type enumeration {
              enum unlock {
                value 0 ;
                description 'Unlock a user'
                            ;
              }
              enum lock {
                value 1 ;
                description 'Lock a user'
                            ;
              }
            }
            default unlock ;
          }
          leaf change-password-expired {
            description 'Change password after the password expired.'
                        ;
            type enumeration {
              enum enable {
                value 1 ;
              }
              enum disable {
                value 2 ;
              }
            }
            ncd:revise-date 2019-08-20 ;
          }
          container enable-type {
            description 'To configure user enable authentication type.'
                        ;
            choice authen-type {
              description 'Set user enable authentication type'
                          ;
              case local {
                description 'Local authentication'
                            ;
                leaf local-authentication {
                  description 'User enable authentication type local'
                              ;
                  type empty ;
                }
              }
              case aaa {
                description 'AAA authentication'
                            ;
                leaf aaa-authentication {
                  description 'User enable AAA authentication type'
                              ;
                  type empty ;
                  mandatory true ;
                }
                leaf authentication-template {
                  description 'User enable authentication template'
                              ;
                  type uint8 {
                    range 1..128 ;
                  }
                  mandatory true ;
                }
              }
            }
          }
          container password-recover-remind {
            if-feature password-recover-remind ;
            description 'Set the question and answer of user password recover.'
                        ;
            presence 'Mandatory leaves are included.'
                     ;
            leaf question {
              description 'Set the question of user password reset.'
                          ;
              type ncd:string-with-blank {
                length 1..50 ;
              }
              mandatory true ;
            }
            leaf answer {
              description 'Set the answer of user password reset.'
                          ;
              type ncd:string-with-blank {
                length 1..200 ;
              }
              mandatory true ;
            }
          }
          container user-aging {
            if-feature user-aging ;
            description "The configuration of user's user-aging."
                        ;
            leaf day {
              description 'Set the specified local user aging period. If the us'
                        + 'er is not used continuously for a period of time tha'
                        + 't reaches the aging period, the user is disabled. Th'
                        + 'e number of day is 0, indicating that the user is no'
                        + 't aging.'
                          ;
              type uint16 {
                range 0..365 ;
              }
              units day ;
            }
            ncd:revise-date 2018-05-19 ;
          }
          container user-authen-restriction {
            if-feature user-authen-restriction ;
            description 'Set the maximum number of consecutive authentication f'
                      + 'ailures and locking times for local users.'
                        ;
            presence 'Mandatory leaves are included.'
                     ;
            leaf fail-times {
              description 'Set the consecutive failure times.'
                          ;
              type uint8 {
                range 3..16 ;
              }
              mandatory true ;
            }
            leaf lock-time {
              description 'Set the lock time.'
                          ;
              type uint16 {
                range 1..1440 ;
              }
              units minute ;
              mandatory true ;
            }
            leaf period {
              description 'Set the time length of continuous authentication fai'
                        + 'lures. The user will be locked automatically after t'
                        + 'he specified number of times of continuous authentic'
                        + 'ation failures within period.'
                          ;
              type uint16 {
                range 1..120 ;
              }
              units minute ;
              ncd:revise-date 2021-04-06 ;
            }
            ncd:revise-date 2019-10-31 ;
          }
          container change-password {
            description 'The restriction policy of changing password.'
                        ;
            leaf min-period {
              description 'Minimum period between password change.'
                          ;
              type uint32 {
                range 1..12 ;
              }
              units hour ;
            }
            ncd:revise-date 2020-11-26 ;
          }
          container access-time-range {
            if-feature access-time-range ;
            description 'Access time range for users.'
                        ;
            leaf time-range-name {
              description 'Time range name.'
                          ;
              type string {
                length 1..31 ;
              }
            }
            ncd:revise-date 2022-07-22 ;
          }
        }
      }
      container authentication-templates {
        description 'The configuration of authentication template.'
                    ;
        list authen-template {
          description 'The authentication template configuration of ADM_MGR.'
                      ;
          max-elements 128 ;
          key authen-number ;
          leaf authen-number {
            description 'Configure number of authentication template.'
                        ;
            type uint32 {
              range 1..128 ;
            }
          }
          leaf bind-aaa-authen-template {
            description 'Configure template number of AAA which is binded by th'
                      + 'e authentication template.'
                        ;
            type uint32 {
              range 2001..2128 ;
            }
          }
          leaf ipv4-acl {
            description 'Configure IPv4 ACL name binded by the authentication t'
                      + 'emplate.'
                        ;
            type string {
              length 1..31 ;
            }
          }
          leaf ipv6-acl {
            description 'Configure IPv6 ACL name binded by the authentication t'
                      + 'emplate.'
                        ;
            type string {
              length 1..31 ;
            }
          }
          container authentication-method {
            description 'Configure the method of authentication.'
                        ;
            choice method {
              description 'Configure authentication method of the authenticatio'
                        + 'n template.'
                          ;
              default pap-authentication ;
              case chap-authentication {
                description 'Configure authentication method is CHAP.'
                            ;
                leaf chap {
                  description 'Configure authentication method is CHAP.'
                              ;
                  type empty ;
                }
              }
              case pap-authentication {
                description 'Configure authentication method is PAP.'
                            ;
                leaf pap {
                  description 'Configure authentication method is PAP.'
                              ;
                  type empty ;
                }
              }
              case ascii-authentication {
                description 'Configure authentication method is ASCII.'
                            ;
                container ascii {
                  description 'Configure the TACACS+ authentication method as A'
                            + 'SCII. The RADIUS protocol does not support ASCII'
                            + ' authentication. If only the ASCII authenticatio'
                            + 'n mode is specified, but the RADIUS authenticati'
                            + 'on mode is not specified, the default authentica'
                            + 'tion mode is CHAP.'
                              ;
                  presence ascii ;
                  choice radius {
                    description 'Configure RADIUS authentication method.'
                                ;
                    default chap-authentication ;
                    case pap-authentication {
                      description 'Configure RADIUS authentication method is PA'
                                + 'P.'
                                  ;
                      leaf pap {
                        description 'Configure RADIUS authentication method is '
                                  + 'PAP.'
                                    ;
                        type empty ;
                      }
                    }
                    case chap-authentication {
                      description 'Configure authentication method is CHAP.'
                                  ;
                      leaf chap {
                        description 'Configure RADIUS authentication method is '
                                  + 'CHAP.'
                                    ;
                        type empty ;
                      }
                    }
                  }
                }
                ncd:revise-date 2021-02-08 ;
              }
            }
          }
          leaf description {
            description 'Configure description of the authentication template.'
                        ;
            type string {
              length 1..127 ;
            }
          }
        }
      }
      container authorization-templates {
        description 'The configuration of authorization template.'
                    ;
        list author-template {
          description 'The authorization template configuration.'
                      ;
          max-elements 128 ;
          key author-number ;
          leaf author-number {
            description 'The authorization template number'
                        ;
            type uint32 {
              range 1..128 ;
            }
          }
          leaf local-privilege-level {
            description 'Set local privilege level'
                        ;
            type uint8 {
              range 0..15 ;
            }
          }
          leaf bind-aaa-author-template {
            description 'Bind AAA authorization template'
                        ;
            type uint32 {
              range 2001..2128 ;
            }
          }
          leaf description {
            description 'The description of authorization template'
                        ;
            type string {
              length 1..127 ;
            }
          }
          leaf login-sametime-max {
            description 'Set the max times of user login in the same time'
                        ;
            type uint16 {
              range 1..60 ;
            }
          }
          leaf local-cmdgroup-mode {
            description 'Set the command group mode'
                        ;
            type enumeration {
              enum inclusive {
                value 0 ;
                description 'Inclusive mode'
                            ;
              }
              enum exclusive {
                value 1 ;
                description 'Exclusive mode'
                            ;
              }
            }
            default inclusive ;
          }
          container max-access {
            description 'To configure max access authority'
                        ;
            choice access {
              description 'The read-write authority'
                          ;
              case read-write-access {
                description 'The read-write authority'
                            ;
                leaf read-write {
                  description 'The read-write authority.'
                              ;
                  type empty ;
                }
              }
              case read-only-access {
                description 'The read-only authority'
                            ;
                leaf read-only {
                  description 'The read-only authority.'
                              ;
                  type empty ;
                }
              }
            }
          }
          container access-only {
            if-feature access-only {
              ncd:revise-date 2021-10-20 ;
            }
            description 'Set the allowed access type.'
                        ;
            leaf lct {
              description 'LCT port access.'
                          ;
              type enumeration {
                enum deny {
                  value 0 ;
                  description 'Lct access deny'
                              ;
                }
                enum allowed {
                  value 1 ;
                  description 'Lct access allowed'
                              ;
                }
              }
              default allowed ;
            }
            leaf qx {
              description 'QX port access.'
                          ;
              type enumeration {
                enum deny {
                  value 0 ;
                  description 'Qx access deny'
                              ;
                }
                enum allowed {
                  value 1 ;
                  description 'Qx access allowed'
                              ;
                }
              }
              default allowed ;
            }
            leaf dcn {
              description 'DCN access.'
                          ;
              type enumeration {
                enum deny {
                  value 0 ;
                  description 'Dcn access deny'
                              ;
                }
                enum allowed {
                  value 1 ;
                  description 'Dcn access allowed'
                              ;
                }
              }
              default allowed ;
            }
          }
          container ftp-top-directory {
            description 'Set the top directory and access authority of FTP'
                        ;
            leaf directory-name {
              description 'The top directory name'
                          ;
              type string {
                length 1..159 ;
              }
            }
            choice topdir-access {
              description 'The top directory access authority'
                          ;
              case topdir-readonly {
                description 'The read-only authority'
                            ;
                leaf read-only {
                  description 'The read-only authority'
                              ;
                  type empty ;
                }
              }
              case topdir-readwrite-copy {
                description 'The read-write and copy authority'
                            ;
                leaf read-write {
                  description 'The read-write authority'
                              ;
                  type enumeration {
                    enum no {
                      value 0 ;
                      description 'Delete ftp top dir read write'
                                  ;
                    }
                    enum yes {
                      value 1 ;
                      description 'Config ftp top dir read write'
                                  ;
                    }
                  }
                }
                leaf copy {
                  description 'The copy authority'
                              ;
                  type enumeration {
                    enum no {
                      value 0 ;
                      description 'Delete ftp top dir copy'
                                  ;
                    }
                    enum yes {
                      value 1 ;
                      description 'Config ftp top dir copy'
                                  ;
                    }
                  }
                }
              }
            }
          }
          container sftp-top-directory {
            description 'Set the top directory and access authority of SFTP'
                        ;
            leaf directory-name {
              description 'The top directory name'
                          ;
              type string {
                length 1..159 ;
              }
            }
            choice topdir-access {
              description 'The top directory access permission'
                          ;
              case topdir-readonly {
                description 'The read-only authority'
                            ;
                leaf read-only {
                  description 'The read-only authority'
                              ;
                  type empty ;
                }
              }
              case topdir-readwrite-copy {
                description 'The read-write and copy authority'
                            ;
                leaf read-write {
                  description 'The read-write authority'
                              ;
                  type enumeration {
                    enum no {
                      value 0 ;
                      description 'Delete sftp top dir read write'
                                  ;
                    }
                    enum yes {
                      value 1 ;
                      description 'Config sftp top dir read write'
                                  ;
                    }
                  }
                }
                leaf copy {
                  description 'The copy authority'
                              ;
                  type enumeration {
                    enum no {
                      value 0 ;
                      description 'Delete sftp top dir copy'
                                  ;
                    }
                    enum yes {
                      value 1 ;
                      description 'Config sftp top dir copy'
                                  ;
                    }
                  }
                }
              }
            }
          }
          container login-type-allowed {
            description 'Set the login type.'
                        ;
            leaf console {
              description 'Allow users to login via console.'
                          ;
              type enumeration {
                enum deny {
                  value 0 ;
                  description 'Users are not allowed to login by console.'
                              ;
                }
                enum allowed {
                  value 1 ;
                  description 'Users are allowed to login by console.'
                              ;
                }
              }
              default allowed ;
              ncd:revise-date 2018-07-23 ;
            }
            leaf only-telnet {
              description 'Allow users to login via Telnet.'
                          ;
              type enumeration {
                enum deny {
                  value 0 ;
                  description 'Users are not allowed to login by Telnet.'
                              ;
                }
                enum allowed {
                  value 1 ;
                  description 'Users are allowed to login by Telnet.'
                              ;
                }
              }
              default allowed ;
              ncd:revise-date 2018-07-23 ;
            }
            leaf telnet {
              description 'Allow users to login via Telnet and console.'
                          ;
              type enumeration {
                enum deny {
                  value 0 ;
                  description 'Users are not allowed to login by Telnet and con'
                            + 'sole.'
                              ;
                }
                enum allowed {
                  value 1 ;
                  description 'Users are allowed to login by Telnet and console.'
                              ;
                }
              }
              default allowed ;
            }
            leaf ssh {
              description 'Allow users to login via SSH.'
                          ;
              type enumeration {
                enum deny {
                  value 0 ;
                  description 'Users are not allowed to login by SSH.'
                              ;
                }
                enum allowed {
                  value 1 ;
                  description 'Users are allowed to login by SSH.'
                              ;
                }
              }
              default allowed ;
            }
            leaf ftp {
              description 'Allow users to login via FTP.'
                          ;
              type enumeration {
                enum deny {
                  value 0 ;
                  description 'Users are not allowed to login by FTP.'
                              ;
                }
                enum allowed {
                  value 1 ;
                  description 'Users are allowed to login by FTP.'
                              ;
                }
              }
              default allowed ;
            }
            leaf web {
              description 'Allow users to login via WEB.'
                          ;
              type enumeration {
                enum deny {
                  value 0 ;
                  description 'Users are not allowed to login by WEB.'
                              ;
                }
                enum allowed {
                  value 1 ;
                  description 'Users are allowed to login by WEB.'
                              ;
                }
              }
              default allowed ;
            }
            leaf grpc {
              description 'Allow users to login via GRPC.'
                          ;
              type enumeration {
                enum deny {
                  value 0 ;
                  description 'Users are not allowed to login by GRPC.'
                              ;
                }
                enum allowed {
                  value 1 ;
                  description 'Users are allowed to login by GRPC.'
                              ;
                }
              }
              default allowed ;
              ncd:revise-date 2022-01-10 ;
            }
          }
          container logfile-access {
            description 'Set the access permission of logfile.'
                        ;
            list logfile-allowed {
              description 'Set the access permission of log file.'
                          ;
              max-elements 4096 ;
              key log-suffix ;
              leaf log-suffix {
                description 'Set the access permission of log with suffix.'
                            ;
                type string {
                  length 1..32 ;
                }
              }
              choice access {
                description 'The access authority of logfile'
                            ;
                default read-write-copy ;
                case none {
                  description 'The none access authority'
                              ;
                  leaf none-access {
                    description 'None authority.'
                                ;
                    type empty ;
                  }
                }
                case read-only {
                  description 'The read-only access authority'
                              ;
                  leaf read-only-access {
                    description 'The read-only authority .'
                                ;
                    type empty ;
                  }
                }
                case read-write-copy {
                  description 'The read-write and copy access authority'
                              ;
                  leaf read-write-access {
                    description 'The read-write authority .'
                                ;
                    type enumeration {
                      enum no {
                        value 0 ;
                      }
                      enum yes {
                        value 1 ;
                      }
                    }
                  }
                  leaf copy-access {
                    description 'The copy authority .'
                                ;
                    type enumeration {
                      enum no {
                        value 0 ;
                      }
                      enum yes {
                        value 1 ;
                      }
                    }
                  }
                }
              }
            }
          }
          container local-cmdgroups {
            description 'The local command group'
                        ;
            list local-cmd-group {
              description 'Set the local command group.'
                          ;
              key group-name ;
              leaf group-name {
                description 'Set the command group.'
                            ;
                type string {
                  length 1..31 ;
                }
              }
            }
          }
          container chmode-access {
            if-feature chmode-access ;
            description 'Set the access permission of file or directory.'
                        ;
            list chmode {
              description 'Set the access permission of file or directory.'
                          ;
              key absolute-path ;
              leaf absolute-path {
                description 'Set the absolute path of a file or directory'
                            ;
                type string {
                  length 1..159 ;
                }
              }
              leaf operation-mode {
                description access ;
                type enumeration {
                  enum read-only {
                    value 1 ;
                    description 'read-only prilege'
                                ;
                  }
                  enum read-write {
                    value 2 ;
                    description 'read-write privilege'
                                ;
                  }
                  enum none {
                    value 3 ;
                    description 'none privilege'
                                ;
                  }
                }
                mandatory true ;
              }
            }
            ncd:revise-date 2020-07-03 ;
          }
        }
      }
    }
  }
  container state {
    config false ;
    description 'The state model of ADM_MGR.'
                ;
    container adm-mgr {
      description 'The state model of ADM_MGR.'
                  ;
      list user-info {
        description 'User information'
                    ;
        key username ;
        leaf username {
          description Username ;
          type ncd:string-all {
            length 1..65 ;
          }
        }
        leaf encrypt-password {
          description 'Encrypted password, displayed as ******.'
                      ;
          type string {
            length 1..200 ;
          }
        }
        leaf authen-template-number {
          description 'Authentication template number.'
                      ;
          type uint8 {
            range 1..128 ;
          }
        }
        leaf author-template-number {
          description 'Authortication template number.'
                      ;
          type uint8 {
            range 1..128 ;
          }
        }
        leaf age-time {
          description 'The remain validity time of password.'
                      ;
          type string {
            length 1..20 ;
          }
        }
        leaf set-time {
          status deprecated ;
          description 'The creation time of password.'
                      ;
          type ncd:string-with-blank {
            length 1..30 ;
          }
        }
        leaf user-aging-state {
          description 'User aging state'
                      ;
          type enumeration {
            enum active {
              value 0 ;
              description 'User is active.'
                          ;
            }
            enum inactive {
              value 1 ;
              description 'User is inactive.'
                          ;
            }
          }
          ncd:revise-date 2018-05-19 ;
        }
        leaf locked-state {
          description 'User lock state'
                      ;
          type enumeration {
            enum unlocked {
              value 0 ;
              description 'User is unlocked.'
                          ;
            }
            enum locked {
              value 1 ;
              description 'User is locked.'
                          ;
            }
          }
          ncd:revise-date 2018-05-19 ;
        }
      }
      list authen-restriction-info {
        description 'Locked user and login fail user information'
                    ;
        key username ;
        leaf username {
          description Username ;
          type ncd:string-all {
            length 1..65 ;
          }
        }
        leaf locked-state {
          description 'User lock state'
                      ;
          type empty ;
        }
        leaf login-failed-times {
          description 'User login failed times.'
                      ;
          type uint8 ;
        }
        leaf remain-time {
          description 'Locked user remain time.'
                      ;
          type uint16 ;
          units minute ;
        }
      }
      list login-state-info {
        description 'This command queries the configuration of the anti-attack '
                  + 'monitoring function.'
                    ;
        reference 'login block'
                  ;
        key terminal-type ;
        leaf terminal-type {
          description 'The type of login terminal.'
                      ;
          type enumeration {
            enum telnet {
              value 1 ;
              description 'telnet terminal'
                          ;
            }
            enum ssh {
              value 2 ;
              description 'ssh terminal'
                          ;
            }
            enum ftp {
              value 3 ;
              description 'ftp terminal'
                          ;
            }
          }
        }
        leaf current-mode {
          description 'The current mode of login terminal,include Watch-Mode an'
                    + 'd Quiet-Mode.'
                      ;
          type enumeration {
            enum watch-mode {
              value 1 ;
              description 'watch mode'
                          ;
            }
            enum quiet-mode {
              value 2 ;
              description 'quiet mode'
                          ;
            }
          }
        }
        leaf remain-time {
          description 'The remain time of login mode.'
                      ;
          type uint16 {
            range 0..65535 {
              description 'range from 0 to 65535'
                          ;
            }
          }
          units second ;
        }
        leaf login-failed-times {
          description 'The counts of login failure.'
                      ;
          type uint16 {
            range 0..65535 {
              description 'range from 0 to 65535'
                          ;
            }
          }
        }
      }
      list online-user {
        description 'Information of online users.'
                    ;
        key 'username vtyno access-type'
            ;
        leaf username {
          description 'The online username.'
                      ;
          type ncd:string-all {
            length 1..65 ;
          }
        }
        leaf vtyno {
          description 'Vty number.'
                      ;
          type uint8 {
            range 0..255 ;
          }
        }
        leaf access-type {
          description 'User access type. The supported types are CLI, NETCONF a'
                    + 'nd QX.'
                      ;
          type enumeration {
            enum CLI {
              value 1 ;
              description 'Access type of user is CLI.'
                          ;
            }
            enum SNMP {
              value 2 ;
              description 'Access type of user is SNMP.'
                          ;
            }
            enum WEB {
              value 3 ;
              description 'Access type of user is WEB.'
                          ;
            }
            enum NETCONF {
              value 4 ;
              description 'Access type of user is NETCONF.'
                          ;
            }
            enum QX {
              value 5 ;
              description 'Access type of user is QX.'
                          ;
            }
            enum CWMP {
              value 6 ;
              description 'Access type of user is CWMP.'
                          ;
            }
            enum GRPC {
              value 7 ;
              description 'Access type of user is GRPC.'
                          ;
            }
          }
        }
        leaf protocol-type {
          description 'The protocol type'
                      ;
          type enumeration {
            enum NA {
              value 0 ;
              description 'The protocol type is undefined'
                          ;
            }
            enum CONSOLE {
              value 1 ;
              description 'The protocol type is CONSOLE'
                          ;
            }
            enum TELNET {
              value 2 ;
              description 'The protocol type is TELNET'
                          ;
            }
            enum SSH {
              value 3 ;
              description 'The protocol type is SSH'
                          ;
            }
          }
          ncd:revise-date 2018-03-14 ;
        }
        leaf ip-address {
          description 'The IP address of user.'
                      ;
          type string {
            length 0..45 ;
          }
        }
        leaf online-time {
          description 'The user online time.'
                      ;
          type string {
            length 0..32 ;
          }
        }
        leaf idle-time {
          description 'Idle time.'
                      ;
          type string {
            length 0..32 ;
          }
        }
        leaf login-time {
          description 'Login time.'
                      ;
          type ncd:datetime ;
        }
        leaf authentication-method {
          description 'User login authentication method'
                      ;
          type enumeration {
            enum NA {
              value 0 ;
              description 'The authentication method is undefined'
                          ;
            }
            enum none {
              value 1 ;
              description 'The authentication method is none'
                          ;
            }
            enum local {
              value 2 ;
              description 'The authentication method is local'
                          ;
            }
            enum radius {
              value 3 ;
              description 'The authentication method is RADIUS'
                          ;
            }
            enum tacacs {
              value 4 ;
              description 'The authentication method is TACACS'
                          ;
            }
            enum diameter {
              value 5 ;
              description 'The authentication method is DIAMETER'
                          ;
            }
          }
          ncd:revise-date 2018-03-14 ;
        }
        leaf authorization-method {
          description 'User login authorization method'
                      ;
          type enumeration {
            enum NA {
              value 0 ;
              description 'The authorization method is undefined'
                          ;
            }
            enum local {
              value 2 ;
              description 'The authorization method is local'
                          ;
            }
            enum radius {
              value 3 ;
              description 'The authorization method is RADIUS'
                          ;
            }
            enum tacacs {
              value 4 ;
              description 'The authorization method is TACACS'
                          ;
            }
            enum local-default {
              value 6 ;
              description 'The authorization method is local(default)'
                          ;
            }
          }
          ncd:revise-date 2018-03-14 ;
        }
        ncd:select 'username vtyno access-type'
                   ;
      }
      list login-fail-response-info {
        description 'Information of login fail response info.'
                    ;
        key 'seqnum terminal-type'
            ;
        leaf seqnum {
          description 'Login seqnum.'
                      ;
          type int32 {
            range 1..100 ;
          }
        }
        leaf terminal-type {
          description 'The type of login terminal.'
                      ;
          type enumeration {
            enum telnet {
              value 1 ;
              description 'telnet terminal'
                          ;
            }
            enum ssh {
              value 2 ;
              description 'ssh terminal'
                          ;
            }
            enum ftp {
              value 3 ;
              description 'ftp terminal'
                          ;
            }
          }
        }
        leaf username {
          description 'Login name.'
                      ;
          type ncd:string-all {
            length 0..65 ;
          }
        }
        leaf login-time {
          description 'Login time.'
                      ;
          type ncd:string-with-blank {
            length 1..40 ;
          }
        }
        choice ip-address {
          description 'IP address'
                      ;
          case ipv4-type {
            description Ipv4 ;
            leaf ipv4-address {
              description 'IPv4 address.'
                          ;
              type ncd:ipv4-address ;
            }
          }
          case ipv6-type {
            description IPv6 ;
            leaf ipv6-address {
              description 'IPv6 address.'
                          ;
              type ncd:ipv6-address ;
            }
          }
        }
        ncd:select 'seqnum terminal-type'
                   ;
        ncd:select terminal-type ;
      }
      container rootuser-info {
        if-feature show-root-user {
          ncd:revise-date 2022-06-16 ;
        }
        description 'Root user information'
                    ;
        leaf username {
          description 'Root username'
                      ;
          type ncd:string-all {
            length 1..65 ;
          }
        }
        leaf encrypt-password {
          description 'Encrypted password, display actual ciphertext or ****** '
                    + 'according to different product forms.'
                      ;
          type string {
            length 1..200 ;
          }
        }
        leaf set-time {
          description 'The set-time of root user password'
                      ;
          type string {
            length 10 ;
          }
        }
      }
    }
  }
  container operation {
    config false ;
    description 'The operation model of ADM_MGR.'
                ;
    container adm-mgr {
      description 'The operation model of ADM_MGR.'
                  ;
      container clear-online-user {
        description 'Clear the online user.'
                    ;
        choice clear-user {
          if-feature clear-online-user ;
          description 'Clear the online user.'
                      ;
          case user-info {
            description 'The online user informaton'
                        ;
            leaf username {
              description 'Clear user by username.'
                          ;
              type string {
                length 1..65 ;
              }
            }
          }
          case user-access-info {
            description 'The user access information'
                        ;
            leaf access-type {
              description 'Clear user by accesstype.'
                          ;
              type enumeration {
                enum cli {
                  value 0 ;
                  description 'Accesstype cli'
                              ;
                }
                enum qx {
                  value 1 ;
                  description 'Accesstype qx'
                              ;
                }
                enum tl1 {
                  value 2 ;
                  description 'Accesstype tl1'
                              ;
                }
                enum xml {
                  value 3 ;
                  description 'Accesstype xml'
                              ;
                }
                enum web {
                  value 4 ;
                  description 'Accesstype web'
                              ;
                }
                enum grpc {
                  value 5 ;
                  description 'Accesstype grpc'
                              ;
                }
              }
              mandatory true ;
            }
            leaf vtyno {
              description 'Clear user by vtyno.'
                          ;
              type uint8 {
                range 0..255 ;
              }
              mandatory true ;
            }
          }
        }
      }
      container activate-user {
        if-feature activate-user ;
        description 'Activate local user.'
                    ;
        leaf username {
          description 'If the local user is aged, it will be activated. If the '
                    + 'lcal user is not aged, the aging time is update and the '
                    + 'calculation is restarted.'
                      ;
          type string {
            length 1..65 ;
          }
        }
        ncd:revise-date 2018-05-19 ;
      }
    }
  }
  rpc unlock-local-user {
    description 'Unlock local user'
                ;
    input {
      leaf username {
        description 'While the local user is locked after password authenticati'
                  + 'on fails a certain number of times, unlock the local user.'
                    ;
        type string {
          length 1..65 ;
        }
      }
    }
    ncd:revise-date 2019-10-31 ;
  }
  rpc unlock-root-user {
    if-feature unlock-root-user {
      ncd:revise-date 2022-02-22 ;
    }
    description 'Unlock root user'
                ;
    ncd:revise-date 2019-10-31 ;
  }
}
