module gsta-extension {
  namespace "http://www.gsta.com/netconf/gsta-extension";
  prefix ext;

  organization
    "China Telecom Group - Guangdong Telecom Research Institute";
  contact
    "China Telecom Corporation Guangdong Research Institute (hereinafter referred to as:Guangzhou Research Institute)";
  description
    "ac ne extension yang syntax";
	
  revision 2018-07-13 {
    description
      "Initial modeling.";
    reference
      "GSTA IP-RAN 5G Common Yang Model.";
  }
  
   extension support-filter {
    argument value;
    description
      "support-filter";
  }

  extension allowDelete {
    argument value;
    description
      "allowDelete";
  }
  extension value-range {
    argument value;
    description
      " The range of values that can be entered using the id-range type or its derived type node. ";
  }
    
  extension entry-from {
    argument value;
    description "Applies only to a list or presence container whose config is true. " +
      "entry-from specifies an instance to be automatically generated by the system "+
	  "based on other data or to be created by a user.";
  }
  
  extension node-ref {
	argument value;
	description 
      "Indicates the XPath of the data node for which the rpc operation is performed. "+
      "If the rpc operation is performed for the entire system (the corresponding node "+
      "cannot be found in the model tree), this syntax is not required.";
  }
}
