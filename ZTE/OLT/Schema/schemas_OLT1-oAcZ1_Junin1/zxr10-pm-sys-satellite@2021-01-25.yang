module zxr10-pm-sys-satellite {
  namespace 'http://www.zte.com.cn/zxr10/netconf/schema/rosng/pm-sys-satellite'
            ;
  prefix pm-sys-satellite ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  revision 2021-01-25 {
    description 'Initialize version.'
                ;
  }
  container state {
    config false ;
    container sys {
      container systems {
        list system {
          key peid ;
          leaf peid {
            description 'Satellite ID.'
                        ;
            type uint32 {
              range 1..255 {
                description 'peid range.'
                            ;
              }
            }
          }
          leaf system-version {
            type ncd:string-all ;
          }
          leaf boot-time {
            type uint64 ;
          }
          leaf copyright {
            description copyRight ;
            type ncd:string-all ;
          }
          leaf compile-time {
            type ncd:string-all ;
          }
        }
      }
      container shelfs {
        list shelf {
          key peid ;
          leaf peid {
            description 'Satellite ID.'
                        ;
            type uint32 {
              range 1..255 {
                description 'peid range.'
                            ;
              }
            }
          }
          leaf shelfno {
            description 'Shelf number'
                        ;
            type uint8 {
              range 0..255 {
                description 'shelf range.'
                            ;
              }
            }
          }
          leaf shelfsn {
            description 'Shelf series number'
                        ;
            type ncd:string-all ;
          }
        }
      }
      container processor-usages {
        list processor-usage {
          key peid ;
          leaf peid {
            description 'Satellite ID.'
                        ;
            type uint32 {
              range 1..255 {
                description 'peid range.'
                            ;
              }
            }
          }
          leaf shelf {
            description 'Shelf number'
                        ;
            type uint8 {
              range 0..255 {
                description 'shelf range.'
                            ;
              }
            }
          }
          leaf slot {
            description 'Slot number'
                        ;
            type uint8 {
              range 0..255 {
                description 'slot range.'
                            ;
              }
            }
          }
          leaf cpu {
            description 'CPU number'
                        ;
            type uint8 ;
          }
          leaf cpu-usage-5s {
            description 'CPU usage ratio measured in 5 seconds'
                        ;
            type ncd:string-all ;
          }
          leaf cpu-usage-1m {
            description 'CPU usage ratio measured in 1 minute'
                        ;
            type ncd:string-all ;
          }
          leaf cpu-usage-5m {
            description 'CPU usage ratio measured in 5 minute'
                        ;
            type ncd:string-all ;
          }
          leaf cpu-peak {
            description 'CPU peak usage ratio measured in 1 minute'
                        ;
            type ncd:string-all ;
          }
          leaf mem-usage {
            description 'Memory usage ratio'
                        ;
            type ncd:string-all ;
          }
          leaf mem-physical {
            description 'Physical memory'
                        ;
            type uint32 ;
          }
          leaf mem-free {
            description 'Free memory'
                        ;
            type uint32 ;
          }
        }
      }
      container ports {
        list port {
          key peid ;
          ncd:select peid ;
          leaf peid {
            description 'Satellite ID.'
                        ;
            type uint32 {
              range 1..255 {
                description 'Peid range.'
                            ;
              }
            }
          }
          leaf shelf {
            description 'Shelf number.'
                        ;
            type uint8 {
              range 0..255 {
                description 'shelf range.'
                            ;
              }
            }
          }
          leaf slot {
            description 'Slot number.'
                        ;
            type uint8 {
              range 0..255 {
                description 'slot range.'
                            ;
              }
            }
          }
          leaf subslot {
            description 'Subslot number.'
                        ;
            type uint8 ;
          }
          leaf portno {
            description 'Port number.'
                        ;
            type uint32 ;
          }
          leaf porttype {
            description 'Port type.'
                        ;
            type uint16 ;
          }
          leaf portname {
            description 'Port name.'
                        ;
            type string ;
          }
          leaf portphystatus {
            description 'Port physical status.'
                        ;
            type enumeration {
              enum up {
                value 0 ;
                description up. ;
              }
              enum down {
                value 1 ;
                description down. ;
              }
              enum offline {
                value 32 ;
                description offline. ;
              }
            }
          }
          leaf portpemode {
            description 'Port electric optical property.'
                        ;
            type enumeration {
              enum media-copper {
                value 1 ;
                description 'The PEMode of the port is electric.'
                            ;
              }
              enum media-fiber {
                value 2 ;
                description 'The PEMode of the port is optical.'
                            ;
              }
            }
          }
          leaf portspeed {
            description 'Port speed.'
                        ;
            type enumeration {
              enum speed-10M {
                value 1 ;
                description 'Port speed is 10M.'
                            ;
              }
              enum speed-100M {
                value 2 ;
                description 'Port speed is 100M.'
                            ;
              }
              enum speed-1G {
                value 3 ;
                description 'Port speed is 1G.'
                            ;
              }
              enum speed-10G {
                value 4 ;
                description 'Port speed is 10G.'
                            ;
              }
              enum speed-25G {
                value 10 ;
                description 'Port speed is 25G.'
                            ;
              }
              enum speed-40G {
                value 5 ;
                description 'Port speed is 40G.'
                            ;
              }
              enum speed-50G {
                value 11 ;
                description 'Port speed is 50G.'
                            ;
              }
              enum speed-100G {
                value 6 ;
                description 'Port speed is 100G.'
                            ;
              }
              enum speed-200G {
                value 12 ;
                description 'Port speed is 200G.'
                            ;
              }
              enum speed-400G {
                value 13 ;
                description 'Port speed is 400G.'
                            ;
              }
              enum speed-auto {
                value 15 ;
                description 'Port speed is configured to auto, the real speed d'
                          + 'epend on optical module.'
                            ;
              }
            }
          }
          leaf portnegotiation {
            description 'Port negotiation mode.'
                        ;
            type enumeration {
              enum negotiation-force {
                value 1 ;
                description 'Force negotiation mode.'
                            ;
              }
              enum negotiation-auto {
                value 2 ;
                description 'Auto negotiation mode.'
                            ;
              }
            }
            default negotiation-auto ;
          }
          leaf portduplex {
            description 'Port duplex mode.'
                        ;
            type enumeration {
              enum duplex-full {
                value 1 ;
                description 'Full duplex mode.'
                            ;
              }
              enum duplex-half {
                value 2 ;
                description 'Half duplex mode.'
                            ;
              }
            }
          }
        }
      }
    }
  }
}
