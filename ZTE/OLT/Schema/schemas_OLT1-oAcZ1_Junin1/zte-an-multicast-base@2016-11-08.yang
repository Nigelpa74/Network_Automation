module zte-an-multicast-base {
    namespace 'http://www.zte.com.cn/zxr10/netconf/schema/rosng/zx_mcast_mng';
    prefix zx_mcast_mng;
    import zxr10-netconf-defs {
        prefix ncd;
        revision-date 2017-08-15;
    }
    organization "ZTE Corporation";
    contact "Lu Yongbin
                         Mail: lu.yongbing1@zte.com.cn
                         Tel : +86-021-68897487";
    description "The MIB module for the management of ZTE multicast 
                 base management objects.";
    revision 2016-11-08 {
        description "Initial version of this MIB module.";
    }
    container zxAnMulticastBase {
        description "";
        container zxAnMulticastBaseObjects {
            description "";
            container zxAnMulticastVlanTransObjects {
                description "";
                container zxAnMcastVlanGlobalTransTable {
                    description "Global MVLAN translation table.";
                    list zxAnMcastVlanGlobalTransEntry {
                        description "Global MVLAN translation entry.";
                        max-elements 16;
                        key "zxAnMcastVlanGlbTransMVid";
                        leaf zxAnMcastVlanGlbTransMVid {
                            description "MVLAN ID of global MVLAN translation.";
                            type int32 {
                                range 1..4094;
                            }
                        }
                        leaf zxAnMcastVlanGlbTransCVid {
                            description "C-VID of global MVLAN translation. 
                                         Value 0 means translating to untagged packets.";
                            type int32 {
                                range 0..4094;
                            }
                        }
                    }
                }
            }
        }
    }
}
