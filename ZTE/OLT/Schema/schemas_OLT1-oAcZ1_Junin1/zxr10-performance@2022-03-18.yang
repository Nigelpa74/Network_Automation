module zxr10-performance {
  namespace 'http://www.zte.com.cn/zxr10/netconf/schema/rosng/performance'
            ;
  prefix pm ;
  yang-version 1 ;
  import zxr10-netconf-defs {
    prefix ncd ;
  }
  organization 'ZTE Corporation'
               ;
  contact 'ZTE Corporation '+"\n"
        + '         Nanjing Institute of ZTE Corporation'+"\n"
        + '         No.68 Zijinghua Rd. Yuhuatai District, Nanjing, China'+"\n"
        + '         Tel: +86-25-52870000'
          ;
  description 'The netconf module to describe performance'
              ;
  revision 2022-03-18 {
    description '(1)Add configuration\performance\statistics\bandwidth-utilizat'
              + 'ion'
                ;
  }
  revision 2022-01-18 {
    description '(1)Add configuration\performance\statistics\alarm-hysteretic-c'
              + 'haracteristics'
                ;
  }
  revision 2020-08-18 {
    description '(1)Add configuration\performance\statistics\flow'
                ;
  }
  revision 2018-12-12 {
    description '(1)Add configuration\performance\statistics\minute-cycle'
                ;
  }
  revision 2016-11-16 {
    description '(1)Add leaf state\performance\threshold\default-thresholds\zxr'
              + '10analog-default-threshold\tpid-mask'
                ;
  }
  revision 2016-05-05 {
    description '(1)Modify description of leaf operation\performance\monitor\st'
              + 'op\task\taskid;'
                ;
  }
  revision 2015-12-28 {
    description "(1)Obsolete list state\performance\statistics\currentdata\fift"
              + "een-mins\digitaldata\digitaldatum;
\n(2)Add list state\perform"
              + "ance\statistics\currentdata\fifteen-mins\digitaldata\zxr10digi"
              + "taldatum;
\n(3)Obsolete list state\performance\statistics\curr"
              + "entdata\fifteen-mins\analogdata\analogdatum;
\n(4)Add list sta"
              + "te\performance\statistics\currentdata\fifteen-mins\analogdata\z"
              + "xr10analogdatum;
\n(5)Obsolete list state\performance\statisti"
              + "cs\currentdata        wenty-four-hours\digitaldata\digitaldatu"
              + "m;
\n(6)Add list state\performance\statistics\currentdata     "
              + "   wenty-four-hours\digitaldata\zxr10digitaldatum;
\n(7)Obsole"
              + "te list state\performance\statistics\currentdata        wenty-"
              + "four-hours\analogdata\analogdatum;
\n(8)Add list state\perform"
              + "ance\statistics\currentdata        wenty-four-hours\analogdata"
              + "\zxr10analogdatum;
\n(9)Obsolete list state\performance\statis"
              + "tics\historydata\fifteen-mins\digitaldata\digitaldatum;
\n(10)"
              + "Add list state\performance\statistics\historydata\fifteen-mins"
              + "\digitaldata\zxr10digitaldatum;
\n(11)Obsolete list state\perf"
              + "ormance\statistics\historydata\fifteen-mins\analogdata\analogd"
              + "atum;
\n(12)Add list state\performance\statistics\historydata\f"
              + "ifteen-mins\analogdata\zxr10analogdatum;
\n(13)Obsolete list s"
              + "tate\performance\statistics\historydata        wenty-four-hour"
              + "s\digitaldata\digitaldatum;
\n(14)Add list state\performance\s"
              + "tatistics\historydata        wenty-four-hours\digitaldata\zxr1"
              + "0digitaldatum;
\n(15)Obsolete list state\performance\statistic"
              + "s\historydata        wenty-four-hours\analogdata\analogdatum;
"
              + "\n(16)Add list state\performance\statistics\historydata       "
              + " wenty-four-hours\analogdata\zxr10analogdatum;
\n(17)Obsolete "
              + "list state\performance\monitor\perfdata\perfdatum;
\n(18)Add l"
              + "ist state\performance\monitor\perfdata\zxr10perfdatum;
\n(19)O"
              + "bsolete list state\performance        hreshold\default-thresho"
              + "lds\analog-default-threshold;
\n(20)Add list state\performance"
              + "        hreshold\default-thresholds\zxr10analog-default-thresh"
              + "old;
\n(21)Modify length of leaf operation\performance\clear\c"
              + "urrentdata\currentdatum        pid-matcher to 'from 62 to 128'"
              + ";
\n(22)Modify length of leaf operation\performance\clear\curr"
              + "entdata\currentdatum        pid-mask to 'from 8 to 16';
\n(23)"
              + "Modify range of leaf operation\performance\clear\currentdata\c"
              + "urrentdatum        pid-length to 'from 62 to 128';
\n(24)Modif"
              + "y length of leaf operation\performance\monitor\start-up       "
              + " ask\checkpoints\checkpoint        pid to 'from 62 to 128';
\n"
              + "(25)Modify range of leaf operation\performance\monitor\start-u"
              + "p        ask\checkpoints\checkpoint        pid-length to 'from"
              + " 62 to 128';"
                ;
  }
  revision 2015-12-09 {
    description '(1)Modify description of leaf configuration\performance\statis'
              + 'tics\perf-masks\perf-mask\perfcode;'+"\n"
              + '(2)Modify description of leaf configuration\performance\statis'
              + 'tics\perf-masks\perf-mask\cycle;'+"\n"
              + '(3)Modify description of leaf configuration\performance\statis'
              + 'tics\perf-masks\perf-mask\tpid-class;'+"\n"
              + '(4)Modify description of leaf configuration\performance\statis'
              + 'tics\perf-suppresses\perf-suppress\tpid-length;'+"\n"
              + '(5)Add description of leaf configuration\performance\statistic'
              + 's\perf-suppresses\perf-suppress\state;'+"\n"
              + '(6)Add description of container configuration\performance\thre'
              + 'shold\perf-thresholds\fifteen-mins;'+"\n"
              + '(7)Add description of container configuration\performance\thre'
              + 'shold\perf-thresholds\fifteen-mins\digital;'+"\n"
              + '(8)Add description of leaf configuration\performance\threshold'
              + '\perf-thresholds\fifteen-mins\digital\tpid-length;'+"\n"
              + '(9)Add description of container configuration\performance\thre'
              + 'shold\perf-thresholds\fifteen-mins\analog;'+"\n"
              + '(10)Add description of leaf configuration\performance\threshol'
              + 'd\perf-thresholds\fifteen-mins\analog\tpid-length;'+"\n"
              + '(11)Add description of container configuration\performance\thr'
              + 'eshold\perf-thresholds\twenty-four-hours;'+"\n"
              + '(12)Add description of container configuration\performance\thr'
              + 'eshold\perf-thresholds\twenty-four-hours\digital;'+"\n"
              + '(13)Add description of leaf configuration\performance\threshol'
              + 'd\perf-thresholds\twenty-four-hours\digital\tpid-length;'+"\n"
              + '(14)Modify description of container state\performance\statisti'
              + 'cs;'+"\n"
              + '(15)Modify description of leaf state\performance\statistics\cu'
              + 'rrentdata\fifteen-mins\digitaldata\digitaldatum\tpid-class;'+"\n"
              + '(16)Modify description of leaf state\performance\statistics\cu'
              + 'rrentdata\fifteen-mins\digitaldata\digitaldatum\tpid-length;'+"\n"
              + '(17)Modify description of leaf state\performance\statistics\cu'
              + 'rrentdata\fifteen-mins\analogdata\analogdatum\tpid-class;'+"\n"
              + '(18)Modify description of leaf state\performance\statistics\cu'
              + 'rrentdata\fifteen-mins\analogdata\analogdatum\tpid-length;'+"\n"
              + '(19)Modify description of leaf state\performance\statistics\cu'
              + 'rrentdata\twenty-four-hours\digitaldata\digitaldatum\tpid-clas'
              + 's;'+"\n"
              + '(20)Modify description of leaf state\performance\statistics\cu'
              + 'rrentdata\twenty-four-hours\digitaldata\digitaldatum\tpid-leng'
              + 'th;'+"\n"
              + '(21)Modify description of leaf state\performance\statistics\cu'
              + 'rrentdata\twenty-four-hours\analogdata\analogdatum\tpid-class;'
              + ''+"\n"
              + '(22)Modify description of leaf state\performance\statistics\cu'
              + 'rrentdata\twenty-four-hours\analogdata\analogdatum\tpid-length'
              + ';'+"\n"
              + '(23)Modify description of leaf state\performance\statistics\hi'
              + 'storydata\fifteen-mins\digitaldata\digitaldatum\tpid-class;'+"\n"
              + '(24)Modify description of leaf state\performance\statistics\hi'
              + 'storydata\fifteen-mins\digitaldata\digitaldatum\tpid-length;'+"\n"
              + '(25)Modify description of leaf state\performance\statistics\hi'
              + 'storydata\fifteen-mins\digitaldata\digitaldatum\inner-index;'+"\n"
              + '(26)Modify description of container state\performance\statisti'
              + 'cs\historydata\fifteen-mins\analogdata;'+"\n"
              + '(27)Modify description of leaf state\performance\statistics\hi'
              + 'storydata\fifteen-mins\analogdata\analogdatum\tpid-class;'+"\n"
              + '(28)Modify description of leaf state\performance\statistics\hi'
              + 'storydata\fifteen-mins\analogdata\analogdatum\tpid-length;'+"\n"
              + '(29)Modify description of leaf state\performance\statistics\hi'
              + 'storydata\fifteen-mins\analogdata\analogdatum\inner-index;'+"\n"
              + '(30)Modify description of container state\performance\statisti'
              + 'cs\historydata\twenty-four-hours\digitaldata;'+"\n"
              + '(31)Modify description of leaf state\performance\statistics\hi'
              + 'storydata\twenty-four-hours\digitaldata\digitaldatum\tpid-clas'
              + 's;'+"\n"
              + '(32)Modify description of leaf state\performance\statistics\hi'
              + 'storydata\twenty-four-hours\digitaldata\digitaldatum\tpid-leng'
              + 'th;'+"\n"
              + '(33)Modify description of leaf state\performance\statistics\hi'
              + 'storydata\twenty-four-hours\digitaldata\digitaldatum\inner-ind'
              + 'ex;'+"\n"
              + '(34)Modify description of container state\performance\statisti'
              + 'cs\historydata\twenty-four-hours\analogdata;'+"\n"
              + '(35)Modify description of leaf state\performance\statistics\hi'
              + 'storydata\twenty-four-hours\analogdata\analogdatum\tpid-class;'
              + ''+"\n"
              + '(36)Modify description of leaf state\performance\statistics\hi'
              + 'storydata\twenty-four-hours\analogdata\analogdatum\tpid-length'
              + ';'+"\n"
              + '(37)Modify description of leaf state\performance\statistics\hi'
              + 'storydata\twenty-four-hours\analogdata\analogdatum\inner-index'
              + ';'+"\n"
              + '(38)Modify description of leaf state\performance\threshold\def'
              + 'ault-thresholds\analog-default-threshold\tpid-length;'+"\n"
              + '(39)Modify description of leaf operation\performance\clear\cur'
              + 'rentdata\currentdatum\tpid-class;'+"\n"
              + '(40)Modify description of leaf operation\performance\clear\cur'
              + 'rentdata\currentdatum\tpid-length;'
                ;
  }
  revision 2015-08-12 {
    description '(1)Add leaf state\performance\statistics\historydata\fifteen-m'
              + 'ins\analogdata\analogdatum\max-value-time'
                ;
  }
  revision 2014-11-05 {
    description '(1) In order to support the replace configuration, the list no'
              + 'de "configuration\performance\threshold\perf-thresholds\perf-t'
              + 'hreshold" is split into three lists: "configuration\performanc'
              + 'e\threshold\perf-thresholds\fifteen-mins\digital\perf-threshol'
              + 'd","configuration\performance\threshold\perf-thresholds\fiftee'
              + 'n-mins\analog\perf-threshold","configuration\performance\thres'
              + 'hold\perf-thresholds\twenty-four-hours\digital\perf-threshold"'
              + '.'+"\n"
              + '(2) Modify node "configuration\performance\threshold\default-t'
              + 'hreholds\default-threshold\low","configuration\performance\thr'
              + 'eshold\default-threholds\default-threshold\warn-low","configur'
              + 'ation\performance\threshold\default-threholds\default-threshol'
              + 'd\high","configuration\performance\threshold\default-threholds'
              + '\default-threshold\warn-high" to non-mandatory.'
                ;
  }
  revision 2014-09-09 {
    description "(1) Modify leaf configuration\performance\statistics\perf-mask"
              + "s\perf-mask\cycle enumeration 'all' to 3"
                ;
  }
  revision 2014-06-16 {
    description '(1)Add key leaf state\performance\statistics\historydata\fifte'
              + 'en-mins\digitaldata\digitaldatum\inner-index'+"\n"
              + '(2)Add key leaf state\performance\statistics\historydata\fifte'
              + 'en-mins\analogdata\analogdatum\inner-index'+"\n"
              + '(3)Add key leaf state\performance\statistics\historydata\twent'
              + 'y-four-hours\digitaldata\digitaldatum\inner-index'+"\n"
              + '(4)Add key leaf state\performance\statistics\historydata\twent'
              + 'y-four-hours\analogdata\analogdatum\inner-index'
                ;
  }
  revision 2014-05-30 {
    description "(1) Add 'tpid-length' to 'Selects' in 'list' node of state\per"
              + "formance\statistics\currentdata\fifteen-mins\digitaldata\digit"
              + "aldatum
\n(2) Add 'tpid-length' to 'Selects' in 'list' node of"
              + " state\performance\statistics\currentdata\fifteen-mins\analogd"
              + "ata\analogdatum
\n(3) Add 'tpid-length' to 'Selects' in 'list'"
              + " node of state\performance\statistics\currentdata        wenty"
              + "-four-hours\digitaldata\digitaldatum
\n(4) Add 'tpid-length' t"
              + "o 'Selects' in 'list' node of state\performance\statistics\cur"
              + "rentdata        wenty-four-hours\analogdata\analogdatum
\n(5) "
              + "Add 'tpid-length' to 'Selects' in 'list' node of state\perform"
              + "ance\statistics\historydata\fifteen-mins\digitaldata\digitalda"
              + "tum
\n(6) Add 'tpid-length' to 'Selects' in 'list' node of sta"
              + "te\performance\statistics\historydata\fifteen-mins\analogdata\a"
              + "nalogdatum
\n(7) Add 'tpid-length' to 'Selects' in 'list' node"
              + " of state\performance\statistics\historydata        wenty-four"
              + "-hours\digitaldata\digitaldatum
\n(8) Add 'tpid-length' to 'Se"
              + "lects' in 'list' node of state\performance\statistics\historyd"
              + "ata        wenty-four-hours\analogdata\analogdatum
\n(9) Add '"
              + "Selects' in 'list' node of state\performance        hreshold\d"
              + "efault-thresholds\analog-default-threshold
\n(10) Add leaf sta"
              + "te\performance        hreshold\default-thresholds\analog-defau"
              + "lt-threshold        pid-length
\n(11) Modify range of 'length'"
              + " of leaf state\performance        hreshold\default-thresholds\a"
              + "nalog-default-threshold        pid to 'from 1 to 128'
\n(12) M"
              + "odify range of 'length' of leaf operation\performance\monitor\s"
              + "tart-up        ask\checkpoints\checkpoint        pid to 'from "
              + "1 to 128'
\n(13) Modify leaf operation\performance\monitor\sta"
              + "rt-up        ask\checkpoints\checkpoint        pid-length to '"
              + "from 1 to 128'
\n(14)Modify leaf configuration\performance    "
              + "    hreshold\perf-thresholds\perf-threshold        pid-lengh t"
              + "o tpid-length
\n(15)Modify leaf state\performance\statistics\c"
              + "urrentdata\fifteen-mins\digitaldata\digitaldatum        pid-le"
              + "ngh to tpid-length
\n(16)Modify leaf state\performance\statist"
              + "ics\currentdata\fifteen-mins\analogdata\analogdatum        pid"
              + "-lengh to tpid-length
\n(17)Modify leaf state\performance\stat"
              + "istics\currentdata        wenty-four-hours\digitaldata\digital"
              + "datum        pid-lengh to tpid-length
\n(18)Modify leaf state\p"
              + "erformance\statistics\currentdata        wenty-four-hours\anal"
              + "ogdata\analogdatum        pid-lengh to tpid-length
\n(19)Modif"
              + "y leaf state\performance\statistics\historydata\fifteen-mins\d"
              + "igitaldata\digitaldatum        pid-lengh to tpid-length
\n(20)"
              + "Modify leaf state\performance\statistics\historydata\fifteen-m"
              + "ins\analogdata\analogdatum        pid-lengh to tpid-length
\n("
              + "21)Modify leaf state\performance\statistics\historydata       "
              + " wenty-four-hours\digitaldata\digitaldatum        pid-lengh to"
              + " tpid-length
\n(22)Modify leaf state\performance\statistics\hi"
              + "storydata        wenty-four-hours\analogdata\analogdatum      "
              + "  pid-lengh to tpid-length
\n(23) Delete operation\performance"
              + "\clear\currentdata\currentdatum\cycle type 'all'"
                ;
  }
  revision 2014-05-20 {
    description "(1)Add 'tpid-length' to all 'Selects' in 'list' node of state\p"
              + "erformance\monitor\perfdata\perfdatum"
                ;
  }
  revision 2014-04-29 {
    description "(1) Modify range of 'length' of leaf operation\performance\cle"
              + "ar\currentdata\currentdatum        pid-matcher to 'from 1 to 1"
              + "28'
\n(2)Modify range of 'length' of leaf operation\performanc"
              + "e\clear\currentdata\currentdatum        pid-mask to 'from 1 to"
              + " 16'
\n(3)Add leaf operation\performance\clear\currentdata\cur"
              + "rentdatum        pid-length"
                ;
  }
  revision 2014-01-20 {
    description "(1)Add key leaf configuration\performance\statistics\perf-mask"
              + "s\perf-mask        pid-class
\n(2)Modify range of 'length' of "
              + "leaf configuration\performance\statistics\perf-suppresses\perf"
              + "-suppress        pid to 'from 62 to 128'
\n(3)Add leaf configu"
              + "ration\performance\statistics\perf-suppresses\perf-suppress   "
              + "     pid-length
\n(4)Add leaf configuration\performance\statis"
              + "tics\perf-suppresses\perf-suppress\state
\n(5)Add key leaf sta"
              + "te\performance\statistics\currentdata\fifteen-mins\digitaldata"
              + "\digitaldatum        pid-class
\n(6)Modify range of 'length' o"
              + "f leaf state\performance\statistics\currentdata\fifteen-mins\d"
              + "igitaldata\digitaldatum        pid to 'from 1 to 128'
\n(7)Mod"
              + "ify range of 'length' of leaf state\performance\statistics\cur"
              + "rentdata\fifteen-mins\digitaldata\digitaldatum        pid-matc"
              + "her to 'from 1 to 128'
\n(8)Modify range of 'length' of leaf s"
              + "tate\performance\statistics\currentdata\fifteen-mins\digitalda"
              + "ta\digitaldatum        pid-mask to 'from 1 to 16'
\n(9)Add lea"
              + "f state\performance\statistics\currentdata\fifteen-mins\digita"
              + "ldata\digitaldatum        pid-length
\n(10)Add key leaf state\p"
              + "erformance\statistics\currentdata\fifteen-mins\analogdata\anal"
              + "ogdatum        pid-class
\n(11)Modify range of 'length' of lea"
              + "f state\performance\statistics\currentdata\fifteen-mins\analog"
              + "data\analogdatum        pid to 'from 1 to 128'
\n(12)Modify ra"
              + "nge of 'length' of leaf state\performance\statistics\currentda"
              + "ta\fifteen-mins\analogdata\analogdatum        pid-matcher to '"
              + "from 1 to 128'
\n(13)Modify range of 'length' of leaf state\pe"
              + "rformance\statistics\currentdata\fifteen-mins\analogdata\analo"
              + "gdatum        pid-mask to 'from 1 to 16'
\n(14)Add leaf state\p"
              + "erformance\statistics\currentdata\fifteen-mins\analogdata\anal"
              + "ogdatum        pid-length
\n(15)Add key leaf state\performance"
              + "\statistics\currentdata        wenty-four-hours\digitaldata\di"
              + "gitaldatum        pid-class
\n(16)Modify range of 'length' of "
              + "leaf state\performance\statistics\currentdata        wenty-fou"
              + "r-hours\digitaldata\digitaldatum        pid to 'from 1 to 128'"
              + "
\n(17)Modify range of 'length' of leaf state\performance\stat"
              + "istics\currentdata        wenty-four-hours\digitaldata\digital"
              + "datum        pid-matcher to 'from 1 to 128'
\n(18)Modify range"
              + " of 'length' of leaf state\performance\statistics\currentdata "
              + "       wenty-four-hours\digitaldata\digitaldatum        pid-ma"
              + "sk to 'from 1 to 16'
\n(19)Add leaf state\performance\statisti"
              + "cs\currentdata        wenty-four-hours\digitaldata\digitaldatu"
              + "m        pid-length
\n(20)Add key leaf state\performance\stati"
              + "stics\currentdata        wenty-four-hours\analogdata\analogdat"
              + "um        pid-class
\n(21)Modify range of 'length' of leaf sta"
              + "te\performance\statistics\currentdata        wenty-four-hours\a"
              + "nalogdata\analogdatum        pid to 'from 1 to 128'
\n(22)Modi"
              + "fy range of 'length' of leaf state\performance\statistics\curr"
              + "entdata        wenty-four-hours\analogdata\analogdatum        "
              + "pid-matcher to 'from 1 to 128'
\n(23)Modify range of 'length' "
              + "of leaf state\performance\statistics\currentdata        wenty-"
              + "four-hours\analogdata\analogdatum        pid-mask to 'from 1 t"
              + "o 16'
\n(24)Add leaf state\performance\statistics\currentdata "
              + "       wenty-four-hours\analogdata\analogdatum        pid-leng"
              + "th
\n(25)Add key leaf state\performance\statistics\historydata"
              + "\fifteen-mins\digitaldata\digitaldatum        pid-class
\n(26)"
              + "Modify range of 'length' of leaf state\performance\statistics\h"
              + "istorydata\fifteen-mins\digitaldata\digitaldatum        pid to"
              + " 'from 1 to 128'
\n(27)Modify range of 'length' of leaf state\p"
              + "erformance\statistics\historydata\fifteen-mins\digitaldata\dig"
              + "italdatum        pid-matcher to 'from 1 to 128'
\n(28)Modify r"
              + "ange of 'length' of leaf state\performance\statistics\historyd"
              + "ata\fifteen-mins\digitaldata\digitaldatum        pid-mask to '"
              + "from 1 to 16'
\n(29)Add leaf state\performance\statistics\hist"
              + "orydata\fifteen-mins\digitaldata\digitaldatum        pid-lengt"
              + "h
\n(30)Add key leaf state\performance\statistics\historydata\f"
              + "ifteen-mins\analogdata\analogdatum        pid-class
\n(31)Modi"
              + "fy range of 'length' of leaf state\performance\statistics\hist"
              + "orydata\fifteen-mins\analogdata\analogdatum        pid to 'fro"
              + "m 1 to 128'
\n(32)Modify range of 'length' of leaf state\perfo"
              + "rmance\statistics\historydata\fifteen-mins\analogdata\analogda"
              + "tum        pid-matcher to 'from 1 to 128'
\n(33)Modify range o"
              + "f 'length' of leaf state\performance\statistics\historydata\fi"
              + "fteen-mins\analogdata\analogdatum        pid-mask to 'from 1 t"
              + "o 16'
\n(34)Add leaf state\performance\statistics\historydata\f"
              + "ifteen-mins\analogdata\analogdatum        pid-length
\n(35)Add"
              + " key leaf state\performance\statistics\historydata        went"
              + "y-four-hours\digitaldata\digitaldatum        pid-class
\n(36)M"
              + "odify range of 'length' of leaf state\performance\statistics\h"
              + "istorydata        wenty-four-hours\digitaldata\digitaldatum   "
              + "     pid to 'from 1 to 128'
\n(37)Modify range of 'length' of "
              + "leaf state\performance\statistics\historydata        wenty-fou"
              + "r-hours\digitaldata\digitaldatum        pid-matcher to 'from 1"
              + " to 128'
\n(38)Modify range of 'length' of leaf state\performa"
              + "nce\statistics\historydata        wenty-four-hours\digitaldata"
              + "\digitaldatum        pid-mask to 'from 1 to 16'
\n(39)Add leaf"
              + " state\performance\statistics\historydata        wenty-four-ho"
              + "urs\digitaldata\digitaldatum        pid-length
\n(40)Add key l"
              + "eaf state\performance\statistics\historydata        wenty-four"
              + "-hours\analogdata\analogdatum        pid-class
\n(41)Modify ra"
              + "nge of 'length' of leaf state\performance\statistics\historyda"
              + "ta        wenty-four-hours\analogdata\analogdatum        pid t"
              + "o 'from 1 to 128'
\n(42)Modify range of 'length' of leaf state"
              + "\performance\statistics\historydata        wenty-four-hours\an"
              + "alogdata\analogdatum        pid-matcher to 'from 1 to 128'
\n("
              + "43)Modify range of 'length' of leaf state\performance\statisti"
              + "cs\historydata        wenty-four-hours\analogdata\analogdatum "
              + "       pid-mask to 'from 1 to 16'
\n(44)Add leaf state\perform"
              + "ance\statistics\historydata        wenty-four-hours\analogdata"
              + "\analogdatum        pid-length
\n(45)Modify range of 'length' "
              + "of leaf state\performance\monitor\perfdata\perfdatum        pi"
              + "d to 'from 1 to 128'
\n(46)Add leaf state\performance\monitor\p"
              + "erfdata\perfdatum        pid-length
\n(47)Add key leaf operati"
              + "on\performance\clear\currentdata\currentdatum        pid-class"
              + "
\n(48)Modify range of 'length' of leaf state\performance\moni"
              + "tor\perfdata\perfdatum        pid to 'from 62 to 128'
\n(49)Ad"
              + "d leaf operation\performance\monitor\start-up        ask\check"
              + "points\checkpoint        pid-length"
                ;
  }
  revision 2013-12-31 {
    description "(1) Add 'configuration \ performance \ perf-masks \ perf-mask'"
              + " leaf 'tpid-length'
\n(2) Modify Type Range of 'configuration "
              + "\ performance \ perf-masks \ perf-mask ' leaf 'tpid-matcher' t"
              + "o 'from 62 to 128'
\n(3) Delete 'configuration \ performance \ "
              + "perf-suppresses \ perf-suppress'  leaf 'cycle' type 'all'
\n(4"
              + ") Modify Type Range of 'configuration \ performance \ perf-thr"
              + "esholds \ perf-threshold' leaf 'tpid' to 'from 62 to 128'
\n(5"
              + ") Add 'configuration \ performance \ perf-thresholds \ perf-th"
              + "reshold' leaf 'tpid-length'"
                ;
  }
  revision 2013-10-15 {
    description "(1) Leaf node checkpoint-type, perfcode is limited to: 1-65535"
              + ". (2) Real-time performance monitoring of the adoption cycle i"
              + "s limited to: 5-900. (3) Revise 'state\performance\monitor\per"
              + "fdata\perfdatum\perf-type' definition as enumeration. (4) Add "
              + "default value for 'operation\performance\monitor\start-up     "
              + "   ask\auto-report' as false."
                ;
  }
  revision 2013-09-30 {
    description "Current and historical performance modeling of an explicit dis"
              + "tinction between 15 minutes and 24 hours queries. Involving st"
              + "ate node structural changes. 'configuration \ performance \ de"
              + "fault-threholds \ templateId' name changed to template-id."
                ;
  }
  revision 2013-09-24 {
    description 'Add perf-type for realtime query operation.'
                ;
  }
  revision 2013-08-22 {
    description 'The real-time performance monitoring tasks from the configurat'
              + 'ion command to action command.'
                ;
  }
  revision 2013-08-16 {
    description 'Real-time performance statistics add a query that indicates wh'
              + 'ether the value of the first sample query. Namely: state \ per'
              + 'formance \ statistics \ monitor \ perfdata \ perfdatum \ selet'
              + ' \ first \ first-cycle.'
                ;
  }
  revision 2013-08-13 {
    description "(1) Remove the leaf node:
\n'stateperformance hresholddefault-"
              + "thresholdsanalog-default-threshold pid-matcher'.
\n(2) The nod"
              + "e ' state  performance  monitor  perfdata  perfdatum  cycle-en"
              + "d-time' type is changed to ncd: datatime.
\n(3) In the followi"
              + "ng 'list' node, add a layer of 'container' node:
\n     - conf"
              + "igurationperformancestatisticsperf-mask
\n     - configuration"
              + "performancestatisticsperf-suppress
\n     - configurationperfo"
              + "rmance hresholdperf-threshold
\n     - configurationperformanc"
              + "e hresholddefault-threshold"
                ;
  }
  revision 2013-04-22 {
    description 'Initial version.'
                ;
  }
  feature flow-statistics ;
  container configuration {
    description 'Configuration model info.'
                ;
    container performance {
      description 'The configuration info about performance.'
                  ;
      container statistics {
        description 'The configuration info about statistics.'
                    ;
        container perf-masks {
          description 'The rules for performance mask.'
                      ;
          list perf-mask {
            description 'The rules for performance mask.'
                        ;
            key 'checkpoint-type tpid-matcher perfcode cycle tpid-mask tpid-cla'
              + 'ss'
                ;
            leaf checkpoint-type {
              description 'The type of tpid. 0xFFFF for any type.'
                          ;
              type uint16 {
                range 1..65535 ;
              }
            }
            leaf tpid-matcher {
              description 'The matcher about tpid, the format is the same to tp'
                        + 'id. It always to be used with tpid-mask, they can be'
                        + ' indicated a group of tpids.'
                          ;
              type binary {
                length 62..128 ;
              }
            }
            leaf perfcode {
              description 'Performance code, one tpid may have serval performan'
                        + 'ce codes. 0xFFFF for any code.'
                          ;
              type uint16 {
                range 1..65535 ;
              }
            }
            leaf cycle {
              description 'The performance cycle. 15(5) minutes, 24 hours or al'
                        + 'l.'
                          ;
              type enumeration {
                enum fifteen-minutes {
                  value 1 ;
                  description 'Minute cycle. The actual cycle value depends on '
                            + 'the minute-cycle configuration.'
                              ;
                }
                enum twenty-four-hours {
                  value 2 ;
                }
                enum all {
                  value 3 ;
                }
              }
            }
            leaf tpid-mask {
              description 'The mask about tpid-matcher, it indicates which posi'
                        + 'tion of tpid-matcher is available.'
                          ;
              type binary {
                length 8..16 ;
              }
            }
            leaf tpid-length {
              description 'The length of tpid.'
                          ;
              type uint8 {
                range 62..128 ;
              }
            }
            leaf tpid-class {
              description 'The class of TPID.'
                          ;
              type enumeration {
                enum board {
                  value 1 ;
                }
                enum CPU {
                  value 2 ;
                }
                enum system {
                  value 3 ;
                }
                enum all {
                  value 255 ;
                }
              }
            }
          }
        }
        container perf-suppresses {
          description 'The function about performance suppress.'
                      ;
          list perf-suppress {
            description 'The function about performance suppress.'
                        ;
            key 'checkpoint-type tpid cycle'
                ;
            leaf checkpoint-type {
              description 'The type of tpid. Only for any tpid type. The value '
                        + 'is always 0xFFFF.'
                          ;
              type uint16 {
                range 1..65535 ;
              }
            }
            leaf tpid {
              description "Check point id, only every positon's value is 0xFF c"
                        + "an be accepted."
                          ;
              type binary {
                length 62..128 ;
              }
            }
            leaf cycle {
              description 'Statistics cycle.'
                          ;
              type enumeration {
                enum cur15minutes {
                  value 1 ;
                  description 'Current minute cycle. The actual cycle value dep'
                            + 'ends on the minute-cycle configuration.'
                              ;
                }
                enum his15minutes {
                  value 2 ;
                  description 'History minute cycle. The actual cycle value dep'
                            + 'ends on the minute-cycle configuration.'
                              ;
                }
                enum cur24hours {
                  value 3 ;
                }
                enum his24hours {
                  value 4 ;
                }
              }
            }
            leaf tpid-length {
              description 'The length of TPID.'
                          ;
              type uint8 {
                range 62..128 ;
              }
            }
            leaf state {
              description 'Performance suppress state.'
                          ;
              type enumeration {
                enum suppress {
                  value 1 ;
                }
                enum unsuppress {
                  value 2 ;
                }
              }
            }
          }
        }
        container minute-cycle {
          description 'The performance cycle at minute level.'
                      ;
          presence minute-cycle ;
          leaf minute-cycle {
            description 'The performance cycle at minute level. 15 minutes or 5'
                      + ' minutes.'
                        ;
            type enumeration {
              enum fifteen-minutes {
                value 1 ;
              }
              enum five-minutes {
                value 2 ;
              }
            }
            default fifteen-minutes ;
          }
          ncd:revise-date 2018-12-12 ;
        }
        container flow {
          if-feature flow-statistics ;
          description 'Flow statistics.'
                      ;
          presence flow ;
          leaf phy-frame-octs {
            description 'Preamble octets and gap octets between ethernet frames.'
                        ;
            type enumeration {
              enum include {
                value 1 ;
                description 'Include preamble octets and gap octets between eth'
                          + 'ernet frames.'
                            ;
              }
              enum exclude {
                value 2 ;
                description 'Exclude preamble octets and gap octets between eth'
                          + 'ernet frames.'
                            ;
              }
            }
          }
          ncd:revise-date 2020-08-18 ;
        }
        container alarm-hysteretic-characteristics {
          description 'The performance alarm hysteretic characteristics.'
                      ;
          presence alarm-hysteretic-characteristics ;
          leaf percent-value {
            description 'The performance alarm hysteretic characteristics perce'
                      + 'ntage.'
                        ;
            type uint8 {
              range 0..50 ;
            }
            default 0 ;
          }
          ncd:revise-date 2022-01-18 ;
        }
        container bandwidth-utilization {
          description 'The performance bandwidth utilization.'
                      ;
          leaf statistics-cycle {
            description 'The performance bandwidth utilization statistics cycle.'
                        ;
            type enumeration {
              enum sec30 {
                value 30 ;
              }
              enum sec60 {
                value 60 ;
              }
              enum sec180 {
                value 180 ;
              }
            }
            default sec60 ;
          }
          ncd:revise-date 2022-03-18 ;
        }
      }
      container threshold {
        description 'The configuration info about performance threshold.'
                    ;
        container perf-thresholds {
          description 'Set the threshold info about performance.'
                      ;
          container fifteen-mins {
            description 'Set the threshold info about minute cycle performance.'
                      + ' The actual cycle value depends on the minute-cycle co'
                      + 'nfiguration.'
                        ;
            container digital {
              description 'Set the threshold info about digital performance.'
                          ;
              list perf-threshold {
                description "Set the threshold info about performance. 'checkpo"
                          + "int-type' and 'perfcode' must be specified."
                            ;
                key 'checkpoint-type tpid perfcode'
                    ;
                leaf checkpoint-type {
                  description 'TPID type. Must explicitly specify.'
                              ;
                  type uint16 {
                    range 1..65535 ;
                  }
                }
                leaf tpid {
                  description 'The TPID of performance item code belong. May be'
                            + ' a full 0xFF.'
                              ;
                  type binary {
                    length 62..128 ;
                  }
                }
                leaf perfcode {
                  description 'The performance item code of TPID. Must be confi'
                            + 'gured with a valid value (not 0xFFFF).'
                              ;
                  type uint16 {
                    range 1..65535 ;
                  }
                }
                leaf low {
                  description 'Value for low threshold.'
                              ;
                  type binary {
                    length 10 ;
                  }
                }
                leaf warn-low {
                  description 'Value for warn-low threshold.'
                              ;
                  type binary {
                    length 10 ;
                  }
                }
                leaf high {
                  description 'Value for high threshold.'
                              ;
                  type binary {
                    length 10 ;
                  }
                }
                leaf warn-high {
                  description 'Value for warn-high threshold.'
                              ;
                  type binary {
                    length 10 ;
                  }
                }
                leaf tpid-length {
                  description 'The length of TPID.'
                              ;
                  type uint8 {
                    range 62..128 ;
                  }
                }
              }
            }
            container analog {
              description 'Set the threshold info about analog performance.'
                          ;
              list perf-threshold {
                description "Set the threshold info about performance. 'checkpo"
                          + "int-type' and 'perfcode' must be specified."
                            ;
                key 'checkpoint-type tpid perfcode'
                    ;
                leaf checkpoint-type {
                  description 'TPID type. Must explicitly specify.'
                              ;
                  type uint16 {
                    range 1..65535 ;
                  }
                }
                leaf tpid {
                  description 'The TPID of performance item code belong. May be'
                            + ' a full 0xFF.'
                              ;
                  type binary {
                    length 62..128 ;
                  }
                }
                leaf perfcode {
                  description 'The performance item code of TPID. Must be confi'
                            + 'gured with a valid value (not 0xFFFF).'
                              ;
                  type uint16 {
                    range 1..65535 ;
                  }
                }
                leaf low {
                  description 'Value for low threshold.'
                              ;
                  type binary {
                    length 10 ;
                  }
                }
                leaf warn-low {
                  description 'Value for warn-low threshold.'
                              ;
                  type binary {
                    length 10 ;
                  }
                }
                leaf high {
                  description 'Value for high threshold.'
                              ;
                  type binary {
                    length 10 ;
                  }
                }
                leaf warn-high {
                  description 'Value for warn-high threshold.'
                              ;
                  type binary {
                    length 10 ;
                  }
                }
                leaf tpid-length {
                  description 'The length of TPID.'
                              ;
                  type uint8 {
                    range 62..128 ;
                  }
                }
              }
            }
          }
          container twenty-four-hours {
            description "Set the threshold info about twenty four hours perform"
                      + "ance. 'checkpoint-type' and 'perfcode' must be specifi"
                      + "ed."
                        ;
            container digital {
              description 'Set the threshold info about digital performance.'
                          ;
              list perf-threshold {
                description "Set the threshold info about performance. 'checkpo"
                          + "int-type' and 'perfcode' must be specified."
                            ;
                key 'checkpoint-type tpid perfcode'
                    ;
                leaf checkpoint-type {
                  description 'TPID type. Must explicitly specify.'
                              ;
                  type uint16 {
                    range 1..65535 ;
                  }
                }
                leaf tpid {
                  description 'The TPID of performance item code belong. May be'
                            + ' a full 0xFF.'
                              ;
                  type binary {
                    length 62..128 ;
                  }
                }
                leaf perfcode {
                  description 'The performance item code of TPID. Must be confi'
                            + 'gured with a valid value (not 0xFFFF).'
                              ;
                  type uint16 {
                    range 1..65535 ;
                  }
                }
                leaf low {
                  description 'Value for low threshold.'
                              ;
                  type binary {
                    length 10 ;
                  }
                }
                leaf warn-low {
                  description 'Value for warn-low threshold.'
                              ;
                  type binary {
                    length 10 ;
                  }
                }
                leaf high {
                  description 'Value for high threshold.'
                              ;
                  type binary {
                    length 10 ;
                  }
                }
                leaf warn-high {
                  description 'Value for warn-high threshold.'
                              ;
                  type binary {
                    length 10 ;
                  }
                }
                leaf tpid-length {
                  description 'The length of TPID.'
                              ;
                  type uint8 {
                    range 62..128 ;
                  }
                }
              }
            }
          }
        }
        container default-threholds {
          description 'Set template of default threshold performance item.'
                      ;
          list default-threshold {
            description 'Set template of default threshold for analog performan'
                      + 'ce item.'
                        ;
            key 'template-id perfcode'
                ;
            leaf template-id {
              description 'The template ID. Now is the optical module certifica'
                        + 'tion ID.'
                          ;
              type uint32 ;
            }
            leaf perfcode {
              description 'The code of analog performance item. Must be configu'
                        + 'red with a valid value (not 0xFFFF).'
                          ;
              type uint16 {
                range 1..65535 ;
              }
            }
            leaf low {
              description 'Value for low threshold. All 0xFF is invalid.'
                          ;
              type binary {
                length 10 ;
              }
            }
            leaf warn-low {
              description 'Value for warn-low threshold. All 0xFF is invalid.'
                          ;
              type binary {
                length 10 ;
              }
            }
            leaf high {
              description 'Value for high threshold. All 0xFF is invalid.'
                          ;
              type binary {
                length 10 ;
              }
            }
            leaf warn-high {
              description 'Value for warn-high threshold. All 0xFF is invalid.'
                          ;
              type binary {
                length 10 ;
              }
            }
            leaf minvalue {
              description 'The minimum detectable value. Not use.'
                          ;
              type binary {
                length 10 ;
              }
            }
            leaf maxvalue {
              description 'The maximum detectable value. Not use.'
                          ;
              type binary {
                length 10 ;
              }
            }
          }
        }
      }
    }
  }
  container state {
    config false ;
    description 'State info.'
                ;
    container performance {
      description 'State info about performance.'
                  ;
      container statistics {
        description 'Statistics info about performance.'
                    ;
        container currentdata {
          description 'Statistics info about current data.'
                      ;
          container fifteen-mins {
            description 'Current data for minute cycle. The actual cycle value '
                      + 'depends on the minute-cycle configuration.'
                        ;
            container digitaldata {
              description 'Used to query the current digital performance.'
                          ;
              list zxr10digitaldatum {
                description 'Used to query the current digital performance.'
                            ;
                key 'inner-index checkpoint-type tpid perfcode tpid-class tpid-'
                  + 'length'
                    ;
                leaf inner-index {
                  description 'JID Inner Index.'
                              ;
                  type uint16 ;
                }
                leaf checkpoint-type {
                  description 'TPID type. 0xFFFF indicates that the query all t'
                            + 'ype of check-point.'
                              ;
                  type uint16 {
                    range 1..65535 ;
                  }
                }
                leaf tpid {
                  description 'The tpid of detection point.'
                              ;
                  type binary {
                    length 62..128 ;
                  }
                }
                leaf perfcode {
                  description 'The performance code of this tpid. 0xFFFF indica'
                            + 'tes any performance items.'
                              ;
                  type uint16 {
                    range 1..65535 ;
                  }
                }
                leaf tpid-class {
                  description 'The class of TPID.'
                              ;
                  type enumeration {
                    enum board {
                      value 1 ;
                    }
                    enum CPU {
                      value 2 ;
                    }
                    enum system {
                      value 3 ;
                    }
                    enum all {
                      value 255 ;
                    }
                  }
                }
                leaf tpid-length {
                  description 'The length of TPID.'
                              ;
                  type uint8 {
                    range 62..128 ;
                  }
                }
                leaf tpid-matcher {
                  description 'As a conditions tpid, used with tpid-mask.'
                              ;
                  type binary {
                    length 62..128 ;
                  }
                }
                leaf tpid-mask {
                  description "Mask bit of attribute 'tpid-matcher'. Length is "
                            + "always 8 bytes."
                              ;
                  type binary {
                    length 8..16 ;
                  }
                }
                leaf value {
                  description 'The performance value.'
                              ;
                  type binary {
                    length 10 ;
                  }
                }
                leaf isdoubt {
                  description 'Indicates whether the suspect, if the performanc'
                            + 'e test cycle affect the calculation of the event'
                            + 's occurred, they sign into doubt.'
                              ;
                  type boolean ;
                }
                leaf elapsetime {
                  description 'Elapsed time. From the query performance calcula'
                            + 'tion cycle until the time of the current perform'
                            + 'ance elapsed time.'
                              ;
                  type uint32 ;
                  units second ;
                }
                ncd:select 'checkpoint-type perfcode tpid-class tpid-length tpi'
                         + 'd-matcher tpid-mask'
                           ;
                ncd:revise-date 2015-12-28 ;
              }
              list digitaldatum {
                status obsolete {
                  ncd:revise-date 2015-12-28 ;
                }
                description 'Used to query the current digital performance.'
                            ;
                key 'inner-index checkpoint-type tpid perfcode tpid-class'
                    ;
                leaf inner-index {
                  description 'JID Inner Index.'
                              ;
                  type uint16 ;
                }
                leaf checkpoint-type {
                  description 'TPID type. 0xFFFF indicates that the query all t'
                            + 'ype of check-point.'
                              ;
                  type uint16 {
                    range 1..65535 ;
                  }
                }
                leaf tpid {
                  description 'The tpid of detection point.'
                              ;
                  type binary {
                    length 1..128 ;
                  }
                }
                leaf tpid-matcher {
                  description 'As a conditions tpid, used with tpid-mask.'
                              ;
                  type binary {
                    length 1..128 ;
                  }
                }
                leaf tpid-mask {
                  description "Mask bit of attribute 'tpid-matcher'. Length is "
                            + "always 8 bytes."
                              ;
                  type binary {
                    length 1..16 ;
                  }
                }
                leaf perfcode {
                  description 'The performance code of this tpid. 0xFFFF indica'
                            + 'tes any performance items.'
                              ;
                  type uint16 {
                    range 1..65535 ;
                  }
                }
                leaf value {
                  description 'The performance value.'
                              ;
                  type binary {
                    length 10 ;
                  }
                }
                leaf isdoubt {
                  description 'Indicates whether the suspect, if the performanc'
                            + 'e test cycle affect the calculation of the event'
                            + 's occurred, they sign into doubt.'
                              ;
                  type boolean ;
                }
                leaf elapsetime {
                  description 'Elapsed time. From the query performance calcula'
                            + 'tion cycle until the time of the current perform'
                            + 'ance elapsed time.'
                              ;
                  type uint32 ;
                  units second ;
                }
                leaf tpid-class {
                  description 'The class of TPID.'
                              ;
                  type enumeration {
                    enum board {
                      value 1 ;
                    }
                    enum CPU {
                      value 2 ;
                    }
                    enum system {
                      value 3 ;
                    }
                    enum all {
                      value 255 ;
                    }
                  }
                }
                leaf tpid-length {
                  description 'The length of TPID.'
                              ;
                  type uint8 {
                    range 1..128 ;
                  }
                }
                ncd:select 'checkpoint-type tpid-matcher tpid-mask perfcode tpi'
                         + 'd-class tpid-length'
                           ;
              }
            }
            container analogdata {
              description 'Current data about analog check points.'
                          ;
              list zxr10analogdatum {
                description 'Current data about analog check points.'
                            ;
                key 'inner-index checkpoint-type tpid perfcode tpid-class tpid-'
                  + 'length'
                    ;
                leaf inner-index {
                  description 'JID Inner Index.'
                              ;
                  type uint16 ;
                }
                leaf checkpoint-type {
                  description 'TPID type. 0xFFFF indicates that the query all t'
                            + 'ype of check-point.'
                              ;
                  type uint16 {
                    range 1..65535 ;
                  }
                }
                leaf tpid {
                  description 'The tpid of detection point.'
                              ;
                  type binary {
                    length 62..128 ;
                  }
                }
                leaf perfcode {
                  description 'The performance code of this tpid. 0xFFFF indica'
                            + 'tes any performance items.'
                              ;
                  type uint16 {
                    range 1..65535 ;
                  }
                }
                leaf tpid-class {
                  description 'The class of TPID.'
                              ;
                  type enumeration {
                    enum board {
                      value 1 ;
                    }
                    enum CPU {
                      value 2 ;
                    }
                    enum system {
                      value 3 ;
                    }
                    enum all {
                      value 255 ;
                    }
                  }
                }
                leaf tpid-length {
                  description 'The length of TPID.'
                              ;
                  type uint8 {
                    range 62..128 ;
                  }
                }
                leaf tpid-matcher {
                  description 'As a conditions tpid, used with tpid-mask.'
                              ;
                  type binary {
                    length 62..128 ;
                  }
                }
                leaf tpid-mask {
                  description "Mask bit of attribute 'tpid-matcher'. Length is "
                            + "always 8 bytes."
                              ;
                  type binary {
                    length 8..16 ;
                  }
                }
                leaf value {
                  description 'The performance value.'
                              ;
                  type binary {
                    length 10 ;
                  }
                }
                leaf max-value {
                  description 'So far the maximum.'
                              ;
                  type binary {
                    length 10 ;
                  }
                }
                leaf min-value {
                  description 'So far the minimum value.'
                              ;
                  type binary {
                    length 10 ;
                  }
                }
                leaf avg-value {
                  description 'So far the average value.'
                              ;
                  type binary {
                    length 10 ;
                  }
                }
                leaf isdoubt {
                  description 'Indicates whether the suspect, if the performanc'
                            + 'e test cycle affect the calculation of the event'
                            + 's occurred, they sign into doubt.'
                              ;
                  type boolean ;
                }
                leaf elapsetime {
                  description 'Elapsed time. From the query performance calcula'
                            + 'tion cycle until the time of the current perform'
                            + 'ance elapsed time.'
                              ;
                  type uint32 ;
                  units second ;
                }
                ncd:select 'checkpoint-type perfcode tpid-class tpid-length tpi'
                         + 'd-matcher tpid-mask'
                           ;
                ncd:revise-date 2015-12-28 ;
              }
              list analogdatum {
                status obsolete {
                  ncd:revise-date 2015-12-28 ;
                }
                description 'Current data about analog check points.'
                            ;
                key 'inner-index checkpoint-type tpid perfcode tpid-class'
                    ;
                leaf inner-index {
                  description 'JID Inner Index.'
                              ;
                  type uint16 ;
                }
                leaf checkpoint-type {
                  description 'TPID type. 0xFFFF indicates that the query all t'
                            + 'ype of check-point.'
                              ;
                  type uint16 {
                    range 1..65535 ;
                  }
                }
                leaf tpid {
                  description 'The tpid of detection point.'
                              ;
                  type binary {
                    length 1..128 ;
                  }
                }
                leaf tpid-matcher {
                  description 'As a conditions tpid, used with tpid-mask.'
                              ;
                  type binary {
                    length 1..128 ;
                  }
                }
                leaf tpid-mask {
                  description "Mask bit of attribute 'tpid-matcher'. Length is "
                            + "always 8 bytes."
                              ;
                  type binary {
                    length 1..16 ;
                  }
                }
                leaf perfcode {
                  description 'The performance code of this tpid. 0xFFFF indica'
                            + 'tes any performance items.'
                              ;
                  type uint16 {
                    range 1..65535 ;
                  }
                }
                leaf value {
                  description 'The performance value.'
                              ;
                  type binary {
                    length 10 ;
                  }
                }
                leaf max-value {
                  description 'So far the maximum.'
                              ;
                  type binary {
                    length 10 ;
                  }
                }
                leaf min-value {
                  description 'So far the minimum value.'
                              ;
                  type binary {
                    length 10 ;
                  }
                }
                leaf avg-value {
                  description 'So far the average value.'
                              ;
                  type binary {
                    length 10 ;
                  }
                }
                leaf isdoubt {
                  description 'Indicates whether the suspect, if the performanc'
                            + 'e test cycle affect the calculation of the event'
                            + 's occurred, they sign into doubt.'
                              ;
                  type boolean ;
                }
                leaf elapsetime {
                  description 'Elapsed time. From the query performance calcula'
                            + 'tion cycle until the time of the current perform'
                            + 'ance elapsed time.'
                              ;
                  type uint32 ;
                  units second ;
                }
                leaf tpid-class {
                  description 'The class of TPID.'
                              ;
                  type enumeration {
                    enum board {
                      value 1 ;
                    }
                    enum CPU {
                      value 2 ;
                    }
                    enum system {
                      value 3 ;
                    }
                    enum all {
                      value 255 ;
                    }
                  }
                }
                leaf tpid-length {
                  description 'The length of TPID.'
                              ;
                  type uint8 {
                    range 1..128 ;
                  }
                }
                ncd:select 'checkpoint-type tpid-matcher tpid-mask perfcode tpi'
                         + 'd-class tpid-length'
                           ;
              }
            }
          }
          container twenty-four-hours {
            description 'Current data for twenty four hours.'
                        ;
            container digitaldata {
              description 'Used to query the current digital performance.'
                          ;
              list zxr10digitaldatum {
                description 'Used to query the current digital performance.'
                            ;
                key 'inner-index checkpoint-type tpid perfcode tpid-class tpid-'
                  + 'length'
                    ;
                leaf inner-index {
                  description 'JID Inner Index.'
                              ;
                  type uint16 ;
                }
                leaf checkpoint-type {
                  description 'TPID type. 0xFFFF indicates that the query all t'
                            + 'ype of check-point.'
                              ;
                  type uint16 {
                    range 1..65535 ;
                  }
                }
                leaf tpid {
                  description 'The tpid of detection point.'
                              ;
                  type binary {
                    length 62..128 ;
                  }
                }
                leaf perfcode {
                  description 'The performance code of this tpid. 0xFFFF indica'
                            + 'tes any performance items.'
                              ;
                  type uint16 {
                    range 1..65535 ;
                  }
                }
                leaf tpid-class {
                  description 'The class of TPID.'
                              ;
                  type enumeration {
                    enum board {
                      value 1 ;
                    }
                    enum CPU {
                      value 2 ;
                    }
                    enum system {
                      value 3 ;
                    }
                    enum all {
                      value 255 ;
                    }
                  }
                }
                leaf tpid-length {
                  description 'The length of TPID.'
                              ;
                  type uint8 {
                    range 62..128 ;
                  }
                }
                leaf tpid-matcher {
                  description 'As a conditions tpid, used with tpid-mask.'
                              ;
                  type binary {
                    length 62..128 ;
                  }
                }
                leaf tpid-mask {
                  description "Mask bit of attribute 'tpid-matcher'. Length is "
                            + "always 8 bytes."
                              ;
                  type binary {
                    length 8..16 ;
                  }
                }
                leaf value {
                  description 'The performance value.'
                              ;
                  type binary {
                    length 10 ;
                  }
                }
                leaf isdoubt {
                  description 'Indicates whether the suspect, if the performanc'
                            + 'e test cycle affect the calculation of the event'
                            + 's occurred, they sign into doubt.'
                              ;
                  type boolean ;
                }
                leaf elapsetime {
                  description 'Elapsed time. From the query performance calcula'
                            + 'tion cycle until the time of the current perform'
                            + 'ance elapsed time.'
                              ;
                  type uint32 ;
                  units second ;
                }
                ncd:select 'checkpoint-type perfcode tpid-class tpid-length tpi'
                         + 'd-matcher tpid-mask'
                           ;
                ncd:revise-date 2015-12-28 ;
              }
              list digitaldatum {
                status obsolete {
                  ncd:revise-date 2015-12-28 ;
                }
                description 'Used to query the current digital performance.'
                            ;
                key 'inner-index checkpoint-type tpid perfcode tpid-class'
                    ;
                leaf inner-index {
                  description 'JID Inner Index.'
                              ;
                  type uint16 ;
                }
                leaf checkpoint-type {
                  description 'TPID type. 0xFFFF indicates that the query all t'
                            + 'ype of check-point.'
                              ;
                  type uint16 {
                    range 1..65535 ;
                  }
                }
                leaf tpid {
                  description 'The tpid of detection point.'
                              ;
                  type binary {
                    length 1..128 ;
                  }
                }
                leaf tpid-matcher {
                  description 'As a conditions tpid, used with tpid-mask.'
                              ;
                  type binary {
                    length 1..128 ;
                  }
                }
                leaf tpid-mask {
                  description "Mask bit of attribute 'tpid-matcher'. Length is "
                            + "always 8 bytes."
                              ;
                  type binary {
                    length 1..16 ;
                  }
                }
                leaf perfcode {
                  description 'The performance code of this tpid. 0xFFFF indica'
                            + 'tes any performance items.'
                              ;
                  type uint16 {
                    range 1..65535 ;
                  }
                }
                leaf value {
                  description 'The performance value.'
                              ;
                  type binary {
                    length 10 ;
                  }
                }
                leaf isdoubt {
                  description 'Indicates whether the suspect, if the performanc'
                            + 'e test cycle affect the calculation of the event'
                            + 's occurred, they sign into doubt.'
                              ;
                  type boolean ;
                }
                leaf elapsetime {
                  description 'Elapsed time. From the query performance calcula'
                            + 'tion cycle until the time of the current perform'
                            + 'ance elapsed time.'
                              ;
                  type uint32 ;
                  units second ;
                }
                leaf tpid-class {
                  description 'The class of TPID.'
                              ;
                  type enumeration {
                    enum board {
                      value 1 ;
                    }
                    enum CPU {
                      value 2 ;
                    }
                    enum system {
                      value 3 ;
                    }
                    enum all {
                      value 255 ;
                    }
                  }
                }
                leaf tpid-length {
                  description 'The length of TPID.'
                              ;
                  type uint8 {
                    range 1..128 ;
                  }
                }
                ncd:select 'checkpoint-type tpid-matcher tpid-mask perfcode tpi'
                         + 'd-class tpid-length'
                           ;
              }
            }
            container analogdata {
              description 'Current data about analog check points.'
                          ;
              list zxr10analogdatum {
                description 'Current data about analog check points.'
                            ;
                key 'inner-index checkpoint-type tpid perfcode tpid-class tpid-'
                  + 'length'
                    ;
                leaf inner-index {
                  description 'JID Inner Index.'
                              ;
                  type uint16 ;
                }
                leaf checkpoint-type {
                  description 'TPID type. 0xFFFF indicates that the query all t'
                            + 'ype of check-point.'
                              ;
                  type uint16 {
                    range 1..65535 ;
                  }
                }
                leaf tpid {
                  description 'The tpid of detection point.'
                              ;
                  type binary {
                    length 62..128 ;
                  }
                }
                leaf perfcode {
                  description 'The performance code of this tpid. 0xFFFF indica'
                            + 'tes any performance items.'
                              ;
                  type uint16 {
                    range 1..65535 ;
                  }
                }
                leaf tpid-class {
                  description 'The class of TPID.'
                              ;
                  type enumeration {
                    enum board {
                      value 1 ;
                    }
                    enum CPU {
                      value 2 ;
                    }
                    enum system {
                      value 3 ;
                    }
                    enum all {
                      value 255 ;
                    }
                  }
                }
                leaf tpid-length {
                  description 'The length of TPID.'
                              ;
                  type uint8 {
                    range 62..128 ;
                  }
                }
                leaf tpid-matcher {
                  description 'As a conditions tpid, used with tpid-mask.'
                              ;
                  type binary {
                    length 62..128 ;
                  }
                }
                leaf tpid-mask {
                  description "Mask bit of attribute 'tpid-matcher'. Length is "
                            + "always 8 bytes."
                              ;
                  type binary {
                    length 8..16 ;
                  }
                }
                leaf value {
                  description 'The performance value.'
                              ;
                  type binary {
                    length 10 ;
                  }
                }
                leaf max-value {
                  description 'So far the maximum.'
                              ;
                  type binary {
                    length 10 ;
                  }
                }
                leaf min-value {
                  description 'So far the minimum value.'
                              ;
                  type binary {
                    length 10 ;
                  }
                }
                leaf avg-value {
                  description 'So far the average value.'
                              ;
                  type binary {
                    length 10 ;
                  }
                }
                leaf isdoubt {
                  description 'Indicates whether the suspect, if the performanc'
                            + 'e test cycle affect the calculation of the event'
                            + 's occurred, they sign into doubt.'
                              ;
                  type boolean ;
                }
                leaf elapsetime {
                  description 'Elapsed time. From the query performance calcula'
                            + 'tion cycle until the time of the current perform'
                            + 'ance elapsed time.'
                              ;
                  type uint32 ;
                  units second ;
                }
                ncd:select 'checkpoint-type perfcode tpid-class tpid-length tpi'
                         + 'd-matcher tpid-mask'
                           ;
                ncd:revise-date 2015-12-28 ;
              }
              list analogdatum {
                status obsolete {
                  ncd:revise-date 2015-12-28 ;
                }
                description 'Current data about analog check points.'
                            ;
                key 'inner-index checkpoint-type tpid perfcode tpid-class'
                    ;
                leaf inner-index {
                  description 'JID Inner Index.'
                              ;
                  type uint16 ;
                }
                leaf checkpoint-type {
                  description 'TPID type. 0xFFFF indicates that the query all t'
                            + 'ype of check-point.'
                              ;
                  type uint16 {
                    range 1..65535 ;
                  }
                }
                leaf tpid {
                  description 'The tpid of detection point.'
                              ;
                  type binary {
                    length 1..128 ;
                  }
                }
                leaf tpid-matcher {
                  description 'As a conditions tpid, used with tpid-mask.'
                              ;
                  type binary {
                    length 1..128 ;
                  }
                }
                leaf tpid-mask {
                  description "Mask bit of attribute 'tpid-matcher'. Length is "
                            + "always 8 bytes."
                              ;
                  type binary {
                    length 1..16 ;
                  }
                }
                leaf perfcode {
                  description 'The performance code of this tpid. 0xFFFF indica'
                            + 'tes any performance items.'
                              ;
                  type uint16 {
                    range 1..65535 ;
                  }
                }
                leaf value {
                  description 'The performance value.'
                              ;
                  type binary {
                    length 10 ;
                  }
                }
                leaf max-value {
                  description 'So far the maximum.'
                              ;
                  type binary {
                    length 10 ;
                  }
                }
                leaf min-value {
                  description 'So far the minimum value.'
                              ;
                  type binary {
                    length 10 ;
                  }
                }
                leaf avg-value {
                  description 'So far the average value.'
                              ;
                  type binary {
                    length 10 ;
                  }
                }
                leaf isdoubt {
                  description 'Indicates whether the suspect, if the performanc'
                            + 'e test cycle affect the calculation of the event'
                            + 's occurred, they sign into doubt.'
                              ;
                  type boolean ;
                }
                leaf elapsetime {
                  description 'Elapsed time. From the query performance calcula'
                            + 'tion cycle until the time of the current perform'
                            + 'ance elapsed time.'
                              ;
                  type uint32 ;
                  units second ;
                }
                leaf tpid-class {
                  description 'The class of TPID.'
                              ;
                  type enumeration {
                    enum board {
                      value 1 ;
                    }
                    enum CPU {
                      value 2 ;
                    }
                    enum system {
                      value 3 ;
                    }
                    enum all {
                      value 255 ;
                    }
                  }
                }
                leaf tpid-length {
                  description 'The length of TPID.'
                              ;
                  type uint8 {
                    range 1..128 ;
                  }
                }
                ncd:select 'checkpoint-type tpid-matcher tpid-mask perfcode tpi'
                         + 'd-class tpid-length'
                           ;
              }
            }
          }
        }
        container historydata {
          description 'Statistics info about history data.'
                      ;
          container fifteen-mins {
            description 'History data for minute cycle. The actual cycle value '
                      + 'depends on the minute-cycle configuration.'
                        ;
            container digitaldata {
              description 'History data about digital checkpoints'
                          ;
              list zxr10digitaldatum {
                description 'Used to query the history digital performance.'
                            ;
                key 'checkpoint-type tpid perfcode cycle-end-time tpid-class tp'
                  + 'id-length inner-index'
                    ;
                leaf checkpoint-type {
                  description 'TPID type. 0xFFFF indicates that the query all t'
                            + 'ype of check-point.'
                              ;
                  type uint16 {
                    range 1..65535 ;
                  }
                }
                leaf tpid {
                  description 'The tpid of detection point.'
                              ;
                  type binary {
                    length 62..128 ;
                  }
                }
                leaf perfcode {
                  description 'The performance code of this tpid. 0xFFFF indica'
                            + 'tes any performance items.'
                              ;
                  type uint16 {
                    range 1..65535 ;
                  }
                }
                leaf cycle-end-time {
                  description 'The end of the cycle. UTC.'
                              ;
                  type ncd:datetime ;
                }
                leaf tpid-class {
                  description 'The class of TPID.'
                              ;
                  type enumeration {
                    enum board {
                      value 1 ;
                    }
                    enum CPU {
                      value 2 ;
                    }
                    enum system {
                      value 3 ;
                    }
                    enum all {
                      value 255 ;
                    }
                  }
                }
                leaf tpid-length {
                  description 'The length of TPID.'
                              ;
                  type uint8 {
                    range 62..128 ;
                  }
                }
                leaf inner-index {
                  description 'JID inner index.'
                              ;
                  type uint16 ;
                }
                leaf tpid-matcher {
                  description 'As a conditions tpid, used with tpid-mask.'
                              ;
                  type binary {
                    length 62..128 ;
                  }
                }
                leaf tpid-mask {
                  description "Mask bit of attribute 'tpid-matcher'. Length is "
                            + "always 8 bytes."
                              ;
                  type binary {
                    length 8..16 ;
                  }
                }
                leaf begin-time {
                  description 'Start time for query. UTC. End of the cycle time'
                            + ' within the time period is selected.'
                              ;
                  type ncd:datetime ;
                }
                leaf end-time {
                  description 'End time for query. UTC. End of the cycle time w'
                            + 'ithin the time period is selected.'
                              ;
                  type ncd:datetime ;
                }
                leaf value {
                  description 'The performance value.'
                              ;
                  type binary {
                    length 10 ;
                  }
                }
                leaf isdoubt {
                  description 'Indicates whether the suspect, if the performanc'
                            + 'e test cycle affect the calculation of the event'
                            + 's occurred, they sign into doubt.'
                              ;
                  type boolean ;
                }
                ncd:select 'checkpoint-type perfcode tpid-class tpid-length tpi'
                         + 'd-matcher tpid-mask begin-time end-time'
                           ;
                ncd:revise-date 2015-12-28 ;
              }
              list digitaldatum {
                status obsolete {
                  ncd:revise-date 2015-12-28 ;
                }
                description 'Used to query the history digital performance.'
                            ;
                key 'checkpoint-type tpid perfcode cycle-end-time tpid-class in'
                  + 'ner-index'
                    ;
                leaf checkpoint-type {
                  description 'TPID type. 0xFFFF indicates that the query all t'
                            + 'ype of check-point.'
                              ;
                  type uint16 {
                    range 1..65535 ;
                  }
                }
                leaf tpid {
                  description 'The tpid of detection point.'
                              ;
                  type binary {
                    length 1..128 ;
                  }
                }
                leaf tpid-matcher {
                  description 'As a conditions tpid, used with tpid-mask.'
                              ;
                  type binary {
                    length 1..128 ;
                  }
                }
                leaf tpid-mask {
                  description "Mask bit of attribute 'tpid-matcher'. Length is "
                            + "always 8 bytes."
                              ;
                  type binary {
                    length 1..16 ;
                  }
                }
                leaf perfcode {
                  description 'The performance code of this tpid. 0xFFFF indica'
                            + 'tes any performance items.'
                              ;
                  type uint16 {
                    range 1..65535 ;
                  }
                }
                leaf cycle-end-time {
                  description 'The end of the cycle. UTC.'
                              ;
                  type ncd:datetime ;
                }
                leaf begin-time {
                  description 'Start time for query. UTC. End of the cycle time'
                            + ' within the time period is selected.'
                              ;
                  type ncd:datetime ;
                }
                leaf end-time {
                  description 'End time for query. UTC. End of the cycle time w'
                            + 'ithin the time period is selected.'
                              ;
                  type ncd:datetime ;
                }
                leaf value {
                  description 'The performance value.'
                              ;
                  type binary {
                    length 10 ;
                  }
                }
                leaf isdoubt {
                  description 'Indicates whether the suspect, if the performanc'
                            + 'e test cycle affect the calculation of the event'
                            + 's occurred, they sign into doubt.'
                              ;
                  type boolean ;
                }
                leaf tpid-class {
                  description 'The class of TPID.'
                              ;
                  type enumeration {
                    enum board {
                      value 1 ;
                    }
                    enum CPU {
                      value 2 ;
                    }
                    enum system {
                      value 3 ;
                    }
                    enum all {
                      value 255 ;
                    }
                  }
                }
                leaf tpid-length {
                  description 'The length of TPID.'
                              ;
                  type uint8 {
                    range 1..128 ;
                  }
                }
                leaf inner-index {
                  description 'JID inner index.'
                              ;
                  type uint16 ;
                }
                ncd:select 'checkpoint-type tpid-matcher tpid-mask perfcode beg'
                         + 'in-time end-time tpid-class tpid-length'
                           ;
              }
            }
            container analogdata {
              description 'History data about analog checkpoints.'
                          ;
              list zxr10analogdatum {
                description 'History data about analog check points.'
                            ;
                key 'checkpoint-type tpid perfcode cycle-end-time tpid-class tp'
                  + 'id-length inner-index'
                    ;
                leaf checkpoint-type {
                  description 'TPID type. 0xFFFF indicates that the query all t'
                            + 'ype of check-point.'
                              ;
                  type uint16 {
                    range 1..65535 ;
                  }
                }
                leaf tpid {
                  description 'The tpid of detection point.'
                              ;
                  type binary {
                    length 62..128 ;
                  }
                }
                leaf perfcode {
                  description 'The performance code of this tpid. 0xFFFF indica'
                            + 'tes any performance items.'
                              ;
                  type uint16 {
                    range 1..65535 ;
                  }
                }
                leaf cycle-end-time {
                  description 'The end of the cycle. UTC.'
                              ;
                  type ncd:datetime ;
                }
                leaf tpid-class {
                  description 'The class of TPID.'
                              ;
                  type enumeration {
                    enum board {
                      value 1 ;
                    }
                    enum CPU {
                      value 2 ;
                    }
                    enum system {
                      value 3 ;
                    }
                    enum all {
                      value 255 ;
                    }
                  }
                }
                leaf tpid-length {
                  description 'The length of TPID.'
                              ;
                  type uint8 {
                    range 62..128 ;
                  }
                }
                leaf inner-index {
                  description 'JID inner index.'
                              ;
                  type uint16 ;
                }
                leaf tpid-matcher {
                  description 'As a conditions tpid, used with tpid-mask.'
                              ;
                  type binary {
                    length 62..128 ;
                  }
                }
                leaf tpid-mask {
                  description "Mask bit of attribute 'tpid-matcher'. Length is "
                            + "always 8 bytes."
                              ;
                  type binary {
                    length 8..16 ;
                  }
                }
                leaf begin-time {
                  description 'Start time for query. UTC. End of the cycle time'
                            + ' within the time period is selected.'
                              ;
                  type ncd:datetime ;
                }
                leaf end-time {
                  description 'End time for query. UTC. End of the cycle time w'
                            + 'ithin the time period is selected.'
                              ;
                  type ncd:datetime ;
                }
                leaf value {
                  description 'The performance value.'
                              ;
                  type binary {
                    length 10 ;
                  }
                }
                leaf max-value {
                  description 'The maximum value of this cycle.'
                              ;
                  type binary {
                    length 10 ;
                  }
                }
                leaf min-value {
                  description 'The minimum value of this cycle.'
                              ;
                  type binary {
                    length 10 ;
                  }
                }
                leaf avg-value {
                  description 'The average value of this cycle.'
                              ;
                  type binary {
                    length 10 ;
                  }
                }
                leaf isdoubt {
                  description 'Indicates whether the suspect, if the performanc'
                            + 'e test cycle affect the calculation of the event'
                            + 's occurred, they sign into doubt.'
                              ;
                  type boolean ;
                }
                leaf max-value-time {
                  description 'The time of max value. UTC.'
                              ;
                  type ncd:datetime ;
                }
                ncd:select 'checkpoint-type perfcode tpid-class tpid-length tpi'
                         + 'd-matcher tpid-mask begin-time end-time'
                           ;
                ncd:revise-date 2015-12-28 ;
              }
              list analogdatum {
                status obsolete {
                  ncd:revise-date 2015-12-28 ;
                }
                description 'History data about analog check points.'
                            ;
                key 'checkpoint-type tpid perfcode cycle-end-time tpid-class in'
                  + 'ner-index'
                    ;
                leaf checkpoint-type {
                  description 'TPID type. 0xFFFF indicates that the query all t'
                            + 'ype of check-point.'
                              ;
                  type uint16 {
                    range 1..65535 ;
                  }
                }
                leaf tpid {
                  description 'The tpid of detection point.'
                              ;
                  type binary {
                    length 1..128 ;
                  }
                }
                leaf tpid-matcher {
                  description 'As a conditions tpid, used with tpid-mask.'
                              ;
                  type binary {
                    length 1..128 ;
                  }
                }
                leaf tpid-mask {
                  description "Mask bit of attribute 'tpid-matcher'. Length is "
                            + "always 8 bytes."
                              ;
                  type binary {
                    length 1..16 ;
                  }
                }
                leaf perfcode {
                  description 'The performance code of this tpid. 0xFFFF indica'
                            + 'tes any performance items.'
                              ;
                  type uint16 {
                    range 1..65535 ;
                  }
                }
                leaf cycle-end-time {
                  description 'The end of the cycle. UTC.'
                              ;
                  type ncd:datetime ;
                }
                leaf begin-time {
                  description 'Start time for query. UTC. End of the cycle time'
                            + ' within the time period is selected.'
                              ;
                  type ncd:datetime ;
                }
                leaf end-time {
                  description 'End time for query. UTC. End of the cycle time w'
                            + 'ithin the time period is selected.'
                              ;
                  type ncd:datetime ;
                }
                leaf value {
                  description 'The performance value.'
                              ;
                  type binary {
                    length 10 ;
                  }
                }
                leaf max-value {
                  description 'The maximum value of this cycle.'
                              ;
                  type binary {
                    length 10 ;
                  }
                }
                leaf min-value {
                  description 'The minimum value of this cycle.'
                              ;
                  type binary {
                    length 10 ;
                  }
                }
                leaf avg-value {
                  description 'The average value of this cycle.'
                              ;
                  type binary {
                    length 10 ;
                  }
                }
                leaf isdoubt {
                  description 'Indicates whether the suspect, if the performanc'
                            + 'e test cycle affect the calculation of the event'
                            + 's occurred, they sign into doubt.'
                              ;
                  type boolean ;
                }
                leaf tpid-class {
                  description 'The class of TPID.'
                              ;
                  type enumeration {
                    enum board {
                      value 1 ;
                    }
                    enum CPU {
                      value 2 ;
                    }
                    enum system {
                      value 3 ;
                    }
                    enum all {
                      value 255 ;
                    }
                  }
                }
                leaf tpid-length {
                  description 'The length of TPID.'
                              ;
                  type uint8 {
                    range 1..128 ;
                  }
                }
                leaf inner-index {
                  description 'JID inner index.'
                              ;
                  type uint16 ;
                }
                leaf max-value-time {
                  description 'The time of max value. UTC.'
                              ;
                  type ncd:datetime ;
                  ncd:revise-date 2015-08-12 ;
                }
                ncd:select 'checkpoint-type tpid-matcher tpid-mask perfcode beg'
                         + 'in-time end-time tpid-class tpid-length'
                           ;
              }
            }
          }
          container twenty-four-hours {
            description 'History data for twenty four hours.'
                        ;
            container digitaldata {
              description 'History data about digital checkpoints.'
                          ;
              list zxr10digitaldatum {
                description 'Used to query the history digital performance.'
                            ;
                key 'checkpoint-type tpid perfcode cycle-end-time tpid-class tp'
                  + 'id-length inner-index'
                    ;
                leaf checkpoint-type {
                  description 'TPID type. 0xFFFF indicates that the query all t'
                            + 'ype of check-point.'
                              ;
                  type uint16 {
                    range 1..65535 ;
                  }
                }
                leaf tpid {
                  description 'The tpid of detection point.'
                              ;
                  type binary {
                    length 62..128 ;
                  }
                }
                leaf perfcode {
                  description 'The performance code of this tpid. 0xFFFF indica'
                            + 'tes any performance items.'
                              ;
                  type uint16 {
                    range 1..65535 ;
                  }
                }
                leaf cycle-end-time {
                  description 'The end of the cycle. UTC.'
                              ;
                  type ncd:datetime ;
                }
                leaf tpid-class {
                  description 'The class of TPID.'
                              ;
                  type enumeration {
                    enum board {
                      value 1 ;
                    }
                    enum CPU {
                      value 2 ;
                    }
                    enum system {
                      value 3 ;
                    }
                    enum all {
                      value 255 ;
                    }
                  }
                }
                leaf tpid-length {
                  description 'The length of TPID.'
                              ;
                  type uint8 {
                    range 62..128 ;
                  }
                }
                leaf inner-index {
                  description 'JID inner index.'
                              ;
                  type uint16 ;
                }
                leaf tpid-matcher {
                  description 'As a conditions tpid, used with tpid-mask.'
                              ;
                  type binary {
                    length 62..128 ;
                  }
                }
                leaf tpid-mask {
                  description "Mask bit of attribute 'tpid-matcher'. Length is "
                            + "always 8 bytes."
                              ;
                  type binary {
                    length 8..16 ;
                  }
                }
                leaf begin-time {
                  description 'Start time for query. UTC. End of the cycle time'
                            + ' within the time period is selected.'
                              ;
                  type ncd:datetime ;
                }
                leaf end-time {
                  description 'End time for query. UTC. End of the cycle time w'
                            + 'ithin the time period is selected.'
                              ;
                  type ncd:datetime ;
                }
                leaf value {
                  description 'The performance value.'
                              ;
                  type binary {
                    length 10 ;
                  }
                }
                leaf isdoubt {
                  description 'Indicates whether the suspect, if the performanc'
                            + 'e test cycle affect the calculation of the event'
                            + 's occurred, they sign into doubt.'
                              ;
                  type boolean ;
                }
                ncd:select 'checkpoint-type perfcode tpid-class tpid-length tpi'
                         + 'd-matcher tpid-mask begin-time end-time'
                           ;
                ncd:revise-date 2015-12-28 ;
              }
              list digitaldatum {
                status obsolete {
                  ncd:revise-date 2015-12-28 ;
                }
                description 'Used to query the history digital performance.'
                            ;
                key 'checkpoint-type tpid perfcode cycle-end-time tpid-class in'
                  + 'ner-index'
                    ;
                leaf checkpoint-type {
                  description 'TPID type. 0xFFFF indicates that the query all t'
                            + 'ype of check-point.'
                              ;
                  type uint16 {
                    range 1..65535 ;
                  }
                }
                leaf tpid {
                  description 'The tpid of detection point.'
                              ;
                  type binary {
                    length 1..128 ;
                  }
                }
                leaf tpid-matcher {
                  description 'As a conditions tpid, used with tpid-mask.'
                              ;
                  type binary {
                    length 1..128 ;
                  }
                }
                leaf tpid-mask {
                  description "Mask bit of attribute 'tpid-matcher'. Length is "
                            + "always 8 bytes."
                              ;
                  type binary {
                    length 1..16 ;
                  }
                }
                leaf perfcode {
                  description 'The performance code of this tpid. 0xFFFF indica'
                            + 'tes any performance items.'
                              ;
                  type uint16 {
                    range 1..65535 ;
                  }
                }
                leaf cycle-end-time {
                  description 'The end of the cycle. UTC.'
                              ;
                  type ncd:datetime ;
                }
                leaf begin-time {
                  description 'Start time for query. UTC. End of the cycle time'
                            + ' within the time period is selected.'
                              ;
                  type ncd:datetime ;
                }
                leaf end-time {
                  description 'End time for query. UTC. End of the cycle time w'
                            + 'ithin the time period is selected.'
                              ;
                  type ncd:datetime ;
                }
                leaf value {
                  description 'The performance value.'
                              ;
                  type binary {
                    length 10 ;
                  }
                }
                leaf isdoubt {
                  description 'Indicates whether the suspect, if the performanc'
                            + 'e test cycle affect the calculation of the event'
                            + 's occurred, they sign into doubt.'
                              ;
                  type boolean ;
                }
                leaf tpid-class {
                  description 'The class of TPID.'
                              ;
                  type enumeration {
                    enum board {
                      value 1 ;
                    }
                    enum CPU {
                      value 2 ;
                    }
                    enum system {
                      value 3 ;
                    }
                    enum all {
                      value 255 ;
                    }
                  }
                }
                leaf tpid-length {
                  description 'The length of TPID.'
                              ;
                  type uint8 {
                    range 1..128 ;
                  }
                }
                leaf inner-index {
                  description 'JID inner index.'
                              ;
                  type uint16 ;
                }
                ncd:select 'checkpoint-type tpid-matcher tpid-mask perfcode beg'
                         + 'in-time end-time tpid-class tpid-length'
                           ;
              }
            }
            container analogdata {
              description 'History data about analog checkpoints.'
                          ;
              list zxr10analogdatum {
                description 'History data about analog check points.'
                            ;
                key 'checkpoint-type tpid perfcode cycle-end-time tpid-class tp'
                  + 'id-length inner-index'
                    ;
                leaf checkpoint-type {
                  description 'TPID type. 0xFFFF indicates that the query all t'
                            + 'ype of check-point.'
                              ;
                  type uint16 {
                    range 1..65535 ;
                  }
                }
                leaf tpid {
                  description 'The tpid of detection point.'
                              ;
                  type binary {
                    length 62..128 ;
                  }
                }
                leaf perfcode {
                  description 'The performance code of this tpid. 0xFFFF indica'
                            + 'tes any performance items.'
                              ;
                  type uint16 {
                    range 1..65535 ;
                  }
                }
                leaf cycle-end-time {
                  description 'The end of the cycle. UTC.'
                              ;
                  type ncd:datetime ;
                }
                leaf tpid-class {
                  description 'The class of TPID.'
                              ;
                  type enumeration {
                    enum board {
                      value 1 ;
                    }
                    enum CPU {
                      value 2 ;
                    }
                    enum system {
                      value 3 ;
                    }
                    enum all {
                      value 255 ;
                    }
                  }
                }
                leaf tpid-length {
                  description 'The length of TPID.'
                              ;
                  type uint8 {
                    range 62..128 ;
                  }
                }
                leaf inner-index {
                  description 'JID inner index.'
                              ;
                  type uint16 ;
                }
                leaf tpid-matcher {
                  description 'As a conditions tpid, used with tpid-mask.'
                              ;
                  type binary {
                    length 62..128 ;
                  }
                }
                leaf tpid-mask {
                  description "Mask bit of attribute 'tpid-matcher'. Length is "
                            + "always 8 bytes."
                              ;
                  type binary {
                    length 8..16 ;
                  }
                }
                leaf begin-time {
                  description 'Start time for query. UTC. End of the cycle time'
                            + ' within the time period is selected.'
                              ;
                  type ncd:datetime ;
                }
                leaf end-time {
                  description 'End time for query. UTC. End of the cycle time w'
                            + 'ithin the time period is selected.'
                              ;
                  type ncd:datetime ;
                }
                leaf value {
                  description 'The performance value.'
                              ;
                  type binary {
                    length 10 ;
                  }
                }
                leaf max-value {
                  description 'The maximum value of this cycle.'
                              ;
                  type binary {
                    length 10 ;
                  }
                }
                leaf min-value {
                  description 'The minimum value of this cycle.'
                              ;
                  type binary {
                    length 10 ;
                  }
                }
                leaf avg-value {
                  description 'The average value of this cycle.'
                              ;
                  type binary {
                    length 10 ;
                  }
                }
                leaf isdoubt {
                  description 'Indicates whether the suspect, if the performanc'
                            + 'e test cycle affect the calculation of the event'
                            + 's occurred, they sign into doubt.'
                              ;
                  type boolean ;
                }
                ncd:select 'checkpoint-type perfcode tpid-class tpid-length tpi'
                         + 'd-matcher tpid-mask begin-time end-time'
                           ;
                ncd:revise-date 2015-12-28 ;
              }
              list analogdatum {
                status obsolete {
                  ncd:revise-date 2015-12-28 ;
                }
                description 'History data about analog check points.'
                            ;
                key 'checkpoint-type tpid perfcode cycle-end-time tpid-class in'
                  + 'ner-index'
                    ;
                leaf checkpoint-type {
                  description 'TPID type. 0xFFFF indicates that the query all t'
                            + 'ype of check-point.'
                              ;
                  type uint16 {
                    range 1..65535 ;
                  }
                }
                leaf tpid {
                  description 'The tpid of detection point.'
                              ;
                  type binary {
                    length 1..128 ;
                  }
                }
                leaf tpid-matcher {
                  description 'As a conditions tpid, used with tpid-mask.'
                              ;
                  type binary {
                    length 1..128 ;
                  }
                }
                leaf tpid-mask {
                  description "Mask bit of attribute 'tpid-matcher'. Length is "
                            + "always 8 bytes."
                              ;
                  type binary {
                    length 1..16 ;
                  }
                }
                leaf perfcode {
                  description 'The performance code of this tpid. 0xFFFF indica'
                            + 'tes any performance items.'
                              ;
                  type uint16 {
                    range 1..65535 ;
                  }
                }
                leaf cycle-end-time {
                  description 'The end of the cycle. UTC.'
                              ;
                  type ncd:datetime ;
                }
                leaf begin-time {
                  description 'Start time for query. UTC. End of the cycle time'
                            + ' within the time period is selected.'
                              ;
                  type ncd:datetime ;
                }
                leaf end-time {
                  description 'End time for query. UTC. End of the cycle time w'
                            + 'ithin the time period is selected.'
                              ;
                  type ncd:datetime ;
                }
                leaf value {
                  description 'The performance value.'
                              ;
                  type binary {
                    length 10 ;
                  }
                }
                leaf max-value {
                  description 'The maximum value of this cycle.'
                              ;
                  type binary {
                    length 10 ;
                  }
                }
                leaf min-value {
                  description 'The minimum value of this cycle.'
                              ;
                  type binary {
                    length 10 ;
                  }
                }
                leaf avg-value {
                  description 'The average value of this cycle.'
                              ;
                  type binary {
                    length 10 ;
                  }
                }
                leaf isdoubt {
                  description 'Indicates whether the suspect, if the performanc'
                            + 'e test cycle affect the calculation of the event'
                            + 's occurred, they sign into doubt.'
                              ;
                  type boolean ;
                }
                leaf tpid-class {
                  description 'The class of TPID.'
                              ;
                  type enumeration {
                    enum board {
                      value 1 ;
                    }
                    enum CPU {
                      value 2 ;
                    }
                    enum system {
                      value 3 ;
                    }
                    enum all {
                      value 255 ;
                    }
                  }
                }
                leaf tpid-length {
                  description 'The length of TPID.'
                              ;
                  type uint8 {
                    range 1..128 ;
                  }
                }
                leaf inner-index {
                  description 'JID inner index.'
                              ;
                  type uint16 ;
                }
                ncd:select 'checkpoint-type tpid-matcher tpid-mask perfcode beg'
                         + 'in-time end-time tpid-class tpid-length'
                           ;
              }
            }
          }
        }
      }
      container monitor {
        description 'The state info about real-time monitor.'
                    ;
        container perfdata {
          description 'The collect data about real-time monitor.'
                      ;
          list zxr10perfdatum {
            description 'The performance data of real-time monitor.'
                        ;
            key 'taskid checkpoint-type tpid perfcode cycle-end-time tpid-length'
                ;
            leaf taskid {
              description 'Monitor task ID.'
                          ;
              type uint32 ;
            }
            leaf checkpoint-type {
              description 'TPID type.'
                          ;
              type uint16 {
                range 1..65535 ;
              }
            }
            leaf tpid {
              description 'TPID value.'
                          ;
              type binary {
                length 62..128 ;
              }
            }
            leaf perfcode {
              description 'The performance code of this tpid.'
                          ;
              type uint16 {
                range 1..65535 ;
              }
            }
            leaf cycle-end-time {
              description 'The end time of sampling period. UTC.'
                          ;
              type ncd:datetime ;
            }
            leaf tpid-length {
              description 'The length of tpid.'
                          ;
              type uint8 {
                range 62..128 ;
              }
            }
            leaf cycle {
              description 'Sampling period.'
                          ;
              type uint16 {
                range 5..900 ;
              }
              units second ;
              default 30 ;
            }
            leaf value {
              description 'The performance value of this sampling period. Effec'
                        + 'tive for digital item.'
                          ;
              type binary {
                length 10 ;
              }
            }
            leaf max-value {
              description 'Tthe maximum value of this period. Effective for ana'
                        + 'log item.'
                          ;
              type binary {
                length 10 ;
              }
            }
            leaf min-value {
              description 'Tthe minimum value of this period. Effective for ana'
                        + 'log item.'
                          ;
              type binary {
                length 10 ;
              }
            }
            leaf avg-value {
              description 'Tthe average value of this period. Effective for ana'
                        + 'log item.'
                          ;
              type binary {
                length 10 ;
              }
            }
            leaf isdoubt {
              description 'Performance value is doubtful? If the performance te'
                        + 'st cycle affect the calculation of the events occurr'
                        + 'ed, they sign into doubt.'
                          ;
              type boolean ;
            }
            leaf first-cycle {
              description 'Queries the first sample value.'
                          ;
              type boolean ;
            }
            leaf begin-time {
              description 'Start time for query. UTC. End of the cycle time wit'
                        + 'hin the time period is selected.'
                          ;
              type ncd:datetime ;
            }
            leaf end-time {
              description 'End time for query. UTC. End of the cycle time withi'
                        + 'n the time period is selected.'
                          ;
              type ncd:datetime ;
            }
            leaf perf-type {
              description 'Digital or analog.'
                          ;
              type enumeration {
                enum digital {
                  value 1 ;
                }
                enum analog {
                  value 2 ;
                }
              }
            }
            ncd:select 'taskid checkpoint-type tpid perfcode tpid-length first-'
                     + 'cycle'
                       ;
            ncd:select 'taskid checkpoint-type tpid perfcode tpid-length begin-'
                     + 'time end-time'
                       ;
            ncd:revise-date 2015-12-28 ;
          }
          list perfdatum {
            status obsolete {
              ncd:revise-date 2015-12-28 ;
            }
            description 'The performance data of real-time monitor.'
                        ;
            key 'taskid checkpoint-type tpid perfcode cycle-end-time'
                ;
            leaf taskid {
              description 'Monitor task ID.'
                          ;
              type uint32 ;
            }
            leaf cycle {
              description 'Sampling period.'
                          ;
              type uint16 {
                range 5..900 ;
              }
              units second ;
              default 30 ;
            }
            leaf checkpoint-type {
              description 'TPID type.'
                          ;
              type uint16 {
                range 1..65535 ;
              }
            }
            leaf tpid {
              description 'TPID value.'
                          ;
              type binary {
                length 1..128 ;
              }
            }
            leaf perfcode {
              description 'The performance code of this tpid.'
                          ;
              type uint16 {
                range 1..65535 ;
              }
            }
            leaf cycle-end-time {
              description 'The end time of sampling period. UTC.'
                          ;
              type ncd:datetime ;
            }
            leaf value {
              description 'The performance value of this sampling period. Effec'
                        + 'tive for digital item.'
                          ;
              type binary {
                length 10 ;
              }
            }
            leaf max-value {
              description 'Tthe maximum value of this period. Effective for ana'
                        + 'log item.'
                          ;
              type binary {
                length 10 ;
              }
            }
            leaf min-value {
              description 'Tthe minimum value of this period. Effective for ana'
                        + 'log item.'
                          ;
              type binary {
                length 10 ;
              }
            }
            leaf avg-value {
              description 'Tthe average value of this period. Effective for ana'
                        + 'log item.'
                          ;
              type binary {
                length 10 ;
              }
            }
            leaf isdoubt {
              description 'Performance value is doubtful? If the performance te'
                        + 'st cycle affect the calculation of the events occurr'
                        + 'ed, they sign into doubt.'
                          ;
              type boolean ;
            }
            leaf first-cycle {
              description 'Queries the first sample value.'
                          ;
              type boolean ;
            }
            leaf begin-time {
              description 'Start time for query. UTC. End of the cycle time wit'
                        + 'hin the time period is selected.'
                          ;
              type ncd:datetime ;
            }
            leaf end-time {
              description 'End time for query. UTC. End of the cycle time withi'
                        + 'n the time period is selected.'
                          ;
              type ncd:datetime ;
            }
            leaf perf-type {
              description 'Digital or analog.'
                          ;
              type enumeration {
                enum digital {
                  value 1 ;
                }
                enum analog {
                  value 2 ;
                }
              }
            }
            leaf tpid-length {
              description 'The length of tpid.'
                          ;
              type uint8 {
                range 1..128 ;
              }
            }
            ncd:select 'taskid checkpoint-type tpid perfcode first-cycle tpid-l'
                     + 'ength'
                       ;
            ncd:select 'taskid checkpoint-type tpid perfcode begin-time end-tim'
                     + 'e tpid-length'
                       ;
          }
        }
      }
      container threshold {
        description 'Performance threshold query.'
                    ;
        container default-thresholds {
          description 'Info about default-thresholds.'
                      ;
          list zxr10analog-default-threshold {
            description "(1) Selects:checkpoint-type+tpid+perfcode+tpid-length:"
                      + "
\n    1.1 Specify the slot number included in the tpi"
                      + "d. Now, 'checkpoint-type' and 'perfcode' are 0xFF. 
\n"
                      + "    1.2 Do not specify the conditions that get all. No"
                      + "w, 'checkpoint-type', 'tpid' and 'perfcode' are 0xFF.
"
                      + "\n    1.3 Specify the 'tpid' with the wild card 0xFF.
"
                      + "\n
\n(2) Selects:checkpoint-type+tpid+perfcode+tpid-le"
                      + "ngth+tpid-mask:
\n    In this case, specify the 'tpid'"
                      + " with 'tpid-mask'."
                        ;
            key 'checkpoint-type tpid perfcode tpid-length'
                ;
            leaf checkpoint-type {
              description 'TPID type. 0xFFFF indicates that the query all type '
                        + 'of check-point.'
                          ;
              type uint16 {
                range 1..65535 ;
              }
            }
            leaf tpid {
              description 'TPID value. Full 0xFF match all.'
                          ;
              type binary {
                length 62..128 ;
              }
            }
            leaf perfcode {
              description 'The performance code of this tpid. 0xFFFF indicates '
                        + 'any performance items.'
                          ;
              type uint16 {
                range 1..65535 ;
              }
            }
            leaf tpid-length {
              description 'The length of TPID.'
                          ;
              type uint8 {
                range 62..128 ;
              }
            }
            leaf tpid-mask {
              description "Mask bit of attribute 'tpid'. Length is always 8 to "
                        + "16 bytes."
                          ;
              type binary {
                length 8..16 ;
              }
              ncd:revise-date 2016-11-16 ;
            }
            leaf low {
              description 'Value for default low threshold.'
                          ;
              type binary {
                length 10 ;
              }
            }
            leaf high {
              description 'Value for default high threshold.'
                          ;
              type binary {
                length 10 ;
              }
            }
            leaf warnlow {
              description 'Value for default warn-low threshold.'
                          ;
              type binary {
                length 10 ;
              }
            }
            leaf warnhigh {
              description 'Value for default warn-high threshold.'
                          ;
              type binary {
                length 10 ;
              }
            }
            leaf curlow {
              description 'Value for current low threshold.'
                          ;
              type binary {
                length 10 ;
              }
            }
            leaf curhigh {
              description 'Value for current high threshold.'
                          ;
              type binary {
                length 10 ;
              }
            }
            leaf curwarnlow {
              description 'Value for current warn-low threshold.'
                          ;
              type binary {
                length 10 ;
              }
            }
            leaf curwarnhigh {
              description 'Value for current warn-high threshold.'
                          ;
              type binary {
                length 10 ;
              }
            }
            leaf minvalue {
              description 'The minimum detectable value. Not used.'
                          ;
              type binary {
                length 10 ;
              }
            }
            leaf maxvalue {
              description 'The maximum detectable value. Not used.'
                          ;
              type binary {
                length 10 ;
              }
            }
            ncd:select 'checkpoint-type tpid perfcode tpid-length'
                       ;
            ncd:select 'checkpoint-type tpid perfcode tpid-length tpid-mask'
                       ;
            ncd:revise-date 2015-12-28 ;
          }
          list analog-default-threshold {
            status obsolete {
              ncd:revise-date 2015-12-28 ;
            }
            description "Default threshold of analog performance item. Query co"
                      + "ndition: (1) Slot number. Note: Included in the tpid. "
                      + "Now, 'checkpoint-type' and 'perfcode' are 0xFF. (2) Do"
                      + " not specify the conditions that get all. Now, 'checkp"
                      + "oint-type', 'tpid' and 'perfcode' are 0xFF."
                        ;
            key 'checkpoint-type tpid perfcode'
                ;
            leaf checkpoint-type {
              description 'TPID type. 0xFFFF indicates that the query all type '
                        + 'of check-point.'
                          ;
              type uint16 {
                range 1..65535 ;
              }
            }
            leaf tpid {
              description 'TPID value. Full 0xFF match all.'
                          ;
              type binary {
                length 1..128 ;
              }
            }
            leaf perfcode {
              description 'The performance code of this tpid. 0xFFFF indicates '
                        + 'any performance items.'
                          ;
              type uint16 {
                range 1..65535 ;
              }
            }
            leaf low {
              description 'Value for default low threshold.'
                          ;
              type binary {
                length 10 ;
              }
            }
            leaf high {
              description 'Value for default high threshold.'
                          ;
              type binary {
                length 10 ;
              }
            }
            leaf warnlow {
              description 'Value for default warn-low threshold.'
                          ;
              type binary {
                length 10 ;
              }
            }
            leaf warnhigh {
              description 'Value for default warn-high threshold.'
                          ;
              type binary {
                length 10 ;
              }
            }
            leaf curlow {
              description 'Value for current low threshold.'
                          ;
              type binary {
                length 10 ;
              }
            }
            leaf curhigh {
              description 'Value for current high threshold.'
                          ;
              type binary {
                length 10 ;
              }
            }
            leaf curwarnlow {
              description 'Value for current warn-low threshold.'
                          ;
              type binary {
                length 10 ;
              }
            }
            leaf curwarnhigh {
              description 'Value for current warn-high threshold.'
                          ;
              type binary {
                length 10 ;
              }
            }
            leaf minvalue {
              description 'The minimum detectable value. Not used.'
                          ;
              type binary {
                length 10 ;
              }
            }
            leaf maxvalue {
              description 'The maximum detectable value. Not used.'
                          ;
              type binary {
                length 10 ;
              }
            }
            leaf tpid-length {
              description 'The length of TPID.'
                          ;
              type uint8 {
                range 1..128 ;
              }
            }
            ncd:select 'checkpoint-type tpid perfcode tpid-length'
                       ;
          }
        }
      }
    }
  }
  container operation {
    config false ;
    container performance {
      description 'Performance operation.'
                  ;
      container clear {
        description 'Cleared performance data.'
                    ;
        container currentdata {
          description 'Cleared current performance data.'
                      ;
          list currentdatum {
            description 'Used to clear current performance value.'
                        ;
            key 'cycle checkpoint-type tpid-matcher tpid-mask perfcode tpid-cla'
              + 'ss'
                ;
            leaf cycle {
              description 'Performance cycle.'
                          ;
              type enumeration {
                enum fifteen-minutes {
                  value 1 ;
                  description 'Minute cycle. The actual cycle value depends on '
                            + 'the minute-cycle configuration.'
                              ;
                }
                enum twenty-four-hours {
                  value 2 ;
                }
              }
            }
            leaf checkpoint-type {
              description 'TPID type. 0xFFFF for all.'
                          ;
              type uint16 {
                range 1..65535 ;
              }
            }
            leaf tpid-matcher {
              description 'As a conditions tpid, used with tpid-mask.'
                          ;
              type binary {
                length 62..128 ;
              }
            }
            leaf tpid-mask {
              description "Mask bit of attribute 'tpid-matcher'. Length is alwa"
                        + "ys 8 bytes."
                          ;
              type binary {
                length 8..16 ;
              }
            }
            leaf perfcode {
              description 'The specified performance code. 0xFFFF for all.'
                          ;
              type uint16 {
                range 1..65535 ;
              }
            }
            leaf tpid-class {
              description 'The class of TPID.'
                          ;
              type enumeration {
                enum board {
                  value 1 ;
                }
                enum CPU {
                  value 2 ;
                }
                enum system {
                  value 3 ;
                }
                enum all {
                  value 255 ;
                }
              }
            }
            leaf tpid-length {
              description 'The length of TPID.'
                          ;
              type uint8 {
                range 62..128 ;
              }
            }
          }
        }
      }
      container monitor {
        description 'The real-time performance monitoring task operation.'
                    ;
        container start-up {
          description 'Start (i.e., create or generate) real-time performance m'
                    + 'onitoring tasks.'
                      ;
          list task {
            description 'Real-time monitor task.'
                        ;
            key taskid ;
            leaf taskid {
              description 'Monitor task ID.'
                          ;
              type uint32 ;
            }
            leaf cycle {
              description 'Sampling period.'
                          ;
              type uint16 {
                range 5..900 ;
              }
              units second ;
              default 30 ;
            }
            leaf total-time {
              description 'Total duration of monitoring tasks. When filling 0xF'
                        + 'FFFFFFF that the total duration of uncertainty trigg'
                        + 'ered by the user manually stopped.'
                          ;
              type uint32 ;
              units second ;
            }
            leaf auto-report {
              description 'Whether to automatically reported. Only support fals'
                        + 'e.'
                          ;
              type boolean ;
              default false ;
            }
            container checkpoints {
              description 'Performance Item List.'
                          ;
              list checkpoint {
                description 'The performance code of this tpid.'
                            ;
                min-elements 1 ;
                key 'type tpid perfcode'
                    ;
                leaf type {
                  description 'TPID type.'
                              ;
                  type uint16 ;
                }
                leaf tpid {
                  description 'The tpid specified.'
                              ;
                  type binary {
                    length 62..128 ;
                  }
                }
                leaf perfcode {
                  description 'Performance item code.'
                              ;
                  type uint16 {
                    range 1..65535 ;
                  }
                }
                leaf tpid-length {
                  description 'The length of tpid.'
                              ;
                  type uint8 {
                    range 62..128 ;
                  }
                }
              }
            }
          }
        }
        container stop {
          description 'Stop (i.e., delete or cancel) real-time performance moni'
                    + 'toring tasks.'
                      ;
          list task {
            description 'Real-time monitor tasks.'
                        ;
            key taskid ;
            leaf taskid {
              description 'Monitor task ID. 0xFFFFFFFF indicates that stop all '
                        + 'monitor task.'
                          ;
              type uint32 ;
            }
          }
        }
      }
    }
  }
}
