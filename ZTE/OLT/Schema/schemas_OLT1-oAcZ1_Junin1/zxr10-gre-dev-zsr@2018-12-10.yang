module zxr10-gre-dev-zsr {
  namespace 'http://www.zte.com.cn/zxr10/netconf/schema/rosng/gre-dev-zsr'
            ;
  prefix gre-dev-zsr ;
  yang-version 1 ;
  import zxr10-gre {
    prefix gre ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The GRE tunnel netconf module supports route ZSRv2 and PC(MSE).'
              ;
  revision 2018-12-10 {
    description 'Remove "multipoint" from deviation @gre:mode.'
                ;
  }
  revision 2015-07-08 {
    description 'GRE model with zsrv2'
                ;
  }
  deviation /gre:configuration/gre:gre/gre:gre-tunnels/gre:gre-tunnel/gre:mode {
    description 'GRE tunnel mode support mgre'
                ;
    deviate replace {
      type enumeration {
        enum ip {
          value 1 ;
          description 'GRE over IP'
                      ;
        }
        enum ipv6 {
          value 6 ;
          description 'GRE over IPv6'
                      ;
        }
        enum ds-lite-static {
          value 9 ;
          description 'Static dual stack lite tunnel'
                      ;
        }
        enum ds-lite-dynamic {
          value 10 ;
          description 'Dynamic dual stack lite tunnel'
                      ;
        }
      }
    }
  }
}
