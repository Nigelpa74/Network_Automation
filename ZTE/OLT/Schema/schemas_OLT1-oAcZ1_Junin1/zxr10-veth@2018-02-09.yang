module zxr10-veth {
  namespace 'http://www.zte.com.cn/zxr10/netconf/schema/rosng/veth'
            ;
  prefix veth ;
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  revision 2018-02-09 ;
  container configuration {
    list zxAnVEthMapConfigEntry {
      key zxAnVEthMapNumber ;
      leaf zxAnVEthMapNumber {
        type int32 ;
      }
      leaf zxAnVEthXIfIndex {
        type int32 ;
      }
      leaf zxAnVEthIfIndex {
        type int32 ;
      }
    }
  }
}
