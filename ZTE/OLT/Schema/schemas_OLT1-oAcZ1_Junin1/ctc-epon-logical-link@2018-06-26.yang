module ctc-epon-logical-link{
  yang-version 1.1;
  namespace "urn:ctc:yang:ctc-epon-logical-link";
  prefix ctc-eponll;

  /* Common */

  include ctc-epon-logical-link-traffic-descriptor-profile-body;
  include ctc-epon-logical-link-body;

  organization
    "中国电信股份有限公司上海分公司
     Shanghai Research Institute of China Telecom Corp. Ltd.";

  description
    "YANG module for EPON for managing logical link and 
     traffic descriptors.
     描述更新";

  revision 2018-06-26 {
    description
      "CTC OAN SDN Yang Module V1.0";
  }
}
