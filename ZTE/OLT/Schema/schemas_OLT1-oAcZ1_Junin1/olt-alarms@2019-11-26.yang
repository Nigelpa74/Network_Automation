module olt-alarms {
  yang-version 1.1;
  namespace "http://www.zte.com.cn/zxr10/netconf/schema/rosng/olt-alarms";

  prefix oltalm;

  import ietf-alarms{
    prefix al;
  }
  
  organization "ZTE Corporation";
  contact "ZTE Corporation";


  description
    "This module contains alarm type identity definitions.";

  revision 2019-11-26 {
    description
      "Initial revision.
       * Approval Date:    2019-11-26.
       * Publication Date: see revision date above.";
    reference
      "x733";
  }

  identity communications-alarm {
    base al:alarm-type-id ;
    description
      "communications-alarm type";
  }

  identity quality-of-service-alarm {
    base al:alarm-type-id ;
    description
      "quality-of-service-alarm type";
  }

  identity equipment-alarm {
    base al:alarm-type-id ;
    description
      "equipment-alarm type";
  }
  
  identity processing-error-alarm {
    base al:alarm-type-id ;
    description
      "processing-error-alarm type";
  }
  
  identity environmental-alarm {
    base al:alarm-type-id ;
    description
      "environmental-alarm type";
  }  

}
