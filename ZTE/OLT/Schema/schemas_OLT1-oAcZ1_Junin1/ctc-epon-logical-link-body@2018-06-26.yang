submodule ctc-epon-logical-link-body {
  yang-version 1.1;
  belongs-to ctc-epon-logical-link {
    prefix ctc-eponll;
  }

  import ietf-interfaces {
    prefix if;
  }

  import ctc-epon-if-type {
    prefix ctc-eponift;
  }

  import bbf-qos-traffic-mngt {
    prefix bbf-qos-tm;
  }

  import ieee802-ethernet-pon {
    prefix "ieee802-eth-pon";
  }

  include ctc-epon-logical-link-traffic-descriptor-profile-body;

  organization
    "中国电信股份有限公司上海研究院
     Shanghai Research Institute of China Telecom Corp. Ltd.";

  description
    "This module contains the data of logical links.";

  revision 2018-06-26 {
    description
      "CTC OAN SDN Yang Module V1.0";
  }

/*
--
-- Pending consensus review
--
  feature configurable-alloc-id {
    description
      "Indicates support for configuration of the alloc ID.";
  }
*/

  container logical-link {
    description
      "logical links configuration data.";
    uses logical-link-data;
  }

  grouping logical-link-data {
    description
      "The config data for all logical links.";

    list logical-link {
      key name;
      description
        "List of logical links.";
      leaf name {
        type string;
        description
          "Name of the logical link.";
      }

      leaf logical-link-id {
        type ieee802-eth-pon:mpcp-llid;
        config false;
        
        description
          "Logical Link Identifiers (LLIDs) are used to identify a single
           MAC from a number of MACs which may be present in the
           EPON OLT or ONU. LLIDs between the value of 0x07FFE
           and 0x7FFF are reserved for other uses.
           Other LLIDs are dynamically assigned by the OLT during the
           registration process. For a complete description of how the
           LLID is used in an EPON device; see IEEE Std 802.3,
           65.1.3.3 for 1G-EPON and 76.2.6.1.3 for 10G-EPON.";

        reference
          "IEEE Std 802.3, 76.2.6.1.3.2 (1G-EPON and 10G-EPON)";
      }

      leaf interface-reference {
        type if:interface-ref;
        must
          "/if:interfaces/if:interface[if:name=current()]
           /if:type='ctc-eponift:v-ani'" {
          error-message
            "must reference a v-ani interface";
        }
        description
          "Reference to v-ani interface.";
      }

      uses bbf-qos-tm:tm-root;

      leaf traffic-descriptor-profile-ref {
        type leafref {
          path "/ctc-eponll:traffic-descriptor-profiles/"
                     + "ctc-eponll:traffic-descriptor-profile/"
                     + "ctc-eponll:name";
        }
        description
          "References an existing traffic descriptor profile.";
      }
    }
  }
}
