module zte-an-qos-traffic {
    namespace 'http://www.zte.com.cn/zxr10/netconf/schema/rosng/zxan-qos-traffic';
    prefix zxan-qos-traffic;
    import zxr10-netconf-defs {
        prefix ncd;
        revision-date 2017-08-15;
    }
    organization "ZTE Corporation";
    contact "Luo Feima     ZTE Corporation
                    Mail : luo.feima@zte.com.cn
                    Tel  : +86-21-68896470.";
    description "This MIB defines ZTE Access Node QoS Traffic managed objects.";
    revision 2011-09-22 {
        description "Modification of some spelling error for this MIB module.";
    }
    revision 2011-08-25 {
        description "Modification of the descriptions for this MIB module.";
    }
    revision 2011-08-19 {
        description "Modification of the comments for this MIB module.";
    }
    revision 2011-07-05 {
        description "Conformance supplement for this MIB module.";
    }
    revision 2010-10-28 {
        description "Initial version of this MIB module.";
    }
    container zxAnQosTraffic {
        description "";
        container zxAnQosTrafficObjects {
            description "";
            container zxAnQosTrafficIfShapingConfTable {
                description "Egress or ingress traffic shaping configuration based on the
                             interface table.";
                list zxAnQosTrafficIfShapingConfEntry {
                    description "Egress or ingress traffic shaping configuration based on the
                                 interface entry.
                                 This table contains QoS traffic configuration parameters
                                 for physical interfaces (including ethernet interfaces and GPON OLT
                                 interfaces) and GPON ONU interfaces.";
                    max-elements 65535;
                    key "ifIndex zxAnSubIfIndex zxAnQosTrafficIfShapingDirection";
                    leaf ifIndex {
                        description "A unique value, greater than zero, for each interface.  It
                                     is recommended that values are assigned contiguously
                                     starting from 1.  The value for each interface sub-layer
                                     must remain constant at least from one re-initialization of
                                     the entity's network management system to the next re-
                                     initialization.";
                        type int32 {
                            range 1..2147483647;
                        }
                    }
                    leaf zxAnSubIfIndex {
                        description "Sub-interface index at this interface.";
                        type int32;
                    }
                    leaf zxAnQosTrafficIfShapingDirection {
                        description "The direction of the interface.";
                        type int32 {
                            range 1..2147483647;
                        }
                    }
                    leaf zxAnQosTrafficIfShapingConfPrf {
                        description "Traffic configuration profile. The value of this object is the name
                                     of the referenced profile in the zxAnQosTrafficPrfTable.";
                        type string {
                            length 1..32;
                        }
                    }
                }
            }
        }
    }
}
