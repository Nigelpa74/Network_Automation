module zxr10-pm-hardware {
  namespace 'http://www.zte.com.cn/zxr10/netconf/schema/rosng/pm-hardware'
            ;
  prefix pm-hardware ;
  import zxr10-netconf-defs {
    prefix ncd ;
    revision-date 2018-09-30 ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  revision 2019-07-24 {
    description create ;
  }
  container configuration {
    list component {
      key name ;
      leaf name {
        type ncd:string-all {
          length 0..32 ;
        }
      }
      leaf class {
        type string ;
      }
      leaf parent {
        type string ;
      }
      leaf parent-rel-pos {
        type int32 ;
      }
      leaf alias {
        type string ;
        default unknown ;
      }
      leaf asset-id {
        type string ;
        default unknown ;
      }
      container state {
        leaf admin-state {
          type enumeration {
            enum unknown {
              value 1 ;
              description powersave ;
            }
            enum locked {
              value 2 ;
              description inservice ;
            }
            enum shutting-down {
              value 3 ;
              description 'typemismatch hwonline configing'
                          ;
            }
            enum unlocked {
              value 4 ;
              description offline ;
            }
          }
          default unknown ;
        }
      }
      leaf expected-model-name {
        type string ;
      }
      list uri {
        key id ;
        leaf id {
          type int32 ;
        }
        leaf name {
          type string ;
        }
      }
    }
  }
  container state {
    config false ;
    leaf last-change {
      type ncd:string-all {
        length 0..64 ;
      }
    }
    list component {
      key name ;
      leaf name {
        type ncd:string-all {
          length 0..32 ;
        }
      }
      leaf class {
        type string ;
      }
      leaf physical-index {
        type int32 ;
      }
      leaf description {
        type string ;
      }
      leaf parent {
        type string ;
      }
      leaf parent-rel-pos {
        type int32 ;
      }
      leaf hardware-rev {
        type string ;
      }
      leaf firmware-rev {
        type string ;
      }
      leaf software-rev {
        type string ;
      }
      leaf serial-num {
        type string ;
      }
      leaf mfg-name {
        type string ;
      }
      leaf model-name {
        type ncd:string-with-blank ;
      }
      leaf alias {
        type string ;
      }
      leaf asset-id {
        type string ;
      }
      leaf is-fru {
        type boolean ;
      }
      leaf mfg-date {
        type string ;
      }
	  leaf uuid {
        type string ;
      }
      leaf slot-number {
        type string ;
      }
      leaf card-type {
        type ncd:string-with-blank ;
      }
      leaf is-hot-pluggable-to-parent {
        type boolean ;
      }
      leaf is-hot-pluggable-to-child {
        type boolean ;
      }
      leaf cage-module-type {
        type string ;
      }
      container state {
        leaf state-last-changed {
          type ncd:string-with-blank ;
        }
        leaf admin-state {
          type enumeration {
            enum unknown {
              value 1 ;
              description powersave ;
            }
            enum locked {
              value 2 ;
              description inservice ;
            }
            enum shutting-down {
              value 3 ;
              description 'typemismatch hwonline configing'
                          ;
            }
            enum unlocked {
              value 4 ;
              description offline ;
            }
          }
        }
        leaf oper-state {
          type enumeration {
            enum unknown {
              value 1 ;
            }
            enum enabled {
              value 2 ;
            }
            enum disabled {
              value 3 ;
            }
            enum testing {
              value 4 ;
            }
          }
        }
        leaf usage-state {
          type enumeration {
            enum unknown {
              value 1 ;
            }
            enum idle {
              value 2 ;
            }
            enum active {
              value 3 ;
            }
            enum busy {
              value 4 ;
            }
          }
        }
        leaf alarm-state {
          type enumeration {
            enum unknown {
              value 1 ;
            }
            enum under-repair {
              value 2 ;
            }
            enum critical {
              value 3 ;
            }
            enum major {
              value 4 ;
            }
            enum minor {
              value 5 ;
            }
            enum warning {
              value 6 ;
            }
            enum indeterminate {
              value 7 ;
            }
            enum no-alarm {
              value 0 ;
            }
          }
        }
        leaf standby-state {
          type enumeration {
            enum unknown {
              value 1 ;
            }
            enum hot-standby {
              value 2 ;
            }
            enum cold-standby {
              value 3 ;
            }
          }
        }
      }
      leaf expected-model-name {
        type string ;
      }
      container cpu-processor-data {
        container system-load {
          leaf average-system-load-1-min {
            type int32 ;
          }
          leaf average-system-load-5-min {
            type int32 ;
          }
          leaf average-system-load-15-min {
            type int32 ;
          }
        }
        container percent-cpu-usage {
          leaf percent-cpu-user {
            type int32 ;
          }
          leaf percent-cpu-idle {
            type int32 ;
          }
        }
        container memory-usage {
          leaf used-mem {
            type int32 ;
          }
          leaf total-memory {
            type int32 ;
          }
          leaf free-memory {
            type int32 ;
          }
        }
      }
      list contains-child {
        key id ;
        leaf id {
          type int32 ;
        }
        leaf name {
          type string ;
        }
      }
      list uri {
        key id ;
        leaf id {
          type int32 ;
        }
        leaf name {
          type string ;
        }
      }
    }
  }
  notification hardware-state-change {
    leaf last-change {
      config false ;
      type leafref {
        path /state/last-change ;
      }
    }
  }
  notification hardware-state-oper-enabled {
    leaf name {
      config false ;
      type leafref {
        path /state/component/name ;
      }
    }
    leaf admin-state {
      config false ;
      type leafref {
        path /state/component/state/admin-state ;
      }
    }
    leaf alarm-state {
      config false ;
      type leafref {
        path /state/component/state/alarm-state ;
      }
    }
  }
  notification hardware-state-oper-disabled {
    leaf name {
      config false ;
      type leafref {
        path /state/component/name ;
      }
    }
    leaf admin-state {
      config false ;
      type leafref {
        path /state/component/state/admin-state ;
      }
    }
    leaf alarm-state {
      config false ;
      type leafref {
        path /state/component/state/alarm-state ;
      }
    }
  }
}
