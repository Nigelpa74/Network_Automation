module zxr10-interface-supp {
  namespace 'http://www.zte.com.cn/zxr10/netconf/schema/rosng/interface-supp'
            ;
  prefix ifsupp ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'This module is the supplement of zxr10-interface module by provi'
            + 'ding another yang-tree to manage configuration about interfaces.'
              ;
  revision 2019-08-07 {
    description 'The initial version'
                ;
  }
  container configuration {
    description 'Common interface management, which includes the creating and d'
              + 'eleting interfaces.'
                ;
    container physical-interfaces {
      description 'The list of physical interfaces'
                  ;
      container ether-interfaces {
        description 'The list of ether interfaces'
                    ;
        list ether-interface {
          description 'The list of ether interfaces'
                      ;
          key name ;
          leaf name {
            description 'The name of the interface'
                        ;
            type ncd:ifname ;
          }
          container sub-interfaces {
            description 'The list of sub-interfaces'
                        ;
            list sub-interface {
              description 'The list of sub-interfaces'
                          ;
              key subport ;
              leaf subport {
                description 'The subport of the interface'
                            ;
                type uint32 {
                  range 1..99999999 ;
                }
              }
            }
          }
        }
      }
      container pos-interfaces {
        description 'The list of POS interfaces'
                    ;
        list pos-interface {
          description 'The list of POS interfaces'
                      ;
          key name ;
          leaf name {
            description 'The name of the interface'
                        ;
            type ncd:ifname ;
          }
          container sub-interfaces {
            description 'The list of sub-interfaces'
                        ;
            list sub-interface {
              description 'The list of sub-interfaces'
                          ;
              key subport ;
              leaf subport {
                description 'The subport of the interface'
                            ;
                type uint32 {
                  range 1..100 ;
                }
              }
            }
          }
        }
      }
      container atm-interfaces {
        description 'The list of ATM interfaces'
                    ;
        list atm-interface {
          description 'The list of ATM interfaces'
                      ;
          key name ;
          leaf name {
            description 'The name of the interface'
                        ;
            type ncd:ifname ;
          }
          container sub-interfaces {
            description 'The list of sub-interfaces'
                        ;
            list sub-interface {
              description 'The list of sub-interfaces'
                          ;
              key subport ;
              leaf subport {
                description 'The subport of the interface'
                            ;
                type uint32 {
                  range 1..4000 ;
                }
              }
            }
          }
        }
      }
      container ucom-interfaces {
        description 'The list of UCOM interfaces'
                    ;
        list ucom-interface {
          description 'The list of UCOM interfaces'
                      ;
          key name ;
          leaf name {
            description 'The name of the interface'
                        ;
            type ncd:ifname ;
          }
          container sub-interfaces {
            description 'The list of sub-interfaces'
                        ;
            list sub-interface {
              description 'The list of sub-interfaces'
                          ;
              key subport ;
              leaf subport {
                description 'The subport of the interface'
                            ;
                type uint32 {
                  range 1..4000 ;
                }
              }
            }
          }
        }
      }
      container ulei-interfaces {
        description 'The list of ULEI interfaces'
                    ;
        list ulei-interface {
          key name ;
          leaf name {
            description 'The name of the interface'
                        ;
            type ncd:ifname ;
          }
          container sub-interfaces {
            description 'The list of sub-interfaces'
                        ;
            list sub-interface {
              description 'The list of sub-interfaces'
                          ;
              key subport ;
              leaf subport {
                description 'The subport of the interface'
                            ;
                type uint32 {
                  range 1..4000 ;
                }
              }
            }
          }
        }
      }
      container gfp-fe-interfaces {
        description 'The list of gfp_fe interfaces'
                    ;
        list gfp-fe-interface {
          description 'The list of gfp_fe interfaces'
                      ;
          key name ;
          leaf name {
            description 'The name of the interface'
                        ;
            type ncd:ifname ;
          }
          container sub-interfaces {
            description 'The list of sub-interfaces'
                        ;
            list sub-interface {
              description 'The list of sub-interfaces'
                          ;
              key subport ;
              leaf subport {
                description 'The subport of the interface'
                            ;
                type uint32 {
                  range 1..4094 ;
                }
              }
            }
          }
        }
      }
    }
    container logical-interfaces {
      description 'The list of logical interfaces'
                  ;
      container loopback-interfaces {
        description 'The list of loopback interfaces'
                    ;
        list loopback-interface {
          description 'The list of loopback interfaces'
                      ;
          key name ;
          leaf name {
            description 'The name of the interface'
                        ;
            type ncd:ifname ;
          }
        }
      }
      container multilink-interfaces {
        description 'The list of multilink interfaces'
                    ;
        list multilink-interface {
          description 'The list of multilink interfaces'
                      ;
          key name ;
          leaf name {
            description 'The name of the interface'
                        ;
            type ncd:ifname ;
          }
        }
      }
      container vlan-interfaces {
        description 'The list of VLAN interfaces'
                    ;
        list vlan-interface {
          description 'The list of VLAN interfaces'
                      ;
          key name ;
          leaf name {
            description 'The name of the interface'
                        ;
            type ncd:ifname ;
          }
        }
      }
      container smartgroup-interfaces {
        description 'The list of smartgroup interfaces'
                    ;
        list smartgroup-interface {
          description 'The list of smartgroup interfaces'
                      ;
          key name ;
          leaf name {
            description 'The name of the interface'
                        ;
            type ncd:ifname ;
          }
          container sub-interfaces {
            description 'The list of sub-interfaces'
                        ;
            list sub-interface {
              description 'The list of sub-interfaces'
                          ;
              key subport ;
              leaf subport {
                description 'The subport of the interface'
                            ;
                type uint32 {
                  range 1..99999999 ;
                }
              }
            }
          }
        }
      }
      container supervlan-interfaces {
        description 'The list of superVLAN interfaces'
                    ;
        list supervlan-interface {
          description 'The list of superVLAN interfaces'
                      ;
          key name ;
          leaf name {
            description 'The name of the interface'
                        ;
            type ncd:ifname ;
          }
        }
      }
      container dialer-interfaces {
        description 'The list of dialer interfaces'
                    ;
        list dialer-interface {
          description 'The list of dialer interfaces'
                      ;
          key name ;
          leaf name {
            description 'The name of the interface'
                        ;
            type ncd:ifname ;
          }
        }
      }
      container vbui-interfaces {
        description 'The list of VBUI interfaces'
                    ;
        list vbui-interface {
          description 'The list of VBUI interfaces'
                      ;
          key name ;
          leaf name {
            description 'The name of the interface'
                        ;
            type ncd:ifname ;
          }
        }
      }
      container virtual-template-interfaces {
        description 'The list of virtual_template interfaces'
                    ;
        list virtual-template-interface {
          description 'The list of virtual_template interfaces'
                      ;
          key name ;
          leaf name {
            description 'The name of the interface'
                        ;
            type ncd:ifname ;
          }
          container sub-interfaces {
            description 'The list of sub-interfaces'
                        ;
            list sub-interface {
              description 'The list of sub-interfaces'
                          ;
              key subport ;
              leaf subport {
                description 'The subport of the interface'
                            ;
                type uint32 {
                  range 1..4095 ;
                }
              }
            }
          }
        }
      }
      container te-tunnels {
        description 'The list of te_tunnels'
                    ;
        list te-tunnel {
          description 'The list of te_tunnels'
                      ;
          key name ;
          leaf name {
            description 'The name of the tunnel'
                        ;
            type ncd:ifname ;
          }
        }
      }
      container gre-tunnels {
        description 'The list of gre_tunnels'
                    ;
        list gre-tunnel {
          description 'The list of gre_tunnels'
                      ;
          key name ;
          leaf name {
            description 'The name of the tunnel'
                        ;
            type ncd:ifname ;
          }
        }
      }
      container v6-tunnels {
        description 'The list of v6_tunnels'
                    ;
        list v6-tunnel {
          description 'The list of v6_tunnels'
                      ;
          key name ;
          leaf name {
            description 'The name of the tunnel'
                        ;
            type ncd:ifname ;
          }
        }
      }
      container posgroup-interfaces {
        description 'The list of posgroup interfaces'
                    ;
        list posgroup-interface {
          description 'The list of posgroup interfaces'
                      ;
          key name ;
          leaf name {
            description 'The name of the interface'
                        ;
            type ncd:ifname ;
          }
        }
      }
      container ipsec-tunnels {
        description 'The list of ipsec_tunnels'
                    ;
        list ipsec-tunnel {
          description 'The list of ipsec_tunnels'
                      ;
          key name ;
          leaf name {
            description 'The name of the tunnel'
                        ;
            type ncd:ifname ;
          }
        }
      }
      container cip-interfaces {
        description 'The list of CIP interfaces'
                    ;
        list cip-interface {
          description 'The list of CIP interfaces'
                      ;
          key name ;
          leaf name {
            description 'The name of the interface'
                        ;
            type ncd:ifname ;
          }
        }
      }
      container eth-dslgroup-interfaces {
        description 'The list of eth_dslgroup interfaces'
                    ;
        list eth-dslgroup-interface {
          description 'The list of eth_dslgroup interfaces'
                      ;
          key name ;
          leaf name {
            description 'The name of the interface'
                        ;
            type ncd:ifname ;
          }
          container sub-interfaces {
            description 'The list of sub-interfaces'
                        ;
            list sub-interface {
              description 'The list of sub-interfaces'
                          ;
              key subport ;
              leaf subport {
                description 'The subport of the interface'
                            ;
                type uint32 {
                  range 1..4000 ;
                }
              }
            }
          }
        }
      }
      container atm-dslgroup-interfaces {
        description 'The list of atm_dslgroup interfaces'
                    ;
        list atm-dslgroup-interface {
          description 'The list of atm_dslgroup interfaces'
                      ;
          key name ;
          leaf name {
            description 'The name of the interface'
                        ;
            type ncd:ifname ;
          }
        }
      }
      container mte-tunnels {
        description 'The list of mte_tunnels'
                    ;
        list mte-tunnel {
          description 'The list of mte_tunnels'
                      ;
          key name ;
          leaf name {
            description 'The name of the tunnel'
                        ;
            type ncd:ifname ;
          }
        }
      }
      container bvi-interfaces {
        description 'The list of BVI interfaces'
                    ;
        list bvi-interface {
          description 'The list of BVI interfaces'
                      ;
          key name ;
          leaf name {
            description 'The name of the interface'
                        ;
            type ncd:ifname ;
          }
          container sub-interfaces {
            description 'The list of sub-interfaces'
                        ;
            list sub-interface {
              description 'The list of sub-interfaces'
                          ;
              key subport ;
              leaf subport {
                description 'The subport of the interface'
                            ;
                type uint32 {
                  range 1..4000 ;
                }
              }
            }
          }
        }
      }
      container l3vi-interfaces {
        description 'The list of l3vi interfaces'
                    ;
        list l3vi-interface {
          description 'The list of l3vi interfaces'
                      ;
          key name ;
          leaf name {
            description 'The name of the interface'
                        ;
            type ncd:ifname ;
          }
          container sub-interfaces {
            description 'The list of sub-interfaces'
                        ;
            list sub-interface {
              description 'The list of sub-interfaces'
                          ;
              key subport ;
              leaf subport {
                description 'The subport of the interface'
                            ;
                type uint32 {
                  range 1..16 ;
                }
              }
            }
          }
        }
      }
      container vxlan-tunnels {
        description 'The list of vxlan_tunnels'
                    ;
        list vxlan-tunnel {
          description 'The list of vxlan_tunnels'
                      ;
          key name ;
          leaf name {
            description 'The name of the tunnel'
                        ;
            type ncd:ifname ;
          }
        }
      }
      container vci-interfaces {
        description 'The list of VCI interfaces'
                    ;
        list vci-interface {
          description 'The list of VCI interfaces'
                      ;
          key name ;
          leaf name {
            description 'The name of the interface'
                        ;
            type ncd:ifname ;
          }
        }
      }
    }
  }
}
