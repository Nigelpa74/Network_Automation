/*
Copyright (C) 2013-2018 China Telecom Group. All rights reserved.
*/
module gsta-interfacemng {
    namespace "http://www.gsta.com/netconf/gsta-interfacemng";
    prefix ifm;
      
    import gsta-extension {
        prefix ext;
    }
    import ietf-inet-types {
        prefix inet;
    }
    include gsta-interfacemng-type;
      
    organization
        "China Telecom Group - Guangdong Telecom Research Institute";
    contact
        "China Telecom Corporation Guangdong Research Institute (hereinafter referred to as:Guangzhou Research Institute)";
    description
        "Common interface management, which includes the public configuration of interfaces.";
      
    revision 2018-07-13 {
        description
          "Initial modeling.";
        reference
          "GSTA IP-RAN 5G Common Yang Model.";
    }

    container ifm {
        description
            "Common interface management, which includes the public configuration of interfaces.";
        container interfaces {
            description
                "List of interfaces.";
            list interface {
                key "ifName";
                description
                  "Information about an interface.";
                leaf ifName {
                  type InterfaceNameType;
                  description
                    "The textual name of the interface.  The value of this object should be the name of the interface as assigned by the local device and should be suitable for use in commands entered at the device's `console'.  This might be a text name, such as ` NULL0 ', depending on the interface naming syntax of the device.";
                }
                
                leaf ifClass {
                  type ifmcommIfClassType;
                  default "mainInterface";
                  config false;
                  description
                    "Identify a main interface or a sub-interface.";
                  ext:support-filter "true";
                }
                leaf ifPhyType {
                  type ifmcommPhyType;
                  config false;
                  description
                    "Type of an interface. Port types include physical ports and logical ports.";
                  ext:support-filter "true";
                }
                leaf ifParentIfName {
                  when "../ifClass='subInterface'";
                  type leafref {
                    path "/ifm:ifm/ifm:interfaces/ifm:interface/ifm:ifName";
                  }
                  config false;
                  description
                    "Name of the main interface. For example, ethernet0/1/0.";
                }
                leaf ifNumber {
                  type string {
                    length "1..63";
                    pattern '(\d+/\d+/\d+/\d+)|(\d+/\d+/\d+)|(\d+/\d+)|(\d+)|(\d+/\d+/\d+[:]\d+)|(\d+/\d+/\d+[:]\d+[:]\d+[:]\d+)|(\d+/\d+/\d+/\d+[:]\d+)|(\d+/\d+/\d+/\d+[:]\d+[:]\d+[:]\d+)|(\d+/\d+/\d+/\d+/\d+[:]\d+)|(\d+/\d+[:]\d+)';
                  }
                  config false;
                  description
                    "Number of an interface. For example,1, 0/1/0, or 2:1.";
                }
                leaf ifDescr {
                  type string {
                    length "1..242";
                  }
                  description
                    "Description of an interface.";
                  ext:allowDelete "true";
                }
                leaf ifAdminStatus {
                  type ifmcommAdminStaType;
                  description
                    "Administrative status of an interface.";
                  ext:allowDelete "true";
                }
                leaf ifDf {
                  type boolean;
                  default "false";
                  description
                    "Clear the Don't Fragment field of IP packets on an interface.";
                }
                leaf ifTrapEnable {
                  type boolean;
                  default "true";
                  description
                    "Enable the trap function on an interface.";
                }
                leaf ifStatiEnable {
                  type boolean;
                  description
                    "Enable the statistics function on an interface.";
                  ext:allowDelete "true";
                }
                leaf statMode {
                  type ifmcommStatMode;
                  description
                    "Mode of statistics collection. statistics by interface or vlangroup";
                  ext:allowDelete "true";
                }
                leaf ifMtu {
                  type uint32 {
                    range "0..64000";
                  }
                  description
                    "IPV4 Maximum transmission unit of an interface.
                     Special explanation:
                     Range: The server may restrict the allowed values for this leaf, depending on the interface's type.";
                 ext:allowDelete "true";
                }
                leaf spreadMtuFlag {
                  type boolean;
                  default "false";
                  description
                    "Spread the MTU of main interface to subinterface(optional).";
                  ext:allowDelete "true";
                }
                leaf ifBandwidth {
                  type uint32 {
                    range "1..1000000";
                  }
                  description
                    "Specify MIB-referenced bandwidth of an interface. ";
                  ext:allowDelete "true";
                }
                leaf ifStatItvl {
                  type uint32 {
                    range "10..600";
                  }
                  description
                    "Interval at which flow statistics are collected on an interface. The value must be a multiple of 10. unit is second";
                  ext:allowDelete "true";
                }
                leaf downDelayTime {
                  when "../ifPhyType='Eth-Trunk'";
                  type uint32 {
                    range "0..1000";
                  }
                  description
                    "Specify down-delay-time value in milliseconds. It must be a multiple of 100.";
                  ext:allowDelete "true";
                }
                leaf ifCfgMac {
                  type MacAddressType {
                    length "0..255";
				
                  }
                  ext:allowDelete "true";
                  description
                    "Config MAC Address, in the format of HH-HH-HH.";
                }
                
                container ipv4Config {
                  description
                    "IPv4 configurations.";
                  leaf addrCfgType {
                    type ifmam4CfgType;
                    default "config";
                    description
                      "IPv4 address configuration type.";
                  }
                  container am4CfgAddrs {
                    description
                      "List of IPv4 addresses.";
                    list am4CfgAddr {
                      when "not(../../addrCfgType='negotiation' or ../../addrCfgType='unnumbered')";
                      key "ifIpAddr";
                      description
                        "IPv4 address configurations.";
                      leaf ifIpAddr {
                        type inet:ipv4-address-no-zone;
                        description  "IPv4 address.";
                      }
                      leaf subnetMask {
                        type ifmIpv4Mask {
                          length "9..15";
                          pattern '((([1-9]?[0-9]|1[0-9][0-9]|2[0-4][0-9]|25[0-5])\.){3}([1-9]?[0-9]|1[0-9][0-9]|2[0-4][0-9]|25[0-5]))';
                        }
                        mandatory true;
                        description
                          "IPv4 address mask.";
                      }
                      leaf addrType {
                        type ifmam4IpAddrType;
                        must "((../addrType='main' or ../addrType='sub') )";
                        mandatory true;
                        description
                          "IPv4 address type.";
                      }
                    }
                  }
                  leaf unNumIfName {
                    when "../addrCfgType='unnumbered'";
                    type leafref {
                      path "/ifm:ifm/ifm:interfaces/ifm:interface/ifm:ifName";
                    }
                    description
                      "Name of an unnumbered interface. For example, ethernet0/1/0.";
                    ext:allowDelete "true";
                  }
                }// ipv4 config 

                container ipv6Config {
                  description
                    "IPv6 configurations.";
                  leaf enableFlag {
                    type boolean;
                    default "false";
                    description
                      "It is used to control whether an interface is enabled with the IPv6 function.";
                  }
                  leaf ifMtu6 {
                    when "../enableFlag!='false'";
                    type uint32 {
                      range "0..50000";
                    }
                    description
                      "IPv6 maximum transmission unit of an interface.
                       Special explanation:
                       Range: The server may restrict the allowed values for this leaf, depending on the interface's type.";
                    ext:allowDelete "true";
                  }
                  leaf spreadMtu6Flag {
                    type boolean;
                    must "not(../enableFlag='false' and ../spreadMtu6Flag='true')";
                    default "false";
                    description
                      "Spread the IPv6 MTU of main interface to subinterface.";
                    ext:allowDelete "true";
                  }
                  leaf autoLinkLocal {
                    type boolean;
                    must "not(../enableFlag='false' and ../autoLinkLocal='true')";
                    default "false";
                    description
                      "It is used to control whether an interface is enabled with the auto linklocal address function.";
                  }
                  container am6CfgAddrs {
                    when "../enableFlag!='false'";
                    description
                      "List of IPv6 addresses.";
                    list am6CfgAddr {
                      key "ifIp6Addr";
                      description
                        "IPv6 address configurations.";
                      leaf ifIp6Addr {
                        type inet:ipv6-address-no-zone;
                        description
                          "IPv6 address.";
                      }
                      leaf addrPrefixLen {
                        type uint32 {
                          range "1..128";
                        }
                        must "not(../addrType6='linkLocal') or (../addrType6='linkLocal' and ../addrPrefixLen=10)";
                        mandatory true;
                        description
                          "Length of the IPv6 address prefix.";
                      }
                      leaf addrType6 {
                        type ifmam6IpAddr6Type;
                        must "((../addrType6='global' or ../addrType6='linkLocal' or ../addrType6='anycast') )";
                        mandatory true;
                        description
                          "IPv6 address type.";
                      }
                      leaf ifIDGenType {
                        type ifmam6IDGenType;
                        must "(../addrType6='global' and (../ifIDGenType='none' or ../ifIDGenType='cga' or ../ifIDGenType='eui64') ) or (../addrType6='linkLocal' and (../ifIDGenType='none' or ../ifIDGenType='cga') ) or (../addrType6='anycast' and ../ifIDGenType='none')";
                        default "none";
                        description
                          "Address algorithm.";
                        ext:allowDelete "true";
                      }
                      leaf collisionCount {
                        type uint32 {
                          range "0..3";
                        }
                        config false;
                        description
                          "Number of IPv6 address collisions.";
                      }
                    }
                  }
                }
                
                container ifControlFlap {
                  description
                    "Interface status suppression.";
                  leaf ifCtrlFlapEnbl {
                    type boolean;
                    default "false";
                    description
                      "Enable the control flap function on an interface.";
                  }
                  leaf ifSuppress {
                    when "../ifCtrlFlapEnbl='true'";
                    type uint32 {
                      range "1..20000";
                    }
                    must "(../ifSuppress>../ifReuse) and ((../ifSuppress<../ifCeiling))";
                    default "2000";
                    description
                      "Suppression threshold on an interface. The value must be greater than the reusing threshold and smaller than the suppression upper limit.";
                  }
                  leaf ifReuse {
                    when "../ifCtrlFlapEnbl='true'";
                    type uint32 {
                      range "1..20000";
                    }
                    must "(../ifReuse<../ifSuppress)";
                    default "750";
                    description
                      "Reusing threshold of an interface. The value must be smaller than the suppression threshold.";
                  }
                  leaf ifCeiling {
                    when "../ifCtrlFlapEnbl='true'";
                    type uint32 {
                      range "1001..20000";
                    }
                    must "(../ifCeiling>../ifSuppress)";
                    default "6000";
                    description
                      "Maximum suppression value on an interface. The value should be greater than the Damping Suppression Threshold.";
                  }
                  leaf ifDecayOk {
                    when "../ifCtrlFlapEnbl='true'";
                    type uint32 {
                      range "1..900";
                    }
                    units second;
                    default "54";
                    description
                      "The penalty value of an Up interface attenuates to 1/2. The value is expressed in seconds.";
                  }
                  leaf ifDecayNg {
                    when "../ifCtrlFlapEnbl='true'";
                    type uint32 {
                      range "1..900";
                    }
                    units second;
                    default "54";
                    description
                      "The penalty value of a Down interface attenuates to 1/2. The value is expressed in seconds.";
                  }
                }
        
            }
        }

    }
}
