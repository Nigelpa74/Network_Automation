module ctc-mgmd {
    yang-version 1.1;
    namespace "urn:ctc:yang:ctc-mgmd";
    prefix "ctc-mgmd";
    import bbf-mgmd {
        prefix "bbf-mgmd";
    }
    revision 2020-08-05;

    augment "/bbf-mgmd:multicast/bbf-mgmd:mgmd/bbf-mgmd:multicast-vpn/bbf-mgmd"
     + ":multicast-interface-to-host" {
        leaf immediate-leave {
            type enumeration {
                enum enabled {
                    description "Enabled";
                }
                enum disabled {
                    description "Disabled";
                }
            }
            default "disabled";
            description "用户接口级快速离开功能配置";
        }
    }
}
