module zte-an-interface-stats {
    namespace 'http://www.zte.com.cn/zxr10/netconf/schema/rosng/msstat';
    prefix msstat;
   
    organization "ZTE Corporation";
    contact "
                     Zhang Weiping   ZTE Corporation
                     Mail: zhang.weiping@zte.com.cn
                     Tel : 021-68896470

                     Chen Aimin      ZTE Corporation.
                     Mail: chen.aimin@zte.com.cn
                     Tel : 021-68897128
                     ";
    description "The MIB module for the Performance Management of ZTE Access
                 Node interface.";
    revision 2015-10-20 {
        description "Add the object: ethIfLinkStatusChanges.";
    }
    revision 2015-09-06 {
        description "Add the object: zxAnPvcIfStatsGlobalMode.";
    }
    revision 2011-07-02 {
        description "Initial version of this MIB module.";
    }
    container zxAnInterfaceStats {
        description "";
        container zxAnIfPerfObjects {
            description "";
            container zxAnEthIfCurrStatsTable {
                description "Current performance data table of interfaces.";
                list zxAnEthIfCurrStatsEntry {
                    description "Current performance data entry of interfaces.";
                    max-elements 25;
                    key "ifIndex";
                    leaf ifIndex {
                        description "A unique value, greater than zero, for each interface.  It
                                     is recommended that values are assigned contiguously
                                     starting from 1.  The value for each interface sub-layer
                                     must remain constant at least from one re-initialization of
                                     the entity's network management system to the next re-
                                     initialization.";
                        type int32 {
                            range 1..2147483647;
                        }
                    }
                    leaf ethIfInOctets {
                        config false;
                        description "The total number of octets received on the interface,
                                     including framing characters.
                                     
                                     Discontinuities in the value of this counter can occur at
                                     re-initialization of the management system, and at other
                                     times as indicated by the value of
                                     ifCounterDiscontinuityTime.";
                        type uint64;
                    }
                    leaf ethIfInPkts {
                        config false;
                        description "The total number of packets received on the interface,
                                     including framing characters.
                                     
                                     Discontinuities in the value of this counter can occur at
                                     re-initialization of the management system, and at other
                                     times as indicated by the value of
                                     ifCounterDiscontinuityTime.";
                        type uint64;
                    }
                    leaf ethIfInUcastPkts {
                        config false;
                        description "The number of packets, delivered by this sub-layer to a
                                     higher (sub-)layer, which were not addressed to a multicast
                                     or broadcast address at this sub-layer.
                                     
                                     Discontinuities in the value of this counter can occur at
                                     re-initialization of the management system, and at other
                                     times as indicated by the value of
                                     ifCounterDiscontinuityTime.";
                        type uint64;
                    }
                    leaf ethIfInMcastPkts {
                        config false;
                        description "The number of packets, delivered by this sub-layer to a
                                     higher (sub-)layer, which were addressed to a multicast
                                     address at this sub-layer.  For a MAC layer protocol, this
                                     includes both Group and Functional addresses.
                                     
                                     Discontinuities in the value of this counter can occur at
                                     re-initialization of the management system, and at other
                                     times as indicated by the value of
                                     ifCounterDiscontinuityTime.";
                        type uint64;
                    }
                    leaf ethIfInBcastPkts {
                        config false;
                        description "The number of packets, delivered by this sub-layer to a
                                     higher (sub-)layer, which were addressed to a broadcast
                                     address at this sub-layer.
                                     
                                     Discontinuities in the value of this counter can occur at
                                     re-initialization of the management system, and at other
                                     times as indicated by the value of
                                     ifCounterDiscontinuityTime.";
                        type uint64;
                    }
                    leaf ethIfInOversizedPkts {
                        config false;
                        description "The total number of packets received that were longer than 
                                     1518 octets (excluding framing bits, but including FCS octets) 
                                     and were otherwise well formed.";
                        type uint64;
                    }
                    leaf ethIfInUndersizedPkts {
                        config false;
                        description "The total number of packets received that were less than 64 
                                     octets long (excluding framing bits, but including FCS octets) 
                                     and were otherwise well formed.";
                        type uint64;
                    }
                    leaf ethIfOutOctets {
                        config false;
                        description "The total number of octets transmitted out of the interface,
                                     including framing characters.";
                        type uint64;
                    }
                    leaf ethIfOutPkts {
                        config false;
                        description "The total number of packets transmitted out of the interface,
                                     including framing characters.";
                        type uint64;
                    }
                    leaf ethIfOutUcastPkts {
                        config false;
                        description "The total number of packets that higher-level protocols
                                     requested be transmitted, and which were not addressed to a
                                     multicast or broadcast address at this sub-layer, including
                                     those that were discarded or not sent.
                                     
                                     Discontinuities in the value of this counter can occur at
                                     re-initialization of the management system, and at other
                                     times as indicated by the value of
                                     ifCounterDiscontinuityTime.";
                        type uint64;
                    }
                    leaf ethIfOutMcastPkts {
                        config false;
                        description "The total number of packets that higher-level protocols
                                     requested be transmitted, and which were addressed to a
                                     multicast address at this sub-layer, including those that
                                     were discarded or not sent.  For a MAC layer protocol, this
                                     includes both Group and Functional addresses.
                                     
                                     Discontinuities in the value of this counter can occur at
                                     re-initialization of the management system, and at other
                                     times as indicated by the value of
                                     ifCounterDiscontinuityTime";
                        type uint64;
                    }
                    leaf ethIfOutBcastPkts {
                        config false;
                        description "The total number of packets that higher-level protocols
                                     requested be transmitted, and which were addressed to a
                                     broadcast address at this sub-layer, including those that
                                     were discarded or not sent.
                                     
                                     Discontinuities in the value of this counter can occur at
                                     re-initialization of the management system, and at other
                                     times as indicated by the value of
                                     ifCounterDiscontinuityTime.";
                        type uint64;
                    }
                    leaf ethIfOutPausePkts {
                        config false;
                        description "A count of MAC Control frames transmitted on
                                     this interface with an opcode indicating the
                                     PAUSE operation.
                                     
                                     This counter does not increment when the
                                     interface is operating in half-duplex mode.
                                     
                                     For interfaces operating at 10 Gb/s, this
                                     counter can roll over in less than 5 minutes if
                                     it is incrementing at its maximum rate.  Since
                                     that amount of time could be less than a
                                     management station's poll cycle time, in order
                                     to avoid a loss of information, a management
                                     station is advised to poll the
                                     dot3HCOutPauseFrames object for 10 Gb/s or
                                     faster interfaces.
                                     
                                     Discontinuities in the value of this counter can
                                     occur at re-initialization of the management
                                     system, and at other times as indicated by the
                                     value of ifCounterDiscontinuityTime.";
                        type uint64;
                    }
                    leaf ethIfOutDiscardPkts {
                        config false;
                        description "The number of outbound packets which were chosen to be
                                     discarded even though no errors had been detected to prevent
                                     their being transmitted.  One possible reason for discarding
                                     such a packet could be to free up buffer space.
                                     
                                     Discontinuities in the value of this counter can occur at
                                     re-initialization of the management system, and at other
                                     times as indicated by the value of
                                     ifCounterDiscontinuityTime.";
                        type uint64;
                    }
                    leaf ethIfOutCollisions {
                        config false;
                        description "A count of frames that are involved in out collision and
                                     are subsequently transmitted successfully.
                                     
                                     A frame that is counted by an instance of this
                                     object is also counted by the corresponding
                                     instance of either the ifOutUcastPkts,
                                     ifOutMulticastPkts, or ifOutBroadcastPkts,
                                     and is not counted by the corresponding
                                     instance of the dot3StatsSingleCollisionFrames
                                     object.
                                     
                                     This counter does not increment when the
                                     interface is operating in full-duplex mode.
                                     
                                     Discontinuities in the value of this counter can
                                     occur at re-initialization of the management
                                     system, and at other times as indicated by the
                                     value of ifCounterDiscontinuityTime.";
                        type uint64;
                    }
                    leaf ethIfSingleCollisions {
                        config false;
                        description "A count of frames that are involved in a single
                                     collision, and are subsequently transmitted
                                     successfully.
                                     
                                     A frame that is counted by an instance of this
                                     object is also counted by the corresponding
                                     instance of either the ifOutUcastPkts,
                                     ifOutMulticastPkts, or ifOutBroadcastPkts,
                                     and is not counted by the corresponding
                                     instance of the dot3StatsMultipleCollisionFrames
                                     object.
                                     
                                     This counter does not increment when the
                                     interface is operating in full-duplex mode.
                                     
                                     Discontinuities in the value of this counter can
                                     occur at re-initialization of the management
                                     system, and at other times as indicated by the
                                     value of ifCounterDiscontinuityTime.";
                        type uint64;
                    }
                    leaf ethIfMultipleCollisions {
                        config false;
                        description "A count of frames that are involved in more
                                     than one collision and are subsequently
                                     transmitted successfully.
                                     
                                     A frame that is counted by an instance of this
                                     object is also counted by the corresponding
                                     instance of either the ifOutUcastPkts,
                                     ifOutMulticastPkts, or ifOutBroadcastPkts,
                                     and is not counted by the corresponding
                                     instance of the dot3StatsSingleCollisionFrames
                                     object.
                                     
                                     This counter does not increment when the
                                     interface is operating in full-duplex mode.
                                     
                                     Discontinuities in the value of this counter can
                                     occur at re-initialization of the management
                                     system, and at other times as indicated by the
                                     value of ifCounterDiscontinuityTime.";
                        type uint64;
                    }
                    leaf ethIfFcsErrors {
                        config false;
                        description "A count of frames received on a particular
                                     interface that are an integral number of octets
                                     in length but do not pass the FCS check.  This
                                     count does not include frames received with
                                     frame-too-long or frame-too-short error.
                                     
                                     The count represented by an instance of this
                                     object is incremented when the frameCheckError
                                     status is returned by the MAC service to the
                                     LLC (or other MAC user). Received frames for
                                     which multiple error conditions pertain are,
                                     according to the conventions of IEEE 802.3
                                     Layer Management, counted exclusively according
                                     to the error status presented to the LLC.
                                     
                                     Note:  Coding errors detected by the physical
                                     layer for speeds above 10 Mb/s will cause the
                                     frame to fail the FCS check.
                                     
                                     For interfaces operating at 10 Gb/s, this
                                     counter can roll over in less than 5 minutes if
                                     it is incrementing at its maximum rate.  Since
                                     that amount of time could be less than a
                                     management station's poll cycle time, in order
                                     to avoid a loss of information, a management
                                     station is advised to poll the
                                     dot3HCStatsFCSErrors object for 10 Gb/s or
                                     faster interfaces.
                                     
                                     Discontinuities in the value of this counter can
                                     occur at re-initialization of the management
                                     system, and at other times as indicated by the
                                     value of ifCounterDiscontinuityTime.";
                        type uint64;
                    }
                    leaf ethIfAlignmentErrors {
                        config false;
                        description "A count of frames received on a particular
                                     interface that are not an integral number of
                                     octets in length and do not pass the FCS check.
                                     
                                     The count represented by an instance of this
                                     object is incremented when the alignmentError
                                     status is returned by the MAC service to the
                                     LLC (or other MAC user). Received frames for
                                     which multiple error conditions pertain are,
                                     according to the conventions of IEEE 802.3
                                     Layer Management, counted exclusively according
                                     to the error status presented to the LLC.
                                     
                                     This counter does not increment for group
                                     encoding schemes greater than 4 bits per group.
                                     
                                     For interfaces operating at 10 Gb/s, this
                                     counter can roll over in less than 5 minutes if
                                     it is incrementing at its maximum rate.  Since
                                     that amount of time could be less than a
                                     management station's poll cycle time, in order
                                     to avoid a loss of information, a management
                                     station is advised to poll the
                                     dot3HCStatsAlignmentErrors object for 10 Gb/s
                                     or faster interfaces.
                                     
                                     Discontinuities in the value of this counter can
                                     occur at re-initialization of the management
                                     system, and at other times as indicated by the
                                     value of ifCounterDiscontinuityTime.";
                        type uint64;
                    }
                    leaf ethIfInCrcErrPkts {
                        config false;
                        description "The total number of CRC errored packets received on the interface.";
                        type uint64;
                    }
                    leaf ethIfInDiscardPkts {
                        config false;
                        description "The total number of discarded packets received on the interface.";
                        type uint64;
                    }
                    leaf ethIfInErrPkts {
                        config false;
                        description "The total number of errored packets received on the interface.";
                        type uint64;
                    }
                    leaf ethIfOutErrPkts {
                        config false;
                        description "The total number of errored packets that could not be transmitted 
                                     from the interface because of errors.";
                        type uint64;
                    }
                    leaf ethIfLinkStatusChanges {
                        config false;
                        description "The total number of the link status changes on the interface.
                                     The total number starts from zero and is increased when the link
                                     status changes from up to down, or from down to up.";
                        type uint32;
                    }
                    leaf ethIfInDropEvents {
                        config false;
                        description "The total number of events in which packets received were 
                                     dropped by the probe due to lack of resources.
                                     Note that this number is not necessarily the number of packets 
                                     dropped; it is just the number of times this condition has been 
                                     detected.";
                        type uint64;
                    }
                    leaf ethIfOutDropEvents {
                        config false;
                        description "The total number of events in which packets transmitted were 
                                     dropped by the probe due to lack of resources.
                                     Note that this number is not necessarily the number of packets 
                                     dropped; it is just the number of times this condition has been 
                                     detected.";
                        type uint64;
                    }
                    leaf ethIfOutCrcErrPkts {
                        config false;
                        description "The total number of CRC errored packets transmitted out of the 
                                     interface.";
                        type uint64;
                    }
                    leaf ethIfOutOversizedPkts {
                        config false;
                        description "The total number of packets transmitted that were longer than 
                                     1518 octets (excluding framing bits, but including FCS octets) 
                                     and were otherwise well formed.";
                        type uint64;
                    }
                    leaf ethIfOutUndersizedPkts {
                        config false;
                        description "The total number of packets transmitted that were less than 
                                     64 octets long (excluding framing bits, but including FCS 
                                     octets) and were otherwise well formed.";
                        type uint64;
                    }
                    leaf ethIfInFragments {
                        config false;
                        description "The total number of packets received that were less than 64 
                                     octets in length (excluding framing bits but including FCS 
                                     octets) and had either a bad Frame Check Sequence (FCS) with 
                                     an integral number of octets (FCS Error) or a bad FCS with a 
                                     non-integral number of octets (Alignment Error).";
                        type uint64;
                    }
                    leaf ethIfOutFragments {
                        config false;
                        description "The total number of packets transmitted that were less than 64 
                                     octets in length (excluding framing bits but including FCS 
                                     octets) and had either a bad Frame Check Sequence (FCS) with an 
                                     integral number of octets (FCS Error) or a bad FCS with a 
                                     non-integral number of octets (Alignment Error).";
                        type uint64;
                    }
                    leaf ethIfInJabbers {
                        config false;
                        description "The total number of packets received that were longer than 
                                     1518 octets (excluding framing bits, but including FCS octets), 
                                     and had either a bad Frame Check Sequence (FCS) with an integral 
                                     number of octets (FCS Error) or a bad FCS with a non-integral
                                     number of octets (Alignment Error).
                                     
                                     Note that this definition of jabber is different than the 
                                     definition in IEEE-802.3 section 8.2.1.5 (10BASE5) and section 
                                     10.3.1.4 (10BASE2). These documents define jabber as the 
                                     condition where any packet exceeds 20 ms. The allowed range to 
                                     detect jabber is between 20 ms and 150 ms.";
                        type uint64;
                    }
                    leaf ethIfOutJabbers {
                        config false;
                        description "The total number of packets transmitted that were longer than 
                                     1518 octets (excluding framing bits, but including FCS octets), 
                                     and had either a bad Frame Check Sequence (FCS) with an integral 
                                     number of octets (FCS Error) or a bad FCS with a non-integral
                                     number of octets (Alignment Error).
                                     
                                     Note that this definition of jabber is different than the 
                                     definition in IEEE-802.3 section 8.2.1.5 (10BASE5) and section 
                                     10.3.1.4 (10BASE2). These documents define jabber as the 
                                     condition where any packet exceeds 20 ms. The allowed range to 
                                     detect jabber is between 20 ms and 150 ms.";
                        type uint64;
                    }
                    leaf ethIfInPkts64Octets {
                        config false;
                        description "The total number of packets (including bad packets) received 
                                     that were 64 octets in length (excluding framing bits but 
                                     including FCS octets).";
                        type uint64;
                    }
                    leaf ethIfOutPkts64Octets {
                        config false;
                        description "The total number of packets (including bad packets) transmitted 
                                     that were 64 octets in length (excluding framing bits but 
                                     including FCS octets).";
                        type uint64;
                    }
                    leaf ethIfInPkts65to127Octets {
                        config false;
                        description "The total number of packets (including bad packets) received 
                                     that were between 65 and 127 octets in length (excluding 
                                     framing bits but including FCS octets).";
                        type uint64;
                    }
                    leaf ethIfOutPkts65to127Octets {
                        config false;
                        description "The total number of packets (including bad packets) transmitted 
                                     that were between 65 and 127 octets in length (excluding 
                                     framing bits but including FCS octets).";
                        type uint64;
                    }
                    leaf ethIfInPkts128to255Octets {
                        config false;
                        description "The total number of packets (including bad packets) received 
                                     that were between 128 and 255 octets in length (excluding 
                                     framing bits but including FCS octets).";
                        type uint64;
                    }
                    leaf ethIfOutPkts128to255Octets {
                        config false;
                        description "The total number of packets (including bad packets) transmitted 
                                     that were between 128 and 255 octets in length (excluding 
                                     framing bits but including FCS octets).";
                        type uint64;
                    }
                    leaf ethIfInPkts256to511Octets {
                        config false;
                        description "The total number of packets (including bad packets) received 
                                     that were between 256 and 511 octets in length (excluding 
                                     framing bits but including FCS octets).";
                        type uint64;
                    }
                    leaf ethIfOutPkts256to511Octets {
                        config false;
                        description "The total number of packets (including bad packets) transmitted 
                                     that were between 256 and 511 octets in length (excluding 
                                     framing bits but including FCS octets).";
                        type uint64;
                    }
                    leaf ethIfInPkts512to1023Octets {
                        config false;
                        description "The total number of packets (including bad packets) received 
                                     that were between 512 and 1023 octets in length (excluding 
                                     framing bits but including FCS octets).";
                        type uint64;
                    }
                    leaf ethIfOutPkts512to1023Octets {
                        config false;
                        description "The total number of packets (including bad packets) transmitted 
                                     that were between 512 and 1023 octets in length (excluding 
                                     framing bits but including FCS octets).";
                        type uint64;
                    }
                    leaf ethIfInPkts1024to1518Octets {
                        config false;
                        description "The total number of packets (including bad packets) received 
                                     that were between 1024 and 1518 octets in length (excluding 
                                     framing bits but including FCS octets).";
                        type uint64;
                    }
                    leaf ethIfOutPkts1024to1518Octets {
                        config false;
                        description "The total number of packets (including bad packets) transmitted 
                                     that were between 1024 and 1518 octets in length (excluding 
                                     framing bits but including FCS octets).";
                        type uint64;
                    }
                    leaf ethIfReset {
                        description "Clear all the current performance variables. When get this 
                                     When get this variable, always return 1.";
                        type enumeration {
                            enum perfReset {
                                value 1;
                                description "";
                            }
                        }
                    }
                }
            }
            container zxAnBrgIfCurrStatsTable {
                description "Current performance data table of interfaces.";
                list zxAnBrgIfCurrStatsEntry {
                    description "Current performance data entry of interfaces.";
                    max-elements 13;
                    key "ifIndex zxAnSubIfIndex";
                    leaf ifIndex {
                        description "A unique value, greater than zero, for each interface.  It
                                     is recommended that values are assigned contiguously
                                     starting from 1.  The value for each interface sub-layer
                                     must remain constant at least from one re-initialization of
                                     the entity's network management system to the next re-
                                     initialization.";
                        type int32 {
                            range 1..2147483647;
                        }
                    }
                    leaf zxAnSubIfIndex {
                        description "Sub-interface index at this interface.";
                        type int32;
                    }
                    leaf brgIfInOctets {
                        config false;
                        description "The total number of octets received on the interface,
                                     including framing characters.
                                     
                                     Discontinuities in the value of this counter can occur at
                                     re-initialization of the management system, and at other
                                     times as indicated by the value of
                                     ifCounterDiscontinuityTime.";
                        type uint64;
                    }
                    leaf brgIfInUcastPkts {
                        config false;
                        description "The number of packets, delivered by this sub-layer to a
                                     higher (sub-)layer, which were not addressed to a multicast
                                     or broadcast address at this sub-layer.
                                     
                                     Discontinuities in the value of this counter can occur at
                                     re-initialization of the management system, and at other
                                     times as indicated by the value of
                                     ifCounterDiscontinuityTime.";
                        type uint64;
                    }
                    leaf brgIfInMcastPkts {
                        config false;
                        description "The number of packets, delivered by this sub-layer to a
                                     higher (sub-)layer, which were addressed to a multicast
                                     address at this sub-layer.  For a MAC layer protocol, this
                                     includes both Group and Functional addresses.
                                     
                                     Discontinuities in the value of this counter can occur at
                                     re-initialization of the management system, and at other
                                     times as indicated by the value of
                                     ifCounterDiscontinuityTime.";
                        type uint64;
                    }
                    leaf brgIfInBcastPkts {
                        config false;
                        description "The number of packets, delivered by this sub-layer to a
                                     higher (sub-)layer, which were addressed to a broadcast
                                     address at this sub-layer.
                                     
                                     Discontinuities in the value of this counter can occur at
                                     re-initialization of the management system, and at other
                                     times as indicated by the value of
                                     ifCounterDiscontinuityTime.";
                        type uint64;
                    }
                    leaf brgIfOutOctets {
                        config false;
                        description "The total number of octets transmitted out of the interface,
                                     including framing characters.";
                        type uint64;
                    }
                    leaf brgIfOutUcastPkts {
                        config false;
                        description "The total number of packets that higher-level protocols
                                     requested be transmitted, and which were not addressed to a
                                     multicast or broadcast address at this sub-layer, including
                                     those that were discarded or not sent.
                                     
                                     Discontinuities in the value of this counter can occur at
                                     re-initialization of the management system, and at other
                                     times as indicated by the value of
                                     ifCounterDiscontinuityTime.";
                        type uint64;
                    }
                    leaf brgIfOutMcastPkts {
                        config false;
                        description "The total number of packets that higher-level protocols
                                     requested be transmitted, and which were addressed to a
                                     multicast address at this sub-layer, including those that
                                     were discarded or not sent.  For a MAC layer protocol, this
                                     includes both Group and Functional addresses.
                                     
                                     Discontinuities in the value of this counter can occur at
                                     re-initialization of the management system, and at other
                                     times as indicated by the value of
                                     ifCounterDiscontinuityTime";
                        type uint64;
                    }
                    leaf brgIfOutBcastPkts {
                        config false;
                        description "The total number of packets that higher-level protocols
                                     requested be transmitted, and which were addressed to a
                                     broadcast address at this sub-layer, including those that
                                     were discarded or not sent.
                                     
                                     Discontinuities in the value of this counter can occur at
                                     re-initialization of the management system, and at other
                                     times as indicated by the value of
                                     ifCounterDiscontinuityTime.";
                        type uint64;
                    }
                    leaf brgIfInDiscardPkts {
                        config false;
                        description "The total number of received discarded packets.";
                        type uint64;
                    }
                    leaf brgIfOutDiscardPkts {
                        config false;
                        description "The total number of transmitted discarded packets.";
                        type uint64;
                    }
                    leaf brgIfReset {
                        description "Clear all the current performance variables.
                                     When get this variable, always return 1.";
                        type enumeration {
                            enum perfReset {
                                value 1;
                                description "";
                            }
                        }
                    }
                }
            }
            container zxAnIfRateStatsTable {
                description "The rate statistics table of interfaces.";
                list zxAnIfRateStatsEntry {
                    description "The rate statistics entry of interfaces.";
                    max-elements 12;
                    key "ifIndex zxAnSubIfIndex";
                    leaf ifIndex {
                        description "A unique value, greater than zero, for each interface.  It
                                     is recommended that values are assigned contiguously
                                     starting from 1.  The value for each interface sub-layer
                                     must remain constant at least from one re-initialization of
                                     the entity's network management system to the next re-
                                     initialization.";
                        type int32 {
                            range 1..2147483647;
                        }
                    }
                    leaf zxAnSubIfIndex {
                        description "Sub-interface index at this interface.";
                        type int32;
                    }
                    leaf ifCurrTxNetDataRate {
                        config false;
                        description "Current actual transmitted net data rate of the interface.";
                        type int32;
                    }
                    leaf ifCurrRxNetDataRate {
                        config false;
                        description "Current actual received net data rate of the interface.";
                        type int32;
                    }
                    leaf ifCurrTxOctetRate {
                        config false;
                        description "An estimate of the interface's current transmitted bandwidth in
                                     bytes per second.
                                     For interfaces which do not vary in bandwidth or for those where no
                                     accurate estimation can be made, this object should contain the
                                     nominal bandwidth.  If the bandwidth of the interface is greater
                                     than the maximum value reportable by this object then this object
                                     should report its maximum value (4,294,967,295).";
                        type uint32;
                    }
                    leaf ifCurrRxOctetRate {
                        config false;
                        description "An estimate of the interface's current received bandwidth
                                     in bytes per second.
                                     For interfaces which do not vary in bandwidth or for those where no
                                     accurate estimation can be made, this object should contain the
                                     nominal bandwidth.  If the bandwidth of the interface is greater
                                     than the maximum value reportable by this object then this object
                                     should report its maximum value (4,294,967,295).";
                        type uint32;
                    }
                    leaf ifCurrTxPktRate {
                        config false;
                        description "An estimate of the interface's current transmitted bandwidth
                                     in packets per second.
                                     For interfaces which do not vary in bandwidth or for those where no
                                     accurate estimation can be made, this object should contain the
                                     nominal bandwidth.  If the bandwidth of the interface is greater
                                     than the maximum value reportable by this object then this object
                                     should report its maximum value (4,294,967,295).";
                        type uint32;
                    }
                    leaf ifCurrRxPktRate {
                        config false;
                        description "An estimate of the interface's current received bandwidth
                                     in packets per second.
                                     For interfaces which do not vary in bandwidth or for those where no
                                     accurate estimation can be made, this object should contain the
                                     nominal bandwidth.  If the bandwidth of the interface is greater
                                     than the maximum value reportable by this object then this object
                                     should report its maximum value (4,294,967,295).";
                        type uint32;
                    }
                    leaf ifCurrTxOctetPeakRate {
                        config false;
                        description "The interface's peak transmitted bandwidth in bytes per second.
                                     If the bandwidth of the interface is greater than the maximum value
                                     reportable by this object then this object should report its maximum
                                     value (4,294,967,295).";
                        type uint32;
                    }
                    leaf ifCurrRxOctetPeakRate {
                        config false;
                        description "The interface's peak received bandwidth in bytes per second.
                                     If the bandwidth of the interface is greater than the maximum value
                                     reportable by this object then this object should report its maximum
                                     value (4,294,967,295).";
                        type uint32;
                    }
                    leaf ifCurrTxErroredPktRate {
                        config false;
                        description "Current transmitted errored packet rate.";
                        type uint32;
                    }
                    leaf ifCurrRxErroredPktRate {
                        config false;
                        description "Current received errored packet rate.";
                        type uint32;
                    }
                }
            }
            container zxAnIfBandwidthUsingTable {
                description "Bandwidth using ratio and threshold table.";
                list zxAnIfBandwidthUsingEntry {
                    description "Bandwidth using entry.";
                    max-elements 6;
                    key "ifIndex zxAnSubIfIndex";
                    leaf ifIndex {
                        description "A unique value, greater than zero, for each interface.  It
                                     is recommended that values are assigned contiguously
                                     starting from 1.  The value for each interface sub-layer
                                     must remain constant at least from one re-initialization of
                                     the entity's network management system to the next re-
                                     initialization.";
                        type int32 {
                            range 1..2147483647;
                        }
                    }
                    leaf zxAnSubIfIndex {
                        description "Sub-interface index at this interface.";
                        type int32;
                    }
                    leaf ifInBandwidthUsingRatio {
                        config false;
                        description "An estimate of the interface's current received bandwidth using
                                     ratio.";
                        type int32 {
                            range 0..100;
                        }
                    }
                    leaf ifOutBandwidthUsingRatio {
                        config false;
                        description "An estimate of the interface's current transmitted bandwidth using
                                     ratio.";
                        type int32 {
                            range 0..100;
                        }
                    }
                    leaf ifInBandwidthUsingThresh {
                        description "The threshold of ifInBandwidthUsingRatio.
                                     When ifInBandwidthUsingRatio exceeds this threshold,
                                     the ifInBwUsingThreshExceedAlm trap should be generated.
                                     If ifInBandwidthUsingRatio always exceeds the threshold,
                                     only one ifInBwUsingThreshExceedAlm trap should be sent.";
                        type int32 {
                            range 0..100;
                        }
                        default 100;
                    }
                    leaf ifOutBandwidthUsingThresh {
                        description "The threshold of ifOutBandwidthUsingRatio.
                                     When ifOutBandwidthUsingRatio exceeds this threshold,
                                     the ifOutBwUsingThreshExceedAlm trap should be generated.
                                     If ifOutBandwidthUsingRatio always exceeds the threshold,
                                     only one ifOutBwUsingThreshExceedAlm trap should be sent.";
                        type int32 {
                            range 0..100;
                        }
                        default 100;
                    }
                    leaf ifInBandwidthUsingRatioHa {
                        config false;
                        description "The high accuracy value of ifInBandwidthUsingRatio.";
                        type int32 {
                            range 0..10000000;
                        }
                    }
                    leaf ifOutBandwidthUsingRatioHa {
                        config false;
                        description "The high accuracy value of ifOutBandwidthUsingRatio";
                        type int32 {
                            range 0..10000000;
                        }
                    }
                }
            }
            container zxAnIfVlan2CurrStatsTable {
                description "Interface S-VID and C-VID statistic table.";
                list zxAnIfVlan2CurrStatsEntry {
                    description "Interface SVLAN and CVLAN statistic entry.";
                    max-elements 110;
                    key "ifIndex ifVlan2CurrStatsSVid ifVlan2CurrStatsCVid";
                    leaf ifIndex {
                        description "A unique value, greater than zero, for each interface.  It
                                     is recommended that values are assigned contiguously
                                     starting from 1.  The value for each interface sub-layer
                                     must remain constant at least from one re-initialization of
                                     the entity's network management system to the next re-
                                     initialization.";
                        type int32 {
                            range 1..2147483647;
                        }
                    }
                    leaf ifVlan2CurrStatsSVid {
                        description "The interface S-VID.";
                        type int32 {
                            range 1..4094;
                        }
                    }
                    leaf ifVlan2CurrStatsCVid {
                        description "The interface C-VID.
                                     Value 0 means statistics only based on S-VID.";
                        type int32 {
                            range 0..4094;
                        }
                    }
                    leaf ifVlan2InPkts {
                        config false;
                        description "Received packets of the interface VLAN.";
                        type uint64;
                    }
                    leaf ifVlan2OutPkts {
                        config false;
                        description "Transmitted packets of the interface VLAN.";
                        type uint64;
                    }
                    leaf ifVlan2InOctets {
                        config false;
                        description "Received octets of the interface VLAN.";
                        type uint64;
                    }
                    leaf ifVlan2OutOctets {
                        config false;
                        description "Transmitted octets of the interface VLAN.";
                        type uint64;
                    }
                    leaf ifVlan2CurrStatsReset {
                        description "Clear all the current performance variables.
                                     When get this variable, always return 1.
                                     Reset port vlan statistics counter manually when it is set to '1'.";
                        type enumeration {
                            enum perfReset {
                                value 1;
                                description "";
                            }
                        }
                    }
                }
            }
            container zxAnBrgIfCurrPerfStatsTable {
                description "Enable/disable the bridge interface current performance 
                             statistics.";
                list zxAnBrgIfCurrPerfStatsEntry {
                    description "A zxAnBrgIfCurrPerfStatsTable entry.";
                    max-elements 3;
                    key "ifIndex zxAnSubIfIndex";
                    leaf ifIndex {
                        description "A unique value, greater than zero, for each interface.  It
                                     is recommended that values are assigned contiguously
                                     starting from 1.  The value for each interface sub-layer
                                     must remain constant at least from one re-initialization of
                                     the entity's network management system to the next re-
                                     initialization.";
                        type int32 {
                            range 1..2147483647;
                        }
                    }
                    leaf zxAnSubIfIndex {
                        description "Sub-interface index at this interface.";
                        type int32;
                    }
                }
            }
            container zxAnIfVlanCurrPerfStatsTable {
                description "Enable/disable the interface S-VID and C-VID current performance 
                             statistics.";
                list zxAnIfVlanCurrPerfStatsEntry {
                    description "A zxAnIfVlanCurrPerfStatsTable entry.";
                    max-elements 111;
                    key "ifIndex ifVlanPerfStatsSVid ifVlanPerfStatsCVid";
                    leaf ifIndex {
                        description "A unique value, greater than zero, for each interface.  It
                                     is recommended that values are assigned contiguously
                                     starting from 1.  The value for each interface sub-layer
                                     must remain constant at least from one re-initialization of
                                     the entity's network management system to the next re-
                                     initialization.";
                        type int32 {
                            range 1..2147483647;
                        }
                    }
                    leaf ifVlanPerfStatsSVid {
                        description "The interface S-VID.";
                        type int32 {
                            range 1..4094;
                        }
                    }
                    leaf ifVlanPerfStatsCVid {
                        description "The interface C-VID.
                                     Value 0 means statistics only based on S-VID.";
                        type int32 {
                            range 0..4094;
                        }
                    }
                }
            }
        }
    }
}
