module zxr10-acl {
  namespace 'http://www.zte.com.cn/zxr10/netconf/schema/rosng/acl'
            ;
  prefix acl ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The netconf module to describe access-list(ACL).'
              ;
  revision 2022-01-27 {
    description '1. Add log in user defined template ACL:'+"\n"
              + '/configuration/acl/access-list/user-defined-template-acls/user'
              + '-defined-template-acl/rules/rule/log'+"\n"
              + '2. Support user defined template ACL statistics switch:'+"\n"
              + '/configuration/acl/statistics-switch/user-defined-template-log'
              + '-switches;'+"\n"
              + '3. Support user defined template ACL statistics clear:'+"\n"
              + '/operation/acl/user-defined-template-log-clears;'+"\n"
              + '4. Add general user defined template:'+"\n"
              + '/configuration/acl/templates/udf-template-generals.'
                ;
  }
  revision 2022-01-20 {
    description 'In order to support statistics for IPv4 and IPv6 VXLAN ACL, so'
              + 'me nodes are added as follows:'+"\n"
              + '1./configuration/acl/access-list/ipv4-vxlan-access-lists/ipv4-'
              + 'vxlan-access-list/rules/rule/log'+"\n"
              + '2./configuration/acl/access-list/ipv4-vxlan-access-lists/ipv4-'
              + 'vxlan-access-list/rules-transit-inner/rule-transit-inner/log'+"\n"
              + '3./configuration/acl/access-list/ipv4-vxlan-access-lists/ipv4-'
              + 'vxlan-access-list/rules-vtep-inner/rule-vtep-inner/log'+"\n"
              + '4./configuration/acl/access-list/ipv6-vxlan-access-lists/ipv6-'
              + 'vxlan-access-list/rules-transit-inner/rule-transit-inner/log'+"\n"
              + '5./configuration/acl/access-list/ipv6-vxlan-access-lists/ipv6-'
              + 'vxlan-access-list/rules-vtep-inner/rule-vtep-inner/log'+"\n"
              + '6./configuration/acl/statistics-switch/ipv4-vxlan-log-switches'
              + '-by-acl'+"\n"
              + '7./configuration/acl/statistics-switch/ipv6-vxlan-log-switches'
              + '-by-acl'+"\n"
              + '8./operation/acl/ipv4-vxlan-log-clears-by-acl'+"\n"
              + '9./operation/acl/ipv6-vxlan-log-clears-by-acl'+"\n"
              + '10./state/acl/acl-v4-vxlan-statistics-by-acl'+"\n"
              + '11./state/acl/acl-v6-vxlan-statistics-by-acl'
                ;
  }
  revision 2021-11-23 {
    description 'To support default action configuration in empty ACL, some lea'
              + 'f nodes are added as follows:'+"\n"
              + '1./configuration/acl/port-acl/if-ipv4/egress/none-rule-default'
              + '-action;'+"\n"
              + '2./configuration/acl/port-acl/if-ipv4/ingress/none-rule-defaul'
              + 't-action;'+"\n"
              + '3./configuration/acl/port-acl/if-ipv6/egress/none-rule-default'
              + '-action;'+"\n"
              + '4./configuration/acl/port-acl/if-ipv6/ingress/none-rule-defaul'
              + 't-action;'+"\n"
              + '5./configuration/acl/port-acl/if-link/egress/none-rule-default'
              + '-action;'+"\n"
              + '6./configuration/acl/port-acl/if-link/ingress/none-rule-defaul'
              + 't-action.'
                ;
  }
  revision 2021-11-02 {
    description 'To support clear acl statistics in all interface, some list no'
              + 'des are changed to choice-case nodes, and some container nodes'
              + ' are added in choice nodes.'+"\n"
              + '1./operation/acl/ipv4-log-clears;'+"\n"
              + '2./operation/acl/ipv6-log-clears;'+"\n"
              + '3./operation/acl/link-log-clears;'+"\n"
              + '4./operation/acl/ipv4-mixed-log-clears;'
                ;
  }
  revision 2021-10-26 {
    description 'In order to support vxlan link acl, some nodes are added as fo'
              + 'llows:'+"\n"
              + '1. /configuration/acl/access-list/ipv4-vxlan-access-lists/ipv4'
              + '-vxlan-access-list/rules-transit-inner/rule-transit-inner/l2-l'
              + 'ayer;'+"\n"
              + '2. /configuration/acl/access-list/ipv4-vxlan-access-lists/ipv4'
              + '-vxlan-access-list/rules-vtep-inner/rule-vtep-inner/l2-layer;
'
              + ''+"\n"
              + '3. /configuration/acl/access-list/ipv6-vxlan-access-lists/ipv6'
              + '-vxlan-access-list/rules-transit-inner/rule-transit-inner/l2-l'
              + 'ayer;'+"\n"
              + '4. /configuration/acl/access-list/ipv6-vxlan-access-lists/ipv6'
              + '-vxlan-access-list/rules-vtep-inner/rule-vtep-inner/l2-layer;'
                ;
  }
  revision 2021-10-20 {
    description 'Add some nodes to support obtaining statistics by ACL:'+"\n"
              + '1./configuration/acl/statistics-switch/ipv4-log-switchs-by-acl'
              + ''+"\n"
              + '2./configuration/acl/statistics-switch/ipv6-log-switchs-by-acl'
              + ''+"\n"
              + '3./configuration/acl/statistics-switch/link-log-switchs-by-acl'
              + ''+"\n"
              + '4./configuration/acl/statistics-switch/ipv4-mixed-log-switchs-'
              + 'by-acl'+"\n"
              + '5./configuration/acl/statistics-switch/ipv6-mixed-log-switchs-'
              + 'by-acl'+"\n"
              + '6./operation/acl/ipv4-log-clears-by-acl'+"\n"
              + '7./operation/acl/ipv6-log-clears-by-acl'+"\n"
              + '8./operation/acl/link-log-clears-by-acl'+"\n"
              + '9./operation/acl/ipv4-mixed-log-clears-by-acl'+"\n"
              + '10./operation/acl/ipv6-mixed-log-clears-by-acl'+"\n"
              + '11./state/acl/acl-v4-statistics-by-acl'+"\n"
              + '12./state/acl/acl-v6-statistics-by-acl'+"\n"
              + '13./state/acl/acl-link-statistics-by-acl'+"\n"
              + '14./state/acl/acl-v4-mixed-statistics-by-acl'+"\n"
              + '15./state/acl/acl-v6-mixed-statistics-by-acl'
                ;
  }
  revision 2021-08-09 {
    description 'IPv6 wildcard leaf nodes are changed to choice-case nodes, and'
              + ' wildcard-bits case nodes are added in wildcard choice nodes:
'
              + ''+"\n"
              + '1./acl:configuration/acl:acl/acl:access-list/acl:ipv6-access-l'
              + 'ist/acl:rule/acl:src-wildcard-type;'+"\n"
              + '2./acl:configuration/acl:acl/acl:access-list/acl:ipv6-access-l'
              + 'ist/acl:rule/acl:dest-wildcard-type;'+"\n"
              + '3./acl:configuration/acl:acl/acl:access-list/acl:ipv6-mixed-ac'
              + 'cess-list/acl:rule/acl:src-wildcard-type;'+"\n"
              + '4./acl:configuration/acl:acl/acl:access-list/acl:ipv6-mixed-ac'
              + 'cess-list/acl:rule/acl:dest-wildcard-type.'
                ;
  }
  revision 2021-08-04 {
    description 'Add EXP node in IPv6 ACL:'+"\n"
              + '/configuration/acl/access-list/ipv6-mixed-access-list/rule/exp'
              + '.'
                ;
  }
  revision 2021-06-03 {
    description 'In order to support statistics for IPv6 mixed ACL, some nodes '
              + 'are added as follows:'+"\n"
              + '1.Add new feature: ipv6-mixed-log-config'+"\n"
              + '2./configuration/acl/access-list/ipv6-mixed-access-list/rule/l'
              + 'og'+"\n"
              + '3./configuration/acl/statistics-switch/ipv6-mixed-log-switchs
'
              + ''+"\n"
              + '4./operation/acl/ipv6-mixed-log-clears'+"\n"
              + '5./state/acl/acl-v6-mixed-statistics'
                ;
  }
  revision 2021-04-02 {
    description '1.Add time-range nodes in IPv4 vxlan rule as follows:'+"\n"
              + '/configuration/acl/access-list/ipv4-vxlan-access-lists/ipv4-vx'
              + 'lan-access-list/rules/rule/time-range;'+"\n"
              + '/configuration/acl/access-list/ipv4-vxlan-access-lists/ipv4-vx'
              + 'lan-access-list/rules-transit-inner/rule-transit-inner/time-ra'
              + 'nge;'+"\n"
              + '/configuration/acl/access-list/ipv4-vxlan-access-lists/ipv4-vx'
              + 'lan-access-list/rules-transit-outer/rule-transit-outer/time-ra'
              + 'nge;'+"\n"
              + '/configuration/acl/access-list/ipv4-vxlan-access-lists/ipv4-vx'
              + 'lan-access-list/rules-vtep-inner/rule-vtep-inner/time-range;'+"\n"
              + '/configuration/acl/access-list/ipv4-vxlan-access-lists/ipv4-vx'
              + 'lan-access-list/rules-vtep-outer/rule-vtep-outer/time-range.'+"\n"
              + '2.Add time-range nodes in IPv6 vxlan rule as follows:'+"\n"
              + '/configuration/acl/access-list/ipv6-vxlan-access-lists/ipv6-vx'
              + 'lan-access-list/rules-transit-inner/rule-transit-inner/time-ra'
              + 'nge;'+"\n"
              + '/configuration/acl/access-list/ipv6-vxlan-access-lists/ipv6-vx'
              + 'lan-access-list/rules-transit-outer/rule-transit-outer/time-ra'
              + 'nge;'+"\n"
              + '/configuration/acl/access-list/ipv6-vxlan-access-lists/ipv6-vx'
              + 'lan-access-list/rules-vtep-inner/rule-vtep-inner/time-range;'+"\n"
              + '/configuration/acl/access-list/ipv6-vxlan-access-lists/ipv6-vx'
              + 'lan-access-list/rules-vtep-outer/rule-vtep-outer/time-range.'
                ;
  }
  revision 2020-08-21 {
    description '1 Add dscp-range with if-feature ipv6-dscp-range-config in IPv'
              + '6 and IPv6 mixed rule:'+"\n"
              + '/configuration/acl/access-list/ipv6-access-list/rule/dscp-rang'
              + 'e,'+"\n"
              + '/configuration/acl/access-list/ipv6-mixed-access-list/rule/dsc'
              + 'p-range.'+"\n"
              + '2 Add cos-range with if-feature ipv6-cos-range-config in IPv6 '
              + 'mixed rule:'+"\n"
              + '/configuration/acl/access-list/ipv6-mixed-access-list/rule/inn'
              + 'er-cos-range,'+"\n"
              + '/configuration/acl/access-list/ipv6-mixed-access-list/rule/out'
              + 'er-cos-range.'
                ;
  }
  revision 2020-08-17 {
    description 'Some vrf leaf nodes are changed to vrf choice-case nodes, and '
              + 'vrf-dcn case nodes are added in vrf choice nodes:'+"\n"
              + '1./acl:configuration/acl:acl/acl:access-list/acl:ipv4-access-l'
              + 'ist/acl:rule/acl:vrf-config;'+"\n"
              + '2./acl:configuration/acl:acl/acl:access-list/acl:ipv6-access-l'
              + 'ist/acl:rule/acl:vrf-config.'
                ;
  }
  revision 2020-07-13 {
    description '1. Add policy-route-id in IPv4 mixed ACL:'+"\n"
              + '/acl:configuration/acl:acl/acl:access-list/acl:ipv4-mixed-acce'
              + 'ss-list/acl:rule/acl:policy-route-id.'+"\n"
              + '2. Add monitor-group-id in IPv4 mixed ACL:'+"\n"
              + '/acl:configuration/acl:acl/acl:access-list/acl:ipv4-mixed-acce'
              + 'ss-list/acl:rule/acl:extended/acl:source-monitor-group-id;'+"\n"
              + '/acl:configuration/acl:acl/acl:access-list/acl:ipv4-mixed-acce'
              + 'ss-list/acl:rule/acl:extended/acl:destination-monitor-group-id'
              + '.'
                ;
  }
  revision 2020-06-29 {
    description 'In order to describing access list and port acl, new nodes are'
              + ' added as follows:'+"\n"
              + '1./acl:configuration/acl:acl/acl:access-list/acl:ipv6-mixed-ac'
              + 'cess-list/acl:acl-description;'+"\n"
              + '2./acl:configuration/acl:acl/acl:port-acl/acl:vlan-ipv4/acl:eg'
              + 'ress/acl:port-acl-description;'+"\n"
              + '3./acl:configuration/acl:acl/acl:port-acl/acl:vlan-ipv4/acl:in'
              + 'gress/acl:port-acl-description;'+"\n"
              + '4./acl:configuration/acl:acl/acl:port-acl/acl:vlan-ipv4-mixed/'
              + 'acl:egress/acl:port-acl-description;'+"\n"
              + '5./acl:configuration/acl:acl/acl:port-acl/acl:vlan-ipv4-mixed/'
              + 'acl:ingress/acl:port-acl-description;'+"\n"
              + '6./acl:configuration/acl:acl/acl:port-acl/acl:vlan-ipv6/acl:eg'
              + 'ress/acl:port-acl-description;'+"\n"
              + '7./acl:configuration/acl:acl/acl:port-acl/acl:vlan-ipv6/acl:in'
              + 'gress/acl:port-acl-description;'+"\n"
              + '8./acl:configuration/acl:acl/acl:port-acl/acl:if-ipv6-mixed/ac'
              + 'l:egress/acl:port-acl-description;'+"\n"
              + '9./acl:configuration/acl:acl/acl:port-acl/acl:if-ipv6-mixed/ac'
              + 'l:ingress/acl:port-acl-description;'+"\n"
              + '10./acl:configuration/acl:acl/acl:port-acl/acl:vlan-ipv6-mixed'
              + '/acl:egress/acl:port-acl-description;'+"\n"
              + '11./acl:configuration/acl:acl/acl:port-acl/acl:vlan-ipv6-mixed'
              + '/acl:ingress/acl:port-acl-description.'
                ;
  }
  revision 2020-06-18 {
    description 'In order to describing access list and port acl, new nodes are'
              + ' added as follows:'+"\n"
              + '1./acl:configuration/acl:acl/acl:access-list/acl:ipv4-access-l'
              + 'ist/acl:acl-description;'+"\n"
              + '2./acl:configuration/acl:acl/acl:access-list/acl:ipv4-mixed-ac'
              + 'cess-list/acl:acl-description;'+"\n"
              + '3./acl:configuration/acl:acl/acl:access-list/acl:ipv6-access-l'
              + 'ist/acl:acl-description;'+"\n"
              + '4./acl:configuration/acl:acl/acl:port-acl/acl:if-ipv4/acl:egre'
              + 'ss/acl:port-acl-description;'+"\n"
              + '5./acl:configuration/acl:acl/acl:port-acl/acl:if-ipv4/acl:ingr'
              + 'ess/acl:port-acl-description;'+"\n"
              + '6./acl:configuration/acl:acl/acl:port-acl/acl:if-ipv4-mixed/ac'
              + 'l:egress/acl:port-acl-description;'+"\n"
              + '7./acl:configuration/acl:acl/acl:port-acl/acl:if-ipv4-mixed/ac'
              + 'l:ingress/acl:port-acl-description;'+"\n"
              + '8./acl:configuration/acl:acl/acl:port-acl/acl:if-ipv6/acl:egre'
              + 'ss/acl:port-acl-description;'+"\n"
              + '9./acl:configuration/acl:acl/acl:port-acl/acl:if-ipv6/acl:ingr'
              + 'ess/acl:port-acl-description.'
                ;
  }
  revision 2020-03-23 {
    description 'Add time-to-live to ipv6-access-lists:'+"\n"
              + 'configuration/acl/access-list/ipv6-access-list/rule/time-to-li'
              + 've.'
                ;
  }
  revision 2020-03-18 {
    description 'In order to support IPv6 Vxlan ACL, some nodes are added as fo'
              + 'llows:'+"\n"
              + '1./acl:configuration/acl:acl/acl:access-list/acl:ipv6-vxlan-ac'
              + 'cess-lists;'+"\n"
              + '2./acl:configuration/acl:acl/acl:port-acl/acl:if-ipv6-vxlan;'+"\n"
              + '3./acl:configuration/acl:acl/acl:port-acl/acl:vlan-ipv6-vxlan;'
              + ''+"\n"
              + '4./acl:configuration/acl:acl/acl:port-acl/acl:device-ipv6-vxla'
              + 'ns;'
                ;
  }
  revision 2020-03-05 {
    description 'The product T8000 begins to support the Feature [pri-range-con'
              + 'fig], but does not support the Feature [pri-value-config] any '
              + 'more.'
                ;
  }
  revision 2020-01-20 {
    description 'In order to support binding ACL to specified slots, some nodes'
              + ' are added as follows:'+"\n"
              + '1./acl:configuration/acl:acl/acl:port-acl/acl:slot-ipv4s;'+"\n"
              + '2./acl:configuration/acl:acl/acl:port-acl/acl:slot-ipv6s.'
                ;
  }
  revision 2019-12-11 {
    description 'Add source-monitor-group-id in IPv4 ACL and IPv6 ACL:'+"\n"
              + '1./acl:configuration/acl:acl/acl:access-list/acl:ipv4-access-l'
              + 'ist/acl:rule/acl:extended/acl:source-monitor-group-id;'+"\n"
              + '2./acl:configuration/acl:acl/acl:access-list/acl:ipv6-access-l'
              + 'ist/acl:rule/acl:source-monitor-group-id.'
                ;
  }
  revision 2019-12-06 {
    description '1.Support rule description to IPv4 mixed/IPv6 mixed ACL, new n'
              + 'odes added as follows:'+"\n"
              + '/configuration/acl/access-list/ipv4-mixed-access-list/rule/v4m'
              + 'ix-desc'+"\n"
              + '/configuration/acl/access-list/ipv6-mixed-access-list/rule/v6m'
              + 'ix-desc;'+"\n"
              + '2. In order to support configuring mixed ACL rule description '
              + 'separately, some mandatory leaf nodes are adjusted  to be opti'
              + 'onal nodes, modification in detail as follows:'+"\n"
              + '/configuration/acl/access-list/ipv4-mixed-access-list/rule/per'
              + 'mit-deny'+"\n"
              + '/configuration/acl/access-list/ipv4-mixed-access-list/rule/src'
              + '-addr'+"\n"
              + '/configuration/acl/access-list/ipv4-mixed-access-list/rule/rul'
              + 'e-type'+"\n"
              + '/configuration/acl/access-list/ipv4-mixed-access-list/rule/src'
              + '-mac-addr'+"\n"
              + '/configuration/acl/access-list/ipv4-mixed-access-list/rule/des'
              + 't-mac-addr'+"\n"
              + '/configuration/acl/access-list/ipv6-mixed-access-list/rule/per'
              + 'mit-deny'+"\n"
              + '/configuration/acl/access-list/ipv6-mixed-access-list/rule/src'
              + '-addr'+"\n"
              + '/configuration/acl/access-list/ipv6-mixed-access-list/rule/dst'
              + '-addr'+"\n"
              + '/configuration/acl/access-list/ipv6-mixed-access-list/rule/rul'
              + 'e-type'+"\n"
              + '/configuration/acl/access-list/ipv6-mixed-access-list/rule/src'
              + '-mac-addr'+"\n"
              + '/configuration/acl/access-list/ipv6-mixed-access-list/rule/des'
              + 't-mac-addr.'
                ;
  }
  revision 2019-11-26 {
    description 'Add monitor-group-id in IPv4 ACL and IPv6 ACL:'+"\n"
              + '1./acl:configuration/acl:acl/acl:access-list/acl:ipv4-access-l'
              + 'ist/acl:rule/acl:extended/acl:monitor-group-id;'+"\n"
              + '2./acl:configuration/acl:acl/acl:access-list/acl:ipv6-access-l'
              + 'ist/acl:rule/acl:monitor-group-id.'
                ;
  }
  revision 2019-10-08 {
    description 'Add some nodes to support configuring IPv4 mixed ACL and obtai'
              + 'ning its statistics for 15K product. The modifications in deta'
              + 'il are as follows:'+"\n"
              + '1.Add new feature: ipv4-mixed-log-config'+"\n"
              + '2./configuration/acl/access-list/ipv4-mixed-access-list/rule/e'
              + 'xp'+"\n"
              + '3./configuration/acl/access-list/ipv4-mixed-access-list/rule/l'
              + 'abel'+"\n"
              + '4./configuration/acl/access-list/ipv4-mixed-access-list/rule/l'
              + 'abel2'+"\n"
              + '5./configuration/acl/access-list/ipv4-mixed-access-list/rule/l'
              + 'og'+"\n"
              + '6./configuration/acl/statistics-switch/link-log-switchs'+"\n"
              + '7./configuration/acl/statistics-switch/ipv4-mixed-log-switchs
'
              + ''+"\n"
              + '8./operation/acl/ipv4-mixed-log-clears'+"\n"
              + '9./state/acl/acl-link-statistics'+"\n"
              + '10./state/acl/acl-v4-mixed-statistics'
                ;
  }
  revision 2019-09-10 {
    description 'Add policy-route-id in IPv4 ACL and IPv6 ACL:'+"\n"
              + '1./acl:configuration/acl:acl/acl:access-list/acl:ipv4-access-l'
              + 'ist/acl:rule/acl:policy-route-id'+"\n"
              + '2./acl:configuration/acl:acl/acl:access-list/acl:ipv6-access-l'
              + 'ist/acl:rule/acl:policy-route-id'
                ;
  }
  revision 2019-08-14 {
    description 'Add sgt in IPv4 VXLAN ACL:'+"\n"
              + '1./acl:configuration/acl:acl/acl:access-list/acl:ipv4-vxlan-ac'
              + 'cess-lists/acl:ipv4-vxlan-access-list/acl:rules/acl:rule/acl:s'
              + 'gt'+"\n"
              + '2./acl:configuration/acl:acl/acl:access-list/acl:ipv4-vxlan-ac'
              + 'cess-lists/acl:ipv4-vxlan-access-list/acl:rules-transit-inner/'
              + 'acl:rule-transit-inner/acl:sgt'+"\n"
              + '3./acl:configuration/acl:acl/acl:access-list/acl:ipv4-vxlan-ac'
              + 'cess-lists/acl:ipv4-vxlan-access-list/acl:rules-transit-outer/'
              + 'acl:rule-transit-outer/acl:sgt'+"\n"
              + '4./acl:configuration/acl:acl/acl:access-list/acl:ipv4-vxlan-ac'
              + 'cess-lists/acl:ipv4-vxlan-access-list/acl:rules-vtep-inner/acl'
              + ':rule-vtep-inner/acl:sgt'+"\n"
              + '5./acl:configuration/acl:acl/acl:access-list/acl:ipv4-vxlan-ac'
              + 'cess-lists/acl:ipv4-vxlan-access-list/acl:rules-vtep-outer/acl'
              + ':rule-vtep-outer/acl:sgt'
                ;
  }
  revision 2019-06-18 {
    description 'Add label in link ACL, include leafes:'+"\n"
              + '1./acl:configuration/acl:acl/acl:access-list/acl:link-access-l'
              + 'ist/acl:rule/acl:label'+"\n"
              + '2./acl:configuration/acl:acl/acl:access-list/acl:link-access-l'
              + 'ist/acl:rule/acl:label2'
                ;
  }
  revision 2018-09-17 {
    description 'Add mode type node and its rule node in IPv4 VXLAN ACL, add vr'
              + 'f node in rules of default mode:'+"\n"
              + '1./acl:configuration/acl:acl/acl:access-list/acl:ipv4-vxlan-ac'
              + 'cess-lists/acl:ipv4-vxlan-access-list/acl:mode-type'+"\n"
              + '2./acl:configuration/acl:acl/acl:access-list/acl:ipv4-vxlan-ac'
              + 'cess-lists/acl:ipv4-vxlan-access-list/acl:rules/acl:rule/acl:v'
              + 'rf'+"\n"
              + '3./acl:configuration/acl:acl/acl:access-list/acl:ipv4-vxlan-ac'
              + 'cess-lists/acl:ipv4-vxlan-access-list/acl:rules-transit-inner
'
              + ''+"\n"
              + '4./acl:configuration/acl:acl/acl:access-list/acl:ipv4-vxlan-ac'
              + 'cess-lists/acl:ipv4-vxlan-access-list/acl:rules-transit-outer
'
              + ''+"\n"
              + '5./acl:configuration/acl:acl/acl:access-list/acl:ipv4-vxlan-ac'
              + 'cess-lists/acl:ipv4-vxlan-access-list/acl:rules-vtep-inner'+"\n"
              + '6./acl:configuration/acl:acl/acl:access-list/acl:ipv4-vxlan-ac'
              + 'cess-lists/acl:ipv4-vxlan-access-list/acl:rules-vtep-outer'
                ;
  }
  revision 2018-03-12 {
    description 'Add value range of offset and matchlen node in udf-template-vx'
              + 'lan.'+"\n"
              + '/acl:configuration/acl:acl/acl:templates/acl:udf-template-vxla'
              + 'ns/acl:udf-template-vxlan/acl:format/acl:segment3/acl:offset3;'
              + ''+"\n"
              + '/acl:configuration/acl:acl/acl:templates/acl:udf-template-vxla'
              + 'ns/acl:udf-template-vxlan/acl:format/acl:segment4/acl:offset4;'
              + ''+"\n"
              + '/acl:configuration/acl:acl/acl:templates/acl:udf-template-vxla'
              + 'ns/acl:udf-template-vxlan/acl:format/acl:segment5/acl:offset5;'
              + ''+"\n"
              + '/acl:configuration/acl:acl/acl:templates/acl:udf-template-vxla'
              + 'ns/acl:udf-template-vxlan/acl:format/acl:segment6/acl:offset6;'
              + ''+"\n"
              + '/acl:configuration/acl:acl/acl:templates/acl:udf-template-vxla'
              + 'ns/acl:udf-template-vxlan/acl:format/acl:segment7/acl:offset7;'
              + ''+"\n"
              + '/acl:configuration/acl:acl/acl:templates/acl:udf-template-vxla'
              + 'ns/acl:udf-template-vxlan/acl:format/acl:segment8/acl:offset8;'
              + ''+"\n"
              + '/acl:configuration/acl:acl/acl:templates/acl:udf-template-vxla'
              + 'ns/acl:udf-template-vxlan/acl:format/acl:segment2/acl:matchlen'
              + '2;'+"\n"
              + '/acl:configuration/acl:acl/acl:templates/acl:udf-template-vxla'
              + 'ns/acl:udf-template-vxlan/acl:format/acl:segment3/acl:matchlen'
              + '3;'+"\n"
              + '/acl:configuration/acl:acl/acl:templates/acl:udf-template-vxla'
              + 'ns/acl:udf-template-vxlan/acl:format/acl:segment4/acl:matchlen'
              + '4;'+"\n"
              + '/acl:configuration/acl:acl/acl:templates/acl:udf-template-vxla'
              + 'ns/acl:udf-template-vxlan/acl:format/acl:segment5/acl:matchlen'
              + '5;'+"\n"
              + '/acl:configuration/acl:acl/acl:templates/acl:udf-template-vxla'
              + 'ns/acl:udf-template-vxlan/acl:format/acl:segment6/acl:matchlen'
              + '6;'+"\n"
              + '/acl:configuration/acl:acl/acl:templates/acl:udf-template-vxla'
              + 'ns/acl:udf-template-vxlan/acl:format/acl:segment7/acl:matchlen'
              + '7;'+"\n"
              + '/acl:configuration/acl:acl/acl:templates/acl:udf-template-vxla'
              + 'ns/acl:udf-template-vxlan/acl:format/acl:segment8/acl:matchlen'
              + '8.'
                ;
  }
  revision 2017-11-24 {
    description '1. In order to support configuring ACL rule description separa'
              + 'tely, some mandatory leaf nodes are adjusted  to be optional n'
              + 'odes, modification in detail as follows:'+"\n"
              + '/configuration/acl/access-list/ipv4-access-list/rule/permit-de'
              + 'ny'+"\n"
              + '/configuration/acl/access-list/ipv4-access-list/rule/src-addr
'
              + ''+"\n"
              + '/configuration/acl/access-list/ipv4-access-list/rule/rule-type'
              + ''+"\n"
              + '/configuration/acl/access-list/ipv6-access-list/rule/permit-de'
              + 'ny'+"\n"
              + '/configuration/acl/access-list/ipv6-access-list/rule/src-addr
'
              + ''+"\n"
              + '/configuration/acl/access-list/ipv6-access-list/rule/dst-addr
'
              + ''+"\n"
              + '/configuration/acl/access-list/ipv6-access-list/rule/rule-type'
              + ''+"\n"
              + '/configuration/acl/access-list/link-access-list/rule/permit-de'
              + 'ny'+"\n"
              + '/configuration/acl/access-list/link-access-list/rule/src-mac-a'
              + 'ddr'+"\n"
              + '/configuration/acl/access-list/link-access-list/rule/dest-mac-'
              + 'addr.'
                ;
  }
  revision 2017-07-20 {
    description "1.The original netconf model doesn't support to delete optiona"
              + "l configuration of ACL rule independently, such as port, TTL. "
              + "So, discarding the old configuration, and add new some contain"
              + "ers, modification in detail as follows:
\nDiscarding:
\n/confi"
              + "guration/acl/access-list/ipv4-access-list/rule/rule-type/exten"
              + "d/extended/ttl
\n/configuration/acl/access-list/ipv4-access-li"
              + "st/rule/rule-type/extend/extended/ipv4-protocol-type/udp-tcp/u"
              + "dp-tcp/src-port
\n/configuration/acl/access-list/ipv4-access-l"
              + "ist/rule/rule-type/extend/extended/ipv4-protocol-type/udp-tcp/"
              + "udp-tcp/dest-port
\n/configuration/acl/access-list/ipv4-access"
              + "-list/rule/rule-type/extend/extended/ipv4-protocol-type/icmp/i"
              + "cmp-port/src-port
\n/configuration/acl/access-list/ipv4-access"
              + "-list/rule/rule-type/extend/extended/ipv4-protocol-type/icmp/i"
              + "cmp-port/dest-port
\n/configuration/acl/access-list/ipv4-acces"
              + "s-list/rule/rule-type/extend/extended/ipv4-protocol-type/ip/po"
              + "rt/src-port
\n/configuration/acl/access-list/ipv4-access-list/"
              + "rule/rule-type/extend/extended/ipv4-protocol-type/ip/port/dest"
              + "-port
\n/configuration/acl/access-list/ipv4-mixed-access-list/"
              + "rule/rule-type/extend/extended/ipv4-protocol-type/udp-tcp/udp-"
              + "tcp/src-port
\n/configuration/acl/access-list/ipv4-mixed-acces"
              + "s-list/rule/rule-type/extend/extended/ipv4-protocol-type/udp-t"
              + "cp/udp-tcp/dest-port
\n/configuration/acl/access-list/ipv6-acc"
              + "ess-list/rule/rule-type/udp-tcp/udp-tcp/src-port
\n/configurat"
              + "ion/acl/access-list/ipv6-access-list/rule/rule-type/udp-tcp/ud"
              + "p-tcp/dest-port
\n/configuration/acl/access-list/ipv6-access-l"
              + "ist/rule/rule-type/icmp/icmp-port/src-port
\n/configuration/ac"
              + "l/access-list/ipv6-access-list/rule/rule-type/icmp/icmp-port/d"
              + "est-port
\n/configuration/acl/access-list/ipv6-access-list/rul"
              + "e/rule-type/ip/port/src-port
\n/configuration/acl/access-list/"
              + "ipv6-access-list/rule/rule-type/ip/port/dest-port
\n/configura"
              + "tion/acl/access-list/ipv6-mixed-access-list/rule/rule-type/udp"
              + "-tcp/udp-tcp/src-port
\n/configuration/acl/access-list/ipv6-mi"
              + "xed-access-list/rule/rule-type/udp-tcp/udp-tcp/dest-port
\n/co"
              + "nfiguration/acl/access-list/ipv4-vxlan-access-lists/ipv4-vxlan"
              + "-access-list/rules/rule/inner-layer/protocol-type/tcp-udp/tcp-"
              + "udp/src-port
\n/configuration/acl/access-list/ipv4-vxlan-acces"
              + "s-lists/ipv4-vxlan-access-list/rules/rule/inner-layer/protocol"
              + "-type/tcp-udp/tcp-udp/dst-port
\n/configuration/acl/access-lis"
              + "t/ipv4-vxlan-access-lists/ipv4-vxlan-access-list/rules/rule/ou"
              + "ter-layer/src-port
\n/configuration/acl/access-list/ipv4-vxlan"
              + "-access-lists/ipv4-vxlan-access-list/rules/rule/outer-layer/ds"
              + "t-port
\n
\nAdding:
\n/configuration/acl/access-list/ipv4-acce"
              + "ss-list/rule/rule-type/extend/extended/time-to-live
\n/configu"
              + "ration/acl/access-list/ipv4-access-list/rule/rule-type/extend/"
              + "extended/ipv4-protocol-type/udp-tcp/udp-tcp/source-port
\n/con"
              + "figuration/acl/access-list/ipv4-access-list/rule/rule-type/ext"
              + "end/extended/ipv4-protocol-type/udp-tcp/udp-tcp/destination-po"
              + "rt
\n/configuration/acl/access-list/ipv4-access-list/rule/rule"
              + "-type/extend/extended/ipv4-protocol-type/icmp/icmp-port/source"
              + "-port
\n/configuration/acl/access-list/ipv4-access-list/rule/r"
              + "ule-type/extend/extended/ipv4-protocol-type/icmp/icmp-port/des"
              + "tination-port
\n/configuration/acl/access-list/ipv4-access-lis"
              + "t/rule/rule-type/extend/extended/ipv4-protocol-type/ip/port/so"
              + "urce-port
\n/configuration/acl/access-list/ipv4-access-list/ru"
              + "le/rule-type/extend/extended/ipv4-protocol-type/ip/port/destin"
              + "ation-port
\n/configuration/acl/access-list/ipv4-mixed-access-"
              + "list/rule/rule-type/extend/extended/ipv4-protocol-type/udp-tcp"
              + "/udp-tcp/source-port
\n/configuration/acl/access-list/ipv4-mix"
              + "ed-access-list/rule/rule-type/extend/extended/ipv4-protocol-ty"
              + "pe/udp-tcp/udp-tcp/destination-port
\n/configuration/acl/acces"
              + "s-list/ipv6-access-list/rule/rule-type/udp-tcp/udp-tcp/source-"
              + "port
\n/configuration/acl/access-list/ipv6-access-list/rule/ru"
              + "le-type/udp-tcp/udp-tcp/destination-port
\n/configuration/acl/"
              + "access-list/ipv6-access-list/rule/rule-type/icmp/icmp-port/sou"
              + "rce-port
\n/configuration/acl/access-list/ipv6-access-list/rul"
              + "e/rule-type/icmp/icmp-port/destination-port
\n/configuration/a"
              + "cl/access-list/ipv6-access-list/rule/rule-type/ip/port/source-"
              + "port
\n/configuration/acl/access-list/ipv6-access-list/rule/ru"
              + "le-type/ip/port/destination-port
\n/configuration/acl/access-l"
              + "ist/ipv6-mixed-access-list/rule/rule-type/udp-tcp/udp-tcp/sour"
              + "ce-port
\n/configuration/acl/access-list/ipv6-mixed-access-lis"
              + "t/rule/rule-type/udp-tcp/udp-tcp/destination-port
\n/configura"
              + "tion/acl/access-list/ipv4-vxlan-access-lists/ipv4-vxlan-access"
              + "-list/rules/rule/inner-layer/protocol-type/tcp-udp/tcp-udp/sou"
              + "rce-port
\n/configuration/acl/access-list/ipv4-vxlan-access-li"
              + "sts/ipv4-vxlan-access-list/rules/rule/inner-layer/protocol-typ"
              + "e/tcp-udp/tcp-udp/destination-port
\n/configuration/acl/access"
              + "-list/ipv4-vxlan-access-lists/ipv4-vxlan-access-list/rules/rul"
              + "e/outer-layer/source-port
\n/configuration/acl/access-list/ipv"
              + "4-vxlan-access-lists/ipv4-vxlan-access-list/rules/rule/outer-l"
              + "ayer/destination-port"
                ;
  }
  revision 2017-07-12 {
    description 'Add service access point node:'+"\n"
              + '/acl:configuration/acl:acl/acl:access-list/acl:ipv4-mixed-acce'
              + 'ss-list/acl:rule/acl:link-prot/acl:sap;'+"\n"
              + '/acl:configuration/acl:acl/acl:access-list/acl:ipv6-mixed-acce'
              + 'ss-list/acl:rule/acl:link-prot/acl:sap;'+"\n"
              + '/acl:configuration/acl:acl/acl:access-list/acl:link-access-lis'
              + 't/acl:rule/acl:link-prot/acl:sap.'
                ;
  }
  revision 2017-06-20 {
    description '1.Support matching vrf for IPv4/IPv6/Link ACL, add new nodes a'
              + 's follows:'+"\n"
              + 'typedef: acl-vrf-name'+"\n"
              + 'nodes:'+"\n"
              + '/configuration/acl/access-list/ipv4-access-list/rule/vrf'+"\n"
              + '/configuration/acl/access-list/ipv6-access-list/rule/vrf'+"\n"
              + '/configuration/acl/access-list/link-access-list/rule/vrf'+"\n"
              + '2.Support matching packet-length for IPv4/IPv6, add new nodes '
              + 'as follows:'+"\n"
              + 'typedef: acl-pktlen-opr acl-pktlen-range'+"\n"
              + 'nodes:'+"\n"
              + '/configuration/acl/access-list/ipv4-access-list/rule/rule-type'
              + '/extend/extended/packet-length'+"\n"
              + '/configuration/acl/access-list/ipv6-access-list/rule/packet-le'
              + 'ngth'+"\n"
              + '3.Support matching exp for Link ACL, add new nodes as follows:'
              + ''+"\n"
              + 'nodes:'+"\n"
              + '/configuration/acl/access-list/link-access-list/rule/exp'+"\n"
              + '4.Support matching CFI/DEI for Link and IPv4-Mixed ACL, add ne'
              + 'w nodes as follows:'+"\n"
              + 'nodes:'+"\n"
              + '/configuration/acl/access-list/link-access-list/rule/vlan-conf'
              + '/vlan-range/cfi'+"\n"
              + '/configuration/acl/access-list/link-access-list/rule/vlan-conf'
              + '/vlan-range/dei'+"\n"
              + '/configuration/acl/access-list/ipv4-mixed-access-list/rule/vla'
              + 'n-conf/vlan-range/cfi'+"\n"
              + '/configuration/acl/access-list/ipv4-mixed-access-list/rule/vla'
              + 'n-conf/vlan-range/dei'
                ;
  }
  revision 2017-06-13 {
    description 'Modify user defined template ACL and support any segment,modif'
              + 'ied nodes as follows:'+"\n"
              + '/acl:configuration/acl:acl/acl:access-list/acl:user-defined-te'
              + 'mplate-acls/acl:user-defined-template-acl/acl:rules/acl:rule/a'
              + 'cl:segment/'+"\n"
              + '/acl:configuration/acl:acl/acl:access-list/acl:user-defined-te'
              + 'mplate-acls/acl:user-defined-template-acl/acl:rules/acl:rule/a'
              + 'cl:segment/acl:segment-any'+"\n"
              + '/acl:configuration/acl:acl/acl:access-list/acl:user-defined-te'
              + 'mplate-acls/acl:user-defined-template-acl/acl:rules/acl:rule/a'
              + 'cl:segment/acl:segment-value'
                ;
  }
  revision 2017-06-02 {
    description 'Link ACL add link protocol mask:'+"\n"
              + '/acl:configuration/acl:acl/acl:access-list/acl:link-access-lis'
              + 't/acl:rule/acl:link-prot/acl:link-protocol/acl:link-protocol-m'
              + 'ask;'+"\n"
              + '/acl:configuration/acl:acl/acl:access-list/acl:link-access-lis'
              + 't/acl:rule/acl:link-prot/acl:link-protocol-hex/acl:link-protoc'
              + 'ol-hex-mask.'
                ;
  }
  revision 2017-05-08 {
    description 'Support user defined template and user defined template ACL an'
              + 'd user defined template interface bind, new nodes added as fol'
              + 'lows:'+"\n"
              + '/acl:configuration/acl:acl/acl:templates'+"\n"
              + '/acl:configuration/acl:acl/acl:access-list/acl:user-defined-te'
              + 'mplate-acls'+"\n"
              + '/acl:configuration/acl:acl/acl:port-acl/acl:if-udf-template'
                ;
  }
  revision 2017-04-20 {
    description 'These if_features support M6000-S as follows:'+"\n"
              + 'user-protocol-feature'+"\n"
              + 'acl-statistics'+"\n"
              + 'These if_features support 15K as follows:'+"\n"
              + 'url-config'+"\n"
              + 'These if_features delete M6000-S as follows:'+"\n"
              + 'pri-value-config'
                ;
  }
  revision 2017-01-04 {
    description 'IPv4 mixed ACL and IPv6 mixed ACL do not support link-protocol'
              + '-hex.'+"\n"
              + '/acl:configuration/acl:acl/acl:access-list/acl:ipv4-mixed-acce'
              + 'ss-list/acl:rule/acl:link-prot/acl:link-protocol-hex;'+"\n"
              + '/acl:configuration/acl:acl/acl:access-list/acl:ipv6-mixed-acce'
              + 'ss-list/acl:rule/acl:link-prot/acl:link-protocol-hex.'
                ;
  }
  revision 2016-08-18 {
    description 'Support rule description to IPv4/IPv6/Link ACL, new nodes adde'
              + 'd as follows:'+"\n"
              + '1./acl:configuration/acl:acl/acl:access-list/acl:ipv4-access-l'
              + 'ist/acl:rule/acl:description;'+"\n"
              + '2./acl:configuration/acl:acl/acl:access-list/acl:ipv6-access-l'
              + 'ist/acl:rule/acl:description;'+"\n"
              + '3./acl:configuration/acl:acl/acl:access-list/acl:link-access-l'
              + 'ist/acl:rule/acl:description;'
                ;
  }
  revision 2016-06-01 {
    description 'Change these leaf nodes below to mandatory:'+"\n"
              + '/acl:configuration/acl:acl/acl:access-list/acl:ipv4-access-lis'
              + 't/acl:rule/acl:rule-type/acl:extend/acl:extended/acl:ipv4-prot'
              + 'ocol-type/acl:ip/acl:ipv4-protocol;'+"\n"
              + '/acl:configuration/acl:acl/acl:access-list/acl:ipv6-access-lis'
              + 't/acl:rule/acl:rule-type/acl:ip/acl:ipv6-protocol.'
                ;
  }
  revision 2016-05-23 {
    description 'Modify the value range of nodes below:'+"\n"
              + '/acl:configuration/acl:acl/acl:access-list/acl:ipv4-vxlan-acce'
              + 'ss-lists/acl:ipv4-vxlan-access-list/acl:rules/acl:rule/acl:inn'
              + 'er-layer/acl:tcp-udp/acl:src-port-number'+"\n"
              + '/acl:configuration/acl:acl/acl:access-list/acl:ipv4-vxlan-acce'
              + 'ss-lists/acl:ipv4-vxlan-access-list/acl:rules/acl:rule/acl:out'
              + 'er-layer/acl:src-port/acl:src-oper/acl:src-port-number'
                ;
  }
  revision 2016-04-08 {
    description 'Add mandatory attribute in those nodes:'+"\n"
              + '/acl:configuration/acl:acl/acl:access-list/acl:user-defined-li'
              + 'st/acl:rule/acl:any'+"\n"
              + '/acl:configuration/acl:acl/acl:access-list/acl:user-defined-li'
              + 'st/acl:rule/acl:segment-type'
                ;
  }
  revision 2016-03-04 {
    description 'Add nodes as follows:'+"\n"
              + '/acl:configuration/acl:acl/acl:access-list/acl:ipv4-vxlan-acce'
              + 'ss-lists/acl:ipv4-vxlan-access-list'+"\n"
              + '/acl:configuration/acl:acl/acl:port-acl/acl:if-ipv4-vxlan'+"\n"
              + '/acl:configuration/acl:acl/acl:port-acl/acl:vlan-ipv4-vxlan'+"\n"
              + '/acl:configuration/acl:acl/acl:port-acl/acl:device-ipv4-vxlans'
              + ''+"\n"
              + '/acl:configuration/acl:acl/acl:vni-acl'
                ;
  }
  revision 2016-01-13 {
    description 'Add port infomation of any protocol.'+"\n"
              + '/acl:configuration/acl:acl/acl:access-list/acl:ipv4-access-lis'
              + 't/acl:rule/acl:extended/acl:icmp-port;'+"\n"
              + '/acl:configuration/acl:acl/acl:access-list/acl:ipv4-access-lis'
              + 't/acl:rule/acl:extended/acl:port;'+"\n"
              + '/acl:configuration/acl:acl/acl:access-list/acl:ipv6-access-lis'
              + 't/acl:rule/acl:icmp-port;'+"\n"
              + '/acl:configuration/acl:acl/acl:access-list/acl:ipv6-access-lis'
              + 't/acl:rule/acl:port.'
                ;
  }
  revision 2015-12-23 {
    description 'Add nodes as follows:'+"\n"
              + '/acl:configuration/acl:acl/acl:access-list/acl:user-defined-li'
              + 'st/acl:acl-name'+"\n"
              + '/acl:configuration/acl:acl/acl:access-list/acl:user-defined-li'
              + 'st/acl:rule/acl:ruleid'+"\n"
              + '/acl:configuration/acl:acl/acl:access-list/acl:user-defined-li'
              + 'st/acl:rule/acl:permit-deny/acl:deny/acl:deny'+"\n"
              + '/acl:configuration/acl:acl/acl:access-list/acl:user-defined-li'
              + 'st/acl:rule/acl:permit-deny/acl:permit/acl:permit'+"\n"
              + '/acl:configuration/acl:acl/acl:access-list/acl:user-defined-li'
              + 'st/acl:rule/acl:frame-type'+"\n"
              + '/acl:configuration/acl:acl/acl:access-list/acl:user-defined-li'
              + 'st/acl:rule/acl:tag-status'+"\n"
              + '/acl:configuration/acl:acl/acl:access-list/acl:user-defined-li'
              + 'st/acl:rule/acl:ip-flag'+"\n"
              + '/acl:configuration/acl:acl/acl:access-list/acl:user-defined-li'
              + 'st/acl:rule/acl:segment-type/acl:any-segment/acl:any'+"\n"
              + '/acl:configuration/acl:acl/acl:access-list/acl:user-defined-li'
              + 'st/acl:rule/acl:segment-type/acl:segment/acl:segment1/acl:offs'
              + 'et'+"\n"
              + '/acl:configuration/acl:acl/acl:access-list/acl:user-defined-li'
              + 'st/acl:rule/acl:segment-type/acl:segment/acl:segment1/acl:rule'
              + '-string'+"\n"
              + '/acl:configuration/acl:acl/acl:access-list/acl:user-defined-li'
              + 'st/acl:rule/acl:segment-type/acl:segment/acl:segment1/acl:rule'
              + '-mask'+"\n"
              + '/acl:configuration/acl:acl/acl:access-list/acl:user-defined-li'
              + 'st/acl:rule/acl:segment-type/acl:segment/acl:segment1/acl:segm'
              + 'ent2/acl:offset'+"\n"
              + '/acl:configuration/acl:acl/acl:access-list/acl:user-defined-li'
              + 'st/acl:rule/acl:segment-type/acl:segment/acl:segment1/acl:segm'
              + 'ent2/acl:rule-string'+"\n"
              + '/acl:configuration/acl:acl/acl:access-list/acl:user-defined-li'
              + 'st/acl:rule/acl:segment-type/acl:segment/acl:segment1/acl:segm'
              + 'ent2/acl:rule-mask'+"\n"
              + '/acl:configuration/acl:acl/acl:access-list/acl:user-defined-li'
              + 'st/acl:rule/acl:segment-type/acl:segment/acl:segment1/acl:segm'
              + 'ent2/acl:segment3/acl:offset'+"\n"
              + '/acl:configuration/acl:acl/acl:access-list/acl:user-defined-li'
              + 'st/acl:rule/acl:segment-type/acl:segment/acl:segment1/acl:segm'
              + 'ent2/acl:segment3/acl:rule-string'+"\n"
              + '/acl:configuration/acl:acl/acl:access-list/acl:user-defined-li'
              + 'st/acl:rule/acl:segment-type/acl:segment/acl:segment1/acl:segm'
              + 'ent2/acl:segment3/acl:rule-mask'+"\n"
              + '/acl:configuration/acl:acl/acl:access-list/acl:user-defined-li'
              + 'st/acl:rule/acl:segment-type/acl:segment/acl:segment1/acl:segm'
              + 'ent2/acl:segment3/acl:segment4/acl:offset'+"\n"
              + '/acl:configuration/acl:acl/acl:access-list/acl:user-defined-li'
              + 'st/acl:rule/acl:segment-type/acl:segment/acl:segment1/acl:segm'
              + 'ent2/acl:segment3/acl:segment4/acl:rule-string'+"\n"
              + '/acl:configuration/acl:acl/acl:access-list/acl:user-defined-li'
              + 'st/acl:rule/acl:segment-type/acl:segment/acl:segment1/acl:segm'
              + 'ent2/acl:segment3/acl:segment4/acl:rule-mask'+"\n"
              + '/acl:configuration/acl:acl/acl:access-list/acl:user-defined-li'
              + 'st/acl:rule/acl:time-range.'+"\n"
              + 'Feature:user-defined-feature.'+"\n"
              + 'Add an if-feature:user-defined-feature in /acl:configuration/a'
              + 'cl:acl/acl:port-acl/acl:device-user-defineds'
                ;
  }
  revision 2015-12-15 {
    description 'Add nodes as follows:'+"\n"
              + '/acl:configuration/acl:acl/acl:port-acl/acl:device-ipv4s/acl:d'
              + 'evice-ipv4/acl:direction'+"\n"
              + '/acl:configuration/acl:acl/acl:port-acl/acl:device-ipv4s/acl:d'
              + 'evice-ipv4/acl:acl-name'+"\n"
              + '/acl:configuration/acl:acl/acl:port-acl/acl:device-ipv6s/acl:d'
              + 'evice-ipv6/acl:direction'+"\n"
              + '/acl:configuration/acl:acl/acl:port-acl/acl:device-ipv6s/acl:d'
              + 'evice-ipv6/acl:acl-name'+"\n"
              + '/acl:configuration/acl:acl/acl:port-acl/acl:device-links/acl:d'
              + 'evice-link/acl:direction'+"\n"
              + '/acl:configuration/acl:acl/acl:port-acl/acl:device-links/acl:d'
              + 'evice-link/acl:acl-name'+"\n"
              + '/acl:configuration/acl:acl/acl:port-acl/acl:device-ipv4-mixeds'
              + '/acl:device-ipv4-mixed/acl:direction'+"\n"
              + '/acl:configuration/acl:acl/acl:port-acl/acl:device-ipv4-mixeds'
              + '/acl:device-ipv4-mixed/acl:acl-name'+"\n"
              + '/acl:configuration/acl:acl/acl:port-acl/acl:device-ipv6-mixeds'
              + '/acl:device-ipv6-mixed/acl:direction'+"\n"
              + '/acl:configuration/acl:acl/acl:port-acl/acl:device-ipv6-mixeds'
              + '/acl:device-ipv6-mixed/acl:acl-name'+"\n"
              + '/acl:configuration/acl:acl/acl:port-acl/acl:device-user-define'
              + 'ds/acl:device-user-defined/acl:direction'+"\n"
              + '/acl:configuration/acl:acl/acl:port-acl/acl:device-user-define'
              + 'ds/acl:device-user-defined/acl:acl-name'+"\n"
              + 'feature:statics-per-device.'+"\n"
              + 'Add the range(1~2147483644) of uint32 type of leafs,those leaf'
              + ' as follows:'+"\n"
              + '/acl:state/acl:acl/acl:acl-v6-statistics/acl:acl-v6-statistic/'
              + 'acl:acl-ruleid '+"\n"
              + '/acl:state/acl:acl/acl:acl-v4-statistics/acl:acl-v4-statistic/'
              + 'acl:acl-ruleid.'
                ;
  }
  revision 2015-11-04 {
    description 'Add node user-protocol-access-list:'+"\n"
              + '/acl:configuration/acl:acl/acl:access-list/acl:user-protocol-a'
              + 'ccess-list.'
                ;
  }
  revision 2015-08-21 {
    description 'Change DerivedType of the following leaf node from ipv4-mask t'
              + 'o ipv4-address:'+"\n"
              + '/acl:configuration/acl:acl/acl:access-list/acl:ipv4-access-lis'
              + 't/acl:rule/acl:src-wildcard;'+"\n"
              + '/acl:configuration/acl:acl/acl:access-list/acl:ipv4-access-lis'
              + 't/acl:rule/acl:extended/acl:dest-wildcard;'+"\n"
              + '/acl:configuration/acl:acl/acl:access-list/acl:ipv4-mixed-acce'
              + 'ss-list/acl:rule/acl:src-wildcard;'+"\n"
              + '/acl:configuration/acl:acl/acl:access-list/acl:ipv4-mixed-acce'
              + 'ss-list/acl:rule/acl:extended/acl:dest-wildcard.'
                ;
  }
  revision 2015-06-08 {
    description 'Add ACL statistics configuration with Feature: acl-statistics,'
              + ' details as follows:'+"\n"
              + '1.Add acl log switch configuration with the Feature, statistic'
              + 's-switch, new notes added as follows:'+"\n"
              + 'Typedef:acl-if-direction'+"\n"
              + 'Container: /configuration/acl/statistics-switch/'+"\n"
              + 'Container: /configuration/acl/statistics-switch/ipv4-log-switc'
              + 'hs'+"\n"
              + 'Container: /configuration/acl/statistics-switch/ipv6-log-switc'
              + 'hs'+"\n"
              + '2.Add acl log clear operation with the Feature, statistics-cle'
              + 'ar, new notes added as follows:'+"\n"
              + 'Container: /operation/'+"\n"
              + 'Container: /operation/acl/'+"\n"
              + 'Container: /operation/acl/statistics-clear/'+"\n"
              + 'Container: /operation/acl/statistics-clear/ipv4-log-clears'+"\n"
              + 'Container: /operation/acl/statistics-clear/ipv6-log-clears'+"\n"
              + 'Container: /operation/acl/statistics-clear/link-log-clears'+"\n"
              + '3.Add acl log statistics query notes with the Feature, statist'
              + 'ics-query, new notes added as follows:'+"\n"
              + 'Container: /state/'+"\n"
              + 'Container: /state/acl/'+"\n"
              + 'Container: /state/acl/acl-v4-statistics/'+"\n"
              + 'Container: /state/acl/acl-v6-statistics/.'
                ;
  }
  revision 2015-04-20 {
    description '1.Support priority(Precedence,DSCP,CoS) range configuration wi'
              + 'th the feature pre-range-config, new notes added as follows:'+"\n"
              + 'Typedef:acl-prec-range'+"\n"
              + 'Typedef:acl-dscp-range'+"\n"
              + 'Typedef:acl-cos-range'+"\n"
              + 'Feature: pri-range-config'+"\n"
              + 'Feature: pri-value-config'+"\n"
              + 'case: /configuration/acl/access-list/ipv4-access-list/rule/rul'
              + 'e-type/extend/extended/priority/prec-range'+"\n"
              + 'case: /configuration/acl/access-list/ipv4-access-list/rule/rul'
              + 'e-type/extend/extended/priority/dscp-range'+"\n"
              + 'leaf: /configuration/acl/access-list/ipv4-mixed-access-list/ru'
              + 'le/inner-cos-range'+"\n"
              + 'leaf: /configuration/acl/access-list/ipv4-mixed-access-list/ru'
              + 'le/outer-cos-range'+"\n"
              + 'case: /configuration/acl/access-list/ipv4-mixed-access-list/ru'
              + 'le/rule-type/extend/extended/priority/prec-range'+"\n"
              + 'case: /configuration/acl/access-list/ipv4-mixed-access-list/ru'
              + 'le/rule-type/extend/extended/priority/dscp-range'+"\n"
              + 'leaf: /configuration/acl/access-list/link-access-list/rule/inn'
              + 'er-cos-range'+"\n"
              + 'leaf: /configuration/acl/access-list/link-access-list/rule/out'
              + 'er-cos-range'+"\n"
              + '2.Support IPv6/LINK ACL log configuration, new notes added as '
              + 'follows:'+"\n"
              + 'Feature: ipv6-log-config'+"\n"
              + 'Feature: link-log-config'+"\n"
              + 'leaf:/configuration/acl/access-list/ipv6-access-list/rule/log
'
              + ''+"\n"
              + 'leaf:/configuration/acl/access-list/link-access-list/rule/log
'
              + ''+"\n"
              + '3.Add feature:switchvlan-acl for contianer: vlan-ipv4, vlan-ip'
              + 'v6, vlan-link, vlan-ipv4-mixed, vlan-ipv6-mixed.'
                ;
  }
  revision 2015-02-13 {
    description '1 src-url and dest-url add if_feature url-config:'+"\n"
              + '/acl:configuration/acl:acl/acl:access-list/acl:ipv6-access-lis'
              + 't/acl:rule/acl:src-addr/acl:src-url'+"\n"
              + '/acl:configuration/acl:acl/acl:access-list/acl:ipv6-access-lis'
              + 't/acl:rule/acl:dest-addr/acl:dest-url.'
                ;
  }
  revision 2014-04-16 {
    description '1 Add src-url and dest-url with feature url-config:'+"\n"
              + '/acl:configuration/acl:acl/acl:access-list/acl:ipv4-access-lis'
              + 't/acl:rule/acl:src-addr/acl:src-url'+"\n"
              + '/acl:configuration/acl:acl/acl:access-list/acl:ipv4-access-lis'
              + 't/acl:rule/acl:rule-type/acl:extend/acl:extended/acl:dest-addr'
              + '/acl:dest-url'+"\n"
              + '/acl:configuration/acl:acl/acl:access-list/acl:ipv6-access-lis'
              + 't/acl:rule/acl:src-addr/acl:src-url'+"\n"
              + '/acl:configuration/acl:acl/acl:access-list/acl:ipv6-access-lis'
              + 't/acl:rule/acl:dest-addr/acl:dest-url'+"\n"
              + '2 Add feature link-prot-hex-config for case link-protocol-hex:'
              + ''+"\n"
              + '/acl:configuration/acl:acl/acl:access-list/acl:ipv4-mixed-acce'
              + 'ss-list/acl:rule/acl:link-prot/acl:link-protocol-hex'+"\n"
              + '/acl:configuration/acl:acl/acl:access-list/acl:ipv6-mixed-acce'
              + 'ss-list/acl:rule/acl:link-prot/acl:link-protocol-hex'+"\n"
              + '/acl:configuration/acl:acl/acl:access-list/acl:link-access-lis'
              + 't/acl:rule/acl:link-prot/acl:link-protocol-hex'+"\n"
              + '3 Modify value range of leaf link-protocol:'+"\n"
              + '/acl:configuration/acl:acl/acl:access-list/acl:ipv4-mixed-acce'
              + 'ss-list/acl:rule/acl:link-prot/acl:link-protocol/acl:link-prot'
              + 'ocol'+"\n"
              + '/acl:configuration/acl:acl/acl:access-list/acl:ipv6-mixed-acce'
              + 'ss-list/acl:rule/acl:link-prot/acl:link-protocol/acl:link-prot'
              + 'ocol'+"\n"
              + '/acl:configuration/acl:acl/acl:access-list/acl:link-access-lis'
              + 't/acl:rule/acl:link-prot/acl:link-protocol/acl:link-protocol.'
                ;
  }
  revision 2013-10-30 {
    description 'Initial version.'
                ;
  }
  feature ttl-config {
    description 'Match if TTL configures.'
                ;
  }
  feature log-config {
    description 'Match if log configures.'
                ;
  }
  feature ipv6-log-config {
    description 'Support IPv6 ACL log.'
                ;
  }
  feature link-log-config {
    description 'Support LINK ACL log.'
                ;
  }
  feature link-prot-hex-config {
    description 'Match if link protocol hex configures.'
                ;
  }
  feature url-config {
    description 'Match if URL configures.'
                ;
  }
  feature vlan-value-config {
    description 'Match if vlan-value configures.'
                ;
  }
  feature vlan-range-config {
    description 'Match if vlan-range configures.'
                ;
  }
  feature mac-range-config {
    description 'Match if MAC address range configures.'
                ;
  }
  feature pri-value-config {
    description 'Support to configure single priority value, such as Precedence'
              + ', DSCP, CoS(802.1p).'
                ;
  }
  feature pri-range-config {
    description 'Support to configure single priority value or range, such as P'
              + 'recedence, DSCP, CoS(802.1p).'
                ;
  }
  feature ipv4-feature {
    description 'Match if ipv4-access-list configures.'
                ;
  }
  feature ipv4-mixed-feature {
    description 'Match if ipv4-mixed-access-list configures.'
                ;
  }
  feature ipv6-feature {
    description 'Match if ipv6-access-list configures.'
                ;
  }
  feature ipv6-mixed-feature {
    description 'Match if ipv6-mixed-access-list configures.'
                ;
  }
  feature link-feature {
    description 'Match if link-access-list configures.'
                ;
  }
  feature switchvlan-acl {
    description 'Match switch-vlan access-list configures.'
                ;
  }
  feature acl-statistics {
    description 'Match ACL LOG statistics configures.'
                ;
  }
  feature user-protocol-feature {
    description 'Match if user-protocol-mixed-access-list configures.'
                ;
  }
  feature statics-per-device {
    description 'Support for configure that global device statistics of rate.'
                ;
  }
  feature user-defined-feature {
    description 'Match if user-defined-list configures.'
                ;
  }
  feature ipv4-vxlan-feature {
    description 'Match if ipv4-vxlan-access-list configures.'
                ;
  }
  feature udf-template-type {
    description 'Match if user-defined-template configures.'
                ;
  }
  feature sap-feature {
    description 'Match if service access point configures.'
                ;
  }
  feature ipv4-mixed-log-config {
    description 'Support IPv4 mixed ACL log.'
                ;
  }
  feature ipv6-ttl-config {
    description 'Match if TTL configures in ipv6.'
                ;
  }
  feature ipv6-dscp-range-config {
    description 'Match if dscp-range configures in IPv6.'
                ;
  }
  feature ipv6-cos-range-config {
    description 'Match if cos-range configures in IPv6.'
                ;
  }
  feature ipv4-mixed-pri-value {
    description 'Support to configure single priority value in ipv4-mixed-acces'
              + 's-lists, such as Precedence, DSCP.'
                ;
  }
  feature ipv4-mixed-pri-range {
    description 'Support to configure single priority value or range in ipv4-mi'
              + 'xed-access-lists, such as Precedence, DSCP.'
                ;
  }
  feature link-cos-value {
    description 'Support to configure single CoS(802.1p) value in link-access-l'
              + 'ists.'
                ;
  }
  feature link-cos-range {
    description 'Support to configure single CoS(802.1p) value or range in link'
              + '-access-lists.'
                ;
  }
  feature ipv4-mixed-cos-value {
    description 'Support to configure single CoS(802.1p) value in ipv4-mixed-ac'
              + 'cess-lists.'
                ;
  }
  feature ipv4-mixed-cos-range {
    description 'Support to configure single CoS(802.1p) value or range in ipv4'
              + '-mixed-access-lists.'
                ;
  }
  feature ipv6-mixed-log-config {
    description 'Support IPv6 mixed ACL log.'
                ;
  }
  feature l2-layer {
    description 'L2 information.'
                ;
    ncd:revise-date 2021-10-26 ;
  }
  feature none-rule-default-action {
    description 'Configure default action in empty ACL.'
                ;
    ncd:revise-date 2021-11-23 ;
  }
  typedef acl-name-type {
    type string {
      length 1..31 ;
    }
    description 'The definition of ACL name type, support 1-31 characters.'
                ;
  }
  typedef acl-port-range {
    type ncd:single-range {
      pattern '((([1-9][0-9]{1,3})|([1-9][0-9]{0,0})|0|([1-5][0-9]{4,4})|(6[0-4'
            + '][0-9]{3,3})|(65[0-4][0-9]{2,2})|(655[0-2][0-9]{1,1})|(6553[0-4]'
            + ')|65535)(-(([1-9][0-9]{1,3})|([1-9][0-9]{0,0})|0|([1-5][0-9]{4,4'
            + '})|(6[0-4][0-9]{3,3})|(65[0-4][0-9]{2,2})|(655[0-2][0-9]{1,1})|('
            + '6553[0-4])|65535)){0,1})'
              ;
    }
    description 'The definition of ACL port range, support <0-65535>-<0-65535>.'
                ;
  }
  typedef acl-vlan-range {
    type ncd:single-range {
      pattern '((([1-9][0-9]{1,2})|([2-9][0-9]{0,0})|1|([1-3][0-9]{3,3})|(40[0-'
            + '8][0-9]{1,1})|(409[0-3])|4094)(-(([1-9][0-9]{1,2})|([2-9][0-9]{0'
            + ',0})|1|([1-3][0-9]{3,3})|(40[0-8][0-9]{1,1})|(409[0-3])|4094)){0'
            + ',1})'
              ;
    }
    description 'The definition of ACL VLAN range, support <1-4094>-<1-4094>.'
                ;
  }
  typedef acl-ttl-range {
    type ncd:single-range {
      pattern '((([1-9][0-9]{1,1})|([2-9][0-9]{0,0})|1|([1-1][0-9]{2,2})|(2[0-4'
            + '][0-9]{1,1})|(25[0-4])|255)(-(([1-9][0-9]{1,1})|([2-9][0-9]{0,0}'
            + ')|1|([1-1][0-9]{2,2})|(2[0-4][0-9]{1,1})|(25[0-4])|255)){0,1})'
              ;
    }
    description 'The definition of ACL TTL range, support <1-255>-<1-255>.'
                ;
  }
  typedef acl-tcp-flag {
    type enumeration {
      enum - {
        value 0 ;
        description 'Match when the flag not set.'
                    ;
      }
      enum + {
        value 1 ;
        description 'Match when the flag set.'
                    ;
      }
    }
    description 'The definition of ACL TCP flag.'
                ;
  }
  typedef acl-prec-range {
    type ncd:single-range {
      pattern '((([0-7]-[0-7])|([0-7])){1,1})'
              ;
    }
    description 'The definition of ACL Precedence range, support <0-7>-<0-7>.'
                ;
  }
  typedef acl-dscp-range {
    type ncd:single-range {
      pattern '((((([1-9][0-9]{0,0})|0|([1-5][0-9]{1,1})|(6[0-2])|63)-(([1-9][0'
            + '-9]{0,0})|0|([1-5][0-9]{1,1})|(6[0-2])|63))|(([1-9][0-9]{0,0})|0'
            + '|([1-5][0-9]{1,1})|(6[0-2])|63)){1,1})'
              ;
    }
    description 'The definition of ACL DSCP range, support <0-63>-<0-63>.'
                ;
  }
  typedef acl-cos-range {
    type ncd:single-range {
      pattern '((([0-7]-[0-7])|([0-7])){1,1})'
              ;
    }
    description 'The definition of ACL CoS range, support <0-7>-<0-7>.'
                ;
  }
  typedef acl-if-direction {
    type enumeration {
      enum egress {
        value 0 ;
        description 'Direction egress.'
                    ;
      }
      enum ingress {
        value 1 ;
        description 'Direction ingress.'
                    ;
      }
    }
    description 'The definition of interface direction, as follows,'+"\n"
              + '     egress  Direction egress'+"\n"
              + '     ingress Direction ingress.'
                ;
  }
  typedef acl-vrf-name {
    type string {
      length 1..32 {
        description 'VPN Routing/Forwarding instance name, support 1-32 charact'
                  + 'ers.'
                    ;
      }
    }
    description 'VPN Routing/Forwarding instance name, support 1-32 characters.'
                ;
  }
  typedef acl-pktlen-opr {
    type enumeration {
      enum eq {
        value 1 ;
        description 'Match only packets on a given packet length.'
                    ;
      }
      enum gt {
        value 4 ;
        description 'Match only packets with a greater packet length.'
                    ;
      }
      enum lt {
        value 5 ;
        description 'Match only packets with a lower packet length.'
                    ;
      }
      enum neq {
        value 6 ;
        description 'Match only packets not on a given packet length.'
                    ;
      }
    }
    description 'Packet length operator, such as '+"\n"
              + '  eq   Match only packets on a given packet length'+"\n"
              + '  gt   Match only packets with a greater packet length'+"\n"
              + '  lt   Match only packets with a lower packet length'+"\n"
              + '  neq  Match only packets not on a given packet length.'
                ;
  }
  typedef acl-pktlen-range {
    type ncd:single-range {
      pattern '((([1-9][0-9]{1,3})|([2-9][0-9]{0,0})|1|([1-5][0-9]{4,4})|(6[0-4'
            + '][0-9]{3,3})|(65[0-4][0-9]{2,2})|(655[0-2][0-9]{1,1})|(6553[0-4]'
            + ')|65535)(-(([1-9][0-9]{1,3})|([2-9][0-9]{0,0})|1|([1-5][0-9]{4,4'
            + '})|(6[0-4][0-9]{3,3})|(65[0-4][0-9]{2,2})|(655[0-2][0-9]{1,1})|('
            + '6553[0-4])|65535)){0,1})'
              ;
    }
    description 'Match only packets on a given packet length range, support <1-'
              + '65535>-<1-65535>.'
                ;
  }
  typedef vxlan-head-type {
    type enumeration {
      enum outer-l2-head {
        value 1 ;
        description outer-l2-head ;
      }
      enum vxlan-head {
        value 2 ;
        description vxlan-head ;
      }
      enum vxlan-in-v4 {
        value 3 ;
        description vxlan-in-v4 ;
      }
      enum vxlan-in-v4-gre {
        value 4 ;
        description vxlan-in-v4-gre ;
      }
    }
    description 'The definition of head type, as follows,  '+"\n"
              + '  outer-l2-head    Outer-l2-head(1)'+"\n"
              + '  vxlan-head       Vxlan-head(2)'+"\n"
              + '  vxlan-in-v4      Vxlan-Inner-ipv4(3)'+"\n"
              + '  vxlan-in-v4-gre  Vxlan-Inner-ipv4-gre(4)'
                ;
  }
  typedef general-template-head-type {
    type enumeration {
      enum l2-head {
        value 1 ;
        description 'Offset from L2-head'
                    ;
      }
      enum l3-head {
        value 2 ;
        description 'Offset from L3-head'
                    ;
      }
      enum l4-head {
        value 3 ;
        description 'Offset from L4-head'
                    ;
      }
    }
    description 'The definition of head type, as follows,  '+"\n"
              + '  l2-head    Offset from L2-head(1)'+"\n"
              + '  l3-head    Offset from L3-head(2)'+"\n"
              + '  l4-head    Offset from L4-head(3)'
                ;
  }
  container configuration {
    description 'Configuration model.'
                ;
    container acl {
      description 'Configuration about ACL.'
                  ;
      container templates {
        if-feature udf-template-type ;
        description 'Configure user-defined-template.'
                    ;
        container udf-template-vxlans {
          if-feature udf-template-type ;
          description 'Configure VXLAN user-defined-template.'
                      ;
          list udf-template-vxlan {
            if-feature udf-template-type ;
            description 'Configure VXLAN user-defined-template.'
                        ;
            key template-name ;
            leaf template-name {
              description 'Template name'
                          ;
              type acl-name-type ;
            }
            container format {
              description 'Configure user-defined-template format.'
                          ;
              presence format ;
              container segment1 {
                description 'Configure first segment of user-defined-template.'
                            ;
                presence segment1 ;
                leaf head-type1 {
                  description 'Configure VXLAN head type'
                              ;
                  type vxlan-head-type ;
                  mandatory true ;
                }
                leaf offset1 {
                  description 'Configure offset'
                              ;
                  type uint8 {
                    range 0..77 ;
                  }
                  mandatory true ;
                }
                leaf matchlen1 {
                  description 'Configure matchString'
                              ;
                  type uint8 {
                    range 1..4 ;
                  }
                  default 2 ;
                }
              }
              container segment2 {
                description 'Configure second segment of user-defined-template.'
                            ;
                presence segment2 ;
                leaf head-type2 {
                  description 'Configure VXLAN head type'
                              ;
                  type vxlan-head-type ;
                  mandatory true ;
                }
                leaf offset2 {
                  description 'Configure offset'
                              ;
                  type uint8 {
                    range 0..77 ;
                  }
                  mandatory true ;
                }
                leaf matchlen2 {
                  description 'Configure matchString'
                              ;
                  type uint8 {
                    range 1..4 ;
                  }
                  default 2 ;
                }
              }
              container segment3 {
                description 'Configure third segment of user-defined-template.'
                            ;
                presence segment3 ;
                leaf head-type3 {
                  description 'Configure VXLAN head type'
                              ;
                  type vxlan-head-type ;
                  mandatory true ;
                }
                leaf offset3 {
                  description 'Configure offset'
                              ;
                  type uint8 {
                    range 0..77 ;
                  }
                  mandatory true ;
                }
                leaf matchlen3 {
                  description 'Configure matchString'
                              ;
                  type uint8 {
                    range 1..4 ;
                  }
                  default 2 ;
                }
              }
              container segment4 {
                description 'Configure fourth segment of user-defined-template.'
                            ;
                presence segment4 ;
                leaf head-type4 {
                  description 'Configure VXLAN head type'
                              ;
                  type vxlan-head-type ;
                  mandatory true ;
                }
                leaf offset4 {
                  description 'Configure offset'
                              ;
                  type uint8 {
                    range 0..77 ;
                  }
                  mandatory true ;
                }
                leaf matchlen4 {
                  description 'Configure matchString'
                              ;
                  type uint8 {
                    range 1..4 ;
                  }
                  default 2 ;
                }
              }
              container segment5 {
                description 'Configure fifth segment of user-defined-template.'
                            ;
                presence segment5 ;
                leaf head-type5 {
                  description 'Configure VXLAN head type'
                              ;
                  type vxlan-head-type ;
                  mandatory true ;
                }
                leaf offset5 {
                  description 'Configure offset'
                              ;
                  type uint8 {
                    range 0..77 ;
                  }
                  mandatory true ;
                }
                leaf matchlen5 {
                  description 'Configure matchString'
                              ;
                  type uint8 {
                    range 1..4 ;
                  }
                  default 2 ;
                }
              }
              container segment6 {
                description 'Configure sixth segment of user-defined-template.'
                            ;
                presence segment6 ;
                leaf head-type6 {
                  description 'Configure VXLAN head type'
                              ;
                  type vxlan-head-type ;
                  mandatory true ;
                }
                leaf offset6 {
                  description 'Configure offset'
                              ;
                  type uint8 {
                    range 0..77 ;
                  }
                  mandatory true ;
                }
                leaf matchlen6 {
                  description 'Configure matchString'
                              ;
                  type uint8 {
                    range 1..4 ;
                  }
                  default 2 ;
                }
              }
              container segment7 {
                description 'Configure seventh segment of user-defined-template.'
                            ;
                presence segment7 ;
                leaf head-type7 {
                  description 'Configure VXLAN head type'
                              ;
                  type vxlan-head-type ;
                  mandatory true ;
                }
                leaf offset7 {
                  description 'Configure offset'
                              ;
                  type uint8 {
                    range 0..77 ;
                  }
                  mandatory true ;
                }
                leaf matchlen7 {
                  description 'Configure matchString'
                              ;
                  type uint8 {
                    range 1..4 ;
                  }
                  default 2 ;
                }
              }
              container segment8 {
                description 'Configure eighth segment of user-defined-template.'
                            ;
                presence segment8 ;
                leaf head-type8 {
                  description 'Configure VXLAN head type'
                              ;
                  type vxlan-head-type ;
                  mandatory true ;
                }
                leaf offset8 {
                  description 'Configure offset'
                              ;
                  type uint8 {
                    range 0..77 ;
                  }
                  mandatory true ;
                }
                leaf matchlen8 {
                  description 'Configure matchString'
                              ;
                  type uint8 {
                    range 1..4 ;
                  }
                  default 2 ;
                }
              }
            }
          }
        }
        container udf-template-generals {
          description 'Configure general user-defined-template.'
                      ;
          list udf-template-general {
            description 'Configure general user-defined-template.'
                        ;
            key template-name ;
            leaf template-name {
              description 'Template name'
                          ;
              type acl-name-type ;
            }
            container format {
              description 'Configure user-defined-template format.'
                          ;
              presence format ;
              container segment1 {
                description 'Configure first segment of user-defined-template.'
                            ;
                presence segment1 ;
                leaf head-type1 {
                  description 'Configure general head type'
                              ;
                  type general-template-head-type ;
                  mandatory true ;
                }
                leaf offset1 {
                  description 'Configure offset'
                              ;
                  type uint8 {
                    range 0..77 ;
                  }
                  mandatory true ;
                }
                leaf matchlen1 {
                  description 'Configure matchString'
                              ;
                  type uint8 {
                    range 1..4 ;
                  }
                  default 2 ;
                }
              }
              container segment2 {
                description 'Configure second segment of user-defined-template.'
                            ;
                presence segment2 ;
                leaf head-type2 {
                  description 'Configure general head type'
                              ;
                  type general-template-head-type ;
                  mandatory true ;
                }
                leaf offset2 {
                  description 'Configure offset'
                              ;
                  type uint8 {
                    range 0..77 ;
                  }
                  mandatory true ;
                }
                leaf matchlen2 {
                  description 'Configure matchString'
                              ;
                  type uint8 {
                    range 1..4 ;
                  }
                  default 2 ;
                }
              }
              container segment3 {
                description 'Configure third segment of user-defined-template.'
                            ;
                presence segment3 ;
                leaf head-type3 {
                  description 'Configure general head type'
                              ;
                  type general-template-head-type ;
                  mandatory true ;
                }
                leaf offset3 {
                  description 'Configure offset'
                              ;
                  type uint8 {
                    range 0..77 ;
                  }
                  mandatory true ;
                }
                leaf matchlen3 {
                  description 'Configure matchString'
                              ;
                  type uint8 {
                    range 1..4 ;
                  }
                  default 2 ;
                }
              }
              container segment4 {
                description 'Configure fourth segment of user-defined-template.'
                            ;
                presence segment4 ;
                leaf head-type4 {
                  description 'Configure general head type'
                              ;
                  type general-template-head-type ;
                  mandatory true ;
                }
                leaf offset4 {
                  description 'Configure offset'
                              ;
                  type uint8 {
                    range 0..77 ;
                  }
                  mandatory true ;
                }
                leaf matchlen4 {
                  description 'Configure matchString'
                              ;
                  type uint8 {
                    range 1..4 ;
                  }
                  default 2 ;
                }
              }
              container segment5 {
                description 'Configure fifth segment of user-defined-template.'
                            ;
                presence segment5 ;
                leaf head-type5 {
                  description 'Configure general head type'
                              ;
                  type general-template-head-type ;
                  mandatory true ;
                }
                leaf offset5 {
                  description 'Configure offset'
                              ;
                  type uint8 {
                    range 0..77 ;
                  }
                  mandatory true ;
                }
                leaf matchlen5 {
                  description 'Configure matchString'
                              ;
                  type uint8 {
                    range 1..4 ;
                  }
                  default 2 ;
                }
              }
              container segment6 {
                description 'Configure sixth segment of user-defined-template.'
                            ;
                presence segment6 ;
                leaf head-type6 {
                  description 'Configure general head type'
                              ;
                  type general-template-head-type ;
                  mandatory true ;
                }
                leaf offset6 {
                  description 'Configure offset'
                              ;
                  type uint8 {
                    range 0..77 ;
                  }
                  mandatory true ;
                }
                leaf matchlen6 {
                  description 'Configure matchString'
                              ;
                  type uint8 {
                    range 1..4 ;
                  }
                  default 2 ;
                }
              }
              container segment7 {
                description 'Configure seventh segment of user-defined-template.'
                            ;
                presence segment7 ;
                leaf head-type7 {
                  description 'Configure general head type'
                              ;
                  type general-template-head-type ;
                  mandatory true ;
                }
                leaf offset7 {
                  description 'Configure offset'
                              ;
                  type uint8 {
                    range 0..77 ;
                  }
                  mandatory true ;
                }
                leaf matchlen7 {
                  description 'Configure matchString'
                              ;
                  type uint8 {
                    range 1..4 ;
                  }
                  default 2 ;
                }
              }
              container segment8 {
                description 'Configure eighth segment of user-defined-template.'
                            ;
                presence segment8 ;
                leaf head-type8 {
                  description 'Configure general head type'
                              ;
                  type general-template-head-type ;
                  mandatory true ;
                }
                leaf offset8 {
                  description 'Configure offset'
                              ;
                  type uint8 {
                    range 0..77 ;
                  }
                  mandatory true ;
                }
                leaf matchlen8 {
                  description 'Configure matchString'
                              ;
                  type uint8 {
                    range 1..4 ;
                  }
                  default 2 ;
                }
              }
            }
          }
          ncd:revise-date 2022-01-27 ;
        }
        ncd:revise-date 2017-05-08 ;
      }
      container access-list {
        description 'Configuration access-list.'
                    ;
        list ipv4-access-list {
          if-feature ipv4-feature ;
          description 'Configure ipv4-access-list.'
                      ;
          key acl-name ;
          leaf acl-name {
            description 'Name of ACL.'
                        ;
            type acl-name-type ;
          }
          list rule {
            description 'Configure rule of an IPv4 ACL.'
                        ;
            key ruleid ;
            leaf ruleid {
              description 'ID of this rule.'
                          ;
              type uint32 {
                range 1..2147483644 ;
              }
            }
            choice permit-deny {
              description 'Deny  :  Specify packets to reject'+"\n"
                        + 'Permit:  Specify packets to forward.'
                          ;
              case deny {
                description 'Specify packets to reject.'
                            ;
                leaf deny {
                  description 'Specify packets to reject.'
                              ;
                  type empty ;
                  mandatory true ;
                }
              }
              case permit {
                description 'Specify packets to forward.'
                            ;
                leaf permit {
                  description 'Specify packets to forward.'
                              ;
                  type empty ;
                  mandatory true ;
                }
              }
            }
            choice src-addr {
              description 'Specify source address.'
                          ;
              case src-ip-address {
                description 'IP address.'
                            ;
                leaf src-address {
                  description 'IP address.'
                              ;
                  type ncd:ipv4-address ;
                  mandatory true ;
                }
                leaf src-wildcard {
                  description 'Wildcard bits.'
                              ;
                  type ncd:ipv4-address ;
                  mandatory true ;
                }
              }
              case src-any {
                description 'Any IP address.'
                            ;
                leaf src-any {
                  description 'Any IP address.'
                              ;
                  type empty ;
                  mandatory true ;
                }
              }
              case src-url {
                if-feature url-config ;
                description 'Source URL.'
                            ;
                leaf src-url {
                  description 'Source URL.'
                              ;
                  type ncd:url {
                    length 1..95 ;
                  }
                  mandatory true ;
                }
              }
            }
            leaf log {
              if-feature log-config ;
              description 'If log flag is set, the matching times of this rule '
                        + 'will be recorded.'
                          ;
              type boolean ;
              default false ;
            }
            leaf time-range {
              description 'Specify the existed time-range name.'
                          ;
              type string {
                length 1..31 ;
              }
            }
            choice rule-type {
              description 'Specify rule type of an IPv4 ACL.'+"\n"
                        + 'Rule types include standard type,ip type,tcp type,ud'
                        + 'p type,icmp type.'
                          ;
              case std {
                description 'Standard rule type.'
                            ;
                leaf ipv4-protocol-std {
                  description 'Standard rule type.'
                              ;
                  type empty ;
                  mandatory true ;
                }
              }
              case extend {
                description 'Extended rule type.'
                            ;
                container extended {
                  description 'Attributes of extended type.'
                              ;
                  choice dest-addr {
                    description 'Specify destination address.'
                                ;
                    mandatory true ;
                    case dest-ip-address {
                      description 'IP address.'
                                  ;
                      leaf dest-address {
                        description 'IP address.'
                                    ;
                        type ncd:ipv4-address ;
                        mandatory true ;
                      }
                      leaf dest-wildcard {
                        description 'IP address.'
                                    ;
                        type ncd:ipv4-address ;
                        mandatory true ;
                      }
                    }
                    case dest-any {
                      description 'Any IP address.'
                                  ;
                      leaf dest-any {
                        description 'Any IP address.'
                                    ;
                        type empty ;
                      }
                    }
                    case dest-url {
                      if-feature url-config ;
                      description 'Destination URL.'
                                  ;
                      leaf dest-url {
                        description 'Destination URL.'
                                    ;
                        type ncd:url {
                          length 1..95 ;
                        }
                      }
                    }
                  }
                  choice priority {
                    description 'Specify the priority of packets.'+"\n"
                              + 'This is an optional node.'+"\n"
                              + 'If you set this node you can choose precedence'
                              + ', tos, or dscp.'+"\n"
                              + 'None means all case is invalid, And the defaul'
                              + 't state is none.'
                                ;
                    case precedence {
                      if-feature pri-value-config ;
                      description 'Specify the precedence value.'
                                  ;
                      leaf precedence {
                        description 'Precedence value.'
                                    ;
                        type uint8 {
                          range 0..7 ;
                        }
                      }
                    }
                    case prec-range {
                      if-feature pri-range-config ;
                      description 'Specify the precedence value, support single'
                                + ' precedence value or range(such as 0-7).'
                                  ;
                      leaf prec-range {
                        description 'Configure the precedence value, support si'
                                  + 'ngle precedence value or range(such as 0-7'
                                  + ').'
                                    ;
                        type acl-prec-range ;
                      }
                      ncd:revise-date 2015-04-20 ;
                    }
                    case tos {
                      description 'Specify the TOS value.'
                                  ;
                      leaf tos {
                        description 'TOS value.'
                                    ;
                        type uint8 {
                          range 0..15 ;
                        }
                      }
                    }
                    case dscp {
                      if-feature pri-value-config ;
                      description 'Specify the DSCP value.'
                                  ;
                      leaf dscp {
                        description 'DSCP value.'
                                    ;
                        type uint8 {
                          range 0..63 ;
                        }
                      }
                    }
                    case dscp-range {
                      if-feature pri-range-config ;
                      description 'Specify the DSCP value, support single DSCP '
                                + 'value or range(such as 0-63).'
                                  ;
                      leaf dscp-range {
                        description 'Specify the DSCP value, support single DSC'
                                  + 'P value or range(such as 0-63).'
                                    ;
                        type acl-dscp-range ;
                      }
                      ncd:revise-date 2015-04-20 ;
                    }
                  }
                  leaf fragment {
                    description 'Examine non-initial fragments of packet.'
                                ;
                    type boolean ;
                    default false ;
                  }
                  choice ttl {
                    if-feature ttl-config ;
                    status obsolete {
                      ncd:revise-date 2017-07-20 ;
                    }
                    description 'Specify the TTL value'+"\n"
                              + 'The operator value of TTL mean '+"\n"
                              + 'eq(1)   : Match only packets on a given ttl va'
                              + 'lue'+"\n"
                              + 'ge(2)   : Match only packets with a no lower t'
                              + 'tl value'+"\n"
                              + 'le(3)   : Match only packets with a no greater'
                              + ' ttl value'+"\n"
                              + 'neq(6)  : Match only packets with a no equeal '
                              + 'ttl value'+"\n"
                              + 'range(7): Match only packet on a given ttl val'
                              + 'ue range.'
                                ;
                    case ttl-value {
                      status obsolete {
                        ncd:revise-date 2017-07-20 ;
                      }
                      description 'Specify the TTL value.'
                                  ;
                      leaf ttl-value-operator {
                        status obsolete {
                          ncd:revise-date 2017-07-20 ;
                        }
                        description 'Operator type'+"\n"
                                  + 'eq(1)   : Match only packets on a given tt'
                                  + 'l value'+"\n"
                                  + 'ge(2)   : Match only packets with a no low'
                                  + 'er ttl value'+"\n"
                                  + 'le(3)   : Match only packets with a no gre'
                                  + 'ater ttl value'+"\n"
                                  + 'neq(6)  : Match only packets with a no equ'
                                  + 'eal ttl value.'
                                    ;
                        type enumeration {
                          enum eq {
                            value 1 ;
                            description 'Equal to.'
                                        ;
                          }
                          enum ge {
                            value 2 ;
                            description 'Great than or equal to.'
                                        ;
                          }
                          enum le {
                            value 3 ;
                            description 'Less than or equal to.'
                                        ;
                          }
                          enum neq {
                            value 6 ;
                            description 'Not equal to.'
                                        ;
                          }
                        }
                        mandatory true ;
                      }
                      leaf ttl-value {
                        status obsolete {
                          ncd:revise-date 2017-07-20 ;
                        }
                        description 'TTL value.'
                                    ;
                        type uint8 {
                          range 1..255 ;
                        }
                        mandatory true ;
                      }
                    }
                    case ttl-range {
                      status obsolete {
                        ncd:revise-date 2017-07-20 ;
                      }
                      description 'Specify the TTL range.'
                                  ;
                      leaf ttl-range-operator {
                        status obsolete {
                          ncd:revise-date 2017-07-20 ;
                        }
                        description 'Operator type'+"\n"
                                  + 'range(7): Match only packet on a given ttl'
                                  + ' value range.'
                                    ;
                        type empty ;
                        mandatory true ;
                      }
                      leaf ttl-range {
                        status obsolete {
                          ncd:revise-date 2017-07-20 ;
                        }
                        description 'TTL value range.'
                                    ;
                        type acl-ttl-range ;
                        mandatory true ;
                      }
                    }
                  }
                  container time-to-live {
                    if-feature ttl-config ;
                    description 'Specify the TTL(Time To Live) value'+"\n"
                              + 'The operator value of TTL mean '+"\n"
                              + 'eq(1)   : Match only packets on a given ttl va'
                              + 'lue'+"\n"
                              + 'ge(2)   : Match only packets with a no lower t'
                              + 'tl value'+"\n"
                              + 'le(3)   : Match only packets with a no greater'
                              + ' ttl value'+"\n"
                              + 'neq(6)  : Match only packets with a no equeal '
                              + 'ttl value'+"\n"
                              + 'range(7): Match only packet on a given ttl val'
                              + 'ue range.'
                                ;
                    presence 'Specify the TTL'
                             ;
                    choice ttl {
                      description 'Specify the TTL value'+"\n"
                                + 'The operator value of TTL mean '+"\n"
                                + 'eq(1)   : Match only packets on a given ttl '
                                + 'value'+"\n"
                                + 'ge(2)   : Match only packets with a no lower'
                                + ' ttl value'+"\n"
                                + 'le(3)   : Match only packets with a no great'
                                + 'er ttl value'+"\n"
                                + 'neq(6)  : Match only packets with a no equea'
                                + 'l ttl value'+"\n"
                                + 'range(7): Match only packet on a given ttl v'
                                + 'alue range.'
                                  ;
                      mandatory true ;
                      case ttl-value {
                        description 'Specify the TTL value.'
                                    ;
                        container ttl-value {
                          description 'Specify the TTL value.'
                                      ;
                          presence 'Specify the TTL value'
                                   ;
                          leaf ttl-operator {
                            description 'Operator type'+"\n"
                                      + 'eq(1)   : Match only packets on a given ttl value'+"\n"
                                      + 'ge(2)   : Match only packets with a no lower ttl value'+"\n"
                                      + 'le(3)   : Match only packets with a no greater ttl value'+"\n"
                                      + 'neq(6)  : Match only packets with a no equeal ttl value.'
                                        ;
                            type enumeration {
                              enum eq {
                                value 1 ;
                                description 'Equal to.'
                                            ;
                              }
                              enum ge {
                                value 2 ;
                                description 'Great than or equal to.'
                                            ;
                              }
                              enum le {
                                value 3 ;
                                description 'Less than or equal to.'
                                            ;
                              }
                              enum neq {
                                value 6 ;
                                description 'Not equal to.'
                                            ;
                              }
                            }
                            mandatory true ;
                          }
                          leaf ttl-value {
                            description 'TTL value, support 1-255.'
                                        ;
                            type uint8 {
                              range 1..255 {
                                description 'TTL value, support 1-255.'
                                            ;
                              }
                            }
                            mandatory true ;
                          }
                        }
                      }
                      case ttl-range {
                        description 'Specify the TTL range.'
                                    ;
                        container ttl-range {
                          description 'Specify the TTL range.'
                                      ;
                          presence 'Specify the TTL range'
                                   ;
                          leaf ttl-operator {
                            description 'Operator type
range(7): Match only packet on a given ttl value range.'
                                        ;
                            type enumeration {
                              enum range {
                                value 7 ;
                                description Range. ;
                              }
                            }
                            mandatory true ;
                          }
                          leaf ttl-range {
                            description 'TTL value range, support <1-255>-<1-255>.'
                                        ;
                            type acl-ttl-range ;
                            mandatory true ;
                          }
                        }
                      }
                    }
                    ncd:revise-date 2017-07-20 ;
                  }
                  choice ipv4-protocol-type {
                    description 'IPv4 Protocol type.'
                                ;
                    mandatory true ;
                    case udp-tcp {
                      description 'Extended rule type : UDP and TCP.'
                                  ;
                      container udp-tcp {
                        description 'Extended rule type : UDP and TCP.'
                                    ;
                        choice udpOrTcp {
                          description 'Extended rule type : UDP or TCP.'
                                      ;
                          mandatory true ;
                          case udp {
                            description 'Extended rule type : UDP.'
                                        ;
                            leaf ipv4-protocol-udp {
                              description 'Extended rule type : UDP.'
                                          ;
                              type empty ;
                            }
                          }
                          case tcp {
                            description 'Extended rule type : TCP.'
                                        ;
                            leaf ipv4-protocol-tcp {
                              description 'Extended rule type : TCP.'
                                          ;
                              type empty ;
                              mandatory true ;
                            }
                            leaf established {
                              description 'Match established connections.'
                                          ;
                              type boolean ;
                              default false ;
                            }
                            leaf rst {
                              description 'Match when the RST flag set or not.'
                                          ;
                              type acl-tcp-flag ;
                            }
                            leaf ack {
                              description 'Match when the ACK flag set or not.'
                                          ;
                              type acl-tcp-flag ;
                            }
                            leaf fin {
                              description 'Match when the FIN flag set or not.'
                                          ;
                              type acl-tcp-flag ;
                            }
                            leaf syn {
                              description 'Match when the SYN flag set or not.'
                                          ;
                              type acl-tcp-flag ;
                            }
                            leaf psh {
                              description 'Match when the PSH flag set or not.'
                                          ;
                              type acl-tcp-flag ;
                            }
                            leaf urg {
                              description 'Match when the URG flag set or not.'
                                          ;
                              type acl-tcp-flag ;
                            }
                          }
                        }
                        choice src-port {
                          status obsolete {
                            ncd:revise-date 2017-07-20 ;
                          }
                          description 'Specify source port.'+"\n"
                                    + 'When the value of operator is invalid, i'
                                    + 't means match all port range,'+"\n"
                                    + 'the other value of operator means'+"\n"
                                    + 'eq(1)   : match only packets on a given '
                                    + 'port number'+"\n"
                                    + 'ge(2)   : match only packets with a no l'
                                    + 'ower port number'+"\n"
                                    + 'le(3)   : match only packets with a no g'
                                    + 'reater port number'+"\n"
                                    + 'range(7): match only packet on a given p'
                                    + 'ort range.'
                                      ;
                          case src-value {
                            status obsolete {
                              ncd:revise-date 2017-07-20 ;
                            }
                            description 'Configure port number.'
                                        ;
                            leaf src-value-operator {
                              status obsolete {
                                ncd:revise-date 2017-07-20 ;
                              }
                              description 'Operator type'+"\n"
                                        + 'eq(1)   : match only packets on a given port number'+"\n"
                                        + 'ge(2)   : match only packets with a no lower port number'+"\n"
                                        + 'le(3)   : match only packets with a no greater port number.'
                                          ;
                              type enumeration {
                                enum eq {
                                  value 1 ;
                                  description 'Equal to.'
                                              ;
                                }
                                enum ge {
                                  value 2 ;
                                  description 'Great than or equal to.'
                                              ;
                                }
                                enum le {
                                  value 3 ;
                                  description 'Less than or equal to.'
                                              ;
                                }
                              }
                              mandatory true ;
                            }
                            leaf src-port-number {
                              status obsolete {
                                ncd:revise-date 2017-07-20 ;
                              }
                              description 'Port number'+"\n"
                                        + 'Some has specific means:'+"\n"
                                        + 'bootpc       Bootstrap protocol (BOOTP) client (68)'+"\n"
                                        + 'bootps       Bootstrap protocol (BOOTP) server (67)'+"\n"
                                        + 'domain       Domain name service (DNS, 53)'+"\n"
                                        + 'ntp          Network time protocol (123)'+"\n"
                                        + 'pim-auto-rp  PIM auto-RP (496)'+"\n"
                                        + 'rip          Routing information protocol (router, in.routed, 520)'+"\n"
                                        + 'snmp         Simple network management protocol (161)'+"\n"
                                        + 'snmptrap     SNMP traps (162)'+"\n"
                                        + 'tftp         Trivial file transfer protocol (69).'
                                          ;
                              type uint16 {
                                range 0..65535 ;
                              }
                              mandatory true ;
                            }
                          }
                          case src-range {
                            status obsolete {
                              ncd:revise-date 2017-07-20 ;
                            }
                            description 'Configure port range.'
                                        ;
                            leaf src-range-operator {
                              status obsolete {
                                ncd:revise-date 2017-07-20 ;
                              }
                              description 'Operator type
range(7): match only packet on a given port range.'
                                          ;
                              type empty ;
                              mandatory true ;
                            }
                            leaf src-port-range {
                              status obsolete {
                                ncd:revise-date 2017-07-20 ;
                              }
                              description 'Port range.'
                                          ;
                              type acl-port-range ;
                              mandatory true ;
                            }
                          }
                        }
                        choice dest-port {
                          status obsolete {
                            ncd:revise-date 2017-07-20 ;
                          }
                          description 'Specify destination port.'+"\n"
                                    + 'When the value of operator is invalid, i'
                                    + 't means match all port range,'+"\n"
                                    + 'the other value of operator means'+"\n"
                                    + 'eq(1)   : match only packets on a given '
                                    + 'port number'+"\n"
                                    + 'ge(2)   : match only packets with a no l'
                                    + 'ower port number'+"\n"
                                    + 'le(3)   : match only packets with a no g'
                                    + 'reater port number'+"\n"
                                    + 'range(7): match only packet on a given p'
                                    + 'ort range.'
                                      ;
                          case dest-value {
                            status obsolete {
                              ncd:revise-date 2017-07-20 ;
                            }
                            description 'Configure port number.'
                                        ;
                            leaf dest-value-operator {
                              status obsolete {
                                ncd:revise-date 2017-07-20 ;
                              }
                              description 'Operator type'+"\n"
                                        + 'eq(1)   : match only packets on a given port number'+"\n"
                                        + 'ge(2)   : match only packets with a no lower port number'+"\n"
                                        + 'le(3)   : match only packets with a no greater port number.'
                                          ;
                              type enumeration {
                                enum eq {
                                  value 1 ;
                                  description 'Equal to.'
                                              ;
                                }
                                enum ge {
                                  value 2 ;
                                  description 'Great than or equal to.'
                                              ;
                                }
                                enum le {
                                  value 3 ;
                                  description 'Less than or equal to.'
                                              ;
                                }
                              }
                              mandatory true ;
                            }
                            leaf dest-port-number {
                              status obsolete {
                                ncd:revise-date 2017-07-20 ;
                              }
                              description 'Port number'+"\n"
                                        + 'Some has specific means:'+"\n"
                                        + 'bootpc       Bootstrap protocol (BOOTP) client (68)'+"\n"
                                        + 'bootps       Bootstrap protocol (BOOTP) server (67)'+"\n"
                                        + 'domain       Domain name service (DNS, 53)'+"\n"
                                        + 'ntp          Network time protocol (123)'+"\n"
                                        + 'pim-auto-rp  PIM auto-RP (496)'+"\n"
                                        + 'rip          Routing information protocol (router, in.routed, 520)'+"\n"
                                        + 'snmp         Simple network management protocol (161)'+"\n"
                                        + 'snmptrap     SNMP traps (162)'+"\n"
                                        + 'tftp         Trivial file transfer protocol (69).'
                                          ;
                              type uint16 {
                                range 0..65535 ;
                              }
                              mandatory true ;
                            }
                          }
                          case dest-range {
                            status obsolete {
                              ncd:revise-date 2017-07-20 ;
                            }
                            description 'Configure port range.'
                                        ;
                            leaf dest-range-operator {
                              status obsolete {
                                ncd:revise-date 2017-07-20 ;
                              }
                              description 'Operator type
range(7): match only packet on a given port range.'
                                          ;
                              type empty ;
                              mandatory true ;
                            }
                            leaf dest-port-range {
                              status obsolete {
                                ncd:revise-date 2017-07-20 ;
                              }
                              description 'Port range.'
                                          ;
                              type acl-port-range ;
                              mandatory true ;
                            }
                          }
                        }
                        container source-port {
                          description 'Specify source port.'+"\n"
                                    + 'When the value of operator is invalid, i'
                                    + 't means match all port range,'+"\n"
                                    + 'the other value of operator means'+"\n"
                                    + 'eq(1)   : match only packets on a given '
                                    + 'port number'+"\n"
                                    + 'ge(2)   : match only packets with a no l'
                                    + 'ower port number'+"\n"
                                    + 'le(3)   : match only packets with a no g'
                                    + 'reater port number'+"\n"
                                    + 'range(7): match only packet on a given p'
                                    + 'ort range.'
                                      ;
                          presence 'Specify source port'
                                   ;
                          choice source-port {
                            description 'Specify source port.'+"\n"
                                      + 'When the value of operator is invalid, it means match all port range,'+"\n"
                                      + 'the other value of operator means'+"\n"
                                      + 'eq(1)   : match only packets on a given port number'+"\n"
                                      + 'ge(2)   : match only packets with a no lower port number'+"\n"
                                      + 'le(3)   : match only packets with a no greater port number'+"\n"
                                      + 'range(7): match only packet on a given port range.'
                                        ;
                            mandatory true ;
                            case src-port-value {
                              description 'Configure port number.'
                                          ;
                              container src-port-value {
                                description 'Configure port number.'
                                            ;
                                presence 'Configure port number'
                                         ;
                                leaf src-port-operator {
                                  description 'Operator type'+"\n"
                                            + 'eq(1)   : match only packets on a given port number'+"\n"
                                            + 'ge(2)   : match only packets with a no lower port number'+"\n"
                                            + 'le(3)   : match only packets with a no greater port number.'
                                              ;
                                  type enumeration {
                                    enum eq {
                                      value 1 ;
                                      description 'Equal to.'
                                                  ;
                                    }
                                    enum ge {
                                      value 2 ;
                                      description 'Great than or equal to.'
                                                  ;
                                    }
                                    enum le {
                                      value 3 ;
                                      description 'Less than or equal to.'
                                                  ;
                                    }
                                  }
                                  mandatory true ;
                                }
                                leaf src-port-value {
                                  description 'Port number'+"\n"
                                            + 'Some has specific means:'+"\n"
                                            + 'bootpc       Bootstrap protocol (BOOTP) client (68)'+"\n"
                                            + 'bootps       Bootstrap protocol (BOOTP) server (67)'+"\n"
                                            + 'domain       Domain name service (DNS, 53)'+"\n"
                                            + 'ntp          Network time protocol (123)'+"\n"
                                            + 'pim-auto-rp  PIM auto-RP (496)'+"\n"
                                            + 'rip          Routing information protocol (router, in.routed, 520)'+"\n"
                                            + 'snmp         Simple network management protocol (161)'+"\n"
                                            + 'snmptrap     SNMP traps (162)'+"\n"
                                            + 'tftp         Trivial file transfer protocol (69).'
                                              ;
                                  type uint16 {
                                    range 0..65535 ;
                                  }
                                  mandatory true ;
                                }
                              }
                            }
                            case src-port-range {
                              description 'Configure port range.'
                                          ;
                              container src-port-range {
                                description 'Configure port range.'
                                            ;
                                presence 'Configure port range'
                                         ;
                                leaf src-port-operator {
                                  description 'Operator type
range(7): match only packet on a given port range.'
                                              ;
                                  type enumeration {
                                    enum range {
                                      value 7 ;
                                      description Range. ;
                                    }
                                  }
                                  mandatory true ;
                                }
                                leaf src-port-range {
                                  description 'Port range, support <0-65535>-<0-65535>.'
                                              ;
                                  type acl-port-range ;
                                  mandatory true ;
                                }
                              }
                            }
                          }
                          ncd:revise-date 2017-07-20 ;
                        }
                        container destination-port {
                          description 'Specify destination port.'+"\n"
                                    + 'When the value of operator is invalid, i'
                                    + 't means match all port range,'+"\n"
                                    + 'the other value of operator means'+"\n"
                                    + 'eq(1)   : match only packets on a given '
                                    + 'port number'+"\n"
                                    + 'ge(2)   : match only packets with a no l'
                                    + 'ower port number'+"\n"
                                    + 'le(3)   : match only packets with a no g'
                                    + 'reater port number'+"\n"
                                    + 'range(7): match only packet on a given p'
                                    + 'ort range.'
                                      ;
                          presence 'Specify destination port'
                                   ;
                          choice destination-port {
                            description 'Specify destination port.'+"\n"
                                      + 'When the value of operator is invalid, it means match all port range,'+"\n"
                                      + 'the other value of operator means'+"\n"
                                      + 'eq(1)   : match only packets on a given port number'+"\n"
                                      + 'ge(2)   : match only packets with a no lower port number'+"\n"
                                      + 'le(3)   : match only packets with a no greater port number'+"\n"
                                      + 'range(7): match only packet on a given port range.'
                                        ;
                            mandatory true ;
                            case dst-port-value {
                              description 'Configure port number.'
                                          ;
                              container dst-port-value {
                                description 'Configure port number.'
                                            ;
                                presence 'Configure port number'
                                         ;
                                leaf dst-port-operator {
                                  description 'Operator type'+"\n"
                                            + 'eq(1)   : match only packets on a given port number'+"\n"
                                            + 'ge(2)   : match only packets with a no lower port number'+"\n"
                                            + 'le(3)   : match only packets with a no greater port number.'
                                              ;
                                  type enumeration {
                                    enum eq {
                                      value 1 ;
                                      description 'Equal to.'
                                                  ;
                                    }
                                    enum ge {
                                      value 2 ;
                                      description 'Great than or equal to.'
                                                  ;
                                    }
                                    enum le {
                                      value 3 ;
                                      description 'Less than or equal to.'
                                                  ;
                                    }
                                  }
                                  mandatory true ;
                                }
                                leaf dst-port-value {
                                  description 'Port number'+"\n"
                                            + 'Some has specific means:'+"\n"
                                            + 'bootpc       Bootstrap protocol (BOOTP) client (68)'+"\n"
                                            + 'bootps       Bootstrap protocol (BOOTP) server (67)'+"\n"
                                            + 'domain       Domain name service (DNS, 53)'+"\n"
                                            + 'ntp          Network time protocol (123)'+"\n"
                                            + 'pim-auto-rp  PIM auto-RP (496)'+"\n"
                                            + 'rip          Routing information protocol (router, in.routed, 520)'+"\n"
                                            + 'snmp         Simple network management protocol (161)'+"\n"
                                            + 'snmptrap     SNMP traps (162)'+"\n"
                                            + 'tftp         Trivial file transfer protocol (69).'
                                              ;
                                  type uint16 {
                                    range 0..65535 ;
                                  }
                                  mandatory true ;
                                }
                              }
                            }
                            case dst-port-range {
                              description 'Configure port range.'
                                          ;
                              container dst-port-range {
                                description 'Configure port range.'
                                            ;
                                presence 'Configure port range'
                                         ;
                                leaf dst-port-operator {
                                  description 'Operator type
range(7): match only packet on a given port range.'
                                              ;
                                  type enumeration {
                                    enum range {
                                      value 7 ;
                                      description Range. ;
                                    }
                                  }
                                  mandatory true ;
                                }
                                leaf dst-port-range {
                                  description 'Port range, support <0-65535>-<0-65535>.'
                                              ;
                                  type acl-port-range ;
                                  mandatory true ;
                                }
                              }
                            }
                          }
                          ncd:revise-date 2017-07-20 ;
                        }
                      }
                    }
                    case icmp {
                      description 'Extended rule type : ICMP.'
                                  ;
                      leaf ipv4-protocol-icmp {
                        description 'Extended rule type : ICMP.'
                                    ;
                        type empty ;
                        mandatory true ;
                      }
                      container icmp-conf {
                        description 'Specify ICMP type and ICMP code.'
                                    ;
                        presence 'config icmp type and code'
                                 ;
                        leaf icmp-type {
                          description 'ICMP type'+"\n"
                                    + 'Some value has specific means'+"\n"
                                    + 'alternate-address     Alternate address '
                                    + '(6)'+"\n"
                                    + 'echo                  Echo (ping, 8)'+"\n"
                                    + 'echo-reply            Echo reply (0)'+"\n"
                                    + 'information-request   Information reques'
                                    + 'ts (15)'+"\n"
                                    + 'parameter-problem     All parameter prob'
                                    + 'lems (12)'+"\n"
                                    + 'redirect              All redirects (5)
'
                                    + ''+"\n"
                                    + 'router-advertisement  Router discovery a'
                                    + 'dvertisements (9)'+"\n"
                                    + 'router-solicitation   Router discovery s'
                                    + 'olicitations (10)'+"\n"
                                    + 'source-quench         Source quenches (4'
                                    + ')'+"\n"
                                    + 'time-exceeded         All time exceededs'
                                    + ' (11)'+"\n"
                                    + 'timestamp-reply       Timestamp replies '
                                    + '(14)'+"\n"
                                    + 'timestamp-request     Timestamp requests'
                                    + ' (13)'+"\n"
                                    + 'unreachable           All unreachables ('
                                    + '3).'
                                      ;
                          type uint16 {
                            range 0..255 ;
                          }
                          mandatory true ;
                        }
                        leaf icmp-code {
                          description 'ICMP code.'
                                      ;
                          type uint16 {
                            range 0..255 ;
                          }
                        }
                      }
                      container icmp-port {
                        description 'Port infomation.'
                                    ;
                        choice src-port {
                          status obsolete {
                            ncd:revise-date 2017-07-20 ;
                          }
                          description 'Specify source port.'+"\n"
                                    + 'When the value of operator is invalid, i'
                                    + 't means match all port range,'+"\n"
                                    + 'the other value of operator means'+"\n"
                                    + 'eq(1)   : match only packets on a given '
                                    + 'port number'+"\n"
                                    + 'ge(2)   : match only packets with a no l'
                                    + 'ower port number'+"\n"
                                    + 'le(3)   : match only packets with a no g'
                                    + 'reater port number'+"\n"
                                    + 'range(7): match only packet on a given p'
                                    + 'ort range.'
                                      ;
                          case src-value {
                            status obsolete {
                              ncd:revise-date 2017-07-20 ;
                            }
                            description 'Configure port number.'
                                        ;
                            leaf src-value-operator {
                              status obsolete {
                                ncd:revise-date 2017-07-20 ;
                              }
                              description 'Operator type'+"\n"
                                        + 'eq(1)   : match only packets on a given port number'+"\n"
                                        + 'ge(2)   : match only packets with a no lower port number'+"\n"
                                        + 'le(3)   : match only packets with a no greater port number.'
                                          ;
                              type enumeration {
                                enum eq {
                                  value 1 ;
                                  description 'Equal to.'
                                              ;
                                }
                                enum ge {
                                  value 2 ;
                                  description 'Great than or equal to.'
                                              ;
                                }
                                enum le {
                                  value 3 ;
                                  description 'Less than or equal to.'
                                              ;
                                }
                              }
                              mandatory true ;
                            }
                            leaf src-port-number {
                              status obsolete {
                                ncd:revise-date 2017-07-20 ;
                              }
                              description 'Port number'+"\n"
                                        + 'Some has specific means:'+"\n"
                                        + 'bootpc       Bootstrap protocol (BOOTP) client (68)'+"\n"
                                        + 'bootps       Bootstrap protocol (BOOTP) server (67)'+"\n"
                                        + 'domain       Domain name service (DNS, 53)'+"\n"
                                        + 'ntp          Network time protocol (123)'+"\n"
                                        + 'pim-auto-rp  PIM auto-RP (496)'+"\n"
                                        + 'rip          Routing information protocol (router, in.routed, 520)'+"\n"
                                        + 'snmp         Simple network management protocol (161)'+"\n"
                                        + 'snmptrap     SNMP traps (162)'+"\n"
                                        + 'tftp         Trivial file transfer protocol (69).'
                                          ;
                              type uint16 {
                                range 0..65535 ;
                              }
                              mandatory true ;
                            }
                          }
                          case src-range {
                            status obsolete {
                              ncd:revise-date 2017-07-20 ;
                            }
                            description 'Configure port range.'
                                        ;
                            leaf src-range-operator {
                              status obsolete {
                                ncd:revise-date 2017-07-20 ;
                              }
                              description 'Operator type
range(7): match only packet on a given port range.'
                                          ;
                              type empty ;
                              mandatory true ;
                            }
                            leaf src-port-range {
                              status obsolete {
                                ncd:revise-date 2017-07-20 ;
                              }
                              description 'Port range.'
                                          ;
                              type acl-port-range ;
                              mandatory true ;
                            }
                          }
                        }
                        choice dest-port {
                          status obsolete {
                            ncd:revise-date 2017-07-20 ;
                          }
                          description 'Specify destination port.'+"\n"
                                    + 'When the value of operator is invalid, i'
                                    + 't means match all port range,'+"\n"
                                    + 'the other value of operator means'+"\n"
                                    + 'eq(1)   : match only packets on a given '
                                    + 'port number'+"\n"
                                    + 'ge(2)   : match only packets with a no l'
                                    + 'ower port number'+"\n"
                                    + 'le(3)   : match only packets with a no g'
                                    + 'reater port number'+"\n"
                                    + 'range(7): match only packet on a given p'
                                    + 'ort range.'
                                      ;
                          case dest-value {
                            status obsolete {
                              ncd:revise-date 2017-07-20 ;
                            }
                            description 'Configure port number.'
                                        ;
                            leaf dest-value-operator {
                              status obsolete {
                                ncd:revise-date 2017-07-20 ;
                              }
                              description 'Operator type'+"\n"
                                        + 'eq(1)   : match only packets on a given port number'+"\n"
                                        + 'ge(2)   : match only packets with a no lower port number'+"\n"
                                        + 'le(3)   : match only packets with a no greater port number.'
                                          ;
                              type enumeration {
                                enum eq {
                                  value 1 ;
                                  description 'Equal to.'
                                              ;
                                }
                                enum ge {
                                  value 2 ;
                                  description 'Great than or equal to.'
                                              ;
                                }
                                enum le {
                                  value 3 ;
                                  description 'Less than or equal to.'
                                              ;
                                }
                              }
                              mandatory true ;
                            }
                            leaf dest-port-number {
                              status obsolete {
                                ncd:revise-date 2017-07-20 ;
                              }
                              description 'Port number'+"\n"
                                        + 'Some has specific means:'+"\n"
                                        + 'bootpc       Bootstrap protocol (BOOTP) client (68)'+"\n"
                                        + 'bootps       Bootstrap protocol (BOOTP) server (67)'+"\n"
                                        + 'domain       Domain name service (DNS, 53)'+"\n"
                                        + 'ntp          Network time protocol (123)'+"\n"
                                        + 'pim-auto-rp  PIM auto-RP (496)'+"\n"
                                        + 'rip          Routing information protocol (router, in.routed, 520)'+"\n"
                                        + 'snmp         Simple network management protocol (161)'+"\n"
                                        + 'snmptrap     SNMP traps (162)'+"\n"
                                        + 'tftp         Trivial file transfer protocol (69).'
                                          ;
                              type uint16 {
                                range 0..65535 ;
                              }
                              mandatory true ;
                            }
                          }
                          case dest-range {
                            status obsolete {
                              ncd:revise-date 2017-07-20 ;
                            }
                            description 'Configure port range.'
                                        ;
                            leaf dest-range-operator {
                              status obsolete {
                                ncd:revise-date 2017-07-20 ;
                              }
                              description 'Operator type
range(7): match only packet on a given port range.'
                                          ;
                              type empty ;
                              mandatory true ;
                            }
                            leaf dest-port-range {
                              status obsolete {
                                ncd:revise-date 2017-07-20 ;
                              }
                              description 'Port range.'
                                          ;
                              type acl-port-range ;
                              mandatory true ;
                            }
                          }
                        }
                        container source-port {
                          description 'Specify source port.'+"\n"
                                    + 'When the value of operator is invalid, i'
                                    + 't means match all port range,'+"\n"
                                    + 'the other value of operator means'+"\n"
                                    + 'eq(1)   : match only packets on a given '
                                    + 'port number'+"\n"
                                    + 'ge(2)   : match only packets with a no l'
                                    + 'ower port number'+"\n"
                                    + 'le(3)   : match only packets with a no g'
                                    + 'reater port number'+"\n"
                                    + 'range(7): match only packet on a given p'
                                    + 'ort range.'
                                      ;
                          presence 'Specify source port'
                                   ;
                          choice source-port {
                            description 'Specify source port.'+"\n"
                                      + 'When the value of operator is invalid, it means match all port range,'+"\n"
                                      + 'the other value of operator means'+"\n"
                                      + 'eq(1)   : match only packets on a given port number'+"\n"
                                      + 'ge(2)   : match only packets with a no lower port number'+"\n"
                                      + 'le(3)   : match only packets with a no greater port number'+"\n"
                                      + 'range(7): match only packet on a given port range.'
                                        ;
                            mandatory true ;
                            case src-port-value {
                              description 'Configure port number.'
                                          ;
                              container src-port-value {
                                description 'Configure port number.'
                                            ;
                                presence 'Configure port number'
                                         ;
                                leaf src-port-operator {
                                  description 'Operator type'+"\n"
                                            + 'eq(1)   : match only packets on a given port number'+"\n"
                                            + 'ge(2)   : match only packets with a no lower port number'+"\n"
                                            + 'le(3)   : match only packets with a no greater port number.'
                                              ;
                                  type enumeration {
                                    enum eq {
                                      value 1 ;
                                      description 'Equal to.'
                                                  ;
                                    }
                                    enum ge {
                                      value 2 ;
                                      description 'Great than or equal to.'
                                                  ;
                                    }
                                    enum le {
                                      value 3 ;
                                      description 'Less than or equal to.'
                                                  ;
                                    }
                                  }
                                  mandatory true ;
                                }
                                leaf src-port-value {
                                  description 'Port number'+"\n"
                                            + 'Some has specific means:'+"\n"
                                            + 'bootpc       Bootstrap protocol (BOOTP) client (68)'+"\n"
                                            + 'bootps       Bootstrap protocol (BOOTP) server (67)'+"\n"
                                            + 'domain       Domain name service (DNS, 53)'+"\n"
                                            + 'ntp          Network time protocol (123)'+"\n"
                                            + 'pim-auto-rp  PIM auto-RP (496)'+"\n"
                                            + 'rip          Routing information protocol (router, in.routed, 520)'+"\n"
                                            + 'snmp         Simple network management protocol (161)'+"\n"
                                            + 'snmptrap     SNMP traps (162)'+"\n"
                                            + 'tftp         Trivial file transfer protocol (69).'
                                              ;
                                  type uint16 {
                                    range 0..65535 ;
                                  }
                                  mandatory true ;
                                }
                              }
                            }
                            case src-port-range {
                              description 'Configure port range.'
                                          ;
                              container src-port-range {
                                description 'Configure port range.'
                                            ;
                                presence 'Configure port range'
                                         ;
                                leaf src-port-operator {
                                  description 'Operator type
range(7): match only packet on a given port range.'
                                              ;
                                  type enumeration {
                                    enum range {
                                      value 7 ;
                                      description Range. ;
                                    }
                                  }
                                  mandatory true ;
                                }
                                leaf src-port-range {
                                  description 'Port range, support <0-65535>-<0-65535>.'
                                              ;
                                  type acl-port-range ;
                                  mandatory true ;
                                }
                              }
                            }
                          }
                          ncd:revise-date 2017-07-20 ;
                        }
                        container destination-port {
                          description 'Specify destination port.'+"\n"
                                    + 'When the value of operator is invalid, i'
                                    + 't means match all port range,'+"\n"
                                    + 'the other value of operator means'+"\n"
                                    + 'eq(1)   : match only packets on a given '
                                    + 'port number'+"\n"
                                    + 'ge(2)   : match only packets with a no l'
                                    + 'ower port number'+"\n"
                                    + 'le(3)   : match only packets with a no g'
                                    + 'reater port number'+"\n"
                                    + 'range(7): match only packet on a given p'
                                    + 'ort range.'
                                      ;
                          presence 'Specify destination port'
                                   ;
                          choice destination-port {
                            description 'Specify destination port.'+"\n"
                                      + 'When the value of operator is invalid, it means match all port range,'+"\n"
                                      + 'the other value of operator means'+"\n"
                                      + 'eq(1)   : match only packets on a given port number'+"\n"
                                      + 'ge(2)   : match only packets with a no lower port number'+"\n"
                                      + 'le(3)   : match only packets with a no greater port number'+"\n"
                                      + 'range(7): match only packet on a given port range.'
                                        ;
                            mandatory true ;
                            case dst-port-value {
                              description 'Configure port number.'
                                          ;
                              container dst-port-value {
                                description 'Configure port number.'
                                            ;
                                presence 'Configure port number'
                                         ;
                                leaf dst-port-operator {
                                  description 'Operator type'+"\n"
                                            + 'eq(1)   : match only packets on a given port number'+"\n"
                                            + 'ge(2)   : match only packets with a no lower port number'+"\n"
                                            + 'le(3)   : match only packets with a no greater port number.'
                                              ;
                                  type enumeration {
                                    enum eq {
                                      value 1 ;
                                      description 'Equal to.'
                                                  ;
                                    }
                                    enum ge {
                                      value 2 ;
                                      description 'Great than or equal to.'
                                                  ;
                                    }
                                    enum le {
                                      value 3 ;
                                      description 'Less than or equal to.'
                                                  ;
                                    }
                                  }
                                  mandatory true ;
                                }
                                leaf dst-port-value {
                                  description 'Port number'+"\n"
                                            + 'Some has specific means:'+"\n"
                                            + 'bootpc       Bootstrap protocol (BOOTP) client (68)'+"\n"
                                            + 'bootps       Bootstrap protocol (BOOTP) server (67)'+"\n"
                                            + 'domain       Domain name service (DNS, 53)'+"\n"
                                            + 'ntp          Network time protocol (123)'+"\n"
                                            + 'pim-auto-rp  PIM auto-RP (496)'+"\n"
                                            + 'rip          Routing information protocol (router, in.routed, 520)'+"\n"
                                            + 'snmp         Simple network management protocol (161)'+"\n"
                                            + 'snmptrap     SNMP traps (162)'+"\n"
                                            + 'tftp         Trivial file transfer protocol (69).'
                                              ;
                                  type uint16 {
                                    range 0..65535 ;
                                  }
                                  mandatory true ;
                                }
                              }
                            }
                            case dst-port-range {
                              description 'Configure port range.'
                                          ;
                              container dst-port-range {
                                description 'Configure port range.'
                                            ;
                                presence 'Configure port range'
                                         ;
                                leaf dst-port-operator {
                                  description 'Operator type
range(7): match only packet on a given port range.'
                                              ;
                                  type enumeration {
                                    enum range {
                                      value 7 ;
                                      description Range. ;
                                    }
                                  }
                                  mandatory true ;
                                }
                                leaf dst-port-range {
                                  description 'Port range, support <0-65535>-<0-65535>.'
                                              ;
                                  type acl-port-range ;
                                  mandatory true ;
                                }
                              }
                            }
                          }
                          ncd:revise-date 2017-07-20 ;
                        }
                        ncd:revise-date 2016-01-13 ;
                      }
                    }
                    case ip {
                      description 'Extended rule type : IP.'
                                  ;
                      leaf ipv4-protocol {
                        description 'IP protocol number'+"\n"
                                  + 'Some has specific mean:'+"\n"
                                  + 'gre      Generic Routing Encapsulation (47'
                                  + ')'+"\n"
                                  + 'icmp     Internet Control Message Protocol'
                                  + '(1)'+"\n"
                                  + 'igmp     Internet Group Management Protoco'
                                  + 'l (2)'+"\n"
                                  + 'ospf     Open Shortest Path First Protocol'
                                  + ' (89)'+"\n"
                                  + 'pim      Protocol Independent Multicast (1'
                                  + '03)'+"\n"
                                  + 'tcp      Transmission Control Protocol(6)
'
                                  + ''+"\n"
                                  + 'udp      User Datagram Protocol(17)'+"\n"
                                  + 'vrrp     Virtual Router Redundancy Protoco'
                                  + 'l (112)'+"\n"
                                  + 'sctp     Stream Control Transmission Proto'
                                  + 'col (132)'+"\n"
                                  + 'ip       Any IP protocol (65535).'
                                    ;
                        type uint16 {
                          range '0 | 2..5 | 7..16 | 18..255 | 65535'
                                ;
                        }
                        mandatory true ;
                      }
                      container port {
                        description 'Port infomation.'
                                    ;
                        choice src-port {
                          status obsolete {
                            ncd:revise-date 2017-07-20 ;
                          }
                          description 'Specify source port.'+"\n"
                                    + 'When the value of operator is invalid, i'
                                    + 't means match all port range,'+"\n"
                                    + 'the other value of operator means'+"\n"
                                    + 'eq(1)   : match only packets on a given '
                                    + 'port number'+"\n"
                                    + 'ge(2)   : match only packets with a no l'
                                    + 'ower port number'+"\n"
                                    + 'le(3)   : match only packets with a no g'
                                    + 'reater port number'+"\n"
                                    + 'range(7): match only packet on a given p'
                                    + 'ort range.'
                                      ;
                          case src-value {
                            status obsolete {
                              ncd:revise-date 2017-07-20 ;
                            }
                            description 'Configure port number.'
                                        ;
                            leaf src-value-operator {
                              status obsolete {
                                ncd:revise-date 2017-07-20 ;
                              }
                              description 'Operator type'+"\n"
                                        + 'eq(1)   : match only packets on a given port number'+"\n"
                                        + 'ge(2)   : match only packets with a no lower port number'+"\n"
                                        + 'le(3)   : match only packets with a no greater port number.'
                                          ;
                              type enumeration {
                                enum eq {
                                  value 1 ;
                                  description 'Equal to.'
                                              ;
                                }
                                enum ge {
                                  value 2 ;
                                  description 'Great than or equal to.'
                                              ;
                                }
                                enum le {
                                  value 3 ;
                                  description 'Less than or equal to.'
                                              ;
                                }
                              }
                              mandatory true ;
                            }
                            leaf src-port-number {
                              status obsolete {
                                ncd:revise-date 2017-07-20 ;
                              }
                              description 'Port number'+"\n"
                                        + 'Some has specific means:'+"\n"
                                        + 'bootpc       Bootstrap protocol (BOOTP) client (68)'+"\n"
                                        + 'bootps       Bootstrap protocol (BOOTP) server (67)'+"\n"
                                        + 'domain       Domain name service (DNS, 53)'+"\n"
                                        + 'ntp          Network time protocol (123)'+"\n"
                                        + 'pim-auto-rp  PIM auto-RP (496)'+"\n"
                                        + 'rip          Routing information protocol (router, in.routed, 520)'+"\n"
                                        + 'snmp         Simple network management protocol (161)'+"\n"
                                        + 'snmptrap     SNMP traps (162)'+"\n"
                                        + 'tftp         Trivial file transfer protocol (69).'
                                          ;
                              type uint16 {
                                range 0..65535 ;
                              }
                              mandatory true ;
                            }
                          }
                          case src-range {
                            status obsolete {
                              ncd:revise-date 2017-07-20 ;
                            }
                            description 'Configure port range.'
                                        ;
                            leaf src-range-operator {
                              status obsolete {
                                ncd:revise-date 2017-07-20 ;
                              }
                              description 'Operator type
range(7): match only packet on a given port range.'
                                          ;
                              type empty ;
                              mandatory true ;
                            }
                            leaf src-port-range {
                              status obsolete {
                                ncd:revise-date 2017-07-20 ;
                              }
                              description 'Port range.'
                                          ;
                              type acl-port-range ;
                              mandatory true ;
                            }
                          }
                        }
                        choice dest-port {
                          status obsolete {
                            ncd:revise-date 2017-07-20 ;
                          }
                          description 'Specify destination port.'+"\n"
                                    + 'When the value of operator is invalid, i'
                                    + 't means match all port range,'+"\n"
                                    + 'the other value of operator means'+"\n"
                                    + 'eq(1)   : match only packets on a given '
                                    + 'port number'+"\n"
                                    + 'ge(2)   : match only packets with a no l'
                                    + 'ower port number'+"\n"
                                    + 'le(3)   : match only packets with a no g'
                                    + 'reater port number'+"\n"
                                    + 'range(7): match only packet on a given p'
                                    + 'ort range.'
                                      ;
                          case dest-value {
                            status obsolete {
                              ncd:revise-date 2017-07-20 ;
                            }
                            description 'Configure port number.'
                                        ;
                            leaf dest-value-operator {
                              status obsolete {
                                ncd:revise-date 2017-07-20 ;
                              }
                              description 'Operator type'+"\n"
                                        + 'eq(1)   : match only packets on a given port number'+"\n"
                                        + 'ge(2)   : match only packets with a no lower port number'+"\n"
                                        + 'le(3)   : match only packets with a no greater port number.'
                                          ;
                              type enumeration {
                                enum eq {
                                  value 1 ;
                                  description 'Equal to.'
                                              ;
                                }
                                enum ge {
                                  value 2 ;
                                  description 'Great than or equal to.'
                                              ;
                                }
                                enum le {
                                  value 3 ;
                                  description 'Less than or equal to.'
                                              ;
                                }
                              }
                              mandatory true ;
                            }
                            leaf dest-port-number {
                              status obsolete {
                                ncd:revise-date 2017-07-20 ;
                              }
                              description 'Port number'+"\n"
                                        + 'Some has specific means:'+"\n"
                                        + 'bootpc       Bootstrap protocol (BOOTP) client (68)'+"\n"
                                        + 'bootps       Bootstrap protocol (BOOTP) server (67)'+"\n"
                                        + 'domain       Domain name service (DNS, 53)'+"\n"
                                        + 'ntp          Network time protocol (123)'+"\n"
                                        + 'pim-auto-rp  PIM auto-RP (496)'+"\n"
                                        + 'rip          Routing information protocol (router, in.routed, 520)'+"\n"
                                        + 'snmp         Simple network management protocol (161)'+"\n"
                                        + 'snmptrap     SNMP traps (162)'+"\n"
                                        + 'tftp         Trivial file transfer protocol (69).'
                                          ;
                              type uint16 {
                                range 0..65535 ;
                              }
                              mandatory true ;
                            }
                          }
                          case dest-range {
                            status obsolete {
                              ncd:revise-date 2017-07-20 ;
                            }
                            description 'Configure port range.'
                                        ;
                            leaf dest-range-operator {
                              status obsolete {
                                ncd:revise-date 2017-07-20 ;
                              }
                              description 'Operator type
range(7): match only packet on a given port range.'
                                          ;
                              type empty ;
                              mandatory true ;
                            }
                            leaf dest-port-range {
                              status obsolete {
                                ncd:revise-date 2017-07-20 ;
                              }
                              description 'Port range.'
                                          ;
                              type acl-port-range ;
                              mandatory true ;
                            }
                          }
                        }
                        container source-port {
                          description 'Specify source port.'+"\n"
                                    + 'When the value of operator is invalid, i'
                                    + 't means match all port range,'+"\n"
                                    + 'the other value of operator means'+"\n"
                                    + 'eq(1)   : match only packets on a given '
                                    + 'port number'+"\n"
                                    + 'ge(2)   : match only packets with a no l'
                                    + 'ower port number'+"\n"
                                    + 'le(3)   : match only packets with a no g'
                                    + 'reater port number'+"\n"
                                    + 'range(7): match only packet on a given p'
                                    + 'ort range.'
                                      ;
                          presence 'Specify source port'
                                   ;
                          choice source-port {
                            description 'Specify source port.'+"\n"
                                      + 'When the value of operator is invalid, it means match all port range,'+"\n"
                                      + 'the other value of operator means'+"\n"
                                      + 'eq(1)   : match only packets on a given port number'+"\n"
                                      + 'ge(2)   : match only packets with a no lower port number'+"\n"
                                      + 'le(3)   : match only packets with a no greater port number'+"\n"
                                      + 'range(7): match only packet on a given port range.'
                                        ;
                            mandatory true ;
                            case src-port-value {
                              description 'Configure port number.'
                                          ;
                              container src-port-value {
                                description 'Configure port number.'
                                            ;
                                presence 'Configure port number'
                                         ;
                                leaf src-port-operator {
                                  description 'Operator type'+"\n"
                                            + 'eq(1)   : match only packets on a given port number'+"\n"
                                            + 'ge(2)   : match only packets with a no lower port number'+"\n"
                                            + 'le(3)   : match only packets with a no greater port number.'
                                              ;
                                  type enumeration {
                                    enum eq {
                                      value 1 ;
                                      description 'Equal to.'
                                                  ;
                                    }
                                    enum ge {
                                      value 2 ;
                                      description 'Great than or equal to.'
                                                  ;
                                    }
                                    enum le {
                                      value 3 ;
                                      description 'Less than or equal to.'
                                                  ;
                                    }
                                  }
                                  mandatory true ;
                                }
                                leaf src-port-value {
                                  description 'Port number'+"\n"
                                            + 'Some has specific means:'+"\n"
                                            + 'bootpc       Bootstrap protocol (BOOTP) client (68)'+"\n"
                                            + 'bootps       Bootstrap protocol (BOOTP) server (67)'+"\n"
                                            + 'domain       Domain name service (DNS, 53)'+"\n"
                                            + 'ntp          Network time protocol (123)'+"\n"
                                            + 'pim-auto-rp  PIM auto-RP (496)'+"\n"
                                            + 'rip          Routing information protocol (router, in.routed, 520)'+"\n"
                                            + 'snmp         Simple network management protocol (161)'+"\n"
                                            + 'snmptrap     SNMP traps (162)'+"\n"
                                            + 'tftp         Trivial file transfer protocol (69).'
                                              ;
                                  type uint16 {
                                    range 0..65535 ;
                                  }
                                  mandatory true ;
                                }
                              }
                            }
                            case src-port-range {
                              description 'Configure port range.'
                                          ;
                              container src-port-range {
                                description 'Configure port range.'
                                            ;
                                presence 'Configure port range'
                                         ;
                                leaf src-port-operator {
                                  description 'Operator type
range(7): match only packet on a given port range.'
                                              ;
                                  type enumeration {
                                    enum range {
                                      value 7 ;
                                      description Range. ;
                                    }
                                  }
                                  mandatory true ;
                                }
                                leaf src-port-range {
                                  description 'Port range, support <0-65535>-<0-65535>.'
                                              ;
                                  type acl-port-range ;
                                  mandatory true ;
                                }
                              }
                            }
                          }
                          ncd:revise-date 2017-07-20 ;
                        }
                        container destination-port {
                          description 'Specify destination port.'+"\n"
                                    + 'When the value of operator is invalid, i'
                                    + 't means match all port range,'+"\n"
                                    + 'the other value of operator means'+"\n"
                                    + 'eq(1)   : match only packets on a given '
                                    + 'port number'+"\n"
                                    + 'ge(2)   : match only packets with a no l'
                                    + 'ower port number'+"\n"
                                    + 'le(3)   : match only packets with a no g'
                                    + 'reater port number'+"\n"
                                    + 'range(7): match only packet on a given p'
                                    + 'ort range.'
                                      ;
                          presence 'Specify destination port'
                                   ;
                          choice destination-port {
                            description 'Specify destination port.'+"\n"
                                      + 'When the value of operator is invalid, it means match all port range,'+"\n"
                                      + 'the other value of operator means'+"\n"
                                      + 'eq(1)   : match only packets on a given port number'+"\n"
                                      + 'ge(2)   : match only packets with a no lower port number'+"\n"
                                      + 'le(3)   : match only packets with a no greater port number'+"\n"
                                      + 'range(7): match only packet on a given port range.'
                                        ;
                            mandatory true ;
                            case dst-port-value {
                              description 'Configure port number.'
                                          ;
                              container dst-port-value {
                                description 'Configure port number.'
                                            ;
                                presence 'Configure port number'
                                         ;
                                leaf dst-port-operator {
                                  description 'Operator type'+"\n"
                                            + 'eq(1)   : match only packets on a given port number'+"\n"
                                            + 'ge(2)   : match only packets with a no lower port number'+"\n"
                                            + 'le(3)   : match only packets with a no greater port number.'
                                              ;
                                  type enumeration {
                                    enum eq {
                                      value 1 ;
                                      description 'Equal to.'
                                                  ;
                                    }
                                    enum ge {
                                      value 2 ;
                                      description 'Great than or equal to.'
                                                  ;
                                    }
                                    enum le {
                                      value 3 ;
                                      description 'Less than or equal to.'
                                                  ;
                                    }
                                  }
                                  mandatory true ;
                                }
                                leaf dst-port-value {
                                  description 'Port number'+"\n"
                                            + 'Some has specific means:'+"\n"
                                            + 'bootpc       Bootstrap protocol (BOOTP) client (68)'+"\n"
                                            + 'bootps       Bootstrap protocol (BOOTP) server (67)'+"\n"
                                            + 'domain       Domain name service (DNS, 53)'+"\n"
                                            + 'ntp          Network time protocol (123)'+"\n"
                                            + 'pim-auto-rp  PIM auto-RP (496)'+"\n"
                                            + 'rip          Routing information protocol (router, in.routed, 520)'+"\n"
                                            + 'snmp         Simple network management protocol (161)'+"\n"
                                            + 'snmptrap     SNMP traps (162)'+"\n"
                                            + 'tftp         Trivial file transfer protocol (69).'
                                              ;
                                  type uint16 {
                                    range 0..65535 ;
                                  }
                                  mandatory true ;
                                }
                              }
                            }
                            case dst-port-range {
                              description 'Configure port range.'
                                          ;
                              container dst-port-range {
                                description 'Configure port range.'
                                            ;
                                presence 'Configure port range'
                                         ;
                                leaf dst-port-operator {
                                  description 'Operator type
range(7): match only packet on a given port range.'
                                              ;
                                  type enumeration {
                                    enum range {
                                      value 7 ;
                                      description Range. ;
                                    }
                                  }
                                  mandatory true ;
                                }
                                leaf dst-port-range {
                                  description 'Port range, support <0-65535>-<0-65535>.'
                                              ;
                                  type acl-port-range ;
                                  mandatory true ;
                                }
                              }
                            }
                          }
                          ncd:revise-date 2017-07-20 ;
                        }
                        ncd:revise-date 2016-01-13 ;
                      }
                    }
                  }
                  container packet-length {
                    description 'Configure packet length.'
                                ;
                    presence 'Configure packet length'
                             ;
                    choice packet-length {
                      description 'Configure packet length.'
                                  ;
                      mandatory true ;
                      case packet-length-value {
                        description 'Configure packet length, support eq, gt, l'
                                  + 't, neq.'
                                    ;
                        container packet-length-value {
                          description 'Configure packet length, support eq, gt,'
                                    + ' lt, neq.'
                                      ;
                          presence 'Configure packet length'
                                   ;
                          leaf packet-length-oper {
                            description 'Packet length operator, such as '+"\n"
                                      + '  eq   Match only packets on a given packet length'+"\n"
                                      + '  gt   Match only packets with a greater packet length'+"\n"
                                      + '  lt   Match only packets with a lower packet length'+"\n"
                                      + '  neq  Match only packets not on a given packet length.'
                                        ;
                            type acl-pktlen-opr ;
                            mandatory true ;
                          }
                          leaf packet-length-value {
                            description 'Packet length value, support 1-65535.'
                                        ;
                            type uint16 {
                              range 1..65535 {
                                description 'Packet length value, support 1-65535.'
                                            ;
                              }
                            }
                            mandatory true ;
                          }
                        }
                      }
                      case packet-length-range {
                        description 'Configure packet length, support range.'
                                    ;
                        container packet-length-range {
                          description 'Configure packet length, support range.'
                                      ;
                          presence 'Configure packet length'
                                   ;
                          leaf packet-length-oper {
                            description 'Packet length operator, such as '+"\n"
                                      + '  range   Match only packets on a given packet length range.'
                                        ;
                            type enumeration {
                              enum range {
                                value 7 ;
                                description 'Match only packets on a given packet length range.'
                                            ;
                              }
                            }
                            mandatory true ;
                          }
                          leaf packet-length-range {
                            description 'Packet length value range, support <1-65535>-<1-65535>.'
                                        ;
                            type acl-pktlen-range ;
                            mandatory true ;
                          }
                        }
                      }
                    }
                    ncd:revise-date 2017-06-20 ;
                  }
                  leaf monitor-group-id {
                    description 'Specify monitor group id.'
                                ;
                    type uint8 {
                      range 1..63 ;
                    }
                    ncd:revise-date 2019-11-26 ;
                  }
                  leaf source-monitor-group-id {
                    description 'Specify source monitor group id.'
                                ;
                    type uint8 {
                      range 1..63 ;
                    }
                    ncd:revise-date 2019-12-11 ;
                  }
                }
              }
            }
            leaf description {
              description 'Direction for use, support 1-70 characters.'
                          ;
              type ncd:string-with-blank {
                length 1..70 {
                  description 'Direction for use, support 1-70 characters.'
                              ;
                }
              }
              ncd:revise-date 2016-08-18 ;
            }
            choice vrf-config {
              description 'VPN Routing/Forwarding instance.'
                          ;
              case vrf-config-choice-clear {
                description 'Remove value of any entities which belong to any c'
                          + 'ase within this choice.'
                            ;
                container vrf-config-all-clear {
                  description 'Remove this entitiy means to remove value of any'
                            + ' entities which belong to any case within this c'
                            + 'hoice.'
                              ;
                  presence vrf-config-all-clear ;
                }
                ncd:revise-date 2020-08-17 ;
              }
              case vrf {
                description 'VPN Routing/Forwarding instance name, support 1-32'
                          + ' characters.'
                            ;
                leaf vrf {
                  description 'VPN Routing/Forwarding instance name, support 1-'
                            + '32 characters.'
                              ;
                  type acl-vrf-name ;
                }
                ncd:revise-date 2017-06-20 ;
              }
              case vrf-dcn {
                description 'DCN VRF flag.'
                            ;
                leaf vrf-dcn {
                  description 'DCN VRF flag.'
                              ;
                  type empty ;
                }
                ncd:revise-date 2020-08-17 ;
              }
              ncd:revise-date 2017-06-20 ;
            }
            container policy-route-id {
              description 'Specify the policy route id.'
                          ;
              presence 'Specify the policy route id'
                       ;
              choice policy-route-id {
                description 'Policy route id, including source policy route id '
                          + 'and destination policy route id.'
                            ;
                mandatory true ;
                case src {
                  description 'Source policy route id.'
                              ;
                  container source {
                    description 'Specify the source policy route id.'
                                ;
                    presence 'Specify the source policy route id'
                             ;
                    leaf src-policy-route-id {
                      description 'Source policy route id.'
                                  ;
                      type uint8 {
                        range 1..63 ;
                      }
                      mandatory true ;
                    }
                  }
                }
                case dest {
                  description 'Destination policy route id.'
                              ;
                  container destination {
                    description 'Specify the destination policy route id.'
                                ;
                    presence 'Specify the destination policy route id'
                             ;
                    leaf dest-policy-route-id {
                      description 'Destination policy route id.'
                                  ;
                      type uint8 {
                        range 1..63 ;
                      }
                      mandatory true ;
                    }
                  }
                }
              }
              ncd:revise-date 2019-09-10 ;
            }
          }
          container acl-description {
            description 'Description of an access control list, support 1-79 ch'
                      + 'aracters.'
                        ;
            presence 'Specify acl description'
                     ;
            leaf acl-description {
              description 'Description of an access control list, support 1-79 '
                        + 'characters.'
                          ;
              type ncd:string-with-blank {
                length 1..79 {
                  description 'Description of an access control list, support 1'
                            + '-79 characters.'
                              ;
                }
              }
              mandatory true ;
            }
            ncd:revise-date 2020-06-18 ;
          }
        }
        list ipv4-mixed-access-list {
          if-feature ipv4-mixed-feature ;
          description 'Configure ipv4-mixed-access-list.'
                      ;
          key acl-name ;
          leaf acl-name {
            description 'Name of ACL.'
                        ;
            type acl-name-type ;
          }
          list rule {
            description 'Configure rule of an IPv4 mixed ACL.'
                        ;
            key ruleid ;
            leaf ruleid {
              description 'ID of this rule.'
                          ;
              type uint32 {
                range 1..2147483644 ;
              }
            }
            choice link-prot {
              description 'Specify Link protocol type.'
                          ;
              case link-protocol {
                description 'Specify Link protocol type.'
                            ;
                leaf link-protocol {
                  description 'Specify Link protocol type.'
                              ;
                  type uint32 {
                    range 1536..65535 ;
                  }
                }
              }
              case link-protocol-hex {
                if-feature link-prot-hex-config ;
                status obsolete {
                  ncd:revise-date 2017-01-04 ;
                }
                description 'Specify Link protocol type, hex.'
                            ;
                leaf link-protocol-hex {
                  description 'Specify Link protocol type, hex.'
                              ;
                  type ncd:hex ;
                }
              }
              case sap {
                if-feature sap-feature ;
                description 'Specify service access point.'
                            ;
                container dsap-ssap {
                  description 'Specify destination DSAP and SSAP.'
                              ;
                  presence 'config dsap and ssap'
                           ;
                  leaf dsap {
                    description 'Specify destination service access point.'
                                ;
                    type uint16 {
                      range 0..255 ;
                    }
                    mandatory true ;
                  }
                  leaf ssap {
                    description 'Specify source service access point.'
                                ;
                    type uint16 {
                      range 0..255 ;
                    }
                    mandatory true ;
                  }
                }
                ncd:revise-date 2017-07-12 ;
              }
            }
            choice src-mac-addr {
              description 'Specify source MAC address.'
                          ;
              case src-mac-addr {
                description 'MAC address.'
                            ;
                leaf src-mac-address {
                  description 'MAC address.'
                              ;
                  type ncd:mac-address ;
                  mandatory true ;
                }
                leaf src-mac-wildcard {
                  description 'MAC address wildcard.'
                              ;
                  type ncd:mac-address ;
                  mandatory true ;
                }
              }
              case src-mac-any {
                description 'Any MAC address.'
                            ;
                leaf src-mac-any {
                  description 'Any MAC address.'
                              ;
                  type empty ;
                }
              }
              case src-mac-range {
                if-feature mac-range-config ;
                description 'MAC address range.'
                            ;
                leaf src-mac-from1 {
                  description 'Lower limit of MAC address first range.'
                              ;
                  type ncd:mac-address ;
                  mandatory true ;
                }
                leaf src-mac-to1 {
                  description 'Upper limit of MAC address first range.'
                              ;
                  type ncd:mac-address ;
                  mandatory true ;
                }
                container src-mac-range2 {
                  description 'Second MAC address range.'
                              ;
                  presence 'config second source mac range'
                           ;
                  leaf src-mac-from2 {
                    description 'Lower limit of second MAC address range.'
                                ;
                    type ncd:mac-address ;
                    mandatory true ;
                  }
                  leaf src-mac-to2 {
                    description 'Upper limit of second MAC address range.'
                                ;
                    type ncd:mac-address ;
                    mandatory true ;
                  }
                }
              }
            }
            choice dest-mac-addr {
              description 'Specify destination MAC address.'
                          ;
              case dest-mac-addr {
                description 'MAC address.'
                            ;
                leaf dest-mac-address {
                  description 'MAC address.'
                              ;
                  type ncd:mac-address ;
                  mandatory true ;
                }
                leaf dest-mac-wildcard {
                  description 'MAC address wildcard.'
                              ;
                  type ncd:mac-address ;
                  mandatory true ;
                }
              }
              case dest-mac-any {
                description 'Any MAC address.'
                            ;
                leaf dest-mac-any {
                  description 'Any MAC address.'
                              ;
                  type empty ;
                }
              }
              case dest-mac-range {
                if-feature mac-range-config ;
                description 'MAC address range.'
                            ;
                leaf dest-mac-from1 {
                  description 'Lower limit of MAC address first range.'
                              ;
                  type ncd:mac-address ;
                  mandatory true ;
                }
                leaf dest-mac-to1 {
                  description 'Upper limit of MAC address first range.'
                              ;
                  type ncd:mac-address ;
                  mandatory true ;
                }
                container dest-mac-range2 {
                  description 'Second MAC address range.'
                              ;
                  presence 'config second destination mac range'
                           ;
                  leaf dest-mac-from2 {
                    description 'Lower limit of second MAC address range.'
                                ;
                    type ncd:mac-address ;
                    mandatory true ;
                  }
                  leaf dest-mac-to2 {
                    description 'Upper limit of second MAC address range.'
                                ;
                    type ncd:mac-address ;
                    mandatory true ;
                  }
                }
              }
            }
            leaf inner-cos {
              if-feature ipv4-mixed-cos-value ;
              description 'Value of inner CoS.'
                          ;
              type uint8 {
                range 0..7 ;
              }
            }
            leaf inner-cos-range {
              if-feature ipv4-mixed-cos-range ;
              description 'Value of inner CoS, support single CoS value or rang'
                        + 'e(such as 0-7).'
                          ;
              type acl-cos-range ;
              ncd:revise-date 2015-04-20 ;
            }
            leaf outer-cos {
              if-feature ipv4-mixed-cos-value ;
              description 'Value of outer CoS.'
                          ;
              type uint8 {
                range 0..7 ;
              }
            }
            leaf outer-cos-range {
              if-feature ipv4-mixed-cos-range ;
              description 'Value of outer CoS, support single CoS value or rang'
                        + 'e(such as 0-7).'
                          ;
              type acl-cos-range ;
              ncd:revise-date 2015-04-20 ;
            }
            choice vlan-conf {
              description 'Specify VLAN.'
                          ;
              case vlan-value {
                if-feature vlan-value-config ;
                description 'Specify value of VLAN.'
                            ;
                leaf inne-vlan-value {
                  description 'Specify inner VLAN.'
                              ;
                  type uint16 {
                    range 1..4094 ;
                  }
                }
                leaf outer-vlan-value {
                  description 'Specify outer VLAN.'
                              ;
                  type uint16 {
                    range 1..4094 ;
                  }
                }
              }
              case vlan-range {
                if-feature vlan-range-config ;
                description 'Specify range of VLAN.'
                            ;
                leaf inner-vlan-range {
                  description 'Specify range of inner VLAN.'
                              ;
                  type acl-vlan-range ;
                }
                leaf cfi {
                  description 'Match on CFI(Canonical Format Indicator).'
                              ;
                  type enumeration {
                    enum set {
                      value 1 ;
                      description 'Match when the flag is set.'
                                  ;
                    }
                    enum unset {
                      value 0 ;
                      description 'Match when the flag is not set.'
                                  ;
                    }
                  }
                  ncd:revise-date 2017-06-20 ;
                }
                leaf outer-vlan-range {
                  description 'Specify range of outer VLAN.'
                              ;
                  type acl-vlan-range ;
                }
                leaf dei {
                  description 'Match on DEI(Drop EligibleIndicator).'
                              ;
                  type enumeration {
                    enum set {
                      value 1 ;
                      description 'Match when the flag is set.'
                                  ;
                    }
                    enum unset {
                      value 0 ;
                      description 'Match when the flag is not set.'
                                  ;
                    }
                  }
                  ncd:revise-date 2017-06-20 ;
                }
              }
            }
            choice permit-deny {
              description 'Deny  :  Specify packets to reject'+"\n"
                        + 'Permit:  Specify packets to forward.'
                          ;
              case deny {
                description 'Specify packets to reject.'
                            ;
                leaf deny {
                  description 'Specify packets to reject.'
                              ;
                  type empty ;
                }
              }
              case permit {
                description 'Specify packets to forward.'
                            ;
                leaf permit {
                  description 'Specify packets to forward.'
                              ;
                  type empty ;
                }
              }
            }
            choice src-addr {
              description 'Specify source address.'
                          ;
              case src-ip-address {
                description 'IP address.'
                            ;
                leaf src-address {
                  description 'IP address.'
                              ;
                  type ncd:ipv4-address ;
                  mandatory true ;
                }
                leaf src-wildcard {
                  description 'Wildcard bits.'
                              ;
                  type ncd:ipv4-address ;
                  mandatory true ;
                }
              }
              case src-any {
                description 'Any IP address.'
                            ;
                leaf src-any {
                  description 'Any IP address.'
                              ;
                  type empty ;
                }
              }
            }
            leaf time-range {
              description 'Specify the existed time-range name.'
                          ;
              type string {
                length 1..31 ;
              }
            }
            choice rule-type {
              description 'Specify rule type of an IPv4 ACL.'+"\n"
                        + 'Rule types include standard type,ip type,tcp type,ud'
                        + 'p type,icmp type.'
                          ;
              case std {
                description 'Standard rule type.'
                            ;
                leaf ipv4-protocol-std {
                  description 'Standard rule type.'
                              ;
                  type empty ;
                }
              }
              case extend {
                description 'Extended rule type.'
                            ;
                container extended {
                  description 'Attributes of extended type.'
                              ;
                  choice dest-addr {
                    description 'Specify destination address.'
                                ;
                    mandatory true ;
                    case dest-ip-address {
                      description 'IP address.'
                                  ;
                      leaf dest-address {
                        description 'IP address.'
                                    ;
                        type ncd:ipv4-address ;
                        mandatory true ;
                      }
                      leaf dest-wildcard {
                        description 'IP address.'
                                    ;
                        type ncd:ipv4-address ;
                        mandatory true ;
                      }
                    }
                    case dest-any {
                      description 'Any IP address.'
                                  ;
                      leaf dest-any {
                        description 'Any IP address.'
                                    ;
                        type empty ;
                      }
                    }
                  }
                  choice priority {
                    description 'Specify the priority of packets.'+"\n"
                              + 'This is an optional node.'+"\n"
                              + 'If you set this node you can choose precedence'
                              + ', tos, or dscp.'+"\n"
                              + 'None means all case is invalid, And the defaul'
                              + 't state is none.'
                                ;
                    case precedence {
                      if-feature ipv4-mixed-pri-value ;
                      description 'Specify the precedence value.'
                                  ;
                      leaf precedence {
                        description 'Precedence value.'
                                    ;
                        type uint8 {
                          range 0..7 ;
                        }
                      }
                    }
                    case prec-range {
                      if-feature ipv4-mixed-pri-range ;
                      description 'Specify the precedence value, support single'
                                + ' precedence value or range(such as 0-7).'
                                  ;
                      leaf prec-range {
                        description 'Configure the precedence value, support si'
                                  + 'ngle precedence value or range(such as 0-7'
                                  + ').'
                                    ;
                        type acl-prec-range ;
                      }
                      ncd:revise-date 2015-04-20 ;
                    }
                    case tos {
                      description 'Specify the TOS value.'
                                  ;
                      leaf tos {
                        description 'TOS value.'
                                    ;
                        type uint8 {
                          range 0..15 ;
                        }
                      }
                    }
                    case dscp {
                      if-feature ipv4-mixed-pri-value ;
                      description 'Specify the DSCP value.'
                                  ;
                      leaf dscp {
                        description 'DSCP value.'
                                    ;
                        type uint8 {
                          range 0..63 ;
                        }
                      }
                    }
                    case dscp-range {
                      if-feature ipv4-mixed-pri-range ;
                      description 'Specify the DSCP value, support single DSCP '
                                + 'value or range(such as 0-63).'
                                  ;
                      leaf dscp-range {
                        description 'Specify the DSCP value, support single DSC'
                                  + 'P value or range(such as 0-63).'
                                    ;
                        type acl-dscp-range ;
                      }
                      ncd:revise-date 2015-04-20 ;
                    }
                  }
                  leaf fragment {
                    description 'Examine non-initial fragments of packet.'
                                ;
                    type boolean ;
                    default false ;
                  }
                  choice ipv4-protocol-type {
                    description 'IPv4 Protocol type.'
                                ;
                    mandatory true ;
                    case udp-tcp {
                      description 'Extended rule type : UDP and TCP.'
                                  ;
                      container udp-tcp {
                        description 'Extended rule type : UDP and TCP.'
                                    ;
                        choice udpOrTcp {
                          description 'Extended rule type : UDP or TCP.'
                                      ;
                          mandatory true ;
                          case udp {
                            description 'Extended rule type : UDP.'
                                        ;
                            leaf ipv4-protocol-udp {
                              description 'Extended rule type : UDP.'
                                          ;
                              type empty ;
                            }
                          }
                          case tcp {
                            description 'Extended rule type : TCP.'
                                        ;
                            leaf ipv4-protocol-tcp {
                              description 'Extended rule type : TCP.'
                                          ;
                              type empty ;
                              mandatory true ;
                            }
                            leaf established {
                              description 'Match established connections.'
                                          ;
                              type boolean ;
                              default false ;
                            }
                            leaf rst {
                              description 'Match when the RST flag set or not.'
                                          ;
                              type acl-tcp-flag ;
                            }
                            leaf ack {
                              description 'Match when the ACK flag set or not.'
                                          ;
                              type acl-tcp-flag ;
                            }
                            leaf fin {
                              description 'Match when the FIN flag set or not.'
                                          ;
                              type acl-tcp-flag ;
                            }
                            leaf syn {
                              description 'Match when the SYN flag set or not.'
                                          ;
                              type acl-tcp-flag ;
                            }
                            leaf psh {
                              description 'Match when the PSH flag set or not.'
                                          ;
                              type acl-tcp-flag ;
                            }
                            leaf urg {
                              description 'Match when the URG flag set or not.'
                                          ;
                              type acl-tcp-flag ;
                            }
                          }
                        }
                        choice src-port {
                          status obsolete {
                            ncd:revise-date 2017-07-20 ;
                          }
                          description 'Specify source port.'+"\n"
                                    + 'When the value of operator is invalid, i'
                                    + 't means match all port range,'+"\n"
                                    + 'the other value of operator means'+"\n"
                                    + 'eq(1)   : match only packets on a given '
                                    + 'port number'+"\n"
                                    + 'ge(2)   : match only packets with a no l'
                                    + 'ower port number'+"\n"
                                    + 'le(3)   : match only packets with a no g'
                                    + 'reater port number'+"\n"
                                    + 'range(7): match only packet on a given p'
                                    + 'ort range.'
                                      ;
                          case src-value {
                            status obsolete {
                              ncd:revise-date 2017-07-20 ;
                            }
                            description 'Configure port number.'
                                        ;
                            leaf src-value-operator {
                              status obsolete {
                                ncd:revise-date 2017-07-20 ;
                              }
                              description 'Operator type'+"\n"
                                        + 'eq(1)   : match only packets on a given port number'+"\n"
                                        + 'ge(2)   : match only packets with a no lower port number'+"\n"
                                        + 'le(3)   : match only packets with a no greater port number.'
                                          ;
                              type enumeration {
                                enum eq {
                                  value 1 ;
                                  description 'Equal to.'
                                              ;
                                }
                                enum ge {
                                  value 2 ;
                                  description 'Great than or equal to.'
                                              ;
                                }
                                enum le {
                                  value 3 ;
                                  description 'Less than or equal to.'
                                              ;
                                }
                              }
                              mandatory true ;
                            }
                            leaf src-port-number {
                              status obsolete {
                                ncd:revise-date 2017-07-20 ;
                              }
                              description 'Port number'+"\n"
                                        + 'Some has specific means:'+"\n"
                                        + 'bootpc       Bootstrap protocol (BOOTP) client (68)'+"\n"
                                        + 'bootps       Bootstrap protocol (BOOTP) server (67)'+"\n"
                                        + 'domain       Domain name service (DNS, 53)'+"\n"
                                        + 'ntp          Network time protocol (123)'+"\n"
                                        + 'pim-auto-rp  PIM auto-RP (496)'+"\n"
                                        + 'rip          Routing information protocol (router, in.routed, 520)'+"\n"
                                        + 'snmp         Simple network management protocol (161)'+"\n"
                                        + 'snmptrap     SNMP traps (162)'+"\n"
                                        + 'tftp         Trivial file transfer protocol (69).'
                                          ;
                              type uint16 {
                                range 0..65535 ;
                              }
                              mandatory true ;
                            }
                          }
                          case src-range {
                            status obsolete {
                              ncd:revise-date 2017-07-20 ;
                            }
                            description 'Configure port range.'
                                        ;
                            leaf src-range-operator {
                              status obsolete {
                                ncd:revise-date 2017-07-20 ;
                              }
                              description 'Operator type
range(7): match only packet on a given port range.'
                                          ;
                              type empty ;
                              mandatory true ;
                            }
                            leaf src-port-range {
                              status obsolete {
                                ncd:revise-date 2017-07-20 ;
                              }
                              description 'Port range.'
                                          ;
                              type acl-port-range ;
                              mandatory true ;
                            }
                          }
                        }
                        choice dest-port {
                          status obsolete {
                            ncd:revise-date 2017-07-20 ;
                          }
                          description 'Specify destination port.'+"\n"
                                    + 'When the value of operator is invalid, i'
                                    + 't means match all port range,'+"\n"
                                    + 'the other value of operator means'+"\n"
                                    + 'eq(1)   : match only packets on a given '
                                    + 'port number'+"\n"
                                    + 'ge(2)   : match only packets with a no l'
                                    + 'ower port number'+"\n"
                                    + 'le(3)   : match only packets with a no g'
                                    + 'reater port number'+"\n"
                                    + 'range(7): match only packet on a given p'
                                    + 'ort range.'
                                      ;
                          case dest-value {
                            status obsolete {
                              ncd:revise-date 2017-07-20 ;
                            }
                            description 'Configure port number.'
                                        ;
                            leaf dest-value-operator {
                              status obsolete {
                                ncd:revise-date 2017-07-20 ;
                              }
                              description 'Operator type'+"\n"
                                        + 'eq(1)   : match only packets on a given port number'+"\n"
                                        + 'ge(2)   : match only packets with a no lower port number'+"\n"
                                        + 'le(3)   : match only packets with a no greater port number.'
                                          ;
                              type enumeration {
                                enum eq {
                                  value 1 ;
                                  description 'Equal to.'
                                              ;
                                }
                                enum ge {
                                  value 2 ;
                                  description 'Great than or equal to.'
                                              ;
                                }
                                enum le {
                                  value 3 ;
                                  description 'Less than or equal to.'
                                              ;
                                }
                              }
                              mandatory true ;
                            }
                            leaf dest-port-number {
                              status obsolete {
                                ncd:revise-date 2017-07-20 ;
                              }
                              description 'Port number'+"\n"
                                        + 'Some has specific means:'+"\n"
                                        + 'bootpc       Bootstrap protocol (BOOTP) client (68)'+"\n"
                                        + 'bootps       Bootstrap protocol (BOOTP) server (67)'+"\n"
                                        + 'domain       Domain name service (DNS, 53)'+"\n"
                                        + 'ntp          Network time protocol (123)'+"\n"
                                        + 'pim-auto-rp  PIM auto-RP (496)'+"\n"
                                        + 'rip          Routing information protocol (router, in.routed, 520)'+"\n"
                                        + 'snmp         Simple network management protocol (161)'+"\n"
                                        + 'snmptrap     SNMP traps (162)'+"\n"
                                        + 'tftp         Trivial file transfer protocol (69).'
                                          ;
                              type uint16 {
                                range 0..65535 ;
                              }
                              mandatory true ;
                            }
                          }
                          case dest-range {
                            status obsolete {
                              ncd:revise-date 2017-07-20 ;
                            }
                            description 'Configure port range.'
                                        ;
                            leaf dest-range-operator {
                              status obsolete {
                                ncd:revise-date 2017-07-20 ;
                              }
                              description 'Operator type
range(7): match only packet on a given port range.'
                                          ;
                              type empty ;
                              mandatory true ;
                            }
                            leaf dest-port-range {
                              status obsolete {
                                ncd:revise-date 2017-07-20 ;
                              }
                              description 'Port range.'
                                          ;
                              type acl-port-range ;
                              mandatory true ;
                            }
                          }
                        }
                        container source-port {
                          description 'Specify source port.'+"\n"
                                    + 'When the value of operator is invalid, i'
                                    + 't means match all port range,'+"\n"
                                    + 'the other value of operator means'+"\n"
                                    + 'eq(1)   : match only packets on a given '
                                    + 'port number'+"\n"
                                    + 'ge(2)   : match only packets with a no l'
                                    + 'ower port number'+"\n"
                                    + 'le(3)   : match only packets with a no g'
                                    + 'reater port number'+"\n"
                                    + 'range(7): match only packet on a given p'
                                    + 'ort range.'
                                      ;
                          presence 'Specify source port'
                                   ;
                          choice source-port {
                            description 'Specify source port.'+"\n"
                                      + 'When the value of operator is invalid, it means match all port range,'+"\n"
                                      + 'the other value of operator means'+"\n"
                                      + 'eq(1)   : match only packets on a given port number'+"\n"
                                      + 'ge(2)   : match only packets with a no lower port number'+"\n"
                                      + 'le(3)   : match only packets with a no greater port number'+"\n"
                                      + 'range(7): match only packet on a given port range.'
                                        ;
                            mandatory true ;
                            case src-port-value {
                              description 'Configure port number.'
                                          ;
                              container src-port-value {
                                description 'Configure port number.'
                                            ;
                                presence 'Configure port number'
                                         ;
                                leaf src-port-operator {
                                  description 'Operator type'+"\n"
                                            + 'eq(1)   : match only packets on a given port number'+"\n"
                                            + 'ge(2)   : match only packets with a no lower port number'+"\n"
                                            + 'le(3)   : match only packets with a no greater port number.'
                                              ;
                                  type enumeration {
                                    enum eq {
                                      value 1 ;
                                      description 'Equal to.'
                                                  ;
                                    }
                                    enum ge {
                                      value 2 ;
                                      description 'Great than or equal to.'
                                                  ;
                                    }
                                    enum le {
                                      value 3 ;
                                      description 'Less than or equal to.'
                                                  ;
                                    }
                                  }
                                  mandatory true ;
                                }
                                leaf src-port-value {
                                  description 'Port number'+"\n"
                                            + 'Some has specific means:'+"\n"
                                            + 'bootpc       Bootstrap protocol (BOOTP) client (68)'+"\n"
                                            + 'bootps       Bootstrap protocol (BOOTP) server (67)'+"\n"
                                            + 'domain       Domain name service (DNS, 53)'+"\n"
                                            + 'ntp          Network time protocol (123)'+"\n"
                                            + 'pim-auto-rp  PIM auto-RP (496)'+"\n"
                                            + 'rip          Routing information protocol (router, in.routed, 520)'+"\n"
                                            + 'snmp         Simple network management protocol (161)'+"\n"
                                            + 'snmptrap     SNMP traps (162)'+"\n"
                                            + 'tftp         Trivial file transfer protocol (69).'
                                              ;
                                  type uint16 {
                                    range 0..65535 ;
                                  }
                                  mandatory true ;
                                }
                              }
                            }
                            case src-port-range {
                              description 'Configure port range.'
                                          ;
                              container src-port-range {
                                description 'Configure port range.'
                                            ;
                                presence 'Configure port range'
                                         ;
                                leaf src-port-operator {
                                  description 'Operator type
range(7): match only packet on a given port range.'
                                              ;
                                  type enumeration {
                                    enum range {
                                      value 7 ;
                                      description Range. ;
                                    }
                                  }
                                  mandatory true ;
                                }
                                leaf src-port-range {
                                  description 'Port range, support <0-65535>-<0-65535>.'
                                              ;
                                  type acl-port-range ;
                                  mandatory true ;
                                }
                              }
                            }
                          }
                          ncd:revise-date 2017-07-20 ;
                        }
                        container destination-port {
                          description 'Specify destination port.'+"\n"
                                    + 'When the value of operator is invalid, i'
                                    + 't means match all port range,'+"\n"
                                    + 'the other value of operator means'+"\n"
                                    + 'eq(1)   : match only packets on a given '
                                    + 'port number'+"\n"
                                    + 'ge(2)   : match only packets with a no l'
                                    + 'ower port number'+"\n"
                                    + 'le(3)   : match only packets with a no g'
                                    + 'reater port number'+"\n"
                                    + 'range(7): match only packet on a given p'
                                    + 'ort range.'
                                      ;
                          presence 'Specify destination port'
                                   ;
                          choice destination-port {
                            description 'Specify destination port.'+"\n"
                                      + 'When the value of operator is invalid, it means match all port range,'+"\n"
                                      + 'the other value of operator means'+"\n"
                                      + 'eq(1)   : match only packets on a given port number'+"\n"
                                      + 'ge(2)   : match only packets with a no lower port number'+"\n"
                                      + 'le(3)   : match only packets with a no greater port number'+"\n"
                                      + 'range(7): match only packet on a given port range.'
                                        ;
                            mandatory true ;
                            case dst-port-value {
                              description 'Configure port number.'
                                          ;
                              container dst-port-value {
                                description 'Configure port number.'
                                            ;
                                presence 'Configure port number'
                                         ;
                                leaf dst-port-operator {
                                  description 'Operator type'+"\n"
                                            + 'eq(1)   : match only packets on a given port number'+"\n"
                                            + 'ge(2)   : match only packets with a no lower port number'+"\n"
                                            + 'le(3)   : match only packets with a no greater port number.'
                                              ;
                                  type enumeration {
                                    enum eq {
                                      value 1 ;
                                      description 'Equal to.'
                                                  ;
                                    }
                                    enum ge {
                                      value 2 ;
                                      description 'Great than or equal to.'
                                                  ;
                                    }
                                    enum le {
                                      value 3 ;
                                      description 'Less than or equal to.'
                                                  ;
                                    }
                                  }
                                  mandatory true ;
                                }
                                leaf dst-port-value {
                                  description 'Port number'+"\n"
                                            + 'Some has specific means:'+"\n"
                                            + 'bootpc       Bootstrap protocol (BOOTP) client (68)'+"\n"
                                            + 'bootps       Bootstrap protocol (BOOTP) server (67)'+"\n"
                                            + 'domain       Domain name service (DNS, 53)'+"\n"
                                            + 'ntp          Network time protocol (123)'+"\n"
                                            + 'pim-auto-rp  PIM auto-RP (496)'+"\n"
                                            + 'rip          Routing information protocol (router, in.routed, 520)'+"\n"
                                            + 'snmp         Simple network management protocol (161)'+"\n"
                                            + 'snmptrap     SNMP traps (162)'+"\n"
                                            + 'tftp         Trivial file transfer protocol (69).'
                                              ;
                                  type uint16 {
                                    range 0..65535 ;
                                  }
                                  mandatory true ;
                                }
                              }
                            }
                            case dst-port-range {
                              description 'Configure port range.'
                                          ;
                              container dst-port-range {
                                description 'Configure port range.'
                                            ;
                                presence 'Configure port range'
                                         ;
                                leaf dst-port-operator {
                                  description 'Operator type
range(7): match only packet on a given port range.'
                                              ;
                                  type enumeration {
                                    enum range {
                                      value 7 ;
                                      description Range. ;
                                    }
                                  }
                                  mandatory true ;
                                }
                                leaf dst-port-range {
                                  description 'Port range, support <0-65535>-<0-65535>.'
                                              ;
                                  type acl-port-range ;
                                  mandatory true ;
                                }
                              }
                            }
                          }
                          ncd:revise-date 2017-07-20 ;
                        }
                      }
                    }
                    case icmp {
                      description 'Extended rule type : ICMP.'
                                  ;
                      leaf ipv4-protocol-icmp {
                        description 'Extended rule type : ICMP.'
                                    ;
                        type empty ;
                        mandatory true ;
                      }
                      container icmp-conf {
                        description 'Specify ICMP type and ICMP code.'
                                    ;
                        presence 'config icmp type and code'
                                 ;
                        leaf icmp-type {
                          description 'ICMP type'+"\n"
                                    + 'Some value has specific means'+"\n"
                                    + 'alternate-address     Alternate address '
                                    + '(6)'+"\n"
                                    + 'echo                  Echo (ping, 8)'+"\n"
                                    + 'echo-reply            Echo reply (0)'+"\n"
                                    + 'information-request   Information reques'
                                    + 'ts (15)'+"\n"
                                    + 'parameter-problem     All parameter prob'
                                    + 'lems (12)'+"\n"
                                    + 'redirect              All redirects (5)
'
                                    + ''+"\n"
                                    + 'router-advertisement  Router discovery a'
                                    + 'dvertisements (9)'+"\n"
                                    + 'router-solicitation   Router discovery s'
                                    + 'olicitations (10)'+"\n"
                                    + 'source-quench         Source quenches (4'
                                    + ')'+"\n"
                                    + 'time-exceeded         All time exceededs'
                                    + ' (11)'+"\n"
                                    + 'timestamp-reply       Timestamp replies '
                                    + '(14)'+"\n"
                                    + 'timestamp-request     Timestamp requests'
                                    + ' (13)'+"\n"
                                    + 'unreachable           All unreachables ('
                                    + '3).'
                                      ;
                          type uint16 {
                            range 0..255 ;
                          }
                          mandatory true ;
                        }
                        leaf icmp-code {
                          description 'ICMP code.'
                                      ;
                          type uint16 {
                            range 0..255 ;
                          }
                        }
                      }
                    }
                    case ip {
                      description 'Extended rule type : IP.'
                                  ;
                      leaf ipv4-protocol {
                        description 'IP protocol number'+"\n"
                                  + 'Some has specific mean:'+"\n"
                                  + 'gre      Generic Routing Encapsulation (47'
                                  + ')'+"\n"
                                  + 'icmp     Internet Control Message Protocol'
                                  + '(1)'+"\n"
                                  + 'igmp     Internet Group Management Protoco'
                                  + 'l (2)'+"\n"
                                  + 'ospf     Open Shortest Path First Protocol'
                                  + ' (89)'+"\n"
                                  + 'pim      Protocol Independent Multicast (1'
                                  + '03)'+"\n"
                                  + 'tcp      Transmission Control Protocol(6)
'
                                  + ''+"\n"
                                  + 'udp      User Datagram Protocol(17)'+"\n"
                                  + 'vrrp     Virtual Router Redundancy Protoco'
                                  + 'l (112)'+"\n"
                                  + 'ip       Any IP protocol (65535).'
                                    ;
                        type uint16 {
                          range '0 | 2..5 | 7..16 | 18..255 | 65535'
                                ;
                        }
                      }
                    }
                  }
                  leaf source-monitor-group-id {
                    description 'Specify source monitor group id.'
                                ;
                    type uint8 {
                      range 1..63 ;
                    }
                    ncd:revise-date 2020-07-13 ;
                  }
                  leaf destination-monitor-group-id {
                    description 'Specify destination monitor group id.'
                                ;
                    type uint8 {
                      range 1..63 ;
                    }
                    ncd:revise-date 2020-07-13 ;
                  }
                }
              }
            }
            leaf exp {
              description 'Configure exp, support 0-7.'
                          ;
              type uint8 {
                range 0..7 {
                  description 'Value of exp, support 0-7.'
                              ;
                }
              }
              ncd:revise-date 2019-10-08 ;
            }
            leaf label {
              description 'Configure top label.'
                          ;
              type uint32 {
                range 1..1048575 ;
              }
              ncd:revise-date 2019-10-08 ;
            }
            leaf label2 {
              description 'Configure layer2 label.'
                          ;
              type uint32 {
                range 1..1048575 ;
              }
              ncd:revise-date 2019-10-08 ;
            }
            leaf log {
              if-feature ipv4-mixed-log-config ;
              description 'If log flag is set, the matching times of this rule '
                        + 'will be recorded.'
                          ;
              type boolean ;
              default false ;
              ncd:revise-date 2019-10-08 ;
            }
            leaf v4mix-desc {
              description 'Direction for use, support 1-70 characters.'
                          ;
              type ncd:string-with-blank {
                length 1..70 {
                  description 'Direction for use, support 1-70 characters.'
                              ;
                }
              }
              ncd:revise-date 2019-12-06 ;
            }
            container policy-route-id {
              description 'Specify the policy route id.'
                          ;
              presence 'Specify the policy route id'
                       ;
              choice policy-route-id {
                description 'Policy route id, including source policy route id '
                          + 'and destination policy route id.'
                            ;
                mandatory true ;
                case src {
                  description 'Source policy route id.'
                              ;
                  container source {
                    description 'Specify the source policy route id.'
                                ;
                    presence 'Specify the source policy route id'
                             ;
                    leaf src-policy-route-id {
                      description 'Source policy route id.'
                                  ;
                      type uint8 {
                        range 1..63 ;
                      }
                      mandatory true ;
                    }
                  }
                }
                case dest {
                  description 'Destination policy route id.'
                              ;
                  container destination {
                    description 'Specify the destination policy route id.'
                                ;
                    presence 'Specify the destination policy route id'
                             ;
                    leaf dest-policy-route-id {
                      description 'Destination policy route id.'
                                  ;
                      type uint8 {
                        range 1..63 ;
                      }
                      mandatory true ;
                    }
                  }
                }
              }
              ncd:revise-date 2020-07-13 ;
            }
          }
          container acl-description {
            description 'Description of an access control list, support 1-79 ch'
                      + 'aracters.'
                        ;
            presence 'Specify acl description'
                     ;
            leaf acl-description {
              description 'Description of an access control list, support 1-79 '
                        + 'characters.'
                          ;
              type ncd:string-with-blank {
                length 1..79 {
                  description 'Description of an access control list, support 1'
                            + '-79 characters.'
                              ;
                }
              }
              mandatory true ;
            }
            ncd:revise-date 2020-06-18 ;
          }
        }
        list ipv6-access-list {
          if-feature ipv6-feature ;
          description 'Configure ipv6-access-list.'
                      ;
          key acl-name ;
          leaf acl-name {
            description 'Name of ACL.'
                        ;
            type acl-name-type ;
          }
          list rule {
            description 'Configure rule of an IPv4 ACL.'
                        ;
            key ruleid ;
            leaf ruleid {
              description 'ID of this rule.'
                          ;
              type uint32 {
                range 1..2147483644 ;
              }
            }
            choice permit-deny {
              description 'Deny  :  Specify packets to reject'+"\n"
                        + 'Permit:  Specify packets to forward.'
                          ;
              case deny {
                description 'Specify packets to reject.'
                            ;
                leaf deny {
                  description 'Specify packets to reject.'
                              ;
                  type empty ;
                  mandatory true ;
                }
              }
              case permit {
                description 'Specify packets to forward.'
                            ;
                leaf permit {
                  description 'Specify packets to forward.'
                              ;
                  type empty ;
                  mandatory true ;
                }
              }
            }
            leaf flowlabel {
              description 'Flowlabel value.'
                          ;
              type uint32 {
                range 0..1048575 ;
              }
            }
            choice src-addr {
              description 'Specify source address.'
                          ;
              case src-ip-address {
                description 'IP address.'
                            ;
                leaf src-address {
                  description 'IP address.'
                              ;
                  type ncd:ipv6-address ;
                  mandatory true ;
                }
                choice src-wildcard-type {
                  description 'Source wildcard.'
                              ;
                  case wildcard-len {
                    description 'Source wildcard length.'
                                ;
                    leaf src-wildcard {
                      description 'Source wildcard length.'
                                  ;
                      type ncd:ipv6-mask-length ;
                      mandatory true ;
                    }
                  }
                  case wildcard-bits {
                    description 'Source wildcard bits.'
                                ;
                    leaf src-wildcard-bits {
                      description 'Source wildcard bits.'
                                  ;
                      type ncd:ipv6-address ;
                      mandatory true ;
                    }
                    ncd:revise-date 2021-08-09 ;
                  }
                }
              }
              case src-any {
                description 'Any IP address.'
                            ;
                leaf src-any {
                  description 'Any IP address.'
                              ;
                  type empty ;
                  mandatory true ;
                }
              }
              case src-url {
                if-feature url-config ;
                description 'Source URL.'
                            ;
                leaf src-url {
                  description 'Source URL.'
                              ;
                  type ncd:url {
                    length 1..95 ;
                  }
                  mandatory true ;
                }
              }
            }
            choice dest-addr {
              description 'Specify destination address.'
                          ;
              case dest-ip-address {
                description 'IP address.'
                            ;
                leaf dest-address {
                  description 'IP address.'
                              ;
                  type ncd:ipv6-address ;
                  mandatory true ;
                }
                choice dest-wildcard-type {
                  description 'Destination wildcard.'
                              ;
                  case wildcard-len {
                    description 'Destination wildcard length.'
                                ;
                    leaf dest-wildcard {
                      description 'Destination wildcard length.'
                                  ;
                      type ncd:ipv6-mask-length ;
                      mandatory true ;
                    }
                  }
                  case wildcard-bits {
                    description 'Destination wildcard bits.'
                                ;
                    leaf dest-wildcard-bits {
                      description 'Destination wildcard bits.'
                                  ;
                      type ncd:ipv6-address ;
                      mandatory true ;
                    }
                    ncd:revise-date 2021-08-09 ;
                  }
                }
              }
              case dest-any {
                description 'Any IP address.'
                            ;
                leaf dest-any {
                  description 'Any IP address.'
                              ;
                  type empty ;
                  mandatory true ;
                }
              }
              case dest-url {
                if-feature url-config ;
                description 'Destination URL.'
                            ;
                leaf dest-url {
                  description 'Destination URL.'
                              ;
                  type ncd:url {
                    length 1..95 ;
                  }
                  mandatory true ;
                }
              }
            }
            leaf log {
              if-feature ipv6-log-config ;
              description 'If log flag is set, the matching times of this rule '
                        + 'will be recorded.'
                          ;
              type boolean ;
              default false ;
              ncd:revise-date 2015-04-20 ;
            }
            leaf time-range {
              description 'Specify the existed time-range name.'
                          ;
              type string {
                length 1..31 ;
              }
            }
            leaf routing {
              description 'Routing option: match if the specify IPv6 header is '
                        + 'present: true means set, and false means not.'
                          ;
              type boolean ;
              default false ;
            }
            leaf authen {
              description 'Authen option: match if the specify IPv6 header is p'
                        + 'resent: true means set, and false means not.'
                          ;
              type boolean ;
              default false ;
            }
            leaf destopts {
              description 'Destopts option: match if the specify IPv6 header is'
                        + ' present: true means set, and false means not.'
                          ;
              type boolean ;
              default false ;
            }
            leaf fragment {
              description 'Fragments option: match if the specify IPv6 header i'
                        + 's present: true means set, and false means not.'
                          ;
              type boolean ;
              default false ;
            }
            leaf hop-by-hop {
              description 'Hop-by-Hop option: match if the specify IPv6 header '
                        + 'is present: true means set, and false means not.'
                          ;
              type boolean ;
              default false ;
            }
            leaf esp {
              description 'Esp Option: match if the specify IPv6 header is pres'
                        + 'ent: true means set, and false means not.'
                          ;
              type boolean ;
              default false ;
            }
            choice dscp-tc {
              description 'DSCP or traffic-class.'
                          ;
              case dscp {
                description 'DSCP value.'
                            ;
                leaf dscp {
                  description 'DSCP value.'
                              ;
                  type uint8 {
                    range 0..63 ;
                  }
                }
                leaf dscp-range {
                  if-feature ipv6-dscp-range-config ;
                  description 'Specify the DSCP value, support single DSCP valu'
                            + 'e or range(such as 0-63).'
                              ;
                  type acl-dscp-range ;
                  ncd:revise-date 2020-08-21 ;
                }
              }
              case tc {
                description Traffic-class. ;
                leaf traffic-class {
                  description Traffic-class. ;
                  type uint16 {
                    range 0..255 ;
                  }
                }
              }
            }
            choice rule-type {
              description 'Specify rule type of an IPv4 ACL.'+"\n"
                        + 'Rule types include standard type,ip type,tcp type,ud'
                        + 'p type,icmp type.'
                          ;
              case udp-tcp {
                description 'Extended rule type : UDP and TCP.'
                            ;
                container udp-tcp {
                  description 'Extended rule type : UDP and TCP.'
                              ;
                  choice udpOrTcp {
                    description 'Extended rule type : UDP or TCP.'
                                ;
                    mandatory true ;
                    case udp {
                      description 'Extended rule type : UDP.'
                                  ;
                      leaf ipv6-protocol-udp {
                        description 'Extended rule type : UDP.'
                                    ;
                        type empty ;
                      }
                    }
                    case tcp {
                      description 'Extended rule type : TCP.'
                                  ;
                      leaf ipv6-protocol-tcp {
                        description 'Extended rule type : TCP.'
                                    ;
                        type empty ;
                        mandatory true ;
                      }
                      leaf established {
                        description 'Match established connections.'
                                    ;
                        type boolean ;
                        default false ;
                      }
                      leaf rst {
                        description 'Match when the RST flag set or not.'
                                    ;
                        type acl-tcp-flag ;
                      }
                      leaf ack {
                        description 'Match when the ACK flag set or not.'
                                    ;
                        type acl-tcp-flag ;
                      }
                      leaf fin {
                        description 'Match when the FIN flag set or not.'
                                    ;
                        type acl-tcp-flag ;
                      }
                      leaf syn {
                        description 'Match when the SYN flag set or not.'
                                    ;
                        type acl-tcp-flag ;
                      }
                      leaf psh {
                        description 'Match when the PSH flag set or not.'
                                    ;
                        type acl-tcp-flag ;
                      }
                      leaf urg {
                        description 'Match when the URG flag set or not.'
                                    ;
                        type acl-tcp-flag ;
                      }
                    }
                  }
                  choice src-port {
                    status obsolete {
                      ncd:revise-date 2017-07-20 ;
                    }
                    description 'Specify source port.'+"\n"
                              + 'When the value of operator is invalid, it mean'
                              + 's match all port range,'+"\n"
                              + 'the other value of operator means'+"\n"
                              + 'eq(1)   : match only packets on a given port n'
                              + 'umber'+"\n"
                              + 'ge(2)   : match only packets with a no lower p'
                              + 'ort number'+"\n"
                              + 'le(3)   : match only packets with a no greater'
                              + ' port number'+"\n"
                              + 'range(7): match only packet on a given port ra'
                              + 'nge.'
                                ;
                    case src-value {
                      status obsolete {
                        ncd:revise-date 2017-07-20 ;
                      }
                      description 'Configure port number.'
                                  ;
                      leaf src-value-operator {
                        status obsolete {
                          ncd:revise-date 2017-07-20 ;
                        }
                        description 'Operator type'+"\n"
                                  + 'eq(1)   : match only packets on a given po'
                                  + 'rt number'+"\n"
                                  + 'ge(2)   : match only packets with a no low'
                                  + 'er port number'+"\n"
                                  + 'le(3)   : match only packets with a no gre'
                                  + 'ater port number.'
                                    ;
                        type enumeration {
                          enum eq {
                            value 1 ;
                            description 'Equal to.'
                                        ;
                          }
                          enum ge {
                            value 2 ;
                            description 'Great than or equal to.'
                                        ;
                          }
                          enum le {
                            value 3 ;
                            description 'Less than or equal to.'
                                        ;
                          }
                        }
                        mandatory true ;
                      }
                      leaf src-port-number {
                        status obsolete {
                          ncd:revise-date 2017-07-20 ;
                        }
                        description 'Port number'+"\n"
                                  + 'Some has specific means:'+"\n"
                                  + 'bootpc       Bootstrap protocol (BOOTP) cl'
                                  + 'ient (68)'+"\n"
                                  + 'bootps       Bootstrap protocol (BOOTP) se'
                                  + 'rver (67)'+"\n"
                                  + 'domain       Domain name service (DNS, 53)'
                                  + ''+"\n"
                                  + 'ntp          Network time protocol (123)'+"\n"
                                  + 'pim-auto-rp  PIM auto-RP (496)'+"\n"
                                  + 'rip          Routing information protocol '
                                  + '(router, in.routed, 520)'+"\n"
                                  + 'snmp         Simple network management pro'
                                  + 'tocol (161)'+"\n"
                                  + 'snmptrap     SNMP traps (162)'+"\n"
                                  + 'tftp         Trivial file transfer protoco'
                                  + 'l (69).'
                                    ;
                        type uint16 {
                          range 0..65535 ;
                        }
                        mandatory true ;
                      }
                    }
                    case src-range {
                      status obsolete {
                        ncd:revise-date 2017-07-20 ;
                      }
                      description 'Configure port range.'
                                  ;
                      leaf src-range-operator {
                        status obsolete {
                          ncd:revise-date 2017-07-20 ;
                        }
                        description 'Operator type'+"\n"
                                  + 'range(7): match only packet on a given por'
                                  + 't range.'
                                    ;
                        type empty ;
                        mandatory true ;
                      }
                      leaf src-port-range {
                        status obsolete {
                          ncd:revise-date 2017-07-20 ;
                        }
                        description 'Port range.'
                                    ;
                        type acl-port-range ;
                        mandatory true ;
                      }
                    }
                  }
                  choice dest-port {
                    status obsolete {
                      ncd:revise-date 2017-07-20 ;
                    }
                    description 'Specify destination port.'+"\n"
                              + 'When the value of operator is invalid, it mean'
                              + 's match all port range,'+"\n"
                              + 'the other value of operator means'+"\n"
                              + 'eq(1)   : match only packets on a given port n'
                              + 'umber'+"\n"
                              + 'ge(2)   : match only packets with a no lower p'
                              + 'ort number'+"\n"
                              + 'le(3)   : match only packets with a no greater'
                              + ' port number'+"\n"
                              + 'range(7): match only packet on a given port ra'
                              + 'nge.'
                                ;
                    case dest-value {
                      status obsolete {
                        ncd:revise-date 2017-07-20 ;
                      }
                      description 'Configure port number.'
                                  ;
                      leaf dest-value-operator {
                        status obsolete {
                          ncd:revise-date 2017-07-20 ;
                        }
                        description 'Operator type'+"\n"
                                  + 'eq(1)   : match only packets on a given po'
                                  + 'rt number'+"\n"
                                  + 'ge(2)   : match only packets with a no low'
                                  + 'er port number'+"\n"
                                  + 'le(3)   : match only packets with a no gre'
                                  + 'ater port number.'
                                    ;
                        type enumeration {
                          enum eq {
                            value 1 ;
                            description 'Equal to.'
                                        ;
                          }
                          enum ge {
                            value 2 ;
                            description 'Great than or equal to.'
                                        ;
                          }
                          enum le {
                            value 3 ;
                            description 'Less than or equal to.'
                                        ;
                          }
                        }
                        mandatory true ;
                      }
                      leaf dest-port-number {
                        status obsolete {
                          ncd:revise-date 2017-07-20 ;
                        }
                        description 'Port number'+"\n"
                                  + 'Some has specific means:'+"\n"
                                  + 'bootpc       Bootstrap protocol (BOOTP) cl'
                                  + 'ient (68)'+"\n"
                                  + 'bootps       Bootstrap protocol (BOOTP) se'
                                  + 'rver (67)'+"\n"
                                  + 'domain       Domain name service (DNS, 53)'
                                  + ''+"\n"
                                  + 'ntp          Network time protocol (123)'+"\n"
                                  + 'pim-auto-rp  PIM auto-RP (496)'+"\n"
                                  + 'rip          Routing information protocol '
                                  + '(router, in.routed, 520)'+"\n"
                                  + 'snmp         Simple network management pro'
                                  + 'tocol (161)'+"\n"
                                  + 'snmptrap     SNMP traps (162)'+"\n"
                                  + 'tftp         Trivial file transfer protoco'
                                  + 'l (69).'
                                    ;
                        type uint16 {
                          range 0..65535 ;
                        }
                        mandatory true ;
                      }
                    }
                    case dest-range {
                      status obsolete {
                        ncd:revise-date 2017-07-20 ;
                      }
                      description 'Configure port range.'
                                  ;
                      leaf dest-range-operator {
                        status obsolete {
                          ncd:revise-date 2017-07-20 ;
                        }
                        description 'Operator type'+"\n"
                                  + 'range(7): match only packet on a given por'
                                  + 't range.'
                                    ;
                        type empty ;
                        mandatory true ;
                      }
                      leaf dest-port-range {
                        status obsolete {
                          ncd:revise-date 2017-07-20 ;
                        }
                        description 'Port range.'
                                    ;
                        type acl-port-range ;
                        mandatory true ;
                      }
                    }
                  }
                  container source-port {
                    description 'Specify source port.'+"\n"
                              + 'When the value of operator is invalid, it mean'
                              + 's match all port range,'+"\n"
                              + 'the other value of operator means'+"\n"
                              + 'eq(1)   : match only packets on a given port n'
                              + 'umber'+"\n"
                              + 'ge(2)   : match only packets with a no lower p'
                              + 'ort number'+"\n"
                              + 'le(3)   : match only packets with a no greater'
                              + ' port number'+"\n"
                              + 'range(7): match only packet on a given port ra'
                              + 'nge.'
                                ;
                    presence 'Specify source port'
                             ;
                    choice source-port {
                      description 'Specify source port.'+"\n"
                                + 'When the value of operator is invalid, it me'
                                + 'ans match all port range,'+"\n"
                                + 'the other value of operator means'+"\n"
                                + 'eq(1)   : match only packets on a given port'
                                + ' number'+"\n"
                                + 'ge(2)   : match only packets with a no lower'
                                + ' port number'+"\n"
                                + 'le(3)   : match only packets with a no great'
                                + 'er port number'+"\n"
                                + 'range(7): match only packet on a given port '
                                + 'range.'
                                  ;
                      mandatory true ;
                      case src-port-value {
                        description 'Configure port number.'
                                    ;
                        container src-port-value {
                          description 'Configure port number.'
                                      ;
                          presence 'Configure port number'
                                   ;
                          leaf src-port-operator {
                            description 'Operator type'+"\n"
                                      + 'eq(1)   : match only packets on a given port number'+"\n"
                                      + 'ge(2)   : match only packets with a no lower port number'+"\n"
                                      + 'le(3)   : match only packets with a no greater port number.'
                                        ;
                            type enumeration {
                              enum eq {
                                value 1 ;
                                description 'Equal to.'
                                            ;
                              }
                              enum ge {
                                value 2 ;
                                description 'Great than or equal to.'
                                            ;
                              }
                              enum le {
                                value 3 ;
                                description 'Less than or equal to.'
                                            ;
                              }
                            }
                            mandatory true ;
                          }
                          leaf src-port-value {
                            description 'Port number'+"\n"
                                      + 'Some has specific means:'+"\n"
                                      + 'bootpc       Bootstrap protocol (BOOTP) client (68)'+"\n"
                                      + 'bootps       Bootstrap protocol (BOOTP) server (67)'+"\n"
                                      + 'domain       Domain name service (DNS, 53)'+"\n"
                                      + 'ntp          Network time protocol (123)'+"\n"
                                      + 'pim-auto-rp  PIM auto-RP (496)'+"\n"
                                      + 'rip          Routing information protocol (router, in.routed, 520)'+"\n"
                                      + 'snmp         Simple network management protocol (161)'+"\n"
                                      + 'snmptrap     SNMP traps (162)'+"\n"
                                      + 'tftp         Trivial file transfer protocol (69).'
                                        ;
                            type uint16 {
                              range 0..65535 ;
                            }
                            mandatory true ;
                          }
                        }
                      }
                      case src-port-range {
                        description 'Configure port range.'
                                    ;
                        container src-port-range {
                          description 'Configure port range.'
                                      ;
                          presence 'Configure port range'
                                   ;
                          leaf src-port-operator {
                            description 'Operator type
range(7): match only packet on a given port range.'
                                        ;
                            type enumeration {
                              enum range {
                                value 7 ;
                                description Range. ;
                              }
                            }
                            mandatory true ;
                          }
                          leaf src-port-range {
                            description 'Port range, support <0-65535>-<0-65535>.'
                                        ;
                            type acl-port-range ;
                            mandatory true ;
                          }
                        }
                      }
                    }
                    ncd:revise-date 2017-07-20 ;
                  }
                  container destination-port {
                    description 'Specify destination port.'+"\n"
                              + 'When the value of operator is invalid, it mean'
                              + 's match all port range,'+"\n"
                              + 'the other value of operator means'+"\n"
                              + 'eq(1)   : match only packets on a given port n'
                              + 'umber'+"\n"
                              + 'ge(2)   : match only packets with a no lower p'
                              + 'ort number'+"\n"
                              + 'le(3)   : match only packets with a no greater'
                              + ' port number'+"\n"
                              + 'range(7): match only packet on a given port ra'
                              + 'nge.'
                                ;
                    presence 'Specify destination port'
                             ;
                    choice destination-port {
                      description 'Specify destination port.'+"\n"
                                + 'When the value of operator is invalid, it me'
                                + 'ans match all port range,'+"\n"
                                + 'the other value of operator means'+"\n"
                                + 'eq(1)   : match only packets on a given port'
                                + ' number'+"\n"
                                + 'ge(2)   : match only packets with a no lower'
                                + ' port number'+"\n"
                                + 'le(3)   : match only packets with a no great'
                                + 'er port number'+"\n"
                                + 'range(7): match only packet on a given port '
                                + 'range.'
                                  ;
                      mandatory true ;
                      case dst-port-value {
                        description 'Configure port number.'
                                    ;
                        container dst-port-value {
                          description 'Configure port number.'
                                      ;
                          presence 'Configure port number'
                                   ;
                          leaf dst-port-operator {
                            description 'Operator type'+"\n"
                                      + 'eq(1)   : match only packets on a given port number'+"\n"
                                      + 'ge(2)   : match only packets with a no lower port number'+"\n"
                                      + 'le(3)   : match only packets with a no greater port number.'
                                        ;
                            type enumeration {
                              enum eq {
                                value 1 ;
                                description 'Equal to.'
                                            ;
                              }
                              enum ge {
                                value 2 ;
                                description 'Great than or equal to.'
                                            ;
                              }
                              enum le {
                                value 3 ;
                                description 'Less than or equal to.'
                                            ;
                              }
                            }
                            mandatory true ;
                          }
                          leaf dst-port-value {
                            description 'Port number'+"\n"
                                      + 'Some has specific means:'+"\n"
                                      + 'bootpc       Bootstrap protocol (BOOTP) client (68)'+"\n"
                                      + 'bootps       Bootstrap protocol (BOOTP) server (67)'+"\n"
                                      + 'domain       Domain name service (DNS, 53)'+"\n"
                                      + 'ntp          Network time protocol (123)'+"\n"
                                      + 'pim-auto-rp  PIM auto-RP (496)'+"\n"
                                      + 'rip          Routing information protocol (router, in.routed, 520)'+"\n"
                                      + 'snmp         Simple network management protocol (161)'+"\n"
                                      + 'snmptrap     SNMP traps (162)'+"\n"
                                      + 'tftp         Trivial file transfer protocol (69).'
                                        ;
                            type uint16 {
                              range 0..65535 ;
                            }
                            mandatory true ;
                          }
                        }
                      }
                      case dst-port-range {
                        description 'Configure port range.'
                                    ;
                        container dst-port-range {
                          description 'Configure port range.'
                                      ;
                          presence 'Configure port range'
                                   ;
                          leaf dst-port-operator {
                            description 'Operator type
range(7): match only packet on a given port range.'
                                        ;
                            type enumeration {
                              enum range {
                                value 7 ;
                                description Range. ;
                              }
                            }
                            mandatory true ;
                          }
                          leaf dst-port-range {
                            description 'Port range, support <0-65535>-<0-65535>.'
                                        ;
                            type acl-port-range ;
                            mandatory true ;
                          }
                        }
                      }
                    }
                    ncd:revise-date 2017-07-20 ;
                  }
                }
              }
              case icmp {
                description 'Extended rule type : ICMP.'
                            ;
                leaf ipv6-protocol-icmp {
                  description 'Extended rule type : ICMP.'
                              ;
                  type empty ;
                  mandatory true ;
                }
                container icmp-conf {
                  description 'Specify ICMP type and ICMP code.'
                              ;
                  presence 'config icmp type and code'
                           ;
                  leaf icmp-type {
                    description 'ICMP type'+"\n"
                              + 'Some value has specific means'+"\n"
                              + 'alternate-address     Alternate address (6)'+"\n"
                              + 'echo                  Echo (ping, 8)'+"\n"
                              + 'echo-reply            Echo reply (0)'+"\n"
                              + 'information-request   Information requests (15'
                              + ')'+"\n"
                              + 'parameter-problem     All parameter problems ('
                              + '12)'+"\n"
                              + 'redirect              All redirects (5)'+"\n"
                              + 'router-advertisement  Router discovery adverti'
                              + 'sements (9)'+"\n"
                              + 'router-solicitation   Router discovery solicit'
                              + 'ations (10)'+"\n"
                              + 'source-quench         Source quenches (4)'+"\n"
                              + 'time-exceeded         All time exceededs (11)
'
                              + ''+"\n"
                              + 'timestamp-reply       Timestamp replies (14)'+"\n"
                              + 'timestamp-request     Timestamp requests (13)
'
                              + ''+"\n"
                              + 'unreachable           All unreachables (3).'
                                ;
                    type uint16 {
                      range 0..255 ;
                    }
                    mandatory true ;
                  }
                  leaf icmp-code {
                    description 'ICMP code.'
                                ;
                    type uint16 {
                      range 0..255 ;
                    }
                  }
                }
                container icmp-port {
                  description 'Port information.'
                              ;
                  choice src-port {
                    status obsolete {
                      ncd:revise-date 2017-07-20 ;
                    }
                    description 'Specify source port.'+"\n"
                              + 'When the value of operator is invalid, it mean'
                              + 's match all port range,'+"\n"
                              + 'the other value of operator means'+"\n"
                              + 'eq(1)   : match only packets on a given port n'
                              + 'umber'+"\n"
                              + 'ge(2)   : match only packets with a no lower p'
                              + 'ort number'+"\n"
                              + 'le(3)   : match only packets with a no greater'
                              + ' port number'+"\n"
                              + 'range(7): match only packet on a given port ra'
                              + 'nge.'
                                ;
                    case src-value {
                      status obsolete {
                        ncd:revise-date 2017-07-20 ;
                      }
                      description 'Configure port number.'
                                  ;
                      leaf src-value-operator {
                        status obsolete {
                          ncd:revise-date 2017-07-20 ;
                        }
                        description 'Operator type'+"\n"
                                  + 'eq(1)   : match only packets on a given po'
                                  + 'rt number'+"\n"
                                  + 'ge(2)   : match only packets with a no low'
                                  + 'er port number'+"\n"
                                  + 'le(3)   : match only packets with a no gre'
                                  + 'ater port number.'
                                    ;
                        type enumeration {
                          enum eq {
                            value 1 ;
                            description 'Equal to.'
                                        ;
                          }
                          enum ge {
                            value 2 ;
                            description 'Great than or equal to.'
                                        ;
                          }
                          enum le {
                            value 3 ;
                            description 'Less than or equal to.'
                                        ;
                          }
                        }
                        mandatory true ;
                      }
                      leaf src-port-number {
                        status obsolete {
                          ncd:revise-date 2017-07-20 ;
                        }
                        description 'Port number'+"\n"
                                  + 'Some has specific means:'+"\n"
                                  + 'bootpc       Bootstrap protocol (BOOTP) cl'
                                  + 'ient (68)'+"\n"
                                  + 'bootps       Bootstrap protocol (BOOTP) se'
                                  + 'rver (67)'+"\n"
                                  + 'domain       Domain name service (DNS, 53)'
                                  + ''+"\n"
                                  + 'ntp          Network time protocol (123)'+"\n"
                                  + 'pim-auto-rp  PIM auto-RP (496)'+"\n"
                                  + 'rip          Routing information protocol '
                                  + '(router, in.routed, 520)'+"\n"
                                  + 'snmp         Simple network management pro'
                                  + 'tocol (161)'+"\n"
                                  + 'snmptrap     SNMP traps (162)'+"\n"
                                  + 'tftp         Trivial file transfer protoco'
                                  + 'l (69).'
                                    ;
                        type uint16 {
                          range 0..65535 ;
                        }
                        mandatory true ;
                      }
                    }
                    case src-range {
                      status obsolete {
                        ncd:revise-date 2017-07-20 ;
                      }
                      description 'Configure port range.'
                                  ;
                      leaf src-range-operator {
                        status obsolete {
                          ncd:revise-date 2017-07-20 ;
                        }
                        description 'Operator type'+"\n"
                                  + 'range(7): match only packet on a given por'
                                  + 't range.'
                                    ;
                        type empty ;
                        mandatory true ;
                      }
                      leaf src-port-range {
                        status obsolete {
                          ncd:revise-date 2017-07-20 ;
                        }
                        description 'Port range.'
                                    ;
                        type acl-port-range ;
                        mandatory true ;
                      }
                    }
                  }
                  choice dest-port {
                    status obsolete {
                      ncd:revise-date 2017-07-20 ;
                    }
                    description 'Specify destination port.'+"\n"
                              + 'When the value of operator is invalid, it mean'
                              + 's match all port range,'+"\n"
                              + 'the other value of operator means'+"\n"
                              + 'eq(1)   : match only packets on a given port n'
                              + 'umber'+"\n"
                              + 'ge(2)   : match only packets with a no lower p'
                              + 'ort number'+"\n"
                              + 'le(3)   : match only packets with a no greater'
                              + ' port number'+"\n"
                              + 'range(7): match only packet on a given port ra'
                              + 'nge.'
                                ;
                    case dest-value {
                      status obsolete {
                        ncd:revise-date 2017-07-20 ;
                      }
                      description 'Configure port number.'
                                  ;
                      leaf dest-value-operator {
                        status obsolete {
                          ncd:revise-date 2017-07-20 ;
                        }
                        description 'Operator type'+"\n"
                                  + 'eq(1)   : match only packets on a given po'
                                  + 'rt number'+"\n"
                                  + 'ge(2)   : match only packets with a no low'
                                  + 'er port number'+"\n"
                                  + 'le(3)   : match only packets with a no gre'
                                  + 'ater port number.'
                                    ;
                        type enumeration {
                          enum eq {
                            value 1 ;
                            description 'Equal to.'
                                        ;
                          }
                          enum ge {
                            value 2 ;
                            description 'Great than or equal to.'
                                        ;
                          }
                          enum le {
                            value 3 ;
                            description 'Less than or equal to.'
                                        ;
                          }
                        }
                        mandatory true ;
                      }
                      leaf dest-port-number {
                        status obsolete {
                          ncd:revise-date 2017-07-20 ;
                        }
                        description 'Port number'+"\n"
                                  + 'Some has specific means:'+"\n"
                                  + 'bootpc       Bootstrap protocol (BOOTP) cl'
                                  + 'ient (68)'+"\n"
                                  + 'bootps       Bootstrap protocol (BOOTP) se'
                                  + 'rver (67)'+"\n"
                                  + 'domain       Domain name service (DNS, 53)'
                                  + ''+"\n"
                                  + 'ntp          Network time protocol (123)'+"\n"
                                  + 'pim-auto-rp  PIM auto-RP (496)'+"\n"
                                  + 'rip          Routing information protocol '
                                  + '(router, in.routed, 520)'+"\n"
                                  + 'snmp         Simple network management pro'
                                  + 'tocol (161)'+"\n"
                                  + 'snmptrap     SNMP traps (162)'+"\n"
                                  + 'tftp         Trivial file transfer protoco'
                                  + 'l (69).'
                                    ;
                        type uint16 {
                          range 0..65535 ;
                        }
                        mandatory true ;
                      }
                    }
                    case dest-range {
                      status obsolete {
                        ncd:revise-date 2017-07-20 ;
                      }
                      description 'Configure port range.'
                                  ;
                      leaf dest-range-operator {
                        status obsolete {
                          ncd:revise-date 2017-07-20 ;
                        }
                        description 'Operator type'+"\n"
                                  + 'range(7): match only packet on a given por'
                                  + 't range.'
                                    ;
                        type empty ;
                        mandatory true ;
                      }
                      leaf dest-port-range {
                        status obsolete {
                          ncd:revise-date 2017-07-20 ;
                        }
                        description 'Port range.'
                                    ;
                        type acl-port-range ;
                        mandatory true ;
                      }
                    }
                  }
                  container source-port {
                    description 'Specify source port.'+"\n"
                              + 'When the value of operator is invalid, it mean'
                              + 's match all port range,'+"\n"
                              + 'the other value of operator means'+"\n"
                              + 'eq(1)   : match only packets on a given port n'
                              + 'umber'+"\n"
                              + 'ge(2)   : match only packets with a no lower p'
                              + 'ort number'+"\n"
                              + 'le(3)   : match only packets with a no greater'
                              + ' port number'+"\n"
                              + 'range(7): match only packet on a given port ra'
                              + 'nge.'
                                ;
                    presence 'Specify source port'
                             ;
                    choice source-port {
                      description 'Specify source port.'+"\n"
                                + 'When the value of operator is invalid, it me'
                                + 'ans match all port range,'+"\n"
                                + 'the other value of operator means'+"\n"
                                + 'eq(1)   : match only packets on a given port'
                                + ' number'+"\n"
                                + 'ge(2)   : match only packets with a no lower'
                                + ' port number'+"\n"
                                + 'le(3)   : match only packets with a no great'
                                + 'er port number'+"\n"
                                + 'range(7): match only packet on a given port '
                                + 'range.'
                                  ;
                      mandatory true ;
                      case src-port-value {
                        description 'Configure port number.'
                                    ;
                        container src-port-value {
                          description 'Configure port number.'
                                      ;
                          presence 'Configure port number'
                                   ;
                          leaf src-port-operator {
                            description 'Operator type'+"\n"
                                      + 'eq(1)   : match only packets on a given port number'+"\n"
                                      + 'ge(2)   : match only packets with a no lower port number'+"\n"
                                      + 'le(3)   : match only packets with a no greater port number.'
                                        ;
                            type enumeration {
                              enum eq {
                                value 1 ;
                                description 'Equal to.'
                                            ;
                              }
                              enum ge {
                                value 2 ;
                                description 'Great than or equal to.'
                                            ;
                              }
                              enum le {
                                value 3 ;
                                description 'Less than or equal to.'
                                            ;
                              }
                            }
                            mandatory true ;
                          }
                          leaf src-port-value {
                            description 'Port number'+"\n"
                                      + 'Some has specific means:'+"\n"
                                      + 'bootpc       Bootstrap protocol (BOOTP) client (68)'+"\n"
                                      + 'bootps       Bootstrap protocol (BOOTP) server (67)'+"\n"
                                      + 'domain       Domain name service (DNS, 53)'+"\n"
                                      + 'ntp          Network time protocol (123)'+"\n"
                                      + 'pim-auto-rp  PIM auto-RP (496)'+"\n"
                                      + 'rip          Routing information protocol (router, in.routed, 520)'+"\n"
                                      + 'snmp         Simple network management protocol (161)'+"\n"
                                      + 'snmptrap     SNMP traps (162)'+"\n"
                                      + 'tftp         Trivial file transfer protocol (69).'
                                        ;
                            type uint16 {
                              range 0..65535 ;
                            }
                            mandatory true ;
                          }
                        }
                      }
                      case src-port-range {
                        description 'Configure port range.'
                                    ;
                        container src-port-range {
                          description 'Configure port range.'
                                      ;
                          presence 'Configure port range'
                                   ;
                          leaf src-port-operator {
                            description 'Operator type
range(7): match only packet on a given port range.'
                                        ;
                            type enumeration {
                              enum range {
                                value 7 ;
                                description Range. ;
                              }
                            }
                            mandatory true ;
                          }
                          leaf src-port-range {
                            description 'Port range, support <0-65535>-<0-65535>.'
                                        ;
                            type acl-port-range ;
                            mandatory true ;
                          }
                        }
                      }
                    }
                    ncd:revise-date 2017-07-20 ;
                  }
                  container destination-port {
                    description 'Specify destination port.'+"\n"
                              + 'When the value of operator is invalid, it mean'
                              + 's match all port range,'+"\n"
                              + 'the other value of operator means'+"\n"
                              + 'eq(1)   : match only packets on a given port n'
                              + 'umber'+"\n"
                              + 'ge(2)   : match only packets with a no lower p'
                              + 'ort number'+"\n"
                              + 'le(3)   : match only packets with a no greater'
                              + ' port number'+"\n"
                              + 'range(7): match only packet on a given port ra'
                              + 'nge.'
                                ;
                    presence 'Specify destination port'
                             ;
                    choice destination-port {
                      description 'Specify destination port.'+"\n"
                                + 'When the value of operator is invalid, it me'
                                + 'ans match all port range,'+"\n"
                                + 'the other value of operator means'+"\n"
                                + 'eq(1)   : match only packets on a given port'
                                + ' number'+"\n"
                                + 'ge(2)   : match only packets with a no lower'
                                + ' port number'+"\n"
                                + 'le(3)   : match only packets with a no great'
                                + 'er port number'+"\n"
                                + 'range(7): match only packet on a given port '
                                + 'range.'
                                  ;
                      mandatory true ;
                      case dst-port-value {
                        description 'Configure port number.'
                                    ;
                        container dst-port-value {
                          description 'Configure port number.'
                                      ;
                          presence 'Configure port number'
                                   ;
                          leaf dst-port-operator {
                            description 'Operator type'+"\n"
                                      + 'eq(1)   : match only packets on a given port number'+"\n"
                                      + 'ge(2)   : match only packets with a no lower port number'+"\n"
                                      + 'le(3)   : match only packets with a no greater port number.'
                                        ;
                            type enumeration {
                              enum eq {
                                value 1 ;
                                description 'Equal to.'
                                            ;
                              }
                              enum ge {
                                value 2 ;
                                description 'Great than or equal to.'
                                            ;
                              }
                              enum le {
                                value 3 ;
                                description 'Less than or equal to.'
                                            ;
                              }
                            }
                            mandatory true ;
                          }
                          leaf dst-port-value {
                            description 'Port number'+"\n"
                                      + 'Some has specific means:'+"\n"
                                      + 'bootpc       Bootstrap protocol (BOOTP) client (68)'+"\n"
                                      + 'bootps       Bootstrap protocol (BOOTP) server (67)'+"\n"
                                      + 'domain       Domain name service (DNS, 53)'+"\n"
                                      + 'ntp          Network time protocol (123)'+"\n"
                                      + 'pim-auto-rp  PIM auto-RP (496)'+"\n"
                                      + 'rip          Routing information protocol (router, in.routed, 520)'+"\n"
                                      + 'snmp         Simple network management protocol (161)'+"\n"
                                      + 'snmptrap     SNMP traps (162)'+"\n"
                                      + 'tftp         Trivial file transfer protocol (69).'
                                        ;
                            type uint16 {
                              range 0..65535 ;
                            }
                            mandatory true ;
                          }
                        }
                      }
                      case dst-port-range {
                        description 'Configure port range.'
                                    ;
                        container dst-port-range {
                          description 'Configure port range.'
                                      ;
                          presence 'Configure port range'
                                   ;
                          leaf dst-port-operator {
                            description 'Operator type
range(7): match only packet on a given port range.'
                                        ;
                            type enumeration {
                              enum range {
                                value 7 ;
                                description Range. ;
                              }
                            }
                            mandatory true ;
                          }
                          leaf dst-port-range {
                            description 'Port range, support <0-65535>-<0-65535>.'
                                        ;
                            type acl-port-range ;
                            mandatory true ;
                          }
                        }
                      }
                    }
                    ncd:revise-date 2017-07-20 ;
                  }
                  ncd:revise-date 2016-01-13 ;
                }
              }
              case ip {
                description 'Extended rule type : IP.'
                            ;
                leaf ipv6-protocol {
                  description 'IP protocol number'+"\n"
                            + 'Some has specific mean:'+"\n"
                            + 'gre      Generic Routing Encapsulation (47)'+"\n"
                            + 'icmp     Internet Control Message Protocol(1)'+"\n"
                            + 'igmp     Internet Group Management Protocol (2)
'
                            + ''+"\n"
                            + 'ospf     Open Shortest Path First Protocol (89)
'
                            + ''+"\n"
                            + 'pim      Protocol Independent Multicast (103)'+"\n"
                            + 'tcp      Transmission Control Protocol(6)'+"\n"
                            + 'udp      User Datagram Protocol(17)'+"\n"
                            + 'vrrp     Virtual Router Redundancy Protocol (112'
                            + ')'+"\n"
                            + 'sctp     Stream Control Transmission Protocol (1'
                            + '32)'+"\n"
                            + 'ip       Any IP protocol (65535).'
                              ;
                  type uint16 {
                    range '0..5 | 7..16 | 18..57 | 59..255 | 65535'
                          ;
                  }
                  mandatory true ;
                }
                container port {
                  description 'Port information.'
                              ;
                  choice src-port {
                    status obsolete {
                      ncd:revise-date 2017-07-20 ;
                    }
                    description 'Specify source port.'+"\n"
                              + 'When the value of operator is invalid, it mean'
                              + 's match all port range,'+"\n"
                              + 'the other value of operator means'+"\n"
                              + 'eq(1)   : match only packets on a given port n'
                              + 'umber'+"\n"
                              + 'ge(2)   : match only packets with a no lower p'
                              + 'ort number'+"\n"
                              + 'le(3)   : match only packets with a no greater'
                              + ' port number'+"\n"
                              + 'range(7): match only packet on a given port ra'
                              + 'nge.'
                                ;
                    case src-value {
                      status obsolete {
                        ncd:revise-date 2017-07-20 ;
                      }
                      description 'Configure port number.'
                                  ;
                      leaf src-value-operator {
                        status obsolete {
                          ncd:revise-date 2017-07-20 ;
                        }
                        description 'Operator type'+"\n"
                                  + 'eq(1)   : match only packets on a given po'
                                  + 'rt number'+"\n"
                                  + 'ge(2)   : match only packets with a no low'
                                  + 'er port number'+"\n"
                                  + 'le(3)   : match only packets with a no gre'
                                  + 'ater port number.'
                                    ;
                        type enumeration {
                          enum eq {
                            value 1 ;
                            description 'Equal to.'
                                        ;
                          }
                          enum ge {
                            value 2 ;
                            description 'Great than or equal to.'
                                        ;
                          }
                          enum le {
                            value 3 ;
                            description 'Less than or equal to.'
                                        ;
                          }
                        }
                        mandatory true ;
                      }
                      leaf src-port-number {
                        status obsolete {
                          ncd:revise-date 2017-07-20 ;
                        }
                        description 'Port number'+"\n"
                                  + 'Some has specific means:'+"\n"
                                  + 'bootpc       Bootstrap protocol (BOOTP) cl'
                                  + 'ient (68)'+"\n"
                                  + 'bootps       Bootstrap protocol (BOOTP) se'
                                  + 'rver (67)'+"\n"
                                  + 'domain       Domain name service (DNS, 53)'
                                  + ''+"\n"
                                  + 'ntp          Network time protocol (123)'+"\n"
                                  + 'pim-auto-rp  PIM auto-RP (496)'+"\n"
                                  + 'rip          Routing information protocol '
                                  + '(router, in.routed, 520)'+"\n"
                                  + 'snmp         Simple network management pro'
                                  + 'tocol (161)'+"\n"
                                  + 'snmptrap     SNMP traps (162)'+"\n"
                                  + 'tftp         Trivial file transfer protoco'
                                  + 'l (69).'
                                    ;
                        type uint16 {
                          range 0..65535 ;
                        }
                        mandatory true ;
                      }
                    }
                    case src-range {
                      status obsolete {
                        ncd:revise-date 2017-07-20 ;
                      }
                      description 'Configure port range.'
                                  ;
                      leaf src-range-operator {
                        status obsolete {
                          ncd:revise-date 2017-07-20 ;
                        }
                        description 'Operator type'+"\n"
                                  + 'range(7): match only packet on a given por'
                                  + 't range.'
                                    ;
                        type empty ;
                        mandatory true ;
                      }
                      leaf src-port-range {
                        status obsolete {
                          ncd:revise-date 2017-07-20 ;
                        }
                        description 'Port range.'
                                    ;
                        type acl-port-range ;
                        mandatory true ;
                      }
                    }
                  }
                  choice dest-port {
                    status obsolete {
                      ncd:revise-date 2017-07-20 ;
                    }
                    description 'Specify destination port.'+"\n"
                              + 'When the value of operator is invalid, it mean'
                              + 's match all port range,'+"\n"
                              + 'the other value of operator means'+"\n"
                              + 'eq(1)   : match only packets on a given port n'
                              + 'umber'+"\n"
                              + 'ge(2)   : match only packets with a no lower p'
                              + 'ort number'+"\n"
                              + 'le(3)   : match only packets with a no greater'
                              + ' port number'+"\n"
                              + 'range(7): match only packet on a given port ra'
                              + 'nge.'
                                ;
                    case dest-value {
                      status obsolete {
                        ncd:revise-date 2017-07-20 ;
                      }
                      description 'Configure port number.'
                                  ;
                      leaf dest-value-operator {
                        status obsolete {
                          ncd:revise-date 2017-07-20 ;
                        }
                        description 'Operator type'+"\n"
                                  + 'eq(1)   : match only packets on a given po'
                                  + 'rt number'+"\n"
                                  + 'ge(2)   : match only packets with a no low'
                                  + 'er port number'+"\n"
                                  + 'le(3)   : match only packets with a no gre'
                                  + 'ater port number.'
                                    ;
                        type enumeration {
                          enum eq {
                            value 1 ;
                            description 'Equal to.'
                                        ;
                          }
                          enum ge {
                            value 2 ;
                            description 'Great than or equal to.'
                                        ;
                          }
                          enum le {
                            value 3 ;
                            description 'Less than or equal to.'
                                        ;
                          }
                        }
                        mandatory true ;
                      }
                      leaf dest-port-number {
                        status obsolete {
                          ncd:revise-date 2017-07-20 ;
                        }
                        description 'Port number'+"\n"
                                  + 'Some has specific means:'+"\n"
                                  + 'bootpc       Bootstrap protocol (BOOTP) cl'
                                  + 'ient (68)'+"\n"
                                  + 'bootps       Bootstrap protocol (BOOTP) se'
                                  + 'rver (67)'+"\n"
                                  + 'domain       Domain name service (DNS, 53)'
                                  + ''+"\n"
                                  + 'ntp          Network time protocol (123)'+"\n"
                                  + 'pim-auto-rp  PIM auto-RP (496)'+"\n"
                                  + 'rip          Routing information protocol '
                                  + '(router, in.routed, 520)'+"\n"
                                  + 'snmp         Simple network management pro'
                                  + 'tocol (161)'+"\n"
                                  + 'snmptrap     SNMP traps (162)'+"\n"
                                  + 'tftp         Trivial file transfer protoco'
                                  + 'l (69).'
                                    ;
                        type uint16 {
                          range 0..65535 ;
                        }
                        mandatory true ;
                      }
                    }
                    case dest-range {
                      status obsolete {
                        ncd:revise-date 2017-07-20 ;
                      }
                      description 'Configure port range.'
                                  ;
                      leaf dest-range-operator {
                        status obsolete {
                          ncd:revise-date 2017-07-20 ;
                        }
                        description 'Operator type'+"\n"
                                  + 'range(7): match only packet on a given por'
                                  + 't range.'
                                    ;
                        type empty ;
                        mandatory true ;
                      }
                      leaf dest-port-range {
                        status obsolete {
                          ncd:revise-date 2017-07-20 ;
                        }
                        description 'Port range.'
                                    ;
                        type acl-port-range ;
                        mandatory true ;
                      }
                    }
                  }
                  container source-port {
                    description 'Specify source port.'+"\n"
                              + 'When the value of operator is invalid, it mean'
                              + 's match all port range,'+"\n"
                              + 'the other value of operator means'+"\n"
                              + 'eq(1)   : match only packets on a given port n'
                              + 'umber'+"\n"
                              + 'ge(2)   : match only packets with a no lower p'
                              + 'ort number'+"\n"
                              + 'le(3)   : match only packets with a no greater'
                              + ' port number'+"\n"
                              + 'range(7): match only packet on a given port ra'
                              + 'nge.'
                                ;
                    presence 'Specify source port'
                             ;
                    choice source-port {
                      description 'Specify source port.'+"\n"
                                + 'When the value of operator is invalid, it me'
                                + 'ans match all port range,'+"\n"
                                + 'the other value of operator means'+"\n"
                                + 'eq(1)   : match only packets on a given port'
                                + ' number'+"\n"
                                + 'ge(2)   : match only packets with a no lower'
                                + ' port number'+"\n"
                                + 'le(3)   : match only packets with a no great'
                                + 'er port number'+"\n"
                                + 'range(7): match only packet on a given port '
                                + 'range.'
                                  ;
                      mandatory true ;
                      case src-port-value {
                        description 'Configure port number.'
                                    ;
                        container src-port-value {
                          description 'Configure port number.'
                                      ;
                          presence 'Configure port number'
                                   ;
                          leaf src-port-operator {
                            description 'Operator type'+"\n"
                                      + 'eq(1)   : match only packets on a given port number'+"\n"
                                      + 'ge(2)   : match only packets with a no lower port number'+"\n"
                                      + 'le(3)   : match only packets with a no greater port number.'
                                        ;
                            type enumeration {
                              enum eq {
                                value 1 ;
                                description 'Equal to.'
                                            ;
                              }
                              enum ge {
                                value 2 ;
                                description 'Great than or equal to.'
                                            ;
                              }
                              enum le {
                                value 3 ;
                                description 'Less than or equal to.'
                                            ;
                              }
                            }
                            mandatory true ;
                          }
                          leaf src-port-value {
                            description 'Port number'+"\n"
                                      + 'Some has specific means:'+"\n"
                                      + 'bootpc       Bootstrap protocol (BOOTP) client (68)'+"\n"
                                      + 'bootps       Bootstrap protocol (BOOTP) server (67)'+"\n"
                                      + 'domain       Domain name service (DNS, 53)'+"\n"
                                      + 'ntp          Network time protocol (123)'+"\n"
                                      + 'pim-auto-rp  PIM auto-RP (496)'+"\n"
                                      + 'rip          Routing information protocol (router, in.routed, 520)'+"\n"
                                      + 'snmp         Simple network management protocol (161)'+"\n"
                                      + 'snmptrap     SNMP traps (162)'+"\n"
                                      + 'tftp         Trivial file transfer protocol (69).'
                                        ;
                            type uint16 {
                              range 0..65535 ;
                            }
                            mandatory true ;
                          }
                        }
                      }
                      case src-port-range {
                        description 'Configure port range.'
                                    ;
                        container src-port-range {
                          description 'Configure port range.'
                                      ;
                          presence 'Configure port range'
                                   ;
                          leaf src-port-operator {
                            description 'Operator type
range(7): match only packet on a given port range.'
                                        ;
                            type enumeration {
                              enum range {
                                value 7 ;
                                description Range. ;
                              }
                            }
                            mandatory true ;
                          }
                          leaf src-port-range {
                            description 'Port range, support <0-65535>-<0-65535>.'
                                        ;
                            type acl-port-range ;
                            mandatory true ;
                          }
                        }
                      }
                    }
                    ncd:revise-date 2017-07-20 ;
                  }
                  container destination-port {
                    description 'Specify destination port.'+"\n"
                              + 'When the value of operator is invalid, it mean'
                              + 's match all port range,'+"\n"
                              + 'the other value of operator means'+"\n"
                              + 'eq(1)   : match only packets on a given port n'
                              + 'umber'+"\n"
                              + 'ge(2)   : match only packets with a no lower p'
                              + 'ort number'+"\n"
                              + 'le(3)   : match only packets with a no greater'
                              + ' port number'+"\n"
                              + 'range(7): match only packet on a given port ra'
                              + 'nge.'
                                ;
                    presence 'Specify destination port'
                             ;
                    choice destination-port {
                      description 'Specify destination port.'+"\n"
                                + 'When the value of operator is invalid, it me'
                                + 'ans match all port range,'+"\n"
                                + 'the other value of operator means'+"\n"
                                + 'eq(1)   : match only packets on a given port'
                                + ' number'+"\n"
                                + 'ge(2)   : match only packets with a no lower'
                                + ' port number'+"\n"
                                + 'le(3)   : match only packets with a no great'
                                + 'er port number'+"\n"
                                + 'range(7): match only packet on a given port '
                                + 'range.'
                                  ;
                      mandatory true ;
                      case dst-port-value {
                        description 'Configure port number.'
                                    ;
                        container dst-port-value {
                          description 'Configure port number.'
                                      ;
                          presence 'Configure port number'
                                   ;
                          leaf dst-port-operator {
                            description 'Operator type'+"\n"
                                      + 'eq(1)   : match only packets on a given port number'+"\n"
                                      + 'ge(2)   : match only packets with a no lower port number'+"\n"
                                      + 'le(3)   : match only packets with a no greater port number.'
                                        ;
                            type enumeration {
                              enum eq {
                                value 1 ;
                                description 'Equal to.'
                                            ;
                              }
                              enum ge {
                                value 2 ;
                                description 'Great than or equal to.'
                                            ;
                              }
                              enum le {
                                value 3 ;
                                description 'Less than or equal to.'
                                            ;
                              }
                            }
                            mandatory true ;
                          }
                          leaf dst-port-value {
                            description 'Port number'+"\n"
                                      + 'Some has specific means:'+"\n"
                                      + 'bootpc       Bootstrap protocol (BOOTP) client (68)'+"\n"
                                      + 'bootps       Bootstrap protocol (BOOTP) server (67)'+"\n"
                                      + 'domain       Domain name service (DNS, 53)'+"\n"
                                      + 'ntp          Network time protocol (123)'+"\n"
                                      + 'pim-auto-rp  PIM auto-RP (496)'+"\n"
                                      + 'rip          Routing information protocol (router, in.routed, 520)'+"\n"
                                      + 'snmp         Simple network management protocol (161)'+"\n"
                                      + 'snmptrap     SNMP traps (162)'+"\n"
                                      + 'tftp         Trivial file transfer protocol (69).'
                                        ;
                            type uint16 {
                              range 0..65535 ;
                            }
                            mandatory true ;
                          }
                        }
                      }
                      case dst-port-range {
                        description 'Configure port range.'
                                    ;
                        container dst-port-range {
                          description 'Configure port range.'
                                      ;
                          presence 'Configure port range'
                                   ;
                          leaf dst-port-operator {
                            description 'Operator type
range(7): match only packet on a given port range.'
                                        ;
                            type enumeration {
                              enum range {
                                value 7 ;
                                description Range. ;
                              }
                            }
                            mandatory true ;
                          }
                          leaf dst-port-range {
                            description 'Port range, support <0-65535>-<0-65535>.'
                                        ;
                            type acl-port-range ;
                            mandatory true ;
                          }
                        }
                      }
                    }
                    ncd:revise-date 2017-07-20 ;
                  }
                  ncd:revise-date 2016-01-13 ;
                }
              }
            }
            leaf description {
              description 'Direction for use, support 1-70 characters.'
                          ;
              type ncd:string-with-blank {
                length 1..70 {
                  description 'Direction for use, support 1-70 characters.'
                              ;
                }
              }
              ncd:revise-date 2016-08-18 ;
            }
            choice vrf-config {
              description 'VPN Routing/Forwarding instance.'
                          ;
              case vrf-config-choice-clear {
                description 'Remove value of any entities which belong to any c'
                          + 'ase within this choice.'
                            ;
                container vrf-config-all-clear {
                  description 'Remove this entitiy means to remove value of any'
                            + ' entities which belong to any case within this c'
                            + 'hoice.'
                              ;
                  presence vrf-config-all-clear ;
                }
                ncd:revise-date 2020-08-17 ;
              }
              case vrf {
                description 'VPN Routing/Forwarding instance name, support 1-32'
                          + ' characters.'
                            ;
                leaf vrf {
                  description 'VPN Routing/Forwarding instance name, support 1-'
                            + '32 characters.'
                              ;
                  type acl-vrf-name ;
                }
                ncd:revise-date 2017-06-20 ;
              }
              case vrf-dcn {
                description 'DCN VRF flag.'
                            ;
                leaf vrf-dcn {
                  description 'DCN VRF flag.'
                              ;
                  type empty ;
                }
                ncd:revise-date 2020-08-17 ;
              }
              ncd:revise-date 2017-06-20 ;
            }
            container packet-length {
              description 'Configure packet length.'
                          ;
              presence 'Configure packet length'
                       ;
              choice packet-length {
                description 'Configure packet length.'
                            ;
                mandatory true ;
                case packet-length-value {
                  description 'Configure packet length, support eq, gt, lt, neq.'
                              ;
                  container packet-length-value {
                    description 'Configure packet length, support eq, gt, lt, n'
                              + 'eq.'
                                ;
                    presence 'Configure packet length'
                             ;
                    leaf packet-length-oper {
                      description 'Packet length operator, such as '+"\n"
                                + '  eq   Match only packets on a given packet '
                                + 'length'+"\n"
                                + '  gt   Match only packets with a greater pac'
                                + 'ket length'+"\n"
                                + '  lt   Match only packets with a lower packe'
                                + 't length'+"\n"
                                + '  neq  Match only packets not on a given pac'
                                + 'ket length.'
                                  ;
                      type acl-pktlen-opr ;
                      mandatory true ;
                    }
                    leaf packet-length-value {
                      description 'Packet length value, support 1-65535.'
                                  ;
                      type uint16 {
                        range 1..65535 {
                          description 'Packet length value, support 1-65535.'
                                      ;
                        }
                      }
                      mandatory true ;
                    }
                  }
                }
                case packet-length-range {
                  description 'Configure packet length, support range.'
                              ;
                  container packet-length-range {
                    description 'Configure packet length, support range.'
                                ;
                    presence 'Configure packet length'
                             ;
                    leaf packet-length-oper {
                      description 'Packet length operator, such as '+"\n"
                                + '  range   Match only packets on a given pack'
                                + 'et length range.'
                                  ;
                      type enumeration {
                        enum range {
                          value 7 ;
                          description 'Match only packets on a given packet len'
                                    + 'gth range.'
                                      ;
                        }
                      }
                      mandatory true ;
                    }
                    leaf packet-length-range {
                      description 'Packet length value range, support <1-65535>'
                                + '-<1-65535>.'
                                  ;
                      type acl-pktlen-range ;
                      mandatory true ;
                    }
                  }
                }
              }
              ncd:revise-date 2017-06-20 ;
            }
            container policy-route-id {
              description 'Specify the policy route id.'
                          ;
              presence 'Specify the policy route id'
                       ;
              choice policy-route-id {
                description 'Policy route id, including source policy route id '
                          + 'and destination policy route id.'
                            ;
                mandatory true ;
                case src {
                  description 'Source policy route id.'
                              ;
                  container source {
                    description 'Specify the source policy route id.'
                                ;
                    presence 'Specify the source policy route id'
                             ;
                    leaf src-policy-route-id {
                      description 'Source policy route id.'
                                  ;
                      type uint8 {
                        range 1..63 ;
                      }
                      mandatory true ;
                    }
                  }
                }
                case dest {
                  description 'Destination policy route id.'
                              ;
                  container destination {
                    description 'Specify the destination policy route id.'
                                ;
                    presence 'Specify the destination policy route id'
                             ;
                    leaf dest-policy-route-id {
                      description 'Destination policy route id.'
                                  ;
                      type uint8 {
                        range 1..63 ;
                      }
                      mandatory true ;
                    }
                  }
                }
              }
              ncd:revise-date 2019-09-10 ;
            }
            leaf monitor-group-id {
              description 'Specify monitor group id.'
                          ;
              type uint8 {
                range 1..63 ;
              }
              ncd:revise-date 2019-11-26 ;
            }
            leaf source-monitor-group-id {
              description 'Specify source monitor group id.'
                          ;
              type uint8 {
                range 1..63 ;
              }
              ncd:revise-date 2019-12-11 ;
            }
            container time-to-live {
              if-feature ipv6-ttl-config ;
              description 'Specify the TTL(Time To Live) value'+"\n"
                        + 'The operator value of TTL mean '+"\n"
                        + 'eq(1)   : Match only packets on a given ttl value'+"\n"
                        + 'ge(2)   : Match only packets with a no lower ttl val'
                        + 'ue'+"\n"
                        + 'le(3)   : Match only packets with a no greater ttl v'
                        + 'alue'+"\n"
                        + 'neq(6)  : Match only packets with a no equeal ttl va'
                        + 'lue'+"\n"
                        + 'range(7): Match only packet on a given ttl value ran'
                        + 'ge.'
                          ;
              presence 'Specify the TTL'
                       ;
              choice ttl {
                description 'Specify the TTL value'+"\n"
                          + 'The operator value of TTL mean '+"\n"
                          + 'eq(1)   : Match only packets on a given ttl value
'
                          + ''+"\n"
                          + 'ge(2)   : Match only packets with a no lower ttl v'
                          + 'alue'+"\n"
                          + 'le(3)   : Match only packets with a no greater ttl'
                          + ' value'+"\n"
                          + 'neq(6)  : Match only packets with a no equeal ttl '
                          + 'value'+"\n"
                          + 'range(7): Match only packet on a given ttl value r'
                          + 'ange.'
                            ;
                mandatory true ;
                case ttl-value {
                  description 'Specify the TTL value.'
                              ;
                  container ttl-value {
                    description 'Specify the TTL value.'
                                ;
                    presence 'Specify the TTL value'
                             ;
                    leaf ttl-operator {
                      description 'Operator type'+"\n"
                                + 'eq(1)   : Match only packets on a given ttl '
                                + 'value'+"\n"
                                + 'ge(2)   : Match only packets with a no lower'
                                + ' ttl value'+"\n"
                                + 'le(3)   : Match only packets with a no great'
                                + 'er ttl value'+"\n"
                                + 'neq(6)  : Match only packets with a no equea'
                                + 'l ttl value.'
                                  ;
                      type enumeration {
                        enum eq {
                          value 1 ;
                          description 'Equal to.'
                                      ;
                        }
                        enum ge {
                          value 2 ;
                          description 'Great than or equal to.'
                                      ;
                        }
                        enum le {
                          value 3 ;
                          description 'Less than or equal to.'
                                      ;
                        }
                        enum neq {
                          value 6 ;
                          description 'Not equal to.'
                                      ;
                        }
                      }
                      mandatory true ;
                    }
                    leaf ttl-value {
                      description 'TTL value, support 1-255.'
                                  ;
                      type uint8 {
                        range 1..255 {
                          description 'TTL value, support 1-255.'
                                      ;
                        }
                      }
                      mandatory true ;
                    }
                  }
                }
                case ttl-range {
                  description 'Specify the TTL range.'
                              ;
                  container ttl-range {
                    description 'Specify the TTL range.'
                                ;
                    presence 'Specify the TTL range'
                             ;
                    leaf ttl-operator {
                      description 'Operator type'+"\n"
                                + 'range(7): Match only packet on a given ttl v'
                                + 'alue range.'
                                  ;
                      type enumeration {
                        enum range {
                          value 7 ;
                          description Range. ;
                        }
                      }
                      mandatory true ;
                    }
                    leaf ttl-range {
                      description 'TTL value range, support <1-255>-<1-255>.'
                                  ;
                      type acl-ttl-range ;
                      mandatory true ;
                    }
                  }
                }
              }
              ncd:revise-date 2020-03-23 ;
            }
          }
          container acl-description {
            description 'Description of an access control list, support 1-79 ch'
                      + 'aracters.'
                        ;
            presence 'Specify acl description'
                     ;
            leaf acl-description {
              description 'Description of an access control list, support 1-79 '
                        + 'characters.'
                          ;
              type ncd:string-with-blank {
                length 1..79 {
                  description 'Description of an access control list, support 1'
                            + '-79 characters.'
                              ;
                }
              }
              mandatory true ;
            }
            ncd:revise-date 2020-06-18 ;
          }
        }
        list ipv6-mixed-access-list {
          if-feature ipv6-mixed-feature ;
          description 'Configure ipv6-mixed-access-list.'
                      ;
          key acl-name ;
          leaf acl-name {
            description 'Name of ACL.'
                        ;
            type acl-name-type ;
          }
          list rule {
            description 'Configure rule of an IPv6 mixed ACL.'
                        ;
            key ruleid ;
            leaf ruleid {
              description 'ID of this rule.'
                          ;
              type uint32 {
                range 1..2147483644 ;
              }
            }
            choice link-prot {
              description 'Specify Link protocol type.'
                          ;
              case link-protocol {
                description 'Specify Link protocol type.'
                            ;
                leaf link-protocol {
                  description 'Specify Link protocol type.'
                              ;
                  type uint32 {
                    range 1536..65535 ;
                  }
                }
              }
              case link-protocol-hex {
                if-feature link-prot-hex-config ;
                status obsolete {
                  ncd:revise-date 2017-01-04 ;
                }
                description 'Specify Link protocol type, hex.'
                            ;
                leaf link-protocol-hex {
                  description 'Specify Link protocol type, hex.'
                              ;
                  type ncd:hex ;
                }
              }
              case sap {
                if-feature sap-feature ;
                description 'Specify service access point.'
                            ;
                container dsap-ssap {
                  description 'Specify destination DSAP and SSAP.'
                              ;
                  presence 'config dsap and ssap'
                           ;
                  leaf dsap {
                    description 'Specify destination service access point.'
                                ;
                    type uint16 {
                      range 0..255 ;
                    }
                    mandatory true ;
                  }
                  leaf ssap {
                    description 'Specify source service access point.'
                                ;
                    type uint16 {
                      range 0..255 ;
                    }
                    mandatory true ;
                  }
                }
                ncd:revise-date 2017-07-12 ;
              }
            }
            choice src-mac-addr {
              description 'Specify source MAC address.'
                          ;
              case src-mac-addr {
                description 'MAC address.'
                            ;
                leaf src-mac-address {
                  description 'MAC address.'
                              ;
                  type ncd:mac-address ;
                  mandatory true ;
                }
                leaf src-mac-wildcard {
                  description 'MAC address wildcard.'
                              ;
                  type ncd:mac-address ;
                  mandatory true ;
                }
              }
              case src-mac-any {
                description 'Any MAC address.'
                            ;
                leaf src-mac-any {
                  description 'Any MAC address.'
                              ;
                  type empty ;
                }
              }
              case src-mac-range {
                if-feature mac-range-config ;
                description 'MAC address range.'
                            ;
                leaf src-mac-from1 {
                  description 'Lower limit of MAC address first range.'
                              ;
                  type ncd:mac-address ;
                  mandatory true ;
                }
                leaf src-mac-to1 {
                  description 'Upper limit of MAC address first range.'
                              ;
                  type ncd:mac-address ;
                  mandatory true ;
                }
                container src-mac-range2 {
                  description 'Second MAC address range.'
                              ;
                  presence 'config second source mac range'
                           ;
                  leaf src-mac-from2 {
                    description 'Lower limit of second MAC address range.'
                                ;
                    type ncd:mac-address ;
                    mandatory true ;
                  }
                  leaf src-mac-to2 {
                    description 'Upper limit of second MAC address range.'
                                ;
                    type ncd:mac-address ;
                    mandatory true ;
                  }
                }
              }
            }
            choice dest-mac-addr {
              description 'Specify destination MAC address.'
                          ;
              case dest-mac-addr {
                description 'MAC address.'
                            ;
                leaf dest-mac-address {
                  description 'MAC address.'
                              ;
                  type ncd:mac-address ;
                  mandatory true ;
                }
                leaf dest-mac-wildcard {
                  description 'MAC address wildcard.'
                              ;
                  type ncd:mac-address ;
                  mandatory true ;
                }
              }
              case dest-mac-any {
                description 'Any MAC address.'
                            ;
                leaf dest-mac-any {
                  description 'Any MAC address.'
                              ;
                  type empty ;
                }
              }
              case dest-mac-range {
                if-feature mac-range-config ;
                description 'MAC address range.'
                            ;
                leaf dest-mac-from1 {
                  description 'Lower limit of MAC address first range.'
                              ;
                  type ncd:mac-address ;
                  mandatory true ;
                }
                leaf dest-mac-to1 {
                  description 'Upper limit of MAC address first range.'
                              ;
                  type ncd:mac-address ;
                  mandatory true ;
                }
                container dest-mac-range2 {
                  description 'Second MAC address range.'
                              ;
                  presence 'config second destination mac range'
                           ;
                  leaf dest-mac-from2 {
                    description 'Lower limit of second MAC address range.'
                                ;
                    type ncd:mac-address ;
                    mandatory true ;
                  }
                  leaf dest-mac-to2 {
                    description 'Upper limit of second MAC address range.'
                                ;
                    type ncd:mac-address ;
                    mandatory true ;
                  }
                }
              }
            }
            leaf inner-cos {
              description 'Value of inner CoS.'
                          ;
              type uint8 {
                range 0..7 ;
              }
            }
            leaf inner-cos-range {
              if-feature ipv6-cos-range-config ;
              description 'Value of inner CoS, support single CoS value or rang'
                        + 'e(such as 0-7).'
                          ;
              type acl-cos-range ;
              ncd:revise-date 2020-08-21 ;
            }
            leaf outer-cos {
              description 'Value of outer CoS.'
                          ;
              type uint8 {
                range 0..7 ;
              }
            }
            leaf outer-cos-range {
              if-feature ipv6-cos-range-config ;
              description 'Value of outer CoS, support single CoS value or rang'
                        + 'e(such as 0-7).'
                          ;
              type acl-cos-range ;
              ncd:revise-date 2020-08-21 ;
            }
            choice vlan-conf {
              description 'Specify VLAN.'
                          ;
              case vlan-value {
                if-feature vlan-value-config ;
                description 'Specify value of VLAN.'
                            ;
                leaf inne-vlan-value {
                  description 'Specify inner VLAN.'
                              ;
                  type uint16 {
                    range 1..4094 ;
                  }
                }
                leaf outer-vlan-value {
                  description 'Specify outer VLAN.'
                              ;
                  type uint16 {
                    range 1..4094 ;
                  }
                }
              }
              case vlan-range {
                if-feature vlan-range-config ;
                description 'Specify range of VLAN.'
                            ;
                leaf inner-vlan-range {
                  description 'Specify range of inner VLAN.'
                              ;
                  type acl-vlan-range ;
                }
                leaf outer-vlan-range {
                  description 'Specify range of outer VLAN.'
                              ;
                  type acl-vlan-range ;
                }
              }
            }
            choice permit-deny {
              description 'Deny  :  Specify packets to reject'+"\n"
                        + 'Permit:  Specify packets to forward.'
                          ;
              case deny {
                description 'Specify packets to reject.'
                            ;
                leaf deny {
                  description 'Specify packets to reject.'
                              ;
                  type empty ;
                }
              }
              case permit {
                description 'Specify packets to forward.'
                            ;
                leaf permit {
                  description 'Specify packets to forward.'
                              ;
                  type empty ;
                }
              }
            }
            leaf flowlabel {
              description 'Flowlabel value.'
                          ;
              type uint32 {
                range 0..1048575 ;
              }
            }
            choice src-addr {
              description 'Specify source address.'
                          ;
              case src-ip-address {
                description 'IP address.'
                            ;
                leaf src-address {
                  description 'IP address.'
                              ;
                  type ncd:ipv6-address ;
                  mandatory true ;
                }
                choice src-wildcard-type {
                  description 'Source wildcard.'
                              ;
                  case wildcard-len {
                    description 'Source wildcard length.'
                                ;
                    leaf src-wildcard {
                      description 'Source wildcard length.'
                                  ;
                      type ncd:ipv6-mask-length ;
                      mandatory true ;
                    }
                  }
                  case wildcard-bits {
                    description 'Source wildcard bits.'
                                ;
                    leaf src-wildcard-bits {
                      description 'Source wildcard bits.'
                                  ;
                      type ncd:ipv6-address ;
                      mandatory true ;
                    }
                    ncd:revise-date 2021-08-09 ;
                  }
                }
              }
              case src-any {
                description 'Any IP address.'
                            ;
                leaf src-any {
                  description 'Any IP address.'
                              ;
                  type empty ;
                }
              }
            }
            choice dest-addr {
              description 'Specify destination address.'
                          ;
              case dest-ip-address {
                description 'IP address.'
                            ;
                leaf dest-address {
                  description 'IP address.'
                              ;
                  type ncd:ipv6-address ;
                  mandatory true ;
                }
                choice dest-wildcard-type {
                  description 'Destination wildcard.'
                              ;
                  case wildcard-len {
                    description 'Destination wildcard length.'
                                ;
                    leaf dest-wildcard {
                      description 'Destination wildcard length.'
                                  ;
                      type ncd:ipv6-mask-length ;
                      mandatory true ;
                    }
                  }
                  case wildcard-bits {
                    description 'Destination wildcard bits.'
                                ;
                    leaf dest-wildcard-bits {
                      description 'Destination wildcard bits.'
                                  ;
                      type ncd:ipv6-address ;
                      mandatory true ;
                    }
                    ncd:revise-date 2021-08-09 ;
                  }
                }
              }
              case dest-any {
                description 'Any IP address.'
                            ;
                leaf dest-any {
                  description 'Any IP address.'
                              ;
                  type empty ;
                }
              }
            }
            leaf time-range {
              description 'Specify the existed time-range name.'
                          ;
              type string {
                length 1..31 ;
              }
            }
            leaf routing {
              description 'Routing option: match if the specify IPv6 header is '
                        + 'present: true means set, and false means not.'
                          ;
              type boolean ;
              default false ;
            }
            leaf authen {
              description 'Authen option: match if the specify IPv6 header is p'
                        + 'resent: true means set, and false means not.'
                          ;
              type boolean ;
              default false ;
            }
            leaf destopts {
              description 'Destopts option: match if the specify IPv6 header is'
                        + ' present: true means set, and false means not.'
                          ;
              type boolean ;
              default false ;
            }
            leaf fragment {
              description 'Fragments option: match if the specify IPv6 header i'
                        + 's present: true means set, and false means not.'
                          ;
              type boolean ;
              default false ;
            }
            leaf hop-by-hop {
              description 'Hop-by-Hop option: match if the specify IPv6 header '
                        + 'is present: true means set, and false means not.'
                          ;
              type boolean ;
              default false ;
            }
            leaf esp {
              description 'Esp Option: match if the specify IPv6 header is pres'
                        + 'ent: true means set, and false means not.'
                          ;
              type boolean ;
              default false ;
            }
            choice dscp-tc {
              description 'DSCP or traffic-class.'
                          ;
              case dscp {
                description 'DSCP value.'
                            ;
                leaf dscp {
                  description 'DSCP value.'
                              ;
                  type uint8 {
                    range 0..63 ;
                  }
                }
                leaf dscp-range {
                  if-feature ipv6-dscp-range-config ;
                  description 'Specify the DSCP value, support single DSCP valu'
                            + 'e or range(such as 0-63).'
                              ;
                  type acl-dscp-range ;
                  ncd:revise-date 2020-08-21 ;
                }
              }
              case tc {
                description Traffic-class. ;
                leaf traffic-class {
                  description Traffic-class. ;
                  type uint16 {
                    range 0..255 ;
                  }
                }
              }
            }
            choice rule-type {
              description 'Specify rule type of an IPv4 ACL.'+"\n"
                        + 'Rule types include standard type,ip type,tcp type,ud'
                        + 'p type,icmp type.'
                          ;
              case udp-tcp {
                description 'Extended rule type : UDP and TCP.'
                            ;
                container udp-tcp {
                  description 'Extended rule type : UDP and TCP.'
                              ;
                  choice udpOrTcp {
                    description 'Extended rule type : UDP or TCP.'
                                ;
                    mandatory true ;
                    case udp {
                      description 'Extended rule type : UDP.'
                                  ;
                      leaf ipv6-protocol-udp {
                        description 'Extended rule type : UDP.'
                                    ;
                        type empty ;
                      }
                    }
                    case tcp {
                      description 'Extended rule type : TCP.'
                                  ;
                      leaf ipv6-protocol-tcp {
                        description 'Extended rule type : TCP.'
                                    ;
                        type empty ;
                        mandatory true ;
                      }
                      leaf established {
                        description 'Match established connections.'
                                    ;
                        type boolean ;
                        default false ;
                      }
                      leaf rst {
                        description 'Match when the RST flag set or not.'
                                    ;
                        type acl-tcp-flag ;
                      }
                      leaf ack {
                        description 'Match when the ACK flag set or not.'
                                    ;
                        type acl-tcp-flag ;
                      }
                      leaf fin {
                        description 'Match when the FIN flag set or not.'
                                    ;
                        type acl-tcp-flag ;
                      }
                      leaf syn {
                        description 'Match when the SYN flag set or not.'
                                    ;
                        type acl-tcp-flag ;
                      }
                      leaf psh {
                        description 'Match when the PSH flag set or not.'
                                    ;
                        type acl-tcp-flag ;
                      }
                      leaf urg {
                        description 'Match when the URG flag set or not.'
                                    ;
                        type acl-tcp-flag ;
                      }
                    }
                  }
                  choice src-port {
                    status obsolete {
                      ncd:revise-date 2017-07-20 ;
                    }
                    description 'Specify source port.'+"\n"
                              + 'When the value of operator is invalid, it mean'
                              + 's match all port range,'+"\n"
                              + 'the other value of operator means'+"\n"
                              + 'eq(1)   : match only packets on a given port n'
                              + 'umber'+"\n"
                              + 'ge(2)   : match only packets with a no lower p'
                              + 'ort number'+"\n"
                              + 'le(3)   : match only packets with a no greater'
                              + ' port number'+"\n"
                              + 'range(7): match only packet on a given port ra'
                              + 'nge.'
                                ;
                    case src-value {
                      status obsolete {
                        ncd:revise-date 2017-07-20 ;
                      }
                      description 'Configure port number.'
                                  ;
                      leaf src-value-operator {
                        status obsolete {
                          ncd:revise-date 2017-07-20 ;
                        }
                        description 'Operator type'+"\n"
                                  + 'eq(1)   : match only packets on a given po'
                                  + 'rt number'+"\n"
                                  + 'ge(2)   : match only packets with a no low'
                                  + 'er port number'+"\n"
                                  + 'le(3)   : match only packets with a no gre'
                                  + 'ater port number.'
                                    ;
                        type enumeration {
                          enum eq {
                            value 1 ;
                            description 'Equal to.'
                                        ;
                          }
                          enum ge {
                            value 2 ;
                            description 'Great than or equal to.'
                                        ;
                          }
                          enum le {
                            value 3 ;
                            description 'Less than or equal to.'
                                        ;
                          }
                        }
                        mandatory true ;
                      }
                      leaf src-port-number {
                        status obsolete {
                          ncd:revise-date 2017-07-20 ;
                        }
                        description 'Port number'+"\n"
                                  + 'Some has specific means:'+"\n"
                                  + 'bootpc       Bootstrap protocol (BOOTP) cl'
                                  + 'ient (68)'+"\n"
                                  + 'bootps       Bootstrap protocol (BOOTP) se'
                                  + 'rver (67)'+"\n"
                                  + 'domain       Domain name service (DNS, 53)'
                                  + ''+"\n"
                                  + 'ntp          Network time protocol (123)'+"\n"
                                  + 'pim-auto-rp  PIM auto-RP (496)'+"\n"
                                  + 'rip          Routing information protocol '
                                  + '(router, in.routed, 520)'+"\n"
                                  + 'snmp         Simple network management pro'
                                  + 'tocol (161)'+"\n"
                                  + 'snmptrap     SNMP traps (162)'+"\n"
                                  + 'tftp         Trivial file transfer protoco'
                                  + 'l (69).'
                                    ;
                        type uint16 {
                          range 0..65535 ;
                        }
                        mandatory true ;
                      }
                    }
                    case src-range {
                      status obsolete {
                        ncd:revise-date 2017-07-20 ;
                      }
                      description 'Configure port range.'
                                  ;
                      leaf src-range-operator {
                        status obsolete {
                          ncd:revise-date 2017-07-20 ;
                        }
                        description 'Operator type'+"\n"
                                  + 'range(7): match only packet on a given por'
                                  + 't range.'
                                    ;
                        type empty ;
                        mandatory true ;
                      }
                      leaf src-port-range {
                        status obsolete {
                          ncd:revise-date 2017-07-20 ;
                        }
                        description 'Port range.'
                                    ;
                        type acl-port-range ;
                        mandatory true ;
                      }
                    }
                  }
                  choice dest-port {
                    status obsolete {
                      ncd:revise-date 2017-07-20 ;
                    }
                    description 'Specify destination port.'+"\n"
                              + 'When the value of operator is invalid, it mean'
                              + 's match all port range,'+"\n"
                              + 'the other value of operator means'+"\n"
                              + 'eq(1)   : match only packets on a given port n'
                              + 'umber'+"\n"
                              + 'ge(2)   : match only packets with a no lower p'
                              + 'ort number'+"\n"
                              + 'le(3)   : match only packets with a no greater'
                              + ' port number'+"\n"
                              + 'range(7): match only packet on a given port ra'
                              + 'nge.'
                                ;
                    case dest-value {
                      status obsolete {
                        ncd:revise-date 2017-07-20 ;
                      }
                      description 'Configure port number.'
                                  ;
                      leaf dest-value-operator {
                        status obsolete {
                          ncd:revise-date 2017-07-20 ;
                        }
                        description 'Operator type'+"\n"
                                  + 'eq(1)   : match only packets on a given po'
                                  + 'rt number'+"\n"
                                  + 'ge(2)   : match only packets with a no low'
                                  + 'er port number'+"\n"
                                  + 'le(3)   : match only packets with a no gre'
                                  + 'ater port number.'
                                    ;
                        type enumeration {
                          enum eq {
                            value 1 ;
                            description 'Equal to.'
                                        ;
                          }
                          enum ge {
                            value 2 ;
                            description 'Great than or equal to.'
                                        ;
                          }
                          enum le {
                            value 3 ;
                            description 'Less than or equal to.'
                                        ;
                          }
                        }
                        mandatory true ;
                      }
                      leaf dest-port-number {
                        status obsolete {
                          ncd:revise-date 2017-07-20 ;
                        }
                        description 'Port number'+"\n"
                                  + 'Some has specific means:'+"\n"
                                  + 'bootpc       Bootstrap protocol (BOOTP) cl'
                                  + 'ient (68)'+"\n"
                                  + 'bootps       Bootstrap protocol (BOOTP) se'
                                  + 'rver (67)'+"\n"
                                  + 'domain       Domain name service (DNS, 53)'
                                  + ''+"\n"
                                  + 'ntp          Network time protocol (123)'+"\n"
                                  + 'pim-auto-rp  PIM auto-RP (496)'+"\n"
                                  + 'rip          Routing information protocol '
                                  + '(router, in.routed, 520)'+"\n"
                                  + 'snmp         Simple network management pro'
                                  + 'tocol (161)'+"\n"
                                  + 'snmptrap     SNMP traps (162)'+"\n"
                                  + 'tftp         Trivial file transfer protoco'
                                  + 'l (69).'
                                    ;
                        type uint16 {
                          range 0..65535 ;
                        }
                        mandatory true ;
                      }
                    }
                    case dest-range {
                      status obsolete {
                        ncd:revise-date 2017-07-20 ;
                      }
                      description 'Configure port range.'
                                  ;
                      leaf dest-range-operator {
                        status obsolete {
                          ncd:revise-date 2017-07-20 ;
                        }
                        description 'Operator type'+"\n"
                                  + 'range(7): match only packet on a given por'
                                  + 't range.'
                                    ;
                        type empty ;
                        mandatory true ;
                      }
                      leaf dest-port-range {
                        status obsolete {
                          ncd:revise-date 2017-07-20 ;
                        }
                        description 'Port range.'
                                    ;
                        type acl-port-range ;
                        mandatory true ;
                      }
                    }
                  }
                  container source-port {
                    description 'Specify source port.'+"\n"
                              + 'When the value of operator is invalid, it mean'
                              + 's match all port range,'+"\n"
                              + 'the other value of operator means'+"\n"
                              + 'eq(1)   : match only packets on a given port n'
                              + 'umber'+"\n"
                              + 'ge(2)   : match only packets with a no lower p'
                              + 'ort number'+"\n"
                              + 'le(3)   : match only packets with a no greater'
                              + ' port number'+"\n"
                              + 'range(7): match only packet on a given port ra'
                              + 'nge.'
                                ;
                    presence 'Specify source port'
                             ;
                    choice source-port {
                      description 'Specify source port.'+"\n"
                                + 'When the value of operator is invalid, it me'
                                + 'ans match all port range,'+"\n"
                                + 'the other value of operator means'+"\n"
                                + 'eq(1)   : match only packets on a given port'
                                + ' number'+"\n"
                                + 'ge(2)   : match only packets with a no lower'
                                + ' port number'+"\n"
                                + 'le(3)   : match only packets with a no great'
                                + 'er port number'+"\n"
                                + 'range(7): match only packet on a given port '
                                + 'range.'
                                  ;
                      mandatory true ;
                      case src-port-value {
                        description 'Configure port number.'
                                    ;
                        container src-port-value {
                          description 'Configure port number.'
                                      ;
                          presence 'Configure port number'
                                   ;
                          leaf src-port-operator {
                            description 'Operator type'+"\n"
                                      + 'eq(1)   : match only packets on a given port number'+"\n"
                                      + 'ge(2)   : match only packets with a no lower port number'+"\n"
                                      + 'le(3)   : match only packets with a no greater port number.'
                                        ;
                            type enumeration {
                              enum eq {
                                value 1 ;
                                description 'Equal to.'
                                            ;
                              }
                              enum ge {
                                value 2 ;
                                description 'Great than or equal to.'
                                            ;
                              }
                              enum le {
                                value 3 ;
                                description 'Less than or equal to.'
                                            ;
                              }
                            }
                            mandatory true ;
                          }
                          leaf src-port-value {
                            description 'Port number'+"\n"
                                      + 'Some has specific means:'+"\n"
                                      + 'bootpc       Bootstrap protocol (BOOTP) client (68)'+"\n"
                                      + 'bootps       Bootstrap protocol (BOOTP) server (67)'+"\n"
                                      + 'domain       Domain name service (DNS, 53)'+"\n"
                                      + 'ntp          Network time protocol (123)'+"\n"
                                      + 'pim-auto-rp  PIM auto-RP (496)'+"\n"
                                      + 'rip          Routing information protocol (router, in.routed, 520)'+"\n"
                                      + 'snmp         Simple network management protocol (161)'+"\n"
                                      + 'snmptrap     SNMP traps (162)'+"\n"
                                      + 'tftp         Trivial file transfer protocol (69).'
                                        ;
                            type uint16 {
                              range 0..65535 ;
                            }
                            mandatory true ;
                          }
                        }
                      }
                      case src-port-range {
                        description 'Configure port range.'
                                    ;
                        container src-port-range {
                          description 'Configure port range.'
                                      ;
                          presence 'Configure port range'
                                   ;
                          leaf src-port-operator {
                            description 'Operator type
range(7): match only packet on a given port range.'
                                        ;
                            type enumeration {
                              enum range {
                                value 7 ;
                                description Range. ;
                              }
                            }
                            mandatory true ;
                          }
                          leaf src-port-range {
                            description 'Port range, support <0-65535>-<0-65535>.'
                                        ;
                            type acl-port-range ;
                            mandatory true ;
                          }
                        }
                      }
                    }
                    ncd:revise-date 2017-07-20 ;
                  }
                  container destination-port {
                    description 'Specify destination port.'+"\n"
                              + 'When the value of operator is invalid, it mean'
                              + 's match all port range,'+"\n"
                              + 'the other value of operator means'+"\n"
                              + 'eq(1)   : match only packets on a given port n'
                              + 'umber'+"\n"
                              + 'ge(2)   : match only packets with a no lower p'
                              + 'ort number'+"\n"
                              + 'le(3)   : match only packets with a no greater'
                              + ' port number'+"\n"
                              + 'range(7): match only packet on a given port ra'
                              + 'nge.'
                                ;
                    presence 'Specify destination port'
                             ;
                    choice destination-port {
                      description 'Specify destination port.'+"\n"
                                + 'When the value of operator is invalid, it me'
                                + 'ans match all port range,'+"\n"
                                + 'the other value of operator means'+"\n"
                                + 'eq(1)   : match only packets on a given port'
                                + ' number'+"\n"
                                + 'ge(2)   : match only packets with a no lower'
                                + ' port number'+"\n"
                                + 'le(3)   : match only packets with a no great'
                                + 'er port number'+"\n"
                                + 'range(7): match only packet on a given port '
                                + 'range.'
                                  ;
                      mandatory true ;
                      case dst-port-value {
                        description 'Configure port number.'
                                    ;
                        container dst-port-value {
                          description 'Configure port number.'
                                      ;
                          presence 'Configure port number'
                                   ;
                          leaf dst-port-operator {
                            description 'Operator type'+"\n"
                                      + 'eq(1)   : match only packets on a given port number'+"\n"
                                      + 'ge(2)   : match only packets with a no lower port number'+"\n"
                                      + 'le(3)   : match only packets with a no greater port number.'
                                        ;
                            type enumeration {
                              enum eq {
                                value 1 ;
                                description 'Equal to.'
                                            ;
                              }
                              enum ge {
                                value 2 ;
                                description 'Great than or equal to.'
                                            ;
                              }
                              enum le {
                                value 3 ;
                                description 'Less than or equal to.'
                                            ;
                              }
                            }
                            mandatory true ;
                          }
                          leaf dst-port-value {
                            description 'Port number'+"\n"
                                      + 'Some has specific means:'+"\n"
                                      + 'bootpc       Bootstrap protocol (BOOTP) client (68)'+"\n"
                                      + 'bootps       Bootstrap protocol (BOOTP) server (67)'+"\n"
                                      + 'domain       Domain name service (DNS, 53)'+"\n"
                                      + 'ntp          Network time protocol (123)'+"\n"
                                      + 'pim-auto-rp  PIM auto-RP (496)'+"\n"
                                      + 'rip          Routing information protocol (router, in.routed, 520)'+"\n"
                                      + 'snmp         Simple network management protocol (161)'+"\n"
                                      + 'snmptrap     SNMP traps (162)'+"\n"
                                      + 'tftp         Trivial file transfer protocol (69).'
                                        ;
                            type uint16 {
                              range 0..65535 ;
                            }
                            mandatory true ;
                          }
                        }
                      }
                      case dst-port-range {
                        description 'Configure port range.'
                                    ;
                        container dst-port-range {
                          description 'Configure port range.'
                                      ;
                          presence 'Configure port range'
                                   ;
                          leaf dst-port-operator {
                            description 'Operator type
range(7): match only packet on a given port range.'
                                        ;
                            type enumeration {
                              enum range {
                                value 7 ;
                                description Range. ;
                              }
                            }
                            mandatory true ;
                          }
                          leaf dst-port-range {
                            description 'Port range, support <0-65535>-<0-65535>.'
                                        ;
                            type acl-port-range ;
                            mandatory true ;
                          }
                        }
                      }
                    }
                    ncd:revise-date 2017-07-20 ;
                  }
                }
              }
              case icmp {
                description 'Extended rule type : ICMP.'
                            ;
                leaf ipv6-protocol-icmp {
                  description 'Extended rule type : ICMP.'
                              ;
                  type empty ;
                  mandatory true ;
                }
                container icmp-conf {
                  description 'Specify ICMP type and ICMP code.'
                              ;
                  presence 'config icmp type and code'
                           ;
                  leaf icmp-type {
                    description 'ICMP type'+"\n"
                              + 'Some value has specific means'+"\n"
                              + 'alternate-address     Alternate address (6)'+"\n"
                              + 'echo                  Echo (ping, 8)'+"\n"
                              + 'echo-reply            Echo reply (0)'+"\n"
                              + 'information-request   Information requests (15'
                              + ')'+"\n"
                              + 'parameter-problem     All parameter problems ('
                              + '12)'+"\n"
                              + 'redirect              All redirects (5)'+"\n"
                              + 'router-advertisement  Router discovery adverti'
                              + 'sements (9)'+"\n"
                              + 'router-solicitation   Router discovery solicit'
                              + 'ations (10)'+"\n"
                              + 'source-quench         Source quenches (4)'+"\n"
                              + 'time-exceeded         All time exceededs (11)
'
                              + ''+"\n"
                              + 'timestamp-reply       Timestamp replies (14)'+"\n"
                              + 'timestamp-request     Timestamp requests (13)
'
                              + ''+"\n"
                              + 'unreachable           All unreachables (3).'
                                ;
                    type uint16 {
                      range 0..255 ;
                    }
                    mandatory true ;
                  }
                  leaf icmp-code {
                    description 'ICMP code.'
                                ;
                    type uint16 {
                      range 0..255 ;
                    }
                  }
                }
              }
              case ip {
                description 'Extended rule type : IP.'
                            ;
                leaf ipv6-protocol {
                  description 'IP protocol number'+"\n"
                            + 'Some has specific mean:'+"\n"
                            + 'gre      Generic Routing Encapsulation (47)'+"\n"
                            + 'icmp     Internet Control Message Protocol(1)'+"\n"
                            + 'igmp     Internet Group Management Protocol (2)
'
                            + ''+"\n"
                            + 'ospf     Open Shortest Path First Protocol (89)
'
                            + ''+"\n"
                            + 'pim      Protocol Independent Multicast (103)'+"\n"
                            + 'tcp      Transmission Control Protocol(6)'+"\n"
                            + 'udp      User Datagram Protocol(17)'+"\n"
                            + 'vrrp     Virtual Router Redundancy Protocol (112'
                            + ')'+"\n"
                            + 'ip       Any IP protocol (65535).'
                              ;
                  type uint16 {
                    range '0..5 | 7..16 | 18..57 | 59..255 | 65535'
                          ;
                  }
                }
              }
            }
            leaf v6mix-desc {
              description 'Direction for use, support 1-70 characters.'
                          ;
              type ncd:string-with-blank {
                length 1..70 {
                  description 'Direction for use, support 1-70 characters.'
                              ;
                }
              }
              ncd:revise-date 2019-12-06 ;
            }
            leaf log {
              if-feature ipv6-mixed-log-config ;
              description 'If log flag is set, the matching times of this rule '
                        + 'will be recorded.'
                          ;
              type boolean ;
              default false ;
              ncd:revise-date 2021-06-03 ;
            }
            leaf exp {
              description 'Configure exp, support 0-7.'
                          ;
              type uint8 {
                range 0..7 {
                  description 'Value of exp, support 0-7.'
                              ;
                }
              }
              ncd:revise-date 2021-08-04 ;
            }
          }
          container acl-description {
            description 'Description of an access control list, support 1-79 ch'
                      + 'aracters.'
                        ;
            presence 'Specify acl description'
                     ;
            leaf acl-description {
              description 'Description of an access control list, support 1-79 '
                        + 'characters.'
                          ;
              type ncd:string-with-blank {
                length 1..79 {
                  description 'Description of an access control list, support 1'
                            + '-79 characters.'
                              ;
                }
              }
              mandatory true ;
            }
            ncd:revise-date 2020-06-29 ;
          }
        }
        list link-access-list {
          if-feature link-feature ;
          description 'Configure link-access-list.'
                      ;
          key acl-name ;
          leaf acl-name {
            description 'Name of ACL.'
                        ;
            type acl-name-type ;
          }
          list rule {
            description 'Configure rule of an IPv4 mixed ACL.'
                        ;
            key ruleid ;
            leaf ruleid {
              description 'ID of this rule.'
                          ;
              type uint32 {
                range 1..2147483644 ;
              }
            }
            choice permit-deny {
              description 'Deny  :  Specify packets to reject'+"\n"
                        + 'Permit:  Specify packets to forward.'
                          ;
              case deny {
                description 'Specify packets to reject.'
                            ;
                leaf deny {
                  description 'Specify packets to reject.'
                              ;
                  type empty ;
                  mandatory true ;
                }
              }
              case permit {
                description 'Specify packets to forward.'
                            ;
                leaf permit {
                  description 'Specify packets to forward.'
                              ;
                  type empty ;
                  mandatory true ;
                }
              }
            }
            choice link-prot {
              description 'Specify Link protocol type.'
                          ;
              case link-protocol {
                description 'Specify Link protocol type.'
                            ;
                leaf link-protocol {
                  description 'Specify Link protocol type.'
                              ;
                  type uint32 {
                    range 1536..65535 ;
                  }
                }
                leaf link-protocol-mask {
                  description 'Specify Link protocol mask, hex.'
                              ;
                  type ncd:hex {
                    length 3..6 ;
                  }
                  ncd:revise-date 2017-06-02 ;
                }
              }
              case link-protocol-hex {
                if-feature link-prot-hex-config ;
                description 'Specify Link protocol type, hex.'
                            ;
                leaf link-protocol-hex {
                  description 'Specify Link protocol type, hex.'
                              ;
                  type ncd:hex ;
                }
                leaf link-protocol-hex-mask {
                  description 'Specify Link protocol mask, hex.'
                              ;
                  type ncd:hex {
                    length 3..6 ;
                  }
                  ncd:revise-date 2017-06-02 ;
                }
              }
              case sap {
                if-feature sap-feature ;
                description 'Specify service access point.'
                            ;
                container dsap-ssap {
                  description 'Specify destination DSAP and SSAP.'
                              ;
                  presence 'config dsap and ssap'
                           ;
                  leaf dsap {
                    description 'Specify destination service access point.'
                                ;
                    type uint16 {
                      range 0..255 ;
                    }
                    mandatory true ;
                  }
                  leaf ssap {
                    description 'Specify source service access point.'
                                ;
                    type uint16 {
                      range 0..255 ;
                    }
                    mandatory true ;
                  }
                }
                ncd:revise-date 2017-07-12 ;
              }
            }
            choice src-mac-addr {
              description 'Specify source MAC address.'
                          ;
              case src-mac-addr {
                description 'MAC address.'
                            ;
                leaf src-mac-address {
                  description 'MAC address.'
                              ;
                  type ncd:mac-address ;
                  mandatory true ;
                }
                leaf src-mac-wildcard {
                  description 'MAC address wildcard.'
                              ;
                  type ncd:mac-address ;
                  mandatory true ;
                }
              }
              case src-mac-any {
                description 'Any MAC address.'
                            ;
                leaf src-mac-any {
                  description 'Any MAC address.'
                              ;
                  type empty ;
                  mandatory true ;
                }
              }
              case src-mac-range {
                if-feature mac-range-config ;
                description 'MAC address range.'
                            ;
                leaf src-mac-from1 {
                  description 'Lower limit of MAC address first range.'
                              ;
                  type ncd:mac-address ;
                  mandatory true ;
                }
                leaf src-mac-to1 {
                  description 'Upper limit of MAC address first range.'
                              ;
                  type ncd:mac-address ;
                  mandatory true ;
                }
                container src-mac-range2 {
                  description 'Second MAC address range.'
                              ;
                  presence 'config second source mac range'
                           ;
                  leaf src-mac-from2 {
                    description 'Lower limit of second MAC address range.'
                                ;
                    type ncd:mac-address ;
                    mandatory true ;
                  }
                  leaf src-mac-to2 {
                    description 'Upper limit of second MAC address range.'
                                ;
                    type ncd:mac-address ;
                    mandatory true ;
                  }
                }
              }
            }
            choice dest-mac-addr {
              description 'Specify destination MAC address.'
                          ;
              case dest-mac-addr {
                description 'MAC address.'
                            ;
                leaf dest-mac-address {
                  description 'MAC address.'
                              ;
                  type ncd:mac-address ;
                  mandatory true ;
                }
                leaf dest-mac-wildcard {
                  description 'MAC address wildcard.'
                              ;
                  type ncd:mac-address ;
                  mandatory true ;
                }
              }
              case dest-mac-any {
                description 'Any MAC address.'
                            ;
                leaf dest-mac-any {
                  description 'Any MAC address.'
                              ;
                  type empty ;
                  mandatory true ;
                }
              }
              case dest-mac-range {
                if-feature mac-range-config ;
                description 'MAC address range.'
                            ;
                leaf dest-mac-from1 {
                  description 'Lower limit of MAC address first range.'
                              ;
                  type ncd:mac-address ;
                  mandatory true ;
                }
                leaf dest-mac-to1 {
                  description 'Upper limit of MAC address first range.'
                              ;
                  type ncd:mac-address ;
                  mandatory true ;
                }
                container dest-mac-range2 {
                  description 'Second MAC address range.'
                              ;
                  presence 'config second destination mac range'
                           ;
                  leaf dest-mac-from2 {
                    description 'Lower limit of second MAC address range.'
                                ;
                    type ncd:mac-address ;
                    mandatory true ;
                  }
                  leaf dest-mac-to2 {
                    description 'Upper limit of second MAC address range.'
                                ;
                    type ncd:mac-address ;
                    mandatory true ;
                  }
                }
              }
            }
            leaf inner-cos {
              if-feature link-cos-value ;
              description 'Value of inner CoS.'
                          ;
              type uint8 {
                range 0..7 ;
              }
            }
            leaf inner-cos-range {
              if-feature link-cos-range ;
              description 'Value of inner CoS, support single CoS value or rang'
                        + 'e(such as 0-7).'
                          ;
              type acl-cos-range ;
              ncd:revise-date 2015-04-20 ;
            }
            leaf outer-cos {
              if-feature link-cos-value ;
              description 'Value of outer CoS.'
                          ;
              type uint8 {
                range 0..7 ;
              }
            }
            leaf outer-cos-range {
              if-feature link-cos-range ;
              description 'Value of outer CoS, support single CoS value or rang'
                        + 'e(such as 0-7).'
                          ;
              type acl-cos-range ;
              ncd:revise-date 2015-04-20 ;
            }
            choice vlan-conf {
              description 'Specify VLAN.'
                          ;
              case vlan-value {
                if-feature vlan-value-config ;
                description 'Specify value of VLAN.'
                            ;
                leaf inne-vlan-value {
                  description 'Specify inner VLAN.'
                              ;
                  type uint16 {
                    range 1..4094 ;
                  }
                }
                leaf outer-vlan-value {
                  description 'Specify outer VLAN.'
                              ;
                  type uint16 {
                    range 1..4094 ;
                  }
                }
              }
              case vlan-range {
                if-feature vlan-range-config ;
                description 'Specify range of VLAN.'
                            ;
                leaf inner-vlan-range {
                  description 'Specify range of inner VLAN.'
                              ;
                  type acl-vlan-range ;
                }
                leaf cfi {
                  description 'Match on CFI(Canonical Format Indicator).'
                              ;
                  type enumeration {
                    enum set {
                      value 1 ;
                      description 'Match when the flag is set.'
                                  ;
                    }
                    enum unset {
                      value 0 ;
                      description 'Match when the flag is not set.'
                                  ;
                    }
                  }
                  ncd:revise-date 2017-06-20 ;
                }
                leaf outer-vlan-range {
                  description 'Specify range of outer VLAN.'
                              ;
                  type acl-vlan-range ;
                }
                leaf dei {
                  description 'Match on DEI(Drop EligibleIndicator).'
                              ;
                  type enumeration {
                    enum set {
                      value 1 ;
                      description 'Match when the flag is set.'
                                  ;
                    }
                    enum unset {
                      value 0 ;
                      description 'Match when the flag is not set.'
                                  ;
                    }
                  }
                  ncd:revise-date 2017-06-20 ;
                }
              }
            }
            leaf time-range {
              description 'Specify the existed time-range name.'
                          ;
              type string {
                length 1..31 ;
              }
            }
            leaf log {
              if-feature link-log-config ;
              description 'If log flag is set, the matching times of this rule '
                        + 'will be recorded.'
                          ;
              type boolean ;
              default false ;
              ncd:revise-date 2015-04-20 ;
            }
            leaf description {
              description 'Direction for use, support 1-70 characters.'
                          ;
              type ncd:string-with-blank {
                length 1..70 {
                  description 'Direction for use, support 1-70 characters.'
                              ;
                }
              }
              ncd:revise-date 2016-08-18 ;
            }
            leaf vrf {
              description 'VPN Routing/Forwarding instance name, support 1-32 c'
                        + 'haracters.'
                          ;
              type acl-vrf-name {
                length 1..32 {
                  description 'VPN Routing/Forwarding instance name, support 1-'
                            + '32 characters.'
                              ;
                }
              }
              ncd:revise-date 2017-06-20 ;
            }
            leaf exp {
              description 'Configure exp, support 0-7.'
                          ;
              type uint8 {
                range 0..7 {
                  description 'Value of exp, support 0-7.'
                              ;
                }
              }
              ncd:revise-date 2017-06-20 ;
            }
            leaf label {
              description 'Configure top label.'
                          ;
              type uint32 {
                range 1..1048575 ;
              }
              ncd:revise-date 2019-06-18 ;
            }
            leaf label2 {
              description 'Configure layer2 label.'
                          ;
              type uint32 {
                range 1..1048575 ;
              }
              ncd:revise-date 2019-06-18 ;
            }
          }
        }
        list user-protocol-access-list {
          if-feature user-protocol-feature ;
          description 'Configure user protocol ACL.'
                      ;
          key acl-name ;
          leaf acl-name {
            description 'Name of ACL.'
                        ;
            type acl-name-type ;
          }
          list rule {
            description 'Configure rule of a user protocol ACL.'
                        ;
            key ruleid ;
            leaf ruleid {
              description 'ID of this rule.'
                          ;
              type uint32 {
                range 1..2147483644 ;
              }
            }
            choice ethernet-type {
              description 'Specify ethernet type value or any ethernet type.'
                          ;
              mandatory true ;
              case any-ethernet-type {
                description 'Any ethernet type.'
                            ;
                leaf any {
                  description 'Any ethernet type.'
                              ;
                  type empty ;
                }
              }
              case ethernet-type-value {
                description 'Specify ethernet type value.'
                            ;
                leaf ether-type {
                  description 'Specify ethernet type.'
                              ;
                  type ncd:hex {
                    pattern '((0x){1}([1-9]|[a-f]|[A-F]){1}([0-9]|[a-f]|[A-F]){'
                          + '0,3})'
                            ;
                  }
                }
              }
            }
            leaf destination-mac {
              description 'Destination MAC address.'
                          ;
              type ncd:mac-address ;
              mandatory true ;
            }
            leaf destination-mac-wildcard {
              description 'Destination MAC address wildcard.'
                          ;
              type ncd:mac-address ;
              mandatory true ;
            }
          }
          ncd:revise-date 2015-11-04 ;
        }
        list user-defined-list {
          if-feature user-defined-feature ;
          description 'Configure user-defined-access-list.'
                      ;
          key acl-name ;
          leaf acl-name {
            description 'Name of ACL.'
                        ;
            type acl-name-type ;
          }
          list rule {
            description 'Configure rule of a user defined ACL.'
                        ;
            key ruleid ;
            leaf ruleid {
              description 'ID of this rule.'
                          ;
              type uint32 {
                range 1..2147483644 ;
              }
            }
            choice permit-deny {
              description 'Deny  :  Specify packets to reject'+"\n"
                        + 'Permit:  Specify packets to forward.'
                          ;
              mandatory true ;
              case deny {
                description 'Deny  :  Specify packets to reject.'
                            ;
                leaf deny {
                  description 'Deny  :  Specify packets to reject.'
                              ;
                  type empty ;
                }
              }
              case permit {
                description 'Specify packets to forward.'
                            ;
                leaf permit {
                  description 'Specify packets to forward.'
                              ;
                  type empty ;
                  mandatory true ;
                }
              }
            }
            leaf frame-type {
              description 'Type of ethernet frame.'
                          ;
              type enumeration {
                enum any {
                  value 4 ;
                  description 'Any frame.'
                              ;
                }
                enum ethernet2 {
                  value 1 ;
                  description 'Ethernet version II frame.'
                              ;
                }
                enum llc-snap {
                  value 2 ;
                  description 'LLC/SNAP frame in IEEE802.3.'
                              ;
                }
                enum sap {
                  value 3 ;
                  description 'SAP frame in IEEE802.3.'
                              ;
                }
              }
              mandatory true ;
            }
            leaf tag-status {
              description 'Status of VLAN tag.'
                          ;
              type enumeration {
                enum untag {
                  value 1 ;
                  description 'Status with no VLAN tag.'
                              ;
                }
                enum single-tag {
                  value 2 ;
                  description 'Status with VLAN tag.'
                              ;
                }
                enum double-tag {
                  value 3 ;
                  description 'Status with outer and inner VLAN tag.'
                              ;
                }
                enum any {
                  value 4 ;
                  description 'Any status with VLAN tag.'
                              ;
                }
              }
              mandatory true ;
            }
            leaf ip-flag {
              description 'Type of ip packet header.'
                          ;
              type enumeration {
                enum ip4-hdr-only {
                  value 1 ;
                  description 'Segment of only IPv4 header.'
                              ;
                }
                enum ip6-hdr-only {
                  value 2 ;
                  description 'Segment of only IPv6 header.'
                              ;
                }
                enum ip6-fragment {
                  value 3 ;
                  description 'Segment of IPv6 fragment.'
                              ;
                }
                enum ip4-over-ip4 {
                  value 4 ;
                  description 'Segment of IPv4 datagram over IPv4.'
                              ;
                }
                enum ip6-over-ip4 {
                  value 5 ;
                  description 'Segment of IPv6 datagram over IPv4'
                              ;
                }
                enum ip6-fragment-over-ip4 {
                  value 6 ;
                  description 'Segment of IPv6 fragment datagram over IPv4.'
                              ;
                }
                enum ip4-over-ip6 {
                  value 7 ;
                  description 'Segment of IPv4 datagram over IPv6.'
                              ;
                }
                enum ip6-over-ip6 {
                  value 8 ;
                  description 'Segment of IPv6 datagram over IPv6.'
                              ;
                }
                enum gre-ip4-over-ip4 {
                  value 9 ;
                  description 'Segment of IPv4 datagram over IPv4 by GRE.'
                              ;
                }
                enum gre-ip6-over-ip4 {
                  value 10 ;
                  description 'Segment of IPv6 datagram over IPv4 by GRE.'
                              ;
                }
                enum gre-ip4-over-ip6 {
                  value 11 ;
                  description 'Segment of IPv4 datagram over IPv6 by GRE.'
                              ;
                }
                enum gre-ip6-over-ip6 {
                  value 12 ;
                  description 'Segment of IPv6 datagram over IPv6 by GRE.'
                              ;
                }
                enum ip-unused {
                  value 13 ;
                  description 'None IP format datagram.'
                              ;
                }
                enum one-mpls-label {
                  value 14 ;
                  description 'Segment of the first label out of tunnel.'
                              ;
                }
                enum two-mpls-labels {
                  value 15 ;
                  description 'Segment of the second label in tunnel.'
                              ;
                }
                enum any-mpls-labels {
                  value 16 ;
                  description 'Segment of any or multiple MPLS label.'
                              ;
                }
                enum any {
                  value 17 ;
                  description 'Any segment'
                              ;
                }
              }
              mandatory true ;
            }
            choice segment-type {
              description 'Type of rule segment.'
                          ;
              mandatory true ;
              case any-segment {
                description 'Any rule segment.'
                            ;
                leaf any {
                  description 'Any rule segment.'
                              ;
                  type empty ;
                  mandatory true ;
                }
              }
              case segment {
                description 'Rule segment.'
                            ;
                container segment1 {
                  description 'Rule segment one.'
                              ;
                  leaf offset {
                    description 'Offset from packet head (2+4*n, n = 0, 1, 2, .'
                              + '..).'
                                ;
                    type uint32 {
                      range 2..126 ;
                    }
                    mandatory true ;
                  }
                  leaf rule-string {
                    description 'User defined hexadecimal string,as follows:'+"\n"
                              + '0x00000000-0xffffffff.'
                                ;
                    type string {
                      length 10 {
                        description 'User defined hexadecimal string,as follows'
                                  + ':'+"\n"
                                  + '0x00000000-0xffffffff.'
                                    ;
                      }
                    }
                    mandatory true ;
                  }
                  leaf rule-mask {
                    description 'User defined hexadecimal string mask,as follow'
                              + 's:'+"\n"
                              + '0x00000000-0xffffffff.'
                                ;
                    type string {
                      length 10 {
                        description 'User defined hexadecimal string mask,as fo'
                                  + 'llows:'+"\n"
                                  + '0x00000000-0xffffffff.'
                                    ;
                      }
                    }
                    mandatory true ;
                  }
                  container segment2 {
                    description 'Rule segment two.'
                                ;
                    presence segment2 ;
                    leaf offset {
                      description 'Offset from packet head (2+4*n, n = 0, 1, 2,'
                                + ' ...).'
                                  ;
                      type uint32 {
                        range 2..126 ;
                      }
                      mandatory true ;
                    }
                    leaf rule-string {
                      description 'User defined hexadecimal string,as follows:
'
                                + ''+"\n"
                                + '0x00000000-0xffffffff.'
                                  ;
                      type string {
                        length 10 {
                          description 'User defined hexadecimal string,as follo'
                                    + 'ws:'+"\n"
                                    + '0x00000000-0xffffffff.'
                                      ;
                        }
                      }
                      mandatory true ;
                    }
                    leaf rule-mask {
                      description 'User defined hexadecimal string mask,as foll'
                                + 'ows:'+"\n"
                                + '0x00000000-0xffffffff.'
                                  ;
                      type string {
                        length 10 {
                          description 'User defined hexadecimal string mask,as '
                                    + 'follows:'+"\n"
                                    + '0x00000000-0xffffffff.'
                                      ;
                        }
                      }
                      mandatory true ;
                    }
                    container segment3 {
                      description 'Rule segment three.'
                                  ;
                      presence segment3 ;
                      leaf offset {
                        description 'Offset from packet head (2+4*n, n = 0, 1, '
                                  + '2, ...).'
                                    ;
                        type uint32 {
                          range 2..126 ;
                        }
                        mandatory true ;
                      }
                      leaf rule-string {
                        description 'User defined hexadecimal string,as follows'
                                  + ':'+"\n"
                                  + '0x00000000-0xffffffff.'
                                    ;
                        type string {
                          length 10 {
                            description 'User defined hexadecimal string,as follows:
0x00000000-0xffffffff.'
                                        ;
                          }
                        }
                        mandatory true ;
                      }
                      leaf rule-mask {
                        description 'User defined hexadecimal string mask,as fo'
                                  + 'llows:'+"\n"
                                  + '0x00000000-0xffffffff.'
                                    ;
                        type string {
                          length 10 {
                            description 'User defined hexadecimal string mask,as follows:
0x00000000-0xffffffff.'
                                        ;
                          }
                        }
                        mandatory true ;
                      }
                      container segment4 {
                        description 'Rule segment four.'
                                    ;
                        presence segment4 ;
                        leaf offset {
                          description 'Offset from packet head (2+4*n, n = 0, 1'
                                    + ', 2, ...).'
                                      ;
                          type uint32 {
                            range 2..126 ;
                          }
                          mandatory true ;
                        }
                        leaf rule-string {
                          description 'User defined hexadecimal string,as follo'
                                    + 'ws:'+"\n"
                                    + '0x00000000-0xffffffff.'
                                      ;
                          type string {
                            length 10 {
                              description 'User defined hexadecimal string,as follows:
0x00000000-0xffffffff.'
                                          ;
                            }
                          }
                          mandatory true ;
                        }
                        leaf rule-mask {
                          description 'User defined hexadecimal string mask,as '
                                    + 'follows:'+"\n"
                                    + '0x00000000-0xffffffff.'
                                      ;
                          type string {
                            length 10 {
                              description 'User defined hexadecimal string mask,as follows:
0x00000000-0xffffffff.'
                                          ;
                            }
                          }
                          mandatory true ;
                        }
                      }
                    }
                  }
                }
              }
            }
            leaf time-range {
              description 'Time range name.'
                          ;
              type string {
                length 1..31 ;
              }
            }
          }
          ncd:revise-date 2015-12-23 ;
        }
        container ipv4-vxlan-access-lists {
          description 'Configure ipv4-vxlan-access-list.'
                      ;
          list ipv4-vxlan-access-list {
            if-feature ipv4-vxlan-feature ;
            description 'Configure ipv4-vxlan-access-list.'
                        ;
            key acl-name ;
            leaf acl-name {
              description 'Name of ACL.'
                          ;
              type acl-name-type ;
            }
            leaf without-vni {
              description 'Configure rules without virtual network ID.'
                          ;
              type empty ;
            }
            leaf mode-type {
              description 'Mode type of ACL.'
                          ;
              type enumeration {
                enum transit-inner {
                  value 1 ;
                  description 'Transit node match VXLAN inner layer'
                              ;
                }
                enum transit-outer {
                  value 2 ;
                  description 'Transit node match VXLAN outer layer'
                              ;
                }
                enum vtep-inner {
                  value 3 ;
                  description 'VTEP node match VXLAN inner layer'
                              ;
                }
                enum vtep-outer {
                  value 4 ;
                  description 'VTEP node match VXLAN outer layer'
                              ;
                }
              }
              ncd:revise-date 2018-09-17 ;
            }
            container rules {
              description 'Configure rule of an IPv4 VXLAN ACL.'
                          ;
              list rule {
                description 'Configure rule of an IPv4 VXLAN ACL.'
                            ;
                key ruleid ;
                leaf ruleid {
                  description 'ID of this rule.'
                              ;
                  type uint32 {
                    range 1..2147483644 ;
                  }
                }
                choice permit-deny {
                  description 'Deny  :  Specify packets to reject'+"\n"
                            + 'Permit:  Specify packets to forward.'
                              ;
                  mandatory true ;
                  case deny {
                    description 'Deny:Specify packets to reject.'
                                ;
                    leaf deny {
                      description 'Deny:Specify packets to reject.'
                                  ;
                      type empty ;
                      mandatory true ;
                    }
                  }
                  case permit {
                    description 'Permit:  Specify packets to forward.'
                                ;
                    leaf permit {
                      description 'Permit:  Specify packets to forward.'
                                  ;
                      type empty ;
                      mandatory true ;
                    }
                  }
                }
                container inner-layer {
                  description 'The inner-layer protocol of VXLAN.'
                              ;
                  choice protocol-type {
                    description 'Configure protocol type of IPv4 VXLAN acl in i'
                              + 'nner-layer as follows:'+"\n"
                              + 'IP protocol number(0-255)'+"\n"
                              + 'Some has specific mean:'+"\n"
                              + 'gre      Generic Routing Encapsulation (47)'+"\n"
                              + 'icmp     Internet Control Message Protocol(1)
'
                              + ''+"\n"
                              + 'igmp     Internet Group Management Protocol (2'
                              + ')'+"\n"
                              + 'ospf     Open Shortest Path First Protocol (89'
                              + ')'+"\n"
                              + 'pim      Protocol Independent Multicast (103)
'
                              + ''+"\n"
                              + 'tcp      Transmission Control Protocol(6)'+"\n"
                              + 'udp      User Datagram Protocol(17)'+"\n"
                              + 'vrrp     Virtual Router Redundancy Protocol (1'
                              + '12)'+"\n"
                              + 'ip       Any IP protocol (65535).'
                                ;
                    mandatory true ;
                    case tcp-udp {
                      description 'Configure TCP or UDP protocol of IPv4 VXLAN '
                                + 'ACL.'+"\n"
                                + 'tcp      Transmission Control Protocol(6)'+"\n"
                                + 'udp      User Datagram Protocol(17)'
                                  ;
                      container tcp-udp {
                        description 'Configure protocol type of IPv4 VXLAN ACL.'
                                  + ''+"\n"
                                  + 'tcp      Transmission Control Protocol(6)
'
                                  + ''+"\n"
                                  + 'udp      User Datagram Protocol(17)'
                                    ;
                        leaf tcp-udp {
                          description 'Configure protocol type of IPv4 VXLAN AC'
                                    + 'L.'+"\n"
                                    + 'tcp      Transmission Control Protocol(6'
                                    + ')'+"\n"
                                    + 'udp      User Datagram Protocol(17)'
                                      ;
                          type enumeration {
                            enum tcp {
                              value 6 ;
                              description 'Transmission Control Protocol(6)'
                                          ;
                            }
                            enum udp {
                              value 17 ;
                              description 'User Datagram Protocol(17)'
                                          ;
                            }
                          }
                          mandatory true ;
                        }
                        choice src-addr {
                          description 'Configure source address.'
                                      ;
                          mandatory true ;
                          case addr-type {
                            description 'Configure source address.'
                                        ;
                            leaf src-address {
                              description 'Configure source address.'
                                          ;
                              type ncd:ipv4-address ;
                              mandatory true ;
                            }
                            leaf src-wildcard {
                              description 'Source wildcard bits.'
                                          ;
                              type ncd:ipv4-address ;
                              mandatory true ;
                            }
                          }
                          case any-type {
                            description 'Any source address.'
                                        ;
                            leaf src-any-addr {
                              description 'Any source address.'
                                          ;
                              type empty ;
                              mandatory true ;
                            }
                          }
                        }
                        choice src-port {
                          status obsolete {
                            ncd:revise-date 2017-07-20 ;
                          }
                          description 'Configure source port.'
                                      ;
                          case src-oper {
                            status obsolete {
                              ncd:revise-date 2017-07-20 ;
                            }
                            description 'Configure source port.'
                                        ;
                            leaf src-oper {
                              status obsolete {
                                ncd:revise-date 2017-07-20 ;
                              }
                              description 'source port operator.'+"\n"
                                        + 'Operator type'+"\n"
                                        + 'eq(1)   : match only packets on a given port number'+"\n"
                                        + 'ge(2)   : match only packets with a no lower port number'+"\n"
                                        + 'le(3)   : match only packets with a no greater port number.'
                                          ;
                              type enumeration {
                                enum eq {
                                  value 1 ;
                                  description 'Match only packets on a given port number.'
                                              ;
                                }
                                enum ge {
                                  value 2 ;
                                  description 'Match only packets with a no lower port number.'
                                              ;
                                }
                                enum le {
                                  value 3 ;
                                  description 'Match only packets with a no greater port number.'
                                              ;
                                }
                              }
                              mandatory true ;
                            }
                            leaf src-port-number {
                              status obsolete {
                                ncd:revise-date 2017-07-20 ;
                              }
                              description 'Configure port number from 0 to 65535.'+"\n"
                                        + 'Some has specific means when port protocol type is TCP.'+"\n"
                                        + '  bgp        Border gateway protocol (179)'+"\n"
                                        + '  domain     Domain name service (53)'+"\n"
                                        + '  finger     Finger (79)'+"\n"
                                        + '  ftp        File transfer protocol (21)'+"\n"
                                        + '  login      Login (rlogin, 513)'+"\n"
                                        + '  pop2       Post office protocol v2 (109)'+"\n"
                                        + '  pop3       Post office protocol v3 (110)'+"\n"
                                        + '  smtp       Simple mail transport protocol (25)'+"\n"
                                        + '  telnet     Telnet (23)'+"\n"
                                        + '  www        World wide web (HTTP, 80)'+"\n"
                                        + 'Some has specific means when port protocol type is UDP.'+"\n"
                                        + '  bootpc       Bootstrap protocol (BOOTP) client (68)'+"\n"
                                        + '  bootps       Bootstrap protocol (BOOTP) server (67)'+"\n"
                                        + '  domain       Domain name service (DNS, 53)'+"\n"
                                        + '  ntp          Network time protocol (123)'+"\n"
                                        + '  pim-auto-rp  PIM auto-RP (496)'+"\n"
                                        + '  rip          Routing information protocol (router, in.routed, 520)'+"\n"
                                        + '  snmp         Simple network management protocol (161)'+"\n"
                                        + '  snmptrap     SNMP traps (162)'+"\n"
                                        + '  tftp         Trivial file transfer protocol (69).'
                                          ;
                              type uint16 {
                                range 0..65535 ;
                              }
                              mandatory true ;
                            }
                          }
                          case src-range {
                            status obsolete {
                              ncd:revise-date 2017-07-20 ;
                            }
                            description 'configure range type source port.'
                                        ;
                            leaf src-range {
                              status obsolete {
                                ncd:revise-date 2017-07-20 ;
                              }
                              description 'configure range type source port.'
                                          ;
                              type empty ;
                              mandatory true ;
                            }
                            leaf src-range-value {
                              status obsolete {
                                ncd:revise-date 2017-07-20 ;
                              }
                              description 'Port range.'
                                          ;
                              type acl-port-range ;
                              mandatory true ;
                            }
                          }
                        }
                        container source-port {
                          description 'Specify source port.'+"\n"
                                    + 'When the value of operator is invalid, i'
                                    + 't means match all port range,'+"\n"
                                    + 'the other value of operator means'+"\n"
                                    + 'eq(1)   : match only packets on a given '
                                    + 'port number'+"\n"
                                    + 'ge(2)   : match only packets with a no l'
                                    + 'ower port number'+"\n"
                                    + 'le(3)   : match only packets with a no g'
                                    + 'reater port number'+"\n"
                                    + 'range(7): match only packet on a given p'
                                    + 'ort range.'
                                      ;
                          presence 'Specify source port'
                                   ;
                          choice source-port {
                            description 'Specify source port.'+"\n"
                                      + 'When the value of operator is invalid, it means match all port range,'+"\n"
                                      + 'the other value of operator means'+"\n"
                                      + 'eq(1)   : match only packets on a given port number'+"\n"
                                      + 'ge(2)   : match only packets with a no lower port number'+"\n"
                                      + 'le(3)   : match only packets with a no greater port number'+"\n"
                                      + 'range(7): match only packet on a given port range.'
                                        ;
                            mandatory true ;
                            case src-port-value {
                              description 'Configure port number.'
                                          ;
                              container src-port-value {
                                description 'Configure port number.'
                                            ;
                                presence 'Configure port number'
                                         ;
                                leaf src-port-operator {
                                  description 'Operator type'+"\n"
                                            + 'eq(1)   : match only packets on a given port number'+"\n"
                                            + 'ge(2)   : match only packets with a no lower port number'+"\n"
                                            + 'le(3)   : match only packets with a no greater port number.'
                                              ;
                                  type enumeration {
                                    enum eq {
                                      value 1 ;
                                      description 'Equal to.'
                                                  ;
                                    }
                                    enum ge {
                                      value 2 ;
                                      description 'Great than or equal to.'
                                                  ;
                                    }
                                    enum le {
                                      value 3 ;
                                      description 'Less than or equal to.'
                                                  ;
                                    }
                                  }
                                  mandatory true ;
                                }
                                leaf src-port-value {
                                  description 'Configure port number from 0 to 65535.'+"\n"
                                            + 'Some has specific means when port protocol type is TCP.'+"\n"
                                            + '  bgp        Border gateway protocol (179)'+"\n"
                                            + '  domain     Domain name service (53)'+"\n"
                                            + '  finger     Finger (79)'+"\n"
                                            + '  ftp        File transfer protocol (21)'+"\n"
                                            + '  login      Login (rlogin, 513)'+"\n"
                                            + '  pop2       Post office protocol v2 (109)'+"\n"
                                            + '  pop3       Post office protocol v3 (110)'+"\n"
                                            + '  smtp       Simple mail transport protocol (25)'+"\n"
                                            + '  telnet     Telnet (23)'+"\n"
                                            + '  www        World wide web (HTTP, 80)'+"\n"
                                            + 'Some has specific means when port protocol type is UDP.'+"\n"
                                            + '  bootpc       Bootstrap protocol (BOOTP) client (68)'+"\n"
                                            + '  bootps       Bootstrap protocol (BOOTP) server (67)'+"\n"
                                            + '  domain       Domain name service (DNS, 53)'+"\n"
                                            + '  ntp          Network time protocol (123)'+"\n"
                                            + '  pim-auto-rp  PIM auto-RP (496)'+"\n"
                                            + '  rip          Routing information protocol (router, in.routed, 520)'+"\n"
                                            + '  snmp         Simple network management protocol (161)'+"\n"
                                            + '  snmptrap     SNMP traps (162)'+"\n"
                                            + '  tftp         Trivial file transfer protocol (69).'
                                              ;
                                  type uint16 {
                                    range 0..65535 ;
                                  }
                                  mandatory true ;
                                }
                              }
                            }
                            case src-port-range {
                              description 'Configure port range.'
                                          ;
                              container src-port-range {
                                description 'Configure port range.'
                                            ;
                                presence 'Configure port range'
                                         ;
                                leaf src-port-operator {
                                  description 'Operator type
range(7): match only packet on a given port range.'
                                              ;
                                  type enumeration {
                                    enum range {
                                      value 7 ;
                                      description Range. ;
                                    }
                                  }
                                  mandatory true ;
                                }
                                leaf src-port-range {
                                  description 'Port range, support <0-65535>-<0-65535>.'
                                              ;
                                  type acl-port-range ;
                                  mandatory true ;
                                }
                              }
                            }
                          }
                          ncd:revise-date 2017-07-20 ;
                        }
                        choice dst-addr {
                          description 'Configure destination address.'
                                      ;
                          mandatory true ;
                          case addr-type {
                            description 'Configure destination address.'
                                        ;
                            leaf dst-address {
                              description 'Configure destination address.'
                                          ;
                              type ncd:ipv4-address ;
                              mandatory true ;
                            }
                            leaf dst-wildcard {
                              description 'Destination wildcard bits'
                                          ;
                              type ncd:ipv4-address ;
                              mandatory true ;
                            }
                          }
                          case any-type {
                            description 'Any destination address.'
                                        ;
                            leaf dst-any-addr {
                              description 'Any destination address.'
                                          ;
                              type empty ;
                              mandatory true ;
                            }
                          }
                        }
                        choice dst-port {
                          status obsolete {
                            ncd:revise-date 2017-07-20 ;
                          }
                          description 'Configure destination port.'
                                      ;
                          case dst-oper {
                            status obsolete {
                              ncd:revise-date 2017-07-20 ;
                            }
                            description 'Configure destination port with operator flag.'
                                        ;
                            leaf dst-oper {
                              status obsolete {
                                ncd:revise-date 2017-07-20 ;
                              }
                              description 'Operator type'+"\n"
                                        + 'eq(1)   : match only packets on a given port number'+"\n"
                                        + 'ge(2)   : match only packets with a no lower port number'+"\n"
                                        + 'le(3)   : match only packets with a no greater port number.'
                                          ;
                              type enumeration {
                                enum eq {
                                  value 1 ;
                                  description 'Match only packets on a given port number.'
                                              ;
                                }
                                enum ge {
                                  value 2 ;
                                  description 'Match only packets with a no lower port number.'
                                              ;
                                }
                                enum le {
                                  value 3 ;
                                  description 'Match only packets with a no greater port number.'
                                              ;
                                }
                              }
                              mandatory true ;
                            }
                            leaf dst-port-number {
                              status obsolete {
                                ncd:revise-date 2017-07-20 ;
                              }
                              description 'Configure port number from 0 to 65535.'+"\n"
                                        + 'Some has specific means when port protocol type is TCP.'+"\n"
                                        + '  bgp        Border gateway protocol (179)'+"\n"
                                        + '  domain     Domain name service (53)'+"\n"
                                        + '  finger     Finger (79)'+"\n"
                                        + '  ftp        File transfer protocol (21)'+"\n"
                                        + '  login      Login (rlogin, 513)'+"\n"
                                        + '  pop2       Post office protocol v2 (109)'+"\n"
                                        + '  pop3       Post office protocol v3 (110)'+"\n"
                                        + '  smtp       Simple mail transport protocol (25)'+"\n"
                                        + '  telnet     Telnet (23)'+"\n"
                                        + '  www        World wide web (HTTP, 80)'+"\n"
                                        + 'Some has specific means when port protocol type is UDP.'+"\n"
                                        + '  bootpc       Bootstrap protocol (BOOTP) client (68)'+"\n"
                                        + '  bootps       Bootstrap protocol (BOOTP) server (67)'+"\n"
                                        + '  domain       Domain name service (DNS, 53)'+"\n"
                                        + '  ntp          Network time protocol (123)'+"\n"
                                        + '  pim-auto-rp  PIM auto-RP (496)'+"\n"
                                        + '  rip          Routing information protocol (router, in.routed, 520)'+"\n"
                                        + '  snmp         Simple network management protocol (161)'+"\n"
                                        + '  snmptrap     SNMP traps (162)'+"\n"
                                        + '  tftp         Trivial file transfer protocol (69).'
                                          ;
                              type uint16 {
                                range 0..65535 ;
                              }
                              mandatory true ;
                            }
                          }
                          case dst-range {
                            status obsolete {
                              ncd:revise-date 2017-07-20 ;
                            }
                            description 'Configure destination port in range type.'
                                        ;
                            leaf dst-range {
                              status obsolete {
                                ncd:revise-date 2017-07-20 ;
                              }
                              description 'Range operator.'
                                          ;
                              type empty ;
                              mandatory true ;
                            }
                            leaf dst-range-value {
                              status obsolete {
                                ncd:revise-date 2017-07-20 ;
                              }
                              description 'Destination port range.'
                                          ;
                              type acl-port-range ;
                              mandatory true ;
                            }
                          }
                        }
                        container destination-port {
                          description 'Specify destination port.'+"\n"
                                    + 'When the value of operator is invalid, i'
                                    + 't means match all port range,'+"\n"
                                    + 'the other value of operator means'+"\n"
                                    + 'eq(1)   : match only packets on a given '
                                    + 'port number'+"\n"
                                    + 'ge(2)   : match only packets with a no l'
                                    + 'ower port number'+"\n"
                                    + 'le(3)   : match only packets with a no g'
                                    + 'reater port number'+"\n"
                                    + 'range(7): match only packet on a given p'
                                    + 'ort range.'
                                      ;
                          presence 'Specify destination port'
                                   ;
                          choice destination-port {
                            description 'Specify destination port.'+"\n"
                                      + 'When the value of operator is invalid, it means match all port range,'+"\n"
                                      + 'the other value of operator means'+"\n"
                                      + 'eq(1)   : match only packets on a given port number'+"\n"
                                      + 'ge(2)   : match only packets with a no lower port number'+"\n"
                                      + 'le(3)   : match only packets with a no greater port number'+"\n"
                                      + 'range(7): match only packet on a given port range.'
                                        ;
                            mandatory true ;
                            case dst-port-value {
                              description 'Configure port number.'
                                          ;
                              container dst-port-value {
                                description 'Configure port number.'
                                            ;
                                presence 'Configure port number'
                                         ;
                                leaf dst-port-operator {
                                  description 'Operator type'+"\n"
                                            + 'eq(1)   : match only packets on a given port number'+"\n"
                                            + 'ge(2)   : match only packets with a no lower port number'+"\n"
                                            + 'le(3)   : match only packets with a no greater port number.'
                                              ;
                                  type enumeration {
                                    enum eq {
                                      value 1 ;
                                      description 'Equal to.'
                                                  ;
                                    }
                                    enum ge {
                                      value 2 ;
                                      description 'Great than or equal to.'
                                                  ;
                                    }
                                    enum le {
                                      value 3 ;
                                      description 'Less than or equal to.'
                                                  ;
                                    }
                                  }
                                  mandatory true ;
                                }
                                leaf dst-port-value {
                                  description 'Configure port number from 0 to 65535.'+"\n"
                                            + 'Some has specific means when port protocol type is TCP.'+"\n"
                                            + '  bgp        Border gateway protocol (179)'+"\n"
                                            + '  domain     Domain name service (53)'+"\n"
                                            + '  finger     Finger (79)'+"\n"
                                            + '  ftp        File transfer protocol (21)'+"\n"
                                            + '  login      Login (rlogin, 513)'+"\n"
                                            + '  pop2       Post office protocol v2 (109)'+"\n"
                                            + '  pop3       Post office protocol v3 (110)'+"\n"
                                            + '  smtp       Simple mail transport protocol (25)'+"\n"
                                            + '  telnet     Telnet (23)'+"\n"
                                            + '  www        World wide web (HTTP, 80)'+"\n"
                                            + 'Some has specific means when port protocol type is UDP.'+"\n"
                                            + '  bootpc       Bootstrap protocol (BOOTP) client (68)'+"\n"
                                            + '  bootps       Bootstrap protocol (BOOTP) server (67)'+"\n"
                                            + '  domain       Domain name service (DNS, 53)'+"\n"
                                            + '  ntp          Network time protocol (123)'+"\n"
                                            + '  pim-auto-rp  PIM auto-RP (496)'+"\n"
                                            + '  rip          Routing information protocol (router, in.routed, 520)'+"\n"
                                            + '  snmp         Simple network management protocol (161)'+"\n"
                                            + '  snmptrap     SNMP traps (162)'+"\n"
                                            + '  tftp         Trivial file transfer protocol (69).'
                                              ;
                                  type uint16 {
                                    range 0..65535 ;
                                  }
                                  mandatory true ;
                                }
                              }
                            }
                            case dst-port-range {
                              description 'Configure port range.'
                                          ;
                              container dst-port-range {
                                description 'Configure port range.'
                                            ;
                                presence 'Configure port range'
                                         ;
                                leaf dst-port-operator {
                                  description 'Operator type
range(7): match only packet on a given port range.'
                                              ;
                                  type enumeration {
                                    enum range {
                                      value 7 ;
                                      description Range. ;
                                    }
                                  }
                                  mandatory true ;
                                }
                                leaf dst-port-range {
                                  description 'Port range, support <0-65535>-<0-65535>.'
                                              ;
                                  type acl-port-range ;
                                  mandatory true ;
                                }
                              }
                            }
                          }
                          ncd:revise-date 2017-07-20 ;
                        }
                      }
                    }
                    case ip {
                      description 'Configure protocol type of IPv4 VXLAN acl in'
                                + ' inner-layer as follows:'+"\n"
                                + 'IP protocol number(0-255)'+"\n"
                                + 'Some has specific mean:'+"\n"
                                + 'gre      Generic Routing Encapsulation (47)
'
                                + ''+"\n"
                                + 'icmp     Internet Control Message Protocol(1'
                                + ')'+"\n"
                                + 'igmp     Internet Group Management Protocol '
                                + '(2)'+"\n"
                                + 'ospf     Open Shortest Path First Protocol ('
                                + '89)'+"\n"
                                + 'pim      Protocol Independent Multicast (103'
                                + ')'+"\n"
                                + 'vrrp     Virtual Router Redundancy Protocol '
                                + '(112)'+"\n"
                                + 'ip       Any IP protocol (65535).'
                                  ;
                      container ipv4-protocol {
                        description 'Configure protocol type of IPv4 VXLAN acl '
                                  + 'in inner-layer as follows:'+"\n"
                                  + 'IP protocol number(0-255)'+"\n"
                                  + 'Some has specific mean:'+"\n"
                                  + 'gre      Generic Routing Encapsulation (47'
                                  + ')'+"\n"
                                  + 'icmp     Internet Control Message Protocol'
                                  + '(1)'+"\n"
                                  + 'igmp     Internet Group Management Protoco'
                                  + 'l (2)'+"\n"
                                  + 'ospf     Open Shortest Path First Protocol'
                                  + ' (89)'+"\n"
                                  + 'pim      Protocol Independent Multicast (1'
                                  + '03)'+"\n"
                                  + 'vrrp     Virtual Router Redundancy Protoco'
                                  + 'l (112)'+"\n"
                                  + 'ip       Any IP protocol (65535).'
                                    ;
                        leaf protocol-type {
                          description 'IP protocol number'+"\n"
                                    + 'Some has specific mean:'+"\n"
                                    + 'gre      Generic Routing Encapsulation ('
                                    + '47)'+"\n"
                                    + 'icmp     Internet Control Message Protoc'
                                    + 'ol(1)'+"\n"
                                    + 'igmp     Internet Group Management Proto'
                                    + 'col (2)'+"\n"
                                    + 'ospf     Open Shortest Path First Protoc'
                                    + 'ol (89)'+"\n"
                                    + 'pim      Protocol Independent Multicast '
                                    + '(103)'+"\n"
                                    + 'vrrp     Virtual Router Redundancy Proto'
                                    + 'col (112)'+"\n"
                                    + 'ip       Any IP protocol (65535).'
                                      ;
                          type uint16 {
                            range '0..5 | 7..16 | 18..255 | 65535'
                                  ;
                          }
                          mandatory true ;
                        }
                        choice src-addr {
                          description 'Configure source address.'
                                      ;
                          mandatory true ;
                          case addr-type {
                            description 'Configure source address.'
                                        ;
                            leaf src-address {
                              description 'Configure source address.'
                                          ;
                              type ncd:ipv4-address ;
                              mandatory true ;
                            }
                            leaf src-wildcard {
                              description 'Source wildcard bits.'
                                          ;
                              type ncd:ipv4-address ;
                              mandatory true ;
                            }
                          }
                          case any-type {
                            description 'Any source address.'
                                        ;
                            leaf src-any-addr {
                              description 'Any source address.'
                                          ;
                              type empty ;
                              mandatory true ;
                            }
                          }
                        }
                        choice dst-addr {
                          description 'Configure destination address.'
                                      ;
                          mandatory true ;
                          case addr-type {
                            description 'Configure destination address.'
                                        ;
                            leaf dst-address {
                              description 'Configure destination address.'
                                          ;
                              type ncd:ipv4-address ;
                              mandatory true ;
                            }
                            leaf dst-wildcard {
                              description 'Destination wildcard bits'
                                          ;
                              type ncd:ipv4-address ;
                              mandatory true ;
                            }
                          }
                          case any-type {
                            description 'Any destination address.'
                                        ;
                            leaf dst-any-addr {
                              description 'Any destination address.'
                                          ;
                              type empty ;
                              mandatory true ;
                            }
                          }
                        }
                      }
                    }
                  }
                  choice priority {
                    description 'Configure precedence or TOS or DSCP.'
                                ;
                    case dscp {
                      description 'DSCP value.'
                                  ;
                      leaf dscp {
                        description 'DSCP value.'
                                    ;
                        type uint8 {
                          range 0..63 ;
                        }
                      }
                    }
                    case precedence {
                      description 'Precedence level.'
                                  ;
                      leaf precedence {
                        description 'Precedence level.'
                                    ;
                        type uint8 {
                          range 0..7 ;
                        }
                      }
                    }
                    case tos {
                      description 'Type of service(TOS).'
                                  ;
                      leaf tos {
                        description 'Type of service(TOS).'
                                    ;
                        type uint8 {
                          range 0..15 ;
                        }
                      }
                    }
                  }
                }
                container vni {
                  description 'VXLAN ID.'
                              ;
                  presence vni ;
                  leaf vxlan-id {
                    description 'VXLAN ID.'
                                ;
                    type uint32 {
                      range 1..16777215 ;
                    }
                    mandatory true ;
                  }
                }
                container sgt {
                  description 'Security Group Tag'
                              ;
                  presence sgt ;
                  leaf sgt-value {
                    description 'Security Group Tag Value'
                                ;
                    type uint16 ;
                    mandatory true ;
                  }
                  ncd:revise-date 2019-08-14 ;
                }
                container outer-layer {
                  description 'The outer-layer protocol of VXLAN.'
                              ;
                  presence outer-layer ;
                  leaf udp {
                    description 'Configure UDP protocol.'
                                ;
                    type empty ;
                    mandatory true ;
                  }
                  choice src-addr {
                    description 'Configure source address.'
                                ;
                    mandatory true ;
                    case addr-type {
                      description 'Configure source address.'
                                  ;
                      leaf src-address {
                        description 'Configure source address.'
                                    ;
                        type ncd:ipv4-address ;
                        mandatory true ;
                      }
                      leaf src-wildcard {
                        description 'Source wildcard bits.'
                                    ;
                        type ncd:ipv4-address ;
                        mandatory true ;
                      }
                    }
                    case any-type {
                      description 'Any source address.'
                                  ;
                      leaf src-any-addr {
                        description 'Any source address.'
                                    ;
                        type empty ;
                        mandatory true ;
                      }
                    }
                  }
                  choice src-port {
                    status obsolete {
                      ncd:revise-date 2017-07-20 ;
                    }
                    description 'Configure source port.'
                                ;
                    case src-oper {
                      status obsolete {
                        ncd:revise-date 2017-07-20 ;
                      }
                      description 'Configure source port.'
                                  ;
                      leaf src-oper {
                        status obsolete {
                          ncd:revise-date 2017-07-20 ;
                        }
                        description 'source port operator.'+"\n"
                                  + 'Operator type'+"\n"
                                  + 'eq(1)   : match only packets on a given po'
                                  + 'rt number'+"\n"
                                  + 'ge(2)   : match only packets with a no low'
                                  + 'er port number'+"\n"
                                  + 'le(3)   : match only packets with a no gre'
                                  + 'ater port number.'
                                    ;
                        type enumeration {
                          enum eq {
                            value 1 ;
                            description 'Match only packets on a given port number.'
                                        ;
                          }
                          enum ge {
                            value 2 ;
                            description 'Match only packets with a no lower port number.'
                                        ;
                          }
                          enum le {
                            value 3 ;
                            description 'Match only packets with a no greater port number.'
                                        ;
                          }
                        }
                        mandatory true ;
                      }
                      leaf src-port-number {
                        status obsolete {
                          ncd:revise-date 2017-07-20 ;
                        }
                        description 'Port number.'+"\n"
                                  + 'Some has specific means:'+"\n"
                                  + 'bootpc       Bootstrap protocol (BOOTP) cl'
                                  + 'ient (68)'+"\n"
                                  + 'bootps       Bootstrap protocol (BOOTP) se'
                                  + 'rver (67)'+"\n"
                                  + 'domain       Domain name service (DNS, 53)'
                                  + ''+"\n"
                                  + 'ntp          Network time protocol (123)'+"\n"
                                  + 'pim-auto-rp  PIM auto-RP (496)'+"\n"
                                  + 'rip          Routing information protocol '
                                  + '(router, in.routed, 520)'+"\n"
                                  + 'snmp         Simple network management pro'
                                  + 'tocol (161)'+"\n"
                                  + 'snmptrap     SNMP traps (162)'+"\n"
                                  + 'tftp         Trivial file transfer protoco'
                                  + 'l (69).'
                                    ;
                        type uint16 {
                          range 0..65535 ;
                        }
                        mandatory true ;
                      }
                    }
                    case src-range {
                      status obsolete {
                        ncd:revise-date 2017-07-20 ;
                      }
                      description 'configure range type source port.'
                                  ;
                      leaf src-range {
                        status obsolete {
                          ncd:revise-date 2017-07-20 ;
                        }
                        description 'configure range type source port.'
                                    ;
                        type empty ;
                        mandatory true ;
                      }
                      leaf src-range-value {
                        status obsolete {
                          ncd:revise-date 2017-07-20 ;
                        }
                        description 'Port range.'
                                    ;
                        type acl-port-range ;
                        mandatory true ;
                      }
                    }
                  }
                  container source-port {
                    description 'Specify source port.'+"\n"
                              + 'When the value of operator is invalid, it mean'
                              + 's match all port range,'+"\n"
                              + 'the other value of operator means'+"\n"
                              + 'eq(1)   : match only packets on a given port n'
                              + 'umber'+"\n"
                              + 'ge(2)   : match only packets with a no lower p'
                              + 'ort number'+"\n"
                              + 'le(3)   : match only packets with a no greater'
                              + ' port number'+"\n"
                              + 'range(7): match only packet on a given port ra'
                              + 'nge.'
                                ;
                    presence 'Specify source port'
                             ;
                    choice source-port {
                      description 'Specify source port.'+"\n"
                                + 'When the value of operator is invalid, it me'
                                + 'ans match all port range,'+"\n"
                                + 'the other value of operator means'+"\n"
                                + 'eq(1)   : match only packets on a given port'
                                + ' number'+"\n"
                                + 'ge(2)   : match only packets with a no lower'
                                + ' port number'+"\n"
                                + 'le(3)   : match only packets with a no great'
                                + 'er port number'+"\n"
                                + 'range(7): match only packet on a given port '
                                + 'range.'
                                  ;
                      mandatory true ;
                      case src-port-value {
                        description 'Configure port number.'
                                    ;
                        container src-port-value {
                          description 'Configure port number.'
                                      ;
                          presence 'Configure port number'
                                   ;
                          leaf src-port-operator {
                            description 'Operator type'+"\n"
                                      + 'eq(1)   : match only packets on a given port number'+"\n"
                                      + 'ge(2)   : match only packets with a no lower port number'+"\n"
                                      + 'le(3)   : match only packets with a no greater port number.'
                                        ;
                            type enumeration {
                              enum eq {
                                value 1 ;
                                description 'Equal to.'
                                            ;
                              }
                              enum ge {
                                value 2 ;
                                description 'Great than or equal to.'
                                            ;
                              }
                              enum le {
                                value 3 ;
                                description 'Less than or equal to.'
                                            ;
                              }
                            }
                            mandatory true ;
                          }
                          leaf src-port-value {
                            description 'Port number.'+"\n"
                                      + 'Some has specific means:'+"\n"
                                      + 'bootpc       Bootstrap protocol (BOOTP) client (68)'+"\n"
                                      + 'bootps       Bootstrap protocol (BOOTP) server (67)'+"\n"
                                      + 'domain       Domain name service (DNS, 53)'+"\n"
                                      + 'ntp          Network time protocol (123)'+"\n"
                                      + 'pim-auto-rp  PIM auto-RP (496)'+"\n"
                                      + 'rip          Routing information protocol (router, in.routed, 520)'+"\n"
                                      + 'snmp         Simple network management protocol (161)'+"\n"
                                      + 'snmptrap     SNMP traps (162)'+"\n"
                                      + 'tftp         Trivial file transfer protocol (69).'
                                        ;
                            type uint16 {
                              range 0..65535 ;
                            }
                            mandatory true ;
                          }
                        }
                      }
                      case src-port-range {
                        description 'Configure port range.'
                                    ;
                        container src-port-range {
                          description 'Configure port range.'
                                      ;
                          presence 'Configure port range'
                                   ;
                          leaf src-port-operator {
                            description 'Operator type
range(7): match only packet on a given port range.'
                                        ;
                            type enumeration {
                              enum range {
                                value 7 ;
                                description Range. ;
                              }
                            }
                            mandatory true ;
                          }
                          leaf src-port-range {
                            description 'Port range, support <0-65535>-<0-65535>.'
                                        ;
                            type acl-port-range ;
                            mandatory true ;
                          }
                        }
                      }
                    }
                    ncd:revise-date 2017-07-20 ;
                  }
                  choice dst-addr {
                    description 'Configure destination address.'
                                ;
                    mandatory true ;
                    case addr-type {
                      description 'Configure destination address.'
                                  ;
                      leaf dst-address {
                        description 'Configure destination address.'
                                    ;
                        type ncd:ipv4-address ;
                        mandatory true ;
                      }
                      leaf dst-wildcard {
                        description 'Destination wildcard bits'
                                    ;
                        type ncd:ipv4-address ;
                        mandatory true ;
                      }
                    }
                    case any-type {
                      description 'Any destination address.'
                                  ;
                      leaf dst-any-addr {
                        description 'Any destination address.'
                                    ;
                        type empty ;
                        mandatory true ;
                      }
                    }
                  }
                  choice dst-port {
                    status obsolete {
                      ncd:revise-date 2017-07-20 ;
                    }
                    description 'Configure destination port.'
                                ;
                    case dst-oper {
                      status obsolete {
                        ncd:revise-date 2017-07-20 ;
                      }
                      description 'Configure destination port with operator fla'
                                + 'g.'
                                  ;
                      leaf dst-oper {
                        status obsolete {
                          ncd:revise-date 2017-07-20 ;
                        }
                        description 'Operator type'+"\n"
                                  + 'eq(1)   : match only packets on a given po'
                                  + 'rt number'+"\n"
                                  + 'ge(2)   : match only packets with a no low'
                                  + 'er port number'+"\n"
                                  + 'le(3)   : match only packets with a no gre'
                                  + 'ater port number.'
                                    ;
                        type enumeration {
                          enum eq {
                            value 1 ;
                            description 'Match only packets on a given port number.'
                                        ;
                          }
                          enum ge {
                            value 2 ;
                            description 'Match only packets with a no lower port number.'
                                        ;
                          }
                          enum le {
                            value 3 ;
                            description 'Match only packets with a no greater port number.'
                                        ;
                          }
                        }
                        mandatory true ;
                      }
                      leaf dst-port-number {
                        status obsolete {
                          ncd:revise-date 2017-07-20 ;
                        }
                        description 'Port number.'+"\n"
                                  + 'Some has specific means:'+"\n"
                                  + 'bootpc       Bootstrap protocol (BOOTP) cl'
                                  + 'ient (68)'+"\n"
                                  + 'bootps       Bootstrap protocol (BOOTP) se'
                                  + 'rver (67)'+"\n"
                                  + 'domain       Domain name service (DNS, 53)'
                                  + ''+"\n"
                                  + 'ntp          Network time protocol (123)'+"\n"
                                  + 'pim-auto-rp  PIM auto-RP (496)'+"\n"
                                  + 'rip          Routing information protocol '
                                  + '(router, in.routed, 520)'+"\n"
                                  + 'snmp         Simple network management pro'
                                  + 'tocol (161)'+"\n"
                                  + 'snmptrap     SNMP traps (162)'+"\n"
                                  + 'tftp         Trivial file transfer protoco'
                                  + 'l (69).'
                                    ;
                        type uint16 {
                          range 0..65535 ;
                        }
                        mandatory true ;
                      }
                    }
                    case dst-range {
                      status obsolete {
                        ncd:revise-date 2017-07-20 ;
                      }
                      description 'Configure destination port in range type.'
                                  ;
                      leaf dst-range {
                        status obsolete {
                          ncd:revise-date 2017-07-20 ;
                        }
                        description 'Range operator.'
                                    ;
                        type empty ;
                        mandatory true ;
                      }
                      leaf dst-range-value {
                        status obsolete {
                          ncd:revise-date 2017-07-20 ;
                        }
                        description 'Destination port range.'
                                    ;
                        type acl-port-range ;
                        mandatory true ;
                      }
                    }
                  }
                  container destination-port {
                    description 'Specify destination port.'+"\n"
                              + 'When the value of operator is invalid, it mean'
                              + 's match all port range,'+"\n"
                              + 'the other value of operator means'+"\n"
                              + 'eq(1)   : match only packets on a given port n'
                              + 'umber'+"\n"
                              + 'ge(2)   : match only packets with a no lower p'
                              + 'ort number'+"\n"
                              + 'le(3)   : match only packets with a no greater'
                              + ' port number'+"\n"
                              + 'range(7): match only packet on a given port ra'
                              + 'nge.'
                                ;
                    presence 'Specify destination port'
                             ;
                    choice destination-port {
                      description 'Specify destination port.'+"\n"
                                + 'When the value of operator is invalid, it me'
                                + 'ans match all port range,'+"\n"
                                + 'the other value of operator means'+"\n"
                                + 'eq(1)   : match only packets on a given port'
                                + ' number'+"\n"
                                + 'ge(2)   : match only packets with a no lower'
                                + ' port number'+"\n"
                                + 'le(3)   : match only packets with a no great'
                                + 'er port number'+"\n"
                                + 'range(7): match only packet on a given port '
                                + 'range.'
                                  ;
                      mandatory true ;
                      case dst-port-value {
                        description 'Configure port number.'
                                    ;
                        container dst-port-value {
                          description 'Configure port number.'
                                      ;
                          presence 'Configure port number'
                                   ;
                          leaf dst-port-operator {
                            description 'Operator type'+"\n"
                                      + 'eq(1)   : match only packets on a given port number'+"\n"
                                      + 'ge(2)   : match only packets with a no lower port number'+"\n"
                                      + 'le(3)   : match only packets with a no greater port number.'
                                        ;
                            type enumeration {
                              enum eq {
                                value 1 ;
                                description 'Equal to.'
                                            ;
                              }
                              enum ge {
                                value 2 ;
                                description 'Great than or equal to.'
                                            ;
                              }
                              enum le {
                                value 3 ;
                                description 'Less than or equal to.'
                                            ;
                              }
                            }
                            mandatory true ;
                          }
                          leaf dst-port-value {
                            description 'Port number.'+"\n"
                                      + 'Some has specific means:'+"\n"
                                      + 'bootpc       Bootstrap protocol (BOOTP) client (68)'+"\n"
                                      + 'bootps       Bootstrap protocol (BOOTP) server (67)'+"\n"
                                      + 'domain       Domain name service (DNS, 53)'+"\n"
                                      + 'ntp          Network time protocol (123)'+"\n"
                                      + 'pim-auto-rp  PIM auto-RP (496)'+"\n"
                                      + 'rip          Routing information protocol (router, in.routed, 520)'+"\n"
                                      + 'snmp         Simple network management protocol (161)'+"\n"
                                      + 'snmptrap     SNMP traps (162)'+"\n"
                                      + 'tftp         Trivial file transfer protocol (69).'
                                        ;
                            type uint16 {
                              range 0..65535 ;
                            }
                            mandatory true ;
                          }
                        }
                      }
                      case dst-port-range {
                        description 'Configure port range.'
                                    ;
                        container dst-port-range {
                          description 'Configure port range.'
                                      ;
                          presence 'Configure port range'
                                   ;
                          leaf dst-port-operator {
                            description 'Operator type
range(7): match only packet on a given port range.'
                                        ;
                            type enumeration {
                              enum range {
                                value 7 ;
                                description Range. ;
                              }
                            }
                            mandatory true ;
                          }
                          leaf dst-port-range {
                            description 'Port range, support <0-65535>-<0-65535>.'
                                        ;
                            type acl-port-range ;
                            mandatory true ;
                          }
                        }
                      }
                    }
                    ncd:revise-date 2017-07-20 ;
                  }
                  choice priority {
                    description 'Configure precedence or TOS or DSCP.'
                                ;
                    case dscp {
                      description 'DSCP value.'
                                  ;
                      leaf dscp {
                        description 'DSCP value.'
                                    ;
                        type uint8 {
                          range 0..63 ;
                        }
                      }
                    }
                    case precedence {
                      description 'Precedence level.'
                                  ;
                      leaf precedence {
                        description 'Precedence level.'
                                    ;
                        type uint8 {
                          range 0..7 ;
                        }
                      }
                    }
                    case tos {
                      description 'Type of service(TOS).'
                                  ;
                      leaf tos {
                        description 'Type of service(TOS).'
                                    ;
                        type uint8 {
                          range 0..15 ;
                        }
                      }
                    }
                  }
                }
                leaf vrf {
                  description 'VPN Routing/Forwarding instance name, support 1-'
                            + '32 characters.'
                              ;
                  type acl-vrf-name {
                    length 1..32 {
                      description 'VPN Routing/Forwarding instance name, suppor'
                                + 't 1-32 characters.'
                                  ;
                    }
                  }
                  ncd:revise-date 2018-09-17 ;
                }
                leaf time-range {
                  description 'Specify the existed time-range name.'
                              ;
                  type string {
                    length 1..31 ;
                  }
                  ncd:revise-date 2021-04-02 ;
                }
                leaf log {
                  if-feature log-config ;
                  description 'If log flag is set, the matching times of this r'
                            + 'ule will be recorded.'
                              ;
                  type boolean ;
                  default false ;
                  ncd:revise-date 2022-01-20 ;
                }
              }
            }
            container rules-transit-inner {
              description 'Configure rule of an IPv4 VXLAN ACL.'
                          ;
              list rule-transit-inner {
                description 'Configure rule of an IPv4 VXLAN ACL.'
                            ;
                key ruleid ;
                leaf ruleid {
                  description 'ID of this rule.'
                              ;
                  type uint32 {
                    range 1..2147483644 ;
                  }
                }
                choice permit-deny {
                  description 'Deny  :  Specify packets to reject'+"\n"
                            + 'Permit:  Specify packets to forward.'
                              ;
                  mandatory true ;
                  case deny {
                    description 'Deny:Specify packets to reject.'
                                ;
                    leaf deny {
                      description 'Deny:Specify packets to reject.'
                                  ;
                      type empty ;
                      mandatory true ;
                    }
                  }
                  case permit {
                    description 'Permit:  Specify packets to forward.'
                                ;
                    leaf permit {
                      description 'Permit:  Specify packets to forward.'
                                  ;
                      type empty ;
                      mandatory true ;
                    }
                  }
                }
                container inner-layer {
                  description 'The inner-layer protocol of VXLAN.'
                              ;
                  presence inner-layer ;
                  choice protocol-type {
                    description 'Configure protocol type of IPv4 VXLAN acl in i'
                              + 'nner-layer as follows:'+"\n"
                              + 'IP protocol number(0-255)'+"\n"
                              + 'Some has specific mean:'+"\n"
                              + 'gre      Generic Routing Encapsulation (47)'+"\n"
                              + 'icmp     Internet Control Message Protocol(1)
'
                              + ''+"\n"
                              + 'igmp     Internet Group Management Protocol (2'
                              + ')'+"\n"
                              + 'ospf     Open Shortest Path First Protocol (89'
                              + ')'+"\n"
                              + 'pim      Protocol Independent Multicast (103)
'
                              + ''+"\n"
                              + 'tcp      Transmission Control Protocol(6)'+"\n"
                              + 'udp      User Datagram Protocol(17)'+"\n"
                              + 'vrrp     Virtual Router Redundancy Protocol (1'
                              + '12)'+"\n"
                              + 'ip       Any IP protocol (65535).'
                                ;
                    mandatory true ;
                    case tcp-udp {
                      description 'Configure TCP or UDP protocol of IPv4 VXLAN '
                                + 'ACL.'+"\n"
                                + 'tcp      Transmission Control Protocol(6)'+"\n"
                                + 'udp      User Datagram Protocol(17)'
                                  ;
                      container tcp-udp {
                        description 'Configure protocol type of IPv4 VXLAN ACL.'
                                  + ''+"\n"
                                  + 'tcp      Transmission Control Protocol(6)
'
                                  + ''+"\n"
                                  + 'udp      User Datagram Protocol(17)'
                                    ;
                        leaf tcp-udp {
                          description 'Configure protocol type of IPv4 VXLAN AC'
                                    + 'L.'+"\n"
                                    + 'tcp      Transmission Control Protocol(6'
                                    + ')'+"\n"
                                    + 'udp      User Datagram Protocol(17)'
                                      ;
                          type enumeration {
                            enum tcp {
                              value 6 ;
                              description 'Transmission Control Protocol(6)'
                                          ;
                            }
                            enum udp {
                              value 17 ;
                              description 'User Datagram Protocol(17)'
                                          ;
                            }
                          }
                          mandatory true ;
                        }
                        choice src-addr {
                          description 'Configure source address.'
                                      ;
                          mandatory true ;
                          case addr-type {
                            description 'Configure source address.'
                                        ;
                            leaf src-address {
                              description 'Configure source address.'
                                          ;
                              type ncd:ipv4-address ;
                              mandatory true ;
                            }
                            leaf src-wildcard {
                              description 'Source wildcard bits.'
                                          ;
                              type ncd:ipv4-address ;
                              mandatory true ;
                            }
                          }
                          case any-type {
                            description 'Any source address.'
                                        ;
                            leaf src-any-addr {
                              description 'Any source address.'
                                          ;
                              type empty ;
                              mandatory true ;
                            }
                          }
                        }
                        container source-port {
                          description 'Specify source port.'+"\n"
                                    + 'When the value of operator is invalid, i'
                                    + 't means match all port range,'+"\n"
                                    + 'the other value of operator means'+"\n"
                                    + 'eq(1)   : match only packets on a given '
                                    + 'port number'+"\n"
                                    + 'ge(2)   : match only packets with a no l'
                                    + 'ower port number'+"\n"
                                    + 'le(3)   : match only packets with a no g'
                                    + 'reater port number'+"\n"
                                    + 'range(7): match only packet on a given p'
                                    + 'ort range.'
                                      ;
                          presence 'Specify source port'
                                   ;
                          choice source-port {
                            description 'Specify source port.'+"\n"
                                      + 'When the value of operator is invalid, it means match all port range,'+"\n"
                                      + 'the other value of operator means'+"\n"
                                      + 'eq(1)   : match only packets on a given port number'+"\n"
                                      + 'ge(2)   : match only packets with a no lower port number'+"\n"
                                      + 'le(3)   : match only packets with a no greater port number'+"\n"
                                      + 'range(7): match only packet on a given port range.'
                                        ;
                            mandatory true ;
                            case src-port-value {
                              description 'Configure port number.'
                                          ;
                              container src-port-value {
                                description 'Configure port number.'
                                            ;
                                presence 'Configure port number'
                                         ;
                                leaf src-port-operator {
                                  description 'Operator type'+"\n"
                                            + 'eq(1)   : match only packets on a given port number'+"\n"
                                            + 'ge(2)   : match only packets with a no lower port number'+"\n"
                                            + 'le(3)   : match only packets with a no greater port number.'
                                              ;
                                  type enumeration {
                                    enum eq {
                                      value 1 ;
                                      description 'Equal to.'
                                                  ;
                                    }
                                    enum ge {
                                      value 2 ;
                                      description 'Great than or equal to.'
                                                  ;
                                    }
                                    enum le {
                                      value 3 ;
                                      description 'Less than or equal to.'
                                                  ;
                                    }
                                  }
                                  mandatory true ;
                                }
                                leaf src-port-value {
                                  description 'Configure port number from 0 to 65535.'+"\n"
                                            + 'Some has specific means when port protocol type is TCP.'+"\n"
                                            + '  bgp        Border gateway protocol (179)'+"\n"
                                            + '  domain     Domain name service (53)'+"\n"
                                            + '  finger     Finger (79)'+"\n"
                                            + '  ftp        File transfer protocol (21)'+"\n"
                                            + '  login      Login (rlogin, 513)'+"\n"
                                            + '  pop2       Post office protocol v2 (109)'+"\n"
                                            + '  pop3       Post office protocol v3 (110)'+"\n"
                                            + '  smtp       Simple mail transport protocol (25)'+"\n"
                                            + '  telnet     Telnet (23)'+"\n"
                                            + '  www        World wide web (HTTP, 80)'+"\n"
                                            + 'Some has specific means when port protocol type is UDP.'+"\n"
                                            + '  bootpc       Bootstrap protocol (BOOTP) client (68)'+"\n"
                                            + '  bootps       Bootstrap protocol (BOOTP) server (67)'+"\n"
                                            + '  domain       Domain name service (DNS, 53)'+"\n"
                                            + '  ntp          Network time protocol (123)'+"\n"
                                            + '  pim-auto-rp  PIM auto-RP (496)'+"\n"
                                            + '  rip          Routing information protocol (router, in.routed, 520)'+"\n"
                                            + '  snmp         Simple network management protocol (161)'+"\n"
                                            + '  snmptrap     SNMP traps (162)'+"\n"
                                            + '  tftp         Trivial file transfer protocol (69).'
                                              ;
                                  type uint16 {
                                    range 0..65535 ;
                                  }
                                  mandatory true ;
                                }
                              }
                            }
                            case src-port-range {
                              description 'Configure port range.'
                                          ;
                              container src-port-range {
                                description 'Configure port range.'
                                            ;
                                presence 'Configure port range'
                                         ;
                                leaf src-port-operator {
                                  description 'Operator type
range(7): match only packet on a given port range.'
                                              ;
                                  type enumeration {
                                    enum range {
                                      value 7 ;
                                      description Range. ;
                                    }
                                  }
                                  mandatory true ;
                                }
                                leaf src-port-range {
                                  description 'Port range, support <0-65535>-<0-65535>.'
                                              ;
                                  type acl-port-range ;
                                  mandatory true ;
                                }
                              }
                            }
                          }
                        }
                        choice dst-addr {
                          description 'Configure destination address.'
                                      ;
                          mandatory true ;
                          case addr-type {
                            description 'Configure destination address.'
                                        ;
                            leaf dst-address {
                              description 'Configure destination address.'
                                          ;
                              type ncd:ipv4-address ;
                              mandatory true ;
                            }
                            leaf dst-wildcard {
                              description 'Destination wildcard bits'
                                          ;
                              type ncd:ipv4-address ;
                              mandatory true ;
                            }
                          }
                          case any-type {
                            description 'Any destination address.'
                                        ;
                            leaf dst-any-addr {
                              description 'Any destination address.'
                                          ;
                              type empty ;
                              mandatory true ;
                            }
                          }
                        }
                        container destination-port {
                          description 'Specify destination port.'+"\n"
                                    + 'When the value of operator is invalid, i'
                                    + 't means match all port range,'+"\n"
                                    + 'the other value of operator means'+"\n"
                                    + 'eq(1)   : match only packets on a given '
                                    + 'port number'+"\n"
                                    + 'ge(2)   : match only packets with a no l'
                                    + 'ower port number'+"\n"
                                    + 'le(3)   : match only packets with a no g'
                                    + 'reater port number'+"\n"
                                    + 'range(7): match only packet on a given p'
                                    + 'ort range.'
                                      ;
                          presence 'Specify destination port'
                                   ;
                          choice destination-port {
                            description 'Specify destination port.'+"\n"
                                      + 'When the value of operator is invalid, it means match all port range,'+"\n"
                                      + 'the other value of operator means'+"\n"
                                      + 'eq(1)   : match only packets on a given port number'+"\n"
                                      + 'ge(2)   : match only packets with a no lower port number'+"\n"
                                      + 'le(3)   : match only packets with a no greater port number'+"\n"
                                      + 'range(7): match only packet on a given port range.'
                                        ;
                            mandatory true ;
                            case dst-port-value {
                              description 'Configure port number.'
                                          ;
                              container dst-port-value {
                                description 'Configure port number.'
                                            ;
                                presence 'Configure port number'
                                         ;
                                leaf dst-port-operator {
                                  description 'Operator type'+"\n"
                                            + 'eq(1)   : match only packets on a given port number'+"\n"
                                            + 'ge(2)   : match only packets with a no lower port number'+"\n"
                                            + 'le(3)   : match only packets with a no greater port number.'
                                              ;
                                  type enumeration {
                                    enum eq {
                                      value 1 ;
                                      description 'Equal to.'
                                                  ;
                                    }
                                    enum ge {
                                      value 2 ;
                                      description 'Great than or equal to.'
                                                  ;
                                    }
                                    enum le {
                                      value 3 ;
                                      description 'Less than or equal to.'
                                                  ;
                                    }
                                  }
                                  mandatory true ;
                                }
                                leaf dst-port-value {
                                  description 'Configure port number from 0 to 65535.'+"\n"
                                            + 'Some has specific means when port protocol type is TCP.'+"\n"
                                            + '  bgp        Border gateway protocol (179)'+"\n"
                                            + '  domain     Domain name service (53)'+"\n"
                                            + '  finger     Finger (79)'+"\n"
                                            + '  ftp        File transfer protocol (21)'+"\n"
                                            + '  login      Login (rlogin, 513)'+"\n"
                                            + '  pop2       Post office protocol v2 (109)'+"\n"
                                            + '  pop3       Post office protocol v3 (110)'+"\n"
                                            + '  smtp       Simple mail transport protocol (25)'+"\n"
                                            + '  telnet     Telnet (23)'+"\n"
                                            + '  www        World wide web (HTTP, 80)'+"\n"
                                            + 'Some has specific means when port protocol type is UDP.'+"\n"
                                            + '  bootpc       Bootstrap protocol (BOOTP) client (68)'+"\n"
                                            + '  bootps       Bootstrap protocol (BOOTP) server (67)'+"\n"
                                            + '  domain       Domain name service (DNS, 53)'+"\n"
                                            + '  ntp          Network time protocol (123)'+"\n"
                                            + '  pim-auto-rp  PIM auto-RP (496)'+"\n"
                                            + '  rip          Routing information protocol (router, in.routed, 520)'+"\n"
                                            + '  snmp         Simple network management protocol (161)'+"\n"
                                            + '  snmptrap     SNMP traps (162)'+"\n"
                                            + '  tftp         Trivial file transfer protocol (69).'
                                              ;
                                  type uint16 {
                                    range 0..65535 ;
                                  }
                                  mandatory true ;
                                }
                              }
                            }
                            case dst-port-range {
                              description 'Configure port range.'
                                          ;
                              container dst-port-range {
                                description 'Configure port range.'
                                            ;
                                presence 'Configure port range'
                                         ;
                                leaf dst-port-operator {
                                  description 'Operator type
range(7): match only packet on a given port range.'
                                              ;
                                  type enumeration {
                                    enum range {
                                      value 7 ;
                                      description Range. ;
                                    }
                                  }
                                  mandatory true ;
                                }
                                leaf dst-port-range {
                                  description 'Port range, support <0-65535>-<0-65535>.'
                                              ;
                                  type acl-port-range ;
                                  mandatory true ;
                                }
                              }
                            }
                          }
                        }
                      }
                    }
                    case ip {
                      description 'Configure protocol type of IPv4 VXLAN acl in'
                                + ' inner-layer as follows:'+"\n"
                                + 'IP protocol number(0-255)'+"\n"
                                + 'Some has specific mean:'+"\n"
                                + 'gre      Generic Routing Encapsulation (47)
'
                                + ''+"\n"
                                + 'icmp     Internet Control Message Protocol(1'
                                + ')'+"\n"
                                + 'igmp     Internet Group Management Protocol '
                                + '(2)'+"\n"
                                + 'ospf     Open Shortest Path First Protocol ('
                                + '89)'+"\n"
                                + 'pim      Protocol Independent Multicast (103'
                                + ')'+"\n"
                                + 'vrrp     Virtual Router Redundancy Protocol '
                                + '(112)'+"\n"
                                + 'ip       Any IP protocol (65535).'
                                  ;
                      container ipv4-protocol {
                        description 'Configure protocol type of IPv4 VXLAN acl '
                                  + 'in inner-layer as follows:'+"\n"
                                  + 'IP protocol number(0-255)'+"\n"
                                  + 'Some has specific mean:'+"\n"
                                  + 'gre      Generic Routing Encapsulation (47'
                                  + ')'+"\n"
                                  + 'icmp     Internet Control Message Protocol'
                                  + '(1)'+"\n"
                                  + 'igmp     Internet Group Management Protoco'
                                  + 'l (2)'+"\n"
                                  + 'ospf     Open Shortest Path First Protocol'
                                  + ' (89)'+"\n"
                                  + 'pim      Protocol Independent Multicast (1'
                                  + '03)'+"\n"
                                  + 'vrrp     Virtual Router Redundancy Protoco'
                                  + 'l (112)'+"\n"
                                  + 'ip       Any IP protocol (65535).'
                                    ;
                        leaf protocol-type {
                          description 'IP protocol number'+"\n"
                                    + 'Some has specific mean:'+"\n"
                                    + 'gre      Generic Routing Encapsulation ('
                                    + '47)'+"\n"
                                    + 'icmp     Internet Control Message Protoc'
                                    + 'ol(1)'+"\n"
                                    + 'igmp     Internet Group Management Proto'
                                    + 'col (2)'+"\n"
                                    + 'ospf     Open Shortest Path First Protoc'
                                    + 'ol (89)'+"\n"
                                    + 'pim      Protocol Independent Multicast '
                                    + '(103)'+"\n"
                                    + 'vrrp     Virtual Router Redundancy Proto'
                                    + 'col (112)'+"\n"
                                    + 'ip       Any IP protocol (65535).'
                                      ;
                          type uint16 {
                            range '0..5 | 7..16 | 18..255 | 65535'
                                  ;
                          }
                          mandatory true ;
                        }
                        choice src-addr {
                          description 'Configure source address.'
                                      ;
                          mandatory true ;
                          case addr-type {
                            description 'Configure source address.'
                                        ;
                            leaf src-address {
                              description 'Configure source address.'
                                          ;
                              type ncd:ipv4-address ;
                              mandatory true ;
                            }
                            leaf src-wildcard {
                              description 'Source wildcard bits.'
                                          ;
                              type ncd:ipv4-address ;
                              mandatory true ;
                            }
                          }
                          case any-type {
                            description 'Any source address.'
                                        ;
                            leaf src-any-addr {
                              description 'Any source address.'
                                          ;
                              type empty ;
                              mandatory true ;
                            }
                          }
                        }
                        choice dst-addr {
                          description 'Configure destination address.'
                                      ;
                          mandatory true ;
                          case addr-type {
                            description 'Configure destination address.'
                                        ;
                            leaf dst-address {
                              description 'Configure destination address.'
                                          ;
                              type ncd:ipv4-address ;
                              mandatory true ;
                            }
                            leaf dst-wildcard {
                              description 'Destination wildcard bits'
                                          ;
                              type ncd:ipv4-address ;
                              mandatory true ;
                            }
                          }
                          case any-type {
                            description 'Any destination address.'
                                        ;
                            leaf dst-any-addr {
                              description 'Any destination address.'
                                          ;
                              type empty ;
                              mandatory true ;
                            }
                          }
                        }
                      }
                    }
                  }
                  choice priority {
                    description 'Configure precedence or TOS or DSCP.'
                                ;
                    case dscp {
                      description 'DSCP value.'
                                  ;
                      leaf dscp {
                        description 'DSCP value.'
                                    ;
                        type uint8 {
                          range 0..63 ;
                        }
                      }
                    }
                    case precedence {
                      description 'Precedence level.'
                                  ;
                      leaf precedence {
                        description 'Precedence level.'
                                    ;
                        type uint8 {
                          range 0..7 ;
                        }
                      }
                    }
                    case tos {
                      description 'Type of service(TOS).'
                                  ;
                      leaf tos {
                        description 'Type of service(TOS).'
                                    ;
                        type uint8 {
                          range 0..15 ;
                        }
                      }
                    }
                  }
                }
                container vni {
                  description 'VXLAN ID.'
                              ;
                  presence vni ;
                  leaf vxlan-id {
                    description 'VXLAN ID.'
                                ;
                    type uint32 {
                      range 1..16777215 ;
                    }
                    mandatory true ;
                  }
                }
                container sgt {
                  description 'Security Group Tag'
                              ;
                  presence sgt ;
                  leaf sgt-value {
                    description 'Security Group Tag Value'
                                ;
                    type uint16 ;
                    mandatory true ;
                  }
                  ncd:revise-date 2019-08-14 ;
                }
                leaf vrf {
                  description 'VPN Routing/Forwarding instance name, support 1-'
                            + '32 characters.'
                              ;
                  type acl-vrf-name {
                    length 1..32 {
                      description 'VPN Routing/Forwarding instance name, suppor'
                                + 't 1-32 characters.'
                                  ;
                    }
                  }
                }
                leaf time-range {
                  description 'Specify the existed time-range name.'
                              ;
                  type string {
                    length 1..31 ;
                  }
                  ncd:revise-date 2021-04-02 ;
                }
                container l2-layer {
                  if-feature l2-layer ;
                  description 'L2 information.'
                              ;
                  presence l2-layer ;
                  container link-prot {
                    description 'Specify Link protocol type.'
                                ;
                    choice link-prot {
                      description 'Specify Link protocol type.'
                                  ;
                      case link-protocol {
                        description 'Specify Link protocol type.'
                                    ;
                        leaf link-protocol {
                          description 'Specify Link protocol type.'
                                      ;
                          type uint32 {
                            range 1536..65535 ;
                          }
                        }
                      }
                      case link-protocol-hex {
                        if-feature link-prot-hex-config ;
                        description 'Specify Link protocol type, hex.'
                                    ;
                        leaf link-protocol-hex {
                          description 'Specify Link protocol type, hex.'
                                      ;
                          type ncd:hex ;
                        }
                      }
                    }
                  }
                  container source-mac {
                    description 'Specify source MAC address.'
                                ;
                    choice src-mac-addr {
                      description 'Specify source MAC address.'
                                  ;
                      mandatory true ;
                      case src-mac-addr {
                        description 'MAC address.'
                                    ;
                        leaf src-mac-address {
                          description 'MAC address.'
                                      ;
                          type ncd:mac-address ;
                          mandatory true ;
                        }
                        leaf src-mac-wildcard {
                          description 'MAC address wildcard.'
                                      ;
                          type ncd:mac-address ;
                          mandatory true ;
                        }
                      }
                      case src-mac-any {
                        description 'Any MAC address.'
                                    ;
                        leaf src-mac-any {
                          description 'Any MAC address.'
                                      ;
                          type empty ;
                          mandatory true ;
                        }
                      }
                    }
                  }
                  container destination-mac {
                    description 'Specify destination MAC address.'
                                ;
                    choice dest-mac-addr {
                      description 'Specify destination MAC address.'
                                  ;
                      mandatory true ;
                      case dest-mac-addr {
                        description 'MAC address.'
                                    ;
                        leaf dest-mac-address {
                          description 'MAC address.'
                                      ;
                          type ncd:mac-address ;
                          mandatory true ;
                        }
                        leaf dest-mac-wildcard {
                          description 'MAC address wildcard.'
                                      ;
                          type ncd:mac-address ;
                          mandatory true ;
                        }
                      }
                      case dest-mac-any {
                        description 'Any MAC address.'
                                    ;
                        leaf dest-mac-any {
                          description 'Any MAC address.'
                                      ;
                          type empty ;
                          mandatory true ;
                        }
                      }
                    }
                  }
                  leaf inner-cos {
                    if-feature link-cos-value ;
                    description 'Value of inner CoS.'
                                ;
                    type uint8 {
                      range 0..7 ;
                    }
                  }
                  leaf outer-cos {
                    if-feature link-cos-value ;
                    description 'Value of outer CoS.'
                                ;
                    type uint8 {
                      range 0..7 ;
                    }
                  }
                  leaf inner-vlan-range {
                    description 'Specify range of inner VLAN.'
                                ;
                    type acl-vlan-range ;
                  }
                  leaf outer-vlan-range {
                    description 'Specify range of outer VLAN.'
                                ;
                    type acl-vlan-range ;
                  }
                  ncd:revise-date 2021-10-26 ;
                }
                leaf log {
                  if-feature log-config ;
                  description 'If log flag is set, the matching times of this r'
                            + 'ule will be recorded.'
                              ;
                  type boolean ;
                  default false ;
                  ncd:revise-date 2022-01-20 ;
                }
              }
              ncd:revise-date 2018-09-17 ;
            }
            container rules-transit-outer {
              description 'Configure rule of an IPv4 VXLAN ACL.'
                          ;
              list rule-transit-outer {
                description 'Configure rule of an IPv4 VXLAN ACL.'
                            ;
                key ruleid ;
                leaf ruleid {
                  description 'ID of this rule.'
                              ;
                  type uint32 {
                    range 1..2147483644 ;
                  }
                }
                choice permit-deny {
                  description 'Deny  :  Specify packets to reject'+"\n"
                            + 'Permit:  Specify packets to forward.'
                              ;
                  mandatory true ;
                  case deny {
                    description 'Deny:Specify packets to reject.'
                                ;
                    leaf deny {
                      description 'Deny:Specify packets to reject.'
                                  ;
                      type empty ;
                      mandatory true ;
                    }
                  }
                  case permit {
                    description 'Permit:  Specify packets to forward.'
                                ;
                    leaf permit {
                      description 'Permit:  Specify packets to forward.'
                                  ;
                      type empty ;
                      mandatory true ;
                    }
                  }
                }
                container vni {
                  description 'VXLAN ID.'
                              ;
                  presence vni ;
                  leaf vxlan-id {
                    description 'VXLAN ID.'
                                ;
                    type uint32 {
                      range 1..16777215 ;
                    }
                    mandatory true ;
                  }
                }
                container sgt {
                  description 'Security Group Tag'
                              ;
                  presence sgt ;
                  leaf sgt-value {
                    description 'Security Group Tag Value'
                                ;
                    type uint16 ;
                    mandatory true ;
                  }
                  ncd:revise-date 2019-08-14 ;
                }
                container outer-layer {
                  description 'The outer-layer protocol of VXLAN.'
                              ;
                  leaf udp {
                    description 'Configure UDP protocol.'
                                ;
                    type empty ;
                    mandatory true ;
                  }
                  choice src-addr {
                    description 'Configure source address.'
                                ;
                    mandatory true ;
                    case addr-type {
                      description 'Configure source address.'
                                  ;
                      leaf src-address {
                        description 'Configure source address.'
                                    ;
                        type ncd:ipv4-address ;
                        mandatory true ;
                      }
                      leaf src-wildcard {
                        description 'Source wildcard bits.'
                                    ;
                        type ncd:ipv4-address ;
                        mandatory true ;
                      }
                    }
                    case any-type {
                      description 'Any source address.'
                                  ;
                      leaf src-any-addr {
                        description 'Any source address.'
                                    ;
                        type empty ;
                        mandatory true ;
                      }
                    }
                  }
                  container source-port {
                    description 'Specify source port.'+"\n"
                              + 'When the value of operator is invalid, it mean'
                              + 's match all port range,'+"\n"
                              + 'the other value of operator means'+"\n"
                              + 'eq(1)   : match only packets on a given port n'
                              + 'umber'+"\n"
                              + 'ge(2)   : match only packets with a no lower p'
                              + 'ort number'+"\n"
                              + 'le(3)   : match only packets with a no greater'
                              + ' port number'+"\n"
                              + 'range(7): match only packet on a given port ra'
                              + 'nge.'
                                ;
                    presence 'Specify source port'
                             ;
                    choice source-port {
                      description 'Specify source port.'+"\n"
                                + 'When the value of operator is invalid, it me'
                                + 'ans match all port range,'+"\n"
                                + 'the other value of operator means'+"\n"
                                + 'eq(1)   : match only packets on a given port'
                                + ' number'+"\n"
                                + 'ge(2)   : match only packets with a no lower'
                                + ' port number'+"\n"
                                + 'le(3)   : match only packets with a no great'
                                + 'er port number'+"\n"
                                + 'range(7): match only packet on a given port '
                                + 'range.'
                                  ;
                      mandatory true ;
                      case src-port-value {
                        description 'Configure port number.'
                                    ;
                        container src-port-value {
                          description 'Configure port number.'
                                      ;
                          presence 'Configure port number'
                                   ;
                          leaf src-port-operator {
                            description 'Operator type'+"\n"
                                      + 'eq(1)   : match only packets on a given port number'+"\n"
                                      + 'ge(2)   : match only packets with a no lower port number'+"\n"
                                      + 'le(3)   : match only packets with a no greater port number.'
                                        ;
                            type enumeration {
                              enum eq {
                                value 1 ;
                                description 'Equal to.'
                                            ;
                              }
                              enum ge {
                                value 2 ;
                                description 'Great than or equal to.'
                                            ;
                              }
                              enum le {
                                value 3 ;
                                description 'Less than or equal to.'
                                            ;
                              }
                            }
                            mandatory true ;
                          }
                          leaf src-port-value {
                            description 'Port number.'+"\n"
                                      + 'Some has specific means:'+"\n"
                                      + 'bootpc       Bootstrap protocol (BOOTP) client (68)'+"\n"
                                      + 'bootps       Bootstrap protocol (BOOTP) server (67)'+"\n"
                                      + 'domain       Domain name service (DNS, 53)'+"\n"
                                      + 'ntp          Network time protocol (123)'+"\n"
                                      + 'pim-auto-rp  PIM auto-RP (496)'+"\n"
                                      + 'rip          Routing information protocol (router, in.routed, 520)'+"\n"
                                      + 'snmp         Simple network management protocol (161)'+"\n"
                                      + 'snmptrap     SNMP traps (162)'+"\n"
                                      + 'tftp         Trivial file transfer protocol (69).'
                                        ;
                            type uint16 {
                              range 0..65535 ;
                            }
                            mandatory true ;
                          }
                        }
                      }
                      case src-port-range {
                        description 'Configure port range.'
                                    ;
                        container src-port-range {
                          description 'Configure port range.'
                                      ;
                          presence 'Configure port range'
                                   ;
                          leaf src-port-operator {
                            description 'Operator type
range(7): match only packet on a given port range.'
                                        ;
                            type enumeration {
                              enum range {
                                value 7 ;
                                description Range. ;
                              }
                            }
                            mandatory true ;
                          }
                          leaf src-port-range {
                            description 'Port range, support <0-65535>-<0-65535>.'
                                        ;
                            type acl-port-range ;
                            mandatory true ;
                          }
                        }
                      }
                    }
                  }
                  choice dst-addr {
                    description 'Configure destination address.'
                                ;
                    mandatory true ;
                    case addr-type {
                      description 'Configure destination address.'
                                  ;
                      leaf dst-address {
                        description 'Configure destination address.'
                                    ;
                        type ncd:ipv4-address ;
                        mandatory true ;
                      }
                      leaf dst-wildcard {
                        description 'Destination wildcard bits'
                                    ;
                        type ncd:ipv4-address ;
                        mandatory true ;
                      }
                    }
                    case any-type {
                      description 'Any destination address.'
                                  ;
                      leaf dst-any-addr {
                        description 'Any destination address.'
                                    ;
                        type empty ;
                        mandatory true ;
                      }
                    }
                  }
                  container destination-port {
                    description 'Specify destination port.'+"\n"
                              + 'When the value of operator is invalid, it mean'
                              + 's match all port range,'+"\n"
                              + 'the other value of operator means'+"\n"
                              + 'eq(1)   : match only packets on a given port n'
                              + 'umber'+"\n"
                              + 'ge(2)   : match only packets with a no lower p'
                              + 'ort number'+"\n"
                              + 'le(3)   : match only packets with a no greater'
                              + ' port number'+"\n"
                              + 'range(7): match only packet on a given port ra'
                              + 'nge.'
                                ;
                    presence 'Specify destination port'
                             ;
                    choice destination-port {
                      description 'Specify destination port.'+"\n"
                                + 'When the value of operator is invalid, it me'
                                + 'ans match all port range,'+"\n"
                                + 'the other value of operator means'+"\n"
                                + 'eq(1)   : match only packets on a given port'
                                + ' number'+"\n"
                                + 'ge(2)   : match only packets with a no lower'
                                + ' port number'+"\n"
                                + 'le(3)   : match only packets with a no great'
                                + 'er port number'+"\n"
                                + 'range(7): match only packet on a given port '
                                + 'range.'
                                  ;
                      mandatory true ;
                      case dst-port-value {
                        description 'Configure port number.'
                                    ;
                        container dst-port-value {
                          description 'Configure port number.'
                                      ;
                          presence 'Configure port number'
                                   ;
                          leaf dst-port-operator {
                            description 'Operator type'+"\n"
                                      + 'eq(1)   : match only packets on a given port number'+"\n"
                                      + 'ge(2)   : match only packets with a no lower port number'+"\n"
                                      + 'le(3)   : match only packets with a no greater port number.'
                                        ;
                            type enumeration {
                              enum eq {
                                value 1 ;
                                description 'Equal to.'
                                            ;
                              }
                              enum ge {
                                value 2 ;
                                description 'Great than or equal to.'
                                            ;
                              }
                              enum le {
                                value 3 ;
                                description 'Less than or equal to.'
                                            ;
                              }
                            }
                            mandatory true ;
                          }
                          leaf dst-port-value {
                            description 'Port number.'+"\n"
                                      + 'Some has specific means:'+"\n"
                                      + 'bootpc       Bootstrap protocol (BOOTP) client (68)'+"\n"
                                      + 'bootps       Bootstrap protocol (BOOTP) server (67)'+"\n"
                                      + 'domain       Domain name service (DNS, 53)'+"\n"
                                      + 'ntp          Network time protocol (123)'+"\n"
                                      + 'pim-auto-rp  PIM auto-RP (496)'+"\n"
                                      + 'rip          Routing information protocol (router, in.routed, 520)'+"\n"
                                      + 'snmp         Simple network management protocol (161)'+"\n"
                                      + 'snmptrap     SNMP traps (162)'+"\n"
                                      + 'tftp         Trivial file transfer protocol (69).'
                                        ;
                            type uint16 {
                              range 0..65535 ;
                            }
                            mandatory true ;
                          }
                        }
                      }
                      case dst-port-range {
                        description 'Configure port range.'
                                    ;
                        container dst-port-range {
                          description 'Configure port range.'
                                      ;
                          presence 'Configure port range'
                                   ;
                          leaf dst-port-operator {
                            description 'Operator type
range(7): match only packet on a given port range.'
                                        ;
                            type enumeration {
                              enum range {
                                value 7 ;
                                description Range. ;
                              }
                            }
                            mandatory true ;
                          }
                          leaf dst-port-range {
                            description 'Port range, support <0-65535>-<0-65535>.'
                                        ;
                            type acl-port-range ;
                            mandatory true ;
                          }
                        }
                      }
                    }
                  }
                  choice priority {
                    description 'Configure precedence or TOS or DSCP.'
                                ;
                    case dscp {
                      description 'DSCP value.'
                                  ;
                      leaf dscp {
                        description 'DSCP value.'
                                    ;
                        type uint8 {
                          range 0..63 ;
                        }
                      }
                    }
                    case precedence {
                      description 'Precedence level.'
                                  ;
                      leaf precedence {
                        description 'Precedence level.'
                                    ;
                        type uint8 {
                          range 0..7 ;
                        }
                      }
                    }
                    case tos {
                      description 'Type of service(TOS).'
                                  ;
                      leaf tos {
                        description 'Type of service(TOS).'
                                    ;
                        type uint8 {
                          range 0..15 ;
                        }
                      }
                    }
                  }
                }
                leaf vrf {
                  description 'VPN Routing/Forwarding instance name, support 1-'
                            + '32 characters.'
                              ;
                  type acl-vrf-name {
                    length 1..32 {
                      description 'VPN Routing/Forwarding instance name, suppor'
                                + 't 1-32 characters.'
                                  ;
                    }
                  }
                }
                leaf time-range {
                  description 'Specify the existed time-range name.'
                              ;
                  type string {
                    length 1..31 ;
                  }
                  ncd:revise-date 2021-04-02 ;
                }
              }
              ncd:revise-date 2018-09-17 ;
            }
            container rules-vtep-inner {
              description 'Configure rule of an IPv4 VXLAN ACL.'
                          ;
              list rule-vtep-inner {
                description 'Configure rule of an IPv4 VXLAN ACL.'
                            ;
                key ruleid ;
                leaf ruleid {
                  description 'ID of this rule.'
                              ;
                  type uint32 {
                    range 1..2147483644 ;
                  }
                }
                choice permit-deny {
                  description 'Deny  :  Specify packets to reject'+"\n"
                            + 'Permit:  Specify packets to forward.'
                              ;
                  mandatory true ;
                  case deny {
                    description 'Deny:Specify packets to reject.'
                                ;
                    leaf deny {
                      description 'Deny:Specify packets to reject.'
                                  ;
                      type empty ;
                      mandatory true ;
                    }
                  }
                  case permit {
                    description 'Permit:  Specify packets to forward.'
                                ;
                    leaf permit {
                      description 'Permit:  Specify packets to forward.'
                                  ;
                      type empty ;
                      mandatory true ;
                    }
                  }
                }
                container inner-layer {
                  description 'The inner-layer protocol of VXLAN.'
                              ;
                  presence inner-layer ;
                  choice protocol-type {
                    description 'Configure protocol type of IPv4 VXLAN acl in i'
                              + 'nner-layer as follows:'+"\n"
                              + 'IP protocol number(0-255)'+"\n"
                              + 'Some has specific mean:'+"\n"
                              + 'gre      Generic Routing Encapsulation (47)'+"\n"
                              + 'icmp     Internet Control Message Protocol(1)
'
                              + ''+"\n"
                              + 'igmp     Internet Group Management Protocol (2'
                              + ')'+"\n"
                              + 'ospf     Open Shortest Path First Protocol (89'
                              + ')'+"\n"
                              + 'pim      Protocol Independent Multicast (103)
'
                              + ''+"\n"
                              + 'tcp      Transmission Control Protocol(6)'+"\n"
                              + 'udp      User Datagram Protocol(17)'+"\n"
                              + 'vrrp     Virtual Router Redundancy Protocol (1'
                              + '12)'+"\n"
                              + 'ip       Any IP protocol (65535).'
                                ;
                    mandatory true ;
                    case tcp-udp {
                      description 'Configure TCP or UDP protocol of IPv4 VXLAN '
                                + 'ACL.'+"\n"
                                + 'tcp      Transmission Control Protocol(6)'+"\n"
                                + 'udp      User Datagram Protocol(17)'
                                  ;
                      container tcp-udp {
                        description 'Configure protocol type of IPv4 VXLAN ACL.'
                                  + ''+"\n"
                                  + 'tcp      Transmission Control Protocol(6)
'
                                  + ''+"\n"
                                  + 'udp      User Datagram Protocol(17)'
                                    ;
                        leaf tcp-udp {
                          description 'Configure protocol type of IPv4 VXLAN AC'
                                    + 'L.'+"\n"
                                    + 'tcp      Transmission Control Protocol(6'
                                    + ')'+"\n"
                                    + 'udp      User Datagram Protocol(17)'
                                      ;
                          type enumeration {
                            enum tcp {
                              value 6 ;
                              description 'Transmission Control Protocol(6)'
                                          ;
                            }
                            enum udp {
                              value 17 ;
                              description 'User Datagram Protocol(17)'
                                          ;
                            }
                          }
                          mandatory true ;
                        }
                        choice src-addr {
                          description 'Configure source address.'
                                      ;
                          mandatory true ;
                          case addr-type {
                            description 'Configure source address.'
                                        ;
                            leaf src-address {
                              description 'Configure source address.'
                                          ;
                              type ncd:ipv4-address ;
                              mandatory true ;
                            }
                            leaf src-wildcard {
                              description 'Source wildcard bits.'
                                          ;
                              type ncd:ipv4-address ;
                              mandatory true ;
                            }
                          }
                          case any-type {
                            description 'Any source address.'
                                        ;
                            leaf src-any-addr {
                              description 'Any source address.'
                                          ;
                              type empty ;
                              mandatory true ;
                            }
                          }
                        }
                        container source-port {
                          description 'Specify source port.'+"\n"
                                    + 'When the value of operator is invalid, i'
                                    + 't means match all port range,'+"\n"
                                    + 'the other value of operator means'+"\n"
                                    + 'eq(1)   : match only packets on a given '
                                    + 'port number'+"\n"
                                    + 'ge(2)   : match only packets with a no l'
                                    + 'ower port number'+"\n"
                                    + 'le(3)   : match only packets with a no g'
                                    + 'reater port number'+"\n"
                                    + 'range(7): match only packet on a given p'
                                    + 'ort range.'
                                      ;
                          presence 'Specify source port'
                                   ;
                          choice source-port {
                            description 'Specify source port.'+"\n"
                                      + 'When the value of operator is invalid, it means match all port range,'+"\n"
                                      + 'the other value of operator means'+"\n"
                                      + 'eq(1)   : match only packets on a given port number'+"\n"
                                      + 'ge(2)   : match only packets with a no lower port number'+"\n"
                                      + 'le(3)   : match only packets with a no greater port number'+"\n"
                                      + 'range(7): match only packet on a given port range.'
                                        ;
                            mandatory true ;
                            case src-port-value {
                              description 'Configure port number.'
                                          ;
                              container src-port-value {
                                description 'Configure port number.'
                                            ;
                                presence 'Configure port number'
                                         ;
                                leaf src-port-operator {
                                  description 'Operator type'+"\n"
                                            + 'eq(1)   : match only packets on a given port number'+"\n"
                                            + 'ge(2)   : match only packets with a no lower port number'+"\n"
                                            + 'le(3)   : match only packets with a no greater port number.'
                                              ;
                                  type enumeration {
                                    enum eq {
                                      value 1 ;
                                      description 'Equal to.'
                                                  ;
                                    }
                                    enum ge {
                                      value 2 ;
                                      description 'Great than or equal to.'
                                                  ;
                                    }
                                    enum le {
                                      value 3 ;
                                      description 'Less than or equal to.'
                                                  ;
                                    }
                                  }
                                  mandatory true ;
                                }
                                leaf src-port-value {
                                  description 'Configure port number from 0 to 65535.'+"\n"
                                            + 'Some has specific means when port protocol type is TCP.'+"\n"
                                            + '  bgp        Border gateway protocol (179)'+"\n"
                                            + '  domain     Domain name service (53)'+"\n"
                                            + '  finger     Finger (79)'+"\n"
                                            + '  ftp        File transfer protocol (21)'+"\n"
                                            + '  login      Login (rlogin, 513)'+"\n"
                                            + '  pop2       Post office protocol v2 (109)'+"\n"
                                            + '  pop3       Post office protocol v3 (110)'+"\n"
                                            + '  smtp       Simple mail transport protocol (25)'+"\n"
                                            + '  telnet     Telnet (23)'+"\n"
                                            + '  www        World wide web (HTTP, 80)'+"\n"
                                            + 'Some has specific means when port protocol type is UDP.'+"\n"
                                            + '  bootpc       Bootstrap protocol (BOOTP) client (68)'+"\n"
                                            + '  bootps       Bootstrap protocol (BOOTP) server (67)'+"\n"
                                            + '  domain       Domain name service (DNS, 53)'+"\n"
                                            + '  ntp          Network time protocol (123)'+"\n"
                                            + '  pim-auto-rp  PIM auto-RP (496)'+"\n"
                                            + '  rip          Routing information protocol (router, in.routed, 520)'+"\n"
                                            + '  snmp         Simple network management protocol (161)'+"\n"
                                            + '  snmptrap     SNMP traps (162)'+"\n"
                                            + '  tftp         Trivial file transfer protocol (69).'
                                              ;
                                  type uint16 {
                                    range 0..65535 ;
                                  }
                                  mandatory true ;
                                }
                              }
                            }
                            case src-port-range {
                              description 'Configure port range.'
                                          ;
                              container src-port-range {
                                description 'Configure port range.'
                                            ;
                                presence 'Configure port range'
                                         ;
                                leaf src-port-operator {
                                  description 'Operator type
range(7): match only packet on a given port range.'
                                              ;
                                  type enumeration {
                                    enum range {
                                      value 7 ;
                                      description Range. ;
                                    }
                                  }
                                  mandatory true ;
                                }
                                leaf src-port-range {
                                  description 'Port range, support <0-65535>-<0-65535>.'
                                              ;
                                  type acl-port-range ;
                                  mandatory true ;
                                }
                              }
                            }
                          }
                        }
                        choice dst-addr {
                          description 'Configure destination address.'
                                      ;
                          mandatory true ;
                          case addr-type {
                            description 'Configure destination address.'
                                        ;
                            leaf dst-address {
                              description 'Configure destination address.'
                                          ;
                              type ncd:ipv4-address ;
                              mandatory true ;
                            }
                            leaf dst-wildcard {
                              description 'Destination wildcard bits'
                                          ;
                              type ncd:ipv4-address ;
                              mandatory true ;
                            }
                          }
                          case any-type {
                            description 'Any destination address.'
                                        ;
                            leaf dst-any-addr {
                              description 'Any destination address.'
                                          ;
                              type empty ;
                              mandatory true ;
                            }
                          }
                        }
                        container destination-port {
                          description 'Specify destination port.'+"\n"
                                    + 'When the value of operator is invalid, i'
                                    + 't means match all port range,'+"\n"
                                    + 'the other value of operator means'+"\n"
                                    + 'eq(1)   : match only packets on a given '
                                    + 'port number'+"\n"
                                    + 'ge(2)   : match only packets with a no l'
                                    + 'ower port number'+"\n"
                                    + 'le(3)   : match only packets with a no g'
                                    + 'reater port number'+"\n"
                                    + 'range(7): match only packet on a given p'
                                    + 'ort range.'
                                      ;
                          presence 'Specify destination port'
                                   ;
                          choice destination-port {
                            description 'Specify destination port.'+"\n"
                                      + 'When the value of operator is invalid, it means match all port range,'+"\n"
                                      + 'the other value of operator means'+"\n"
                                      + 'eq(1)   : match only packets on a given port number'+"\n"
                                      + 'ge(2)   : match only packets with a no lower port number'+"\n"
                                      + 'le(3)   : match only packets with a no greater port number'+"\n"
                                      + 'range(7): match only packet on a given port range.'
                                        ;
                            mandatory true ;
                            case dst-port-value {
                              description 'Configure port number.'
                                          ;
                              container dst-port-value {
                                description 'Configure port number.'
                                            ;
                                presence 'Configure port number'
                                         ;
                                leaf dst-port-operator {
                                  description 'Operator type'+"\n"
                                            + 'eq(1)   : match only packets on a given port number'+"\n"
                                            + 'ge(2)   : match only packets with a no lower port number'+"\n"
                                            + 'le(3)   : match only packets with a no greater port number.'
                                              ;
                                  type enumeration {
                                    enum eq {
                                      value 1 ;
                                      description 'Equal to.'
                                                  ;
                                    }
                                    enum ge {
                                      value 2 ;
                                      description 'Great than or equal to.'
                                                  ;
                                    }
                                    enum le {
                                      value 3 ;
                                      description 'Less than or equal to.'
                                                  ;
                                    }
                                  }
                                  mandatory true ;
                                }
                                leaf dst-port-value {
                                  description 'Configure port number from 0 to 65535.'+"\n"
                                            + 'Some has specific means when port protocol type is TCP.'+"\n"
                                            + '  bgp        Border gateway protocol (179)'+"\n"
                                            + '  domain     Domain name service (53)'+"\n"
                                            + '  finger     Finger (79)'+"\n"
                                            + '  ftp        File transfer protocol (21)'+"\n"
                                            + '  login      Login (rlogin, 513)'+"\n"
                                            + '  pop2       Post office protocol v2 (109)'+"\n"
                                            + '  pop3       Post office protocol v3 (110)'+"\n"
                                            + '  smtp       Simple mail transport protocol (25)'+"\n"
                                            + '  telnet     Telnet (23)'+"\n"
                                            + '  www        World wide web (HTTP, 80)'+"\n"
                                            + 'Some has specific means when port protocol type is UDP.'+"\n"
                                            + '  bootpc       Bootstrap protocol (BOOTP) client (68)'+"\n"
                                            + '  bootps       Bootstrap protocol (BOOTP) server (67)'+"\n"
                                            + '  domain       Domain name service (DNS, 53)'+"\n"
                                            + '  ntp          Network time protocol (123)'+"\n"
                                            + '  pim-auto-rp  PIM auto-RP (496)'+"\n"
                                            + '  rip          Routing information protocol (router, in.routed, 520)'+"\n"
                                            + '  snmp         Simple network management protocol (161)'+"\n"
                                            + '  snmptrap     SNMP traps (162)'+"\n"
                                            + '  tftp         Trivial file transfer protocol (69).'
                                              ;
                                  type uint16 {
                                    range 0..65535 ;
                                  }
                                  mandatory true ;
                                }
                              }
                            }
                            case dst-port-range {
                              description 'Configure port range.'
                                          ;
                              container dst-port-range {
                                description 'Configure port range.'
                                            ;
                                presence 'Configure port range'
                                         ;
                                leaf dst-port-operator {
                                  description 'Operator type
range(7): match only packet on a given port range.'
                                              ;
                                  type enumeration {
                                    enum range {
                                      value 7 ;
                                      description Range. ;
                                    }
                                  }
                                  mandatory true ;
                                }
                                leaf dst-port-range {
                                  description 'Port range, support <0-65535>-<0-65535>.'
                                              ;
                                  type acl-port-range ;
                                  mandatory true ;
                                }
                              }
                            }
                          }
                        }
                      }
                    }
                    case ip {
                      description 'Configure protocol type of IPv4 VXLAN acl in'
                                + ' inner-layer as follows:'+"\n"
                                + 'IP protocol number(0-255)'+"\n"
                                + 'Some has specific mean:'+"\n"
                                + 'gre      Generic Routing Encapsulation (47)
'
                                + ''+"\n"
                                + 'icmp     Internet Control Message Protocol(1'
                                + ')'+"\n"
                                + 'igmp     Internet Group Management Protocol '
                                + '(2)'+"\n"
                                + 'ospf     Open Shortest Path First Protocol ('
                                + '89)'+"\n"
                                + 'pim      Protocol Independent Multicast (103'
                                + ')'+"\n"
                                + 'vrrp     Virtual Router Redundancy Protocol '
                                + '(112)'+"\n"
                                + 'ip       Any IP protocol (65535).'
                                  ;
                      container ipv4-protocol {
                        description 'Configure protocol type of IPv4 VXLAN acl '
                                  + 'in inner-layer as follows:'+"\n"
                                  + 'IP protocol number(0-255)'+"\n"
                                  + 'Some has specific mean:'+"\n"
                                  + 'gre      Generic Routing Encapsulation (47'
                                  + ')'+"\n"
                                  + 'icmp     Internet Control Message Protocol'
                                  + '(1)'+"\n"
                                  + 'igmp     Internet Group Management Protoco'
                                  + 'l (2)'+"\n"
                                  + 'ospf     Open Shortest Path First Protocol'
                                  + ' (89)'+"\n"
                                  + 'pim      Protocol Independent Multicast (1'
                                  + '03)'+"\n"
                                  + 'vrrp     Virtual Router Redundancy Protoco'
                                  + 'l (112)'+"\n"
                                  + 'ip       Any IP protocol (65535).'
                                    ;
                        leaf protocol-type {
                          description 'IP protocol number'+"\n"
                                    + 'Some has specific mean:'+"\n"
                                    + 'gre      Generic Routing Encapsulation ('
                                    + '47)'+"\n"
                                    + 'icmp     Internet Control Message Protoc'
                                    + 'ol(1)'+"\n"
                                    + 'igmp     Internet Group Management Proto'
                                    + 'col (2)'+"\n"
                                    + 'ospf     Open Shortest Path First Protoc'
                                    + 'ol (89)'+"\n"
                                    + 'pim      Protocol Independent Multicast '
                                    + '(103)'+"\n"
                                    + 'vrrp     Virtual Router Redundancy Proto'
                                    + 'col (112)'+"\n"
                                    + 'ip       Any IP protocol (65535).'
                                      ;
                          type uint16 {
                            range '0..5 | 7..16 | 18..255 | 65535'
                                  ;
                          }
                          mandatory true ;
                        }
                        choice src-addr {
                          description 'Configure source address.'
                                      ;
                          mandatory true ;
                          case addr-type {
                            description 'Configure source address.'
                                        ;
                            leaf src-address {
                              description 'Configure source address.'
                                          ;
                              type ncd:ipv4-address ;
                              mandatory true ;
                            }
                            leaf src-wildcard {
                              description 'Source wildcard bits.'
                                          ;
                              type ncd:ipv4-address ;
                              mandatory true ;
                            }
                          }
                          case any-type {
                            description 'Any source address.'
                                        ;
                            leaf src-any-addr {
                              description 'Any source address.'
                                          ;
                              type empty ;
                              mandatory true ;
                            }
                          }
                        }
                        choice dst-addr {
                          description 'Configure destination address.'
                                      ;
                          mandatory true ;
                          case addr-type {
                            description 'Configure destination address.'
                                        ;
                            leaf dst-address {
                              description 'Configure destination address.'
                                          ;
                              type ncd:ipv4-address ;
                              mandatory true ;
                            }
                            leaf dst-wildcard {
                              description 'Destination wildcard bits'
                                          ;
                              type ncd:ipv4-address ;
                              mandatory true ;
                            }
                          }
                          case any-type {
                            description 'Any destination address.'
                                        ;
                            leaf dst-any-addr {
                              description 'Any destination address.'
                                          ;
                              type empty ;
                              mandatory true ;
                            }
                          }
                        }
                      }
                    }
                  }
                  choice priority {
                    description 'Configure precedence or TOS or DSCP.'
                                ;
                    case dscp {
                      description 'DSCP value.'
                                  ;
                      leaf dscp {
                        description 'DSCP value.'
                                    ;
                        type uint8 {
                          range 0..63 ;
                        }
                      }
                    }
                    case precedence {
                      description 'Precedence level.'
                                  ;
                      leaf precedence {
                        description 'Precedence level.'
                                    ;
                        type uint8 {
                          range 0..7 ;
                        }
                      }
                    }
                    case tos {
                      description 'Type of service(TOS).'
                                  ;
                      leaf tos {
                        description 'Type of service(TOS).'
                                    ;
                        type uint8 {
                          range 0..15 ;
                        }
                      }
                    }
                  }
                }
                container vni {
                  description 'VXLAN ID.'
                              ;
                  presence vni ;
                  leaf vxlan-id {
                    description 'VXLAN ID.'
                                ;
                    type uint32 {
                      range 1..16777215 ;
                    }
                    mandatory true ;
                  }
                }
                container sgt {
                  description 'Security Group Tag'
                              ;
                  presence sgt ;
                  leaf sgt-value {
                    description 'Security Group Tag Value'
                                ;
                    type uint16 ;
                    mandatory true ;
                  }
                  ncd:revise-date 2019-08-14 ;
                }
                leaf vrf {
                  description 'VPN Routing/Forwarding instance name, support 1-'
                            + '32 characters.'
                              ;
                  type acl-vrf-name {
                    length 1..32 {
                      description 'VPN Routing/Forwarding instance name, suppor'
                                + 't 1-32 characters.'
                                  ;
                    }
                  }
                }
                leaf time-range {
                  description 'Specify the existed time-range name.'
                              ;
                  type string {
                    length 1..31 ;
                  }
                  ncd:revise-date 2021-04-02 ;
                }
                container l2-layer {
                  if-feature l2-layer ;
                  description 'L2 information.'
                              ;
                  presence l2-layer ;
                  container link-prot {
                    description 'Specify Link protocol type.'
                                ;
                    choice link-prot {
                      description 'Specify Link protocol type.'
                                  ;
                      case link-protocol {
                        description 'Specify Link protocol type.'
                                    ;
                        leaf link-protocol {
                          description 'Specify Link protocol type.'
                                      ;
                          type uint32 {
                            range 1536..65535 ;
                          }
                        }
                      }
                      case link-protocol-hex {
                        if-feature link-prot-hex-config ;
                        description 'Specify Link protocol type, hex.'
                                    ;
                        leaf link-protocol-hex {
                          description 'Specify Link protocol type, hex.'
                                      ;
                          type ncd:hex ;
                        }
                      }
                    }
                  }
                  container source-mac {
                    description 'Specify source MAC address.'
                                ;
                    choice src-mac-addr {
                      description 'Specify source MAC address.'
                                  ;
                      mandatory true ;
                      case src-mac-addr {
                        description 'MAC address.'
                                    ;
                        leaf src-mac-address {
                          description 'MAC address.'
                                      ;
                          type ncd:mac-address ;
                          mandatory true ;
                        }
                        leaf src-mac-wildcard {
                          description 'MAC address wildcard.'
                                      ;
                          type ncd:mac-address ;
                          mandatory true ;
                        }
                      }
                      case src-mac-any {
                        description 'Any MAC address.'
                                    ;
                        leaf src-mac-any {
                          description 'Any MAC address.'
                                      ;
                          type empty ;
                          mandatory true ;
                        }
                      }
                    }
                  }
                  container destination-mac {
                    description 'Specify destination MAC address.'
                                ;
                    choice dest-mac-addr {
                      description 'Specify destination MAC address.'
                                  ;
                      mandatory true ;
                      case dest-mac-addr {
                        description 'MAC address.'
                                    ;
                        leaf dest-mac-address {
                          description 'MAC address.'
                                      ;
                          type ncd:mac-address ;
                          mandatory true ;
                        }
                        leaf dest-mac-wildcard {
                          description 'MAC address wildcard.'
                                      ;
                          type ncd:mac-address ;
                          mandatory true ;
                        }
                      }
                      case dest-mac-any {
                        description 'Any MAC address.'
                                    ;
                        leaf dest-mac-any {
                          description 'Any MAC address.'
                                      ;
                          type empty ;
                          mandatory true ;
                        }
                      }
                    }
                  }
                  leaf inner-cos {
                    if-feature link-cos-value ;
                    description 'Value of inner CoS.'
                                ;
                    type uint8 {
                      range 0..7 ;
                    }
                  }
                  leaf outer-cos {
                    if-feature link-cos-value ;
                    description 'Value of outer CoS.'
                                ;
                    type uint8 {
                      range 0..7 ;
                    }
                  }
                  leaf inner-vlan-range {
                    description 'Specify range of inner VLAN.'
                                ;
                    type acl-vlan-range ;
                  }
                  leaf outer-vlan-range {
                    description 'Specify range of outer VLAN.'
                                ;
                    type acl-vlan-range ;
                  }
                  ncd:revise-date 2021-10-26 ;
                }
                leaf log {
                  if-feature log-config ;
                  description 'If log flag is set, the matching times of this r'
                            + 'ule will be recorded.'
                              ;
                  type boolean ;
                  default false ;
                  ncd:revise-date 2022-01-20 ;
                }
              }
              ncd:revise-date 2018-09-17 ;
            }
            container rules-vtep-outer {
              description 'Configure rule of an IPv4 VXLAN ACL.'
                          ;
              list rule-vtep-outer {
                description 'Configure rule of an IPv4 VXLAN ACL.'
                            ;
                key ruleid ;
                leaf ruleid {
                  description 'ID of this rule.'
                              ;
                  type uint32 {
                    range 1..2147483644 ;
                  }
                }
                choice permit-deny {
                  description 'Deny  :  Specify packets to reject'+"\n"
                            + 'Permit:  Specify packets to forward.'
                              ;
                  mandatory true ;
                  case deny {
                    description 'Deny:Specify packets to reject.'
                                ;
                    leaf deny {
                      description 'Deny:Specify packets to reject.'
                                  ;
                      type empty ;
                      mandatory true ;
                    }
                  }
                  case permit {
                    description 'Permit:  Specify packets to forward.'
                                ;
                    leaf permit {
                      description 'Permit:  Specify packets to forward.'
                                  ;
                      type empty ;
                      mandatory true ;
                    }
                  }
                }
                container vni {
                  description 'VXLAN ID.'
                              ;
                  presence vni ;
                  leaf vxlan-id {
                    description 'VXLAN ID.'
                                ;
                    type uint32 {
                      range 1..16777215 ;
                    }
                    mandatory true ;
                  }
                }
                container sgt {
                  description 'Security Group Tag'
                              ;
                  presence sgt ;
                  leaf sgt-value {
                    description 'Security Group Tag Value'
                                ;
                    type uint16 ;
                    mandatory true ;
                  }
                  ncd:revise-date 2019-08-14 ;
                }
                container outer-layer {
                  description 'The outer-layer protocol of VXLAN.'
                              ;
                  leaf udp {
                    description 'Configure UDP protocol.'
                                ;
                    type empty ;
                    mandatory true ;
                  }
                  choice src-addr {
                    description 'Configure source address.'
                                ;
                    mandatory true ;
                    case addr-type {
                      description 'Configure source address.'
                                  ;
                      leaf src-address {
                        description 'Configure source address.'
                                    ;
                        type ncd:ipv4-address ;
                        mandatory true ;
                      }
                      leaf src-wildcard {
                        description 'Source wildcard bits.'
                                    ;
                        type ncd:ipv4-address ;
                        mandatory true ;
                      }
                    }
                    case any-type {
                      description 'Any source address.'
                                  ;
                      leaf src-any-addr {
                        description 'Any source address.'
                                    ;
                        type empty ;
                        mandatory true ;
                      }
                    }
                  }
                  container source-port {
                    description 'Specify source port.'+"\n"
                              + 'When the value of operator is invalid, it mean'
                              + 's match all port range,'+"\n"
                              + 'the other value of operator means'+"\n"
                              + 'eq(1)   : match only packets on a given port n'
                              + 'umber'+"\n"
                              + 'ge(2)   : match only packets with a no lower p'
                              + 'ort number'+"\n"
                              + 'le(3)   : match only packets with a no greater'
                              + ' port number'+"\n"
                              + 'range(7): match only packet on a given port ra'
                              + 'nge.'
                                ;
                    presence 'Specify source port'
                             ;
                    choice source-port {
                      description 'Specify source port.'+"\n"
                                + 'When the value of operator is invalid, it me'
                                + 'ans match all port range,'+"\n"
                                + 'the other value of operator means'+"\n"
                                + 'eq(1)   : match only packets on a given port'
                                + ' number'+"\n"
                                + 'ge(2)   : match only packets with a no lower'
                                + ' port number'+"\n"
                                + 'le(3)   : match only packets with a no great'
                                + 'er port number'+"\n"
                                + 'range(7): match only packet on a given port '
                                + 'range.'
                                  ;
                      mandatory true ;
                      case src-port-value {
                        description 'Configure port number.'
                                    ;
                        container src-port-value {
                          description 'Configure port number.'
                                      ;
                          presence 'Configure port number'
                                   ;
                          leaf src-port-operator {
                            description 'Operator type'+"\n"
                                      + 'eq(1)   : match only packets on a given port number'+"\n"
                                      + 'ge(2)   : match only packets with a no lower port number'+"\n"
                                      + 'le(3)   : match only packets with a no greater port number.'
                                        ;
                            type enumeration {
                              enum eq {
                                value 1 ;
                                description 'Equal to.'
                                            ;
                              }
                              enum ge {
                                value 2 ;
                                description 'Great than or equal to.'
                                            ;
                              }
                              enum le {
                                value 3 ;
                                description 'Less than or equal to.'
                                            ;
                              }
                            }
                            mandatory true ;
                          }
                          leaf src-port-value {
                            description 'Port number.'+"\n"
                                      + 'Some has specific means:'+"\n"
                                      + 'bootpc       Bootstrap protocol (BOOTP) client (68)'+"\n"
                                      + 'bootps       Bootstrap protocol (BOOTP) server (67)'+"\n"
                                      + 'domain       Domain name service (DNS, 53)'+"\n"
                                      + 'ntp          Network time protocol (123)'+"\n"
                                      + 'pim-auto-rp  PIM auto-RP (496)'+"\n"
                                      + 'rip          Routing information protocol (router, in.routed, 520)'+"\n"
                                      + 'snmp         Simple network management protocol (161)'+"\n"
                                      + 'snmptrap     SNMP traps (162)'+"\n"
                                      + 'tftp         Trivial file transfer protocol (69).'
                                        ;
                            type uint16 {
                              range 0..65535 ;
                            }
                            mandatory true ;
                          }
                        }
                      }
                      case src-port-range {
                        description 'Configure port range.'
                                    ;
                        container src-port-range {
                          description 'Configure port range.'
                                      ;
                          presence 'Configure port range'
                                   ;
                          leaf src-port-operator {
                            description 'Operator type
range(7): match only packet on a given port range.'
                                        ;
                            type enumeration {
                              enum range {
                                value 7 ;
                                description Range. ;
                              }
                            }
                            mandatory true ;
                          }
                          leaf src-port-range {
                            description 'Port range, support <0-65535>-<0-65535>.'
                                        ;
                            type acl-port-range ;
                            mandatory true ;
                          }
                        }
                      }
                    }
                  }
                  choice dst-addr {
                    description 'Configure destination address.'
                                ;
                    mandatory true ;
                    case addr-type {
                      description 'Configure destination address.'
                                  ;
                      leaf dst-address {
                        description 'Configure destination address.'
                                    ;
                        type ncd:ipv4-address ;
                        mandatory true ;
                      }
                      leaf dst-wildcard {
                        description 'Destination wildcard bits'
                                    ;
                        type ncd:ipv4-address ;
                        mandatory true ;
                      }
                    }
                    case any-type {
                      description 'Any destination address.'
                                  ;
                      leaf dst-any-addr {
                        description 'Any destination address.'
                                    ;
                        type empty ;
                        mandatory true ;
                      }
                    }
                  }
                  container destination-port {
                    description 'Specify destination port.'+"\n"
                              + 'When the value of operator is invalid, it mean'
                              + 's match all port range,'+"\n"
                              + 'the other value of operator means'+"\n"
                              + 'eq(1)   : match only packets on a given port n'
                              + 'umber'+"\n"
                              + 'ge(2)   : match only packets with a no lower p'
                              + 'ort number'+"\n"
                              + 'le(3)   : match only packets with a no greater'
                              + ' port number'+"\n"
                              + 'range(7): match only packet on a given port ra'
                              + 'nge.'
                                ;
                    presence 'Specify destination port'
                             ;
                    choice destination-port {
                      description 'Specify destination port.'+"\n"
                                + 'When the value of operator is invalid, it me'
                                + 'ans match all port range,'+"\n"
                                + 'the other value of operator means'+"\n"
                                + 'eq(1)   : match only packets on a given port'
                                + ' number'+"\n"
                                + 'ge(2)   : match only packets with a no lower'
                                + ' port number'+"\n"
                                + 'le(3)   : match only packets with a no great'
                                + 'er port number'+"\n"
                                + 'range(7): match only packet on a given port '
                                + 'range.'
                                  ;
                      mandatory true ;
                      case dst-port-value {
                        description 'Configure port number.'
                                    ;
                        container dst-port-value {
                          description 'Configure port number.'
                                      ;
                          presence 'Configure port number'
                                   ;
                          leaf dst-port-operator {
                            description 'Operator type'+"\n"
                                      + 'eq(1)   : match only packets on a given port number'+"\n"
                                      + 'ge(2)   : match only packets with a no lower port number'+"\n"
                                      + 'le(3)   : match only packets with a no greater port number.'
                                        ;
                            type enumeration {
                              enum eq {
                                value 1 ;
                                description 'Equal to.'
                                            ;
                              }
                              enum ge {
                                value 2 ;
                                description 'Great than or equal to.'
                                            ;
                              }
                              enum le {
                                value 3 ;
                                description 'Less than or equal to.'
                                            ;
                              }
                            }
                            mandatory true ;
                          }
                          leaf dst-port-value {
                            description 'Port number.'+"\n"
                                      + 'Some has specific means:'+"\n"
                                      + 'bootpc       Bootstrap protocol (BOOTP) client (68)'+"\n"
                                      + 'bootps       Bootstrap protocol (BOOTP) server (67)'+"\n"
                                      + 'domain       Domain name service (DNS, 53)'+"\n"
                                      + 'ntp          Network time protocol (123)'+"\n"
                                      + 'pim-auto-rp  PIM auto-RP (496)'+"\n"
                                      + 'rip          Routing information protocol (router, in.routed, 520)'+"\n"
                                      + 'snmp         Simple network management protocol (161)'+"\n"
                                      + 'snmptrap     SNMP traps (162)'+"\n"
                                      + 'tftp         Trivial file transfer protocol (69).'
                                        ;
                            type uint16 {
                              range 0..65535 ;
                            }
                            mandatory true ;
                          }
                        }
                      }
                      case dst-port-range {
                        description 'Configure port range.'
                                    ;
                        container dst-port-range {
                          description 'Configure port range.'
                                      ;
                          presence 'Configure port range'
                                   ;
                          leaf dst-port-operator {
                            description 'Operator type
range(7): match only packet on a given port range.'
                                        ;
                            type enumeration {
                              enum range {
                                value 7 ;
                                description Range. ;
                              }
                            }
                            mandatory true ;
                          }
                          leaf dst-port-range {
                            description 'Port range, support <0-65535>-<0-65535>.'
                                        ;
                            type acl-port-range ;
                            mandatory true ;
                          }
                        }
                      }
                    }
                  }
                  choice priority {
                    description 'Configure precedence or TOS or DSCP.'
                                ;
                    case dscp {
                      description 'DSCP value.'
                                  ;
                      leaf dscp {
                        description 'DSCP value.'
                                    ;
                        type uint8 {
                          range 0..63 ;
                        }
                      }
                    }
                    case precedence {
                      description 'Precedence level.'
                                  ;
                      leaf precedence {
                        description 'Precedence level.'
                                    ;
                        type uint8 {
                          range 0..7 ;
                        }
                      }
                    }
                    case tos {
                      description 'Type of service(TOS).'
                                  ;
                      leaf tos {
                        description 'Type of service(TOS).'
                                    ;
                        type uint8 {
                          range 0..15 ;
                        }
                      }
                    }
                  }
                }
                leaf vrf {
                  description 'VPN Routing/Forwarding instance name, support 1-'
                            + '32 characters.'
                              ;
                  type acl-vrf-name {
                    length 1..32 {
                      description 'VPN Routing/Forwarding instance name, suppor'
                                + 't 1-32 characters.'
                                  ;
                    }
                  }
                }
                leaf time-range {
                  description 'Specify the existed time-range name.'
                              ;
                  type string {
                    length 1..31 ;
                  }
                  ncd:revise-date 2021-04-02 ;
                }
              }
              ncd:revise-date 2018-09-17 ;
            }
          }
          ncd:revise-date 2016-03-04 ;
        }
        container user-defined-template-acls {
          if-feature udf-template-type ;
          description 'Configure user defined template ACL.'
                      ;
          list user-defined-template-acl {
            if-feature udf-template-type ;
            description 'Configure user defined template ACL.'
                        ;
            key acl-name ;
            leaf acl-name {
              description 'User defined template ACL'
                          ;
              type acl-name-type ;
            }
            leaf template-name {
              description 'Template name'
                          ;
              type acl-name-type ;
              mandatory true ;
            }
            container rules {
              description 'Configure rule of a user defined template ACL.'
                          ;
              list rule {
                description 'Configure rule of a user defined ACL.'
                            ;
                key ruleid ;
                leaf ruleid {
                  description 'ID of this rule.'
                              ;
                  type uint32 {
                    range 1..2147483644 ;
                  }
                }
                choice permit-deny {
                  description 'Deny  :  Specify packets to reject'+"\n"
                            + 'Permit:  Specify packets to forward.'
                              ;
                  mandatory true ;
                  case deny {
                    description 'Deny  :  Specify packets to reject.'
                                ;
                    leaf deny {
                      description 'Deny  :  Specify packets to reject.'
                                  ;
                      type empty ;
                    }
                  }
                  case permit {
                    description 'Specify packets to forward.'
                                ;
                    leaf permit {
                      description 'Specify packets to forward.'
                                  ;
                      type empty ;
                      mandatory true ;
                    }
                  }
                }
                choice segment {
                  description 'Rule segments.'
                              ;
                  mandatory true ;
                  case segment-any {
                    description 'Any segment.'
                                ;
                    leaf any {
                      description 'Any segment.'
                                  ;
                      type empty ;
                    }
                  }
                  case segment-value {
                    description 'Rule segment.'
                                ;
                    container segment1 {
                      description 'Rule segment one.'
                                  ;
                      presence segment1 ;
                      leaf rule-string {
                        description 'User defined hexadecimal string,as follows'
                                  + ':'+"\n"
                                  + '0x00-0xffffffff.'
                                    ;
                        type string {
                          length 4..10 {
                            description 'User defined hexadecimal string,as follows:
0x00-0xffffffff.'
                                        ;
                          }
                        }
                        mandatory true ;
                      }
                      leaf rule-mask {
                        description 'User defined hexadecimal string mask,as fo'
                                  + 'llows:'+"\n"
                                  + '0x00-0xffffffff.'
                                    ;
                        type string {
                          length 4..10 {
                            description 'User defined hexadecimal string mask,as follows:
0x00-0xffffffff.'
                                        ;
                          }
                        }
                        mandatory true ;
                      }
                    }
                    container segment2 {
                      description 'Rule segment two.'
                                  ;
                      presence segment2 ;
                      leaf rule-string {
                        description 'User defined hexadecimal string,as follows'
                                  + ':'+"\n"
                                  + '0x00-0xffffffff.'
                                    ;
                        type string {
                          length 4..10 {
                            description 'User defined hexadecimal string,as follows:
0x00-0xffffffff.'
                                        ;
                          }
                        }
                        mandatory true ;
                      }
                      leaf rule-mask {
                        description 'User defined hexadecimal string mask,as fo'
                                  + 'llows:'+"\n"
                                  + '0x00-0xffffffff.'
                                    ;
                        type string {
                          length 4..10 {
                            description 'User defined hexadecimal string mask,as follows:
0x00-0xffffffff.'
                                        ;
                          }
                        }
                        mandatory true ;
                      }
                    }
                    container segment3 {
                      description 'Rule segment three.'
                                  ;
                      presence segment3 ;
                      leaf rule-string {
                        description 'User defined hexadecimal string,as follows'
                                  + ':'+"\n"
                                  + '0x00-0xffffffff.'
                                    ;
                        type string {
                          length 4..10 {
                            description 'User defined hexadecimal string,as follows:
0x00-0xffffffff.'
                                        ;
                          }
                        }
                        mandatory true ;
                      }
                      leaf rule-mask {
                        description 'User defined hexadecimal string mask,as fo'
                                  + 'llows:'+"\n"
                                  + '0x00-0xffffffff.'
                                    ;
                        type string {
                          length 4..10 {
                            description 'User defined hexadecimal string mask,as follows:
0x00-0xffffffff.'
                                        ;
                          }
                        }
                        mandatory true ;
                      }
                    }
                    container segment4 {
                      description 'Rule segment four.'
                                  ;
                      presence segment4 ;
                      leaf rule-string {
                        description 'User defined hexadecimal string,as follows'
                                  + ':'+"\n"
                                  + '0x00-0xffffffff.'
                                    ;
                        type string {
                          length 4..10 {
                            description 'User defined hexadecimal string,as follows:
0x00-0xffffffff.'
                                        ;
                          }
                        }
                        mandatory true ;
                      }
                      leaf rule-mask {
                        description 'User defined hexadecimal string mask,as fo'
                                  + 'llows:'+"\n"
                                  + '0x00-0xffffffff.'
                                    ;
                        type string {
                          length 4..10 {
                            description 'User defined hexadecimal string mask,as follows:
0x00-0xffffffff.'
                                        ;
                          }
                        }
                        mandatory true ;
                      }
                    }
                    container segment5 {
                      description 'Rule segment five.'
                                  ;
                      presence segment5 ;
                      leaf rule-string {
                        description 'User defined hexadecimal string,as follows'
                                  + ':'+"\n"
                                  + '0x00-0xffffffff.'
                                    ;
                        type string {
                          length 4..10 {
                            description 'User defined hexadecimal string,as follows:
0x00-0xffffffff.'
                                        ;
                          }
                        }
                        mandatory true ;
                      }
                      leaf rule-mask {
                        description 'User defined hexadecimal string mask,as fo'
                                  + 'llows:'+"\n"
                                  + '0x00-0xffffffff.'
                                    ;
                        type string {
                          length 4..10 {
                            description 'User defined hexadecimal string mask,as follows:
0x00-0xffffffff.'
                                        ;
                          }
                        }
                        mandatory true ;
                      }
                    }
                    container segment6 {
                      description 'Rule segment six.'
                                  ;
                      presence segment6 ;
                      leaf rule-string {
                        description 'User defined hexadecimal string,as follows'
                                  + ':'+"\n"
                                  + '0x00-0xffffffff.'
                                    ;
                        type string {
                          length 4..10 {
                            description 'User defined hexadecimal string,as follows:
0x00-0xffffffff.'
                                        ;
                          }
                        }
                        mandatory true ;
                      }
                      leaf rule-mask {
                        description 'User defined hexadecimal string mask,as fo'
                                  + 'llows:'+"\n"
                                  + '0x00-0xffffffff.'
                                    ;
                        type string {
                          length 4..10 {
                            description 'User defined hexadecimal string mask,as follows:
0x00-0xffffffff.'
                                        ;
                          }
                        }
                        mandatory true ;
                      }
                    }
                    container segment7 {
                      description 'Rule segment seven.'
                                  ;
                      presence segment7 ;
                      leaf rule-string {
                        description 'User defined hexadecimal string,as follows'
                                  + ':'+"\n"
                                  + '0x00-0xffffffff.'
                                    ;
                        type string {
                          length 4..10 {
                            description 'User defined hexadecimal string,as follows:
0x00-0xffffffff.'
                                        ;
                          }
                        }
                        mandatory true ;
                      }
                      leaf rule-mask {
                        description 'User defined hexadecimal string mask,as fo'
                                  + 'llows:'+"\n"
                                  + '0x00-0xffffffff.'
                                    ;
                        type string {
                          length 4..10 {
                            description 'User defined hexadecimal string mask,as follows:
0x00-0xffffffff.'
                                        ;
                          }
                        }
                        mandatory true ;
                      }
                    }
                    container segment8 {
                      description 'Rule segment eight.'
                                  ;
                      presence segment8 ;
                      leaf rule-string {
                        description 'User defined hexadecimal string,as follows'
                                  + ':'+"\n"
                                  + '0x00-0xffffffff.'
                                    ;
                        type string {
                          length 4..10 {
                            description 'User defined hexadecimal string,as follows:
0x00-0xffffffff.'
                                        ;
                          }
                        }
                        mandatory true ;
                      }
                      leaf rule-mask {
                        description 'User defined hexadecimal string mask,as fo'
                                  + 'llows:'+"\n"
                                  + '0x00-0xffffffff.'
                                    ;
                        type string {
                          length 4..10 {
                            description 'User defined hexadecimal string mask,as follows:
0x00-0xffffffff.'
                                        ;
                          }
                        }
                        mandatory true ;
                      }
                    }
                  }
                  ncd:revise-date 2017-06-13 ;
                }
                leaf log {
                  if-feature log-config ;
                  description 'If log flag is set, the matching times of this r'
                            + 'ule will be recorded.'
                              ;
                  type boolean ;
                  default false ;
                  ncd:revise-date 2022-01-27 ;
                }
              }
            }
          }
          ncd:revise-date 2017-05-08 ;
        }
        container ipv6-vxlan-access-lists {
          description 'Configure ipv6-vxlan-access-list.'
                      ;
          list ipv6-vxlan-access-list {
            description 'Configure ipv6-vxlan-access-list.'
                        ;
            key acl-name ;
            leaf acl-name {
              description 'Name of ACL.'
                          ;
              type acl-name-type ;
            }
            leaf mode-type {
              description 'Mode type of ACL.'
                          ;
              type enumeration {
                enum transit-inner {
                  value 1 ;
                  description 'Transit node match VXLAN inner layer'
                              ;
                }
                enum transit-outer {
                  value 2 ;
                  description 'Transit node match VXLAN outer layer'
                              ;
                }
                enum vtep-inner {
                  value 3 ;
                  description 'VTEP node match VXLAN inner layer'
                              ;
                }
                enum vtep-outer {
                  value 4 ;
                  description 'VTEP node match VXLAN outer layer'
                              ;
                }
              }
              mandatory true ;
            }
            container rules-transit-inner {
              description 'Configure rule of an IPv6 VXLAN ACL.'
                          ;
              list rule-transit-inner {
                description 'Configure rule of an IPv6 VXLAN ACL.'
                            ;
                key ruleid ;
                leaf ruleid {
                  description 'ID of this rule.'
                              ;
                  type uint32 {
                    range 1..2147483644 ;
                  }
                }
                choice permit-deny {
                  description 'Deny  :  Specify packets to reject'+"\n"
                            + 'Permit:  Specify packets to forward.'
                              ;
                  mandatory true ;
                  case deny {
                    description 'Deny:Specify packets to reject.'
                                ;
                    leaf deny {
                      description 'Deny:Specify packets to reject.'
                                  ;
                      type empty ;
                      mandatory true ;
                    }
                  }
                  case permit {
                    description 'Permit:  Specify packets to forward.'
                                ;
                    leaf permit {
                      description 'Permit:  Specify packets to forward.'
                                  ;
                      type empty ;
                      mandatory true ;
                    }
                  }
                }
                container inner-layer {
                  description 'The inner-layer protocol of VXLAN.'
                              ;
                  presence inner-layer ;
                  choice protocol-type {
                    description 'Configure protocol type of IPv6 VXLAN acl in i'
                              + 'nner-layer as follows:'+"\n"
                              + 'IP protocol number(0-255)'+"\n"
                              + 'Some has specific mean:'+"\n"
                              + 'gre      Generic Routing Encapsulation (47)'+"\n"
                              + 'icmp     Internet Control Message Protocol (58'
                              + ')'+"\n"
                              + 'ospf     Open Shortest Path First Protocol (89'
                              + ')'+"\n"
                              + 'pim      Protocol Independent Multicast (103)
'
                              + ''+"\n"
                              + 'tcp      Transmission Control Protocol(6)'+"\n"
                              + 'udp      User Datagram Protocol(17)'+"\n"
                              + 'vrrp     Virtual Router Redundancy Protocol (1'
                              + '12)'+"\n"
                              + 'ipv6     Any IP protocol (65535).'
                                ;
                    mandatory true ;
                    case tcp-udp {
                      description 'Configure TCP or UDP protocol of IPv6 VXLAN '
                                + 'ACL.'+"\n"
                                + 'tcp      Transmission Control Protocol(6)'+"\n"
                                + 'udp      User Datagram Protocol(17)'
                                  ;
                      container tcp-udp {
                        description 'Configure protocol type of IPv6 VXLAN ACL.'
                                  + ''+"\n"
                                  + 'tcp      Transmission Control Protocol(6)
'
                                  + ''+"\n"
                                  + 'udp      User Datagram Protocol(17)'
                                    ;
                        leaf tcp-udp {
                          description 'Configure protocol type of IPv6 VXLAN AC'
                                    + 'L.'+"\n"
                                    + 'tcp      Transmission Control Protocol(6'
                                    + ')'+"\n"
                                    + 'udp      User Datagram Protocol(17)'
                                      ;
                          type enumeration {
                            enum tcp {
                              value 6 ;
                              description 'Transmission Control Protocol(6)'
                                          ;
                            }
                            enum udp {
                              value 17 ;
                              description 'User Datagram Protocol(17)'
                                          ;
                            }
                          }
                          mandatory true ;
                        }
                        choice src-addr {
                          description 'Configure source address.'
                                      ;
                          mandatory true ;
                          case addr-type {
                            description 'Configure source address.'
                                        ;
                            leaf src-address {
                              description 'Configure source address.'
                                          ;
                              type ncd:ipv6-address ;
                              mandatory true ;
                            }
                            container src-wildcard {
                              description 'Configure source wildcard.'
                                          ;
                              choice wildcard-type {
                                description 'Configure source wildcard.'
                                            ;
                                mandatory true ;
                                case wildcard-len {
                                  description 'Configure source wildcard prefix length.'
                                              ;
                                  leaf src-wildcard-len {
                                    description 'Configure source wildcard prefix length.'
                                                ;
                                    type uint8 {
                                      range 0..128 ;
                                    }
                                    mandatory true ;
                                  }
                                }
                                case wildcard-bits {
                                  description 'Configure source wildcard bits.'
                                              ;
                                  leaf src-wildcard-bits {
                                    description 'Configure source wildcard bits.'
                                                ;
                                    type ncd:ipv6-address ;
                                    mandatory true ;
                                  }
                                }
                              }
                            }
                          }
                          case any-type {
                            description 'Any source address.'
                                        ;
                            leaf src-any-addr {
                              description 'Any source address.'
                                          ;
                              type empty ;
                              mandatory true ;
                            }
                          }
                        }
                        container source-port {
                          description 'Specify source port.'+"\n"
                                    + 'When the value of operator is invalid, i'
                                    + 't means match all port range,'+"\n"
                                    + 'the other value of operator means'+"\n"
                                    + 'eq(1)   : match only packets on a given '
                                    + 'port number'+"\n"
                                    + 'ge(2)   : match only packets with a no l'
                                    + 'ower port number'+"\n"
                                    + 'le(3)   : match only packets with a no g'
                                    + 'reater port number'+"\n"
                                    + 'range(7): match only packet on a given p'
                                    + 'ort range.'
                                      ;
                          presence 'Specify source port'
                                   ;
                          choice source-port {
                            description 'Specify source port.'+"\n"
                                      + 'When the value of operator is invalid, it means match all port range,'+"\n"
                                      + 'the other value of operator means'+"\n"
                                      + 'eq(1)   : match only packets on a given port number'+"\n"
                                      + 'ge(2)   : match only packets with a no lower port number'+"\n"
                                      + 'le(3)   : match only packets with a no greater port number'+"\n"
                                      + 'range(7): match only packet on a given port range.'
                                        ;
                            mandatory true ;
                            case src-port-value {
                              description 'Configure port number.'
                                          ;
                              container src-port-value {
                                description 'Configure port number.'
                                            ;
                                presence 'Configure port number'
                                         ;
                                leaf src-port-operator {
                                  description 'Operator type'+"\n"
                                            + 'eq(1)   : match only packets on a given port number'+"\n"
                                            + 'ge(2)   : match only packets with a no lower port number'+"\n"
                                            + 'le(3)   : match only packets with a no greater port number.'
                                              ;
                                  type enumeration {
                                    enum eq {
                                      value 1 ;
                                      description 'Equal to.'
                                                  ;
                                    }
                                    enum ge {
                                      value 2 ;
                                      description 'Great than or equal to.'
                                                  ;
                                    }
                                    enum le {
                                      value 3 ;
                                      description 'Less than or equal to.'
                                                  ;
                                    }
                                  }
                                  mandatory true ;
                                }
                                leaf src-port-value {
                                  description 'Configure port number from 0 to 65535.'+"\n"
                                            + 'Some has specific means when port protocol type is TCP.'+"\n"
                                            + '  bgp        Border gateway protocol (179)'+"\n"
                                            + '  domain     Domain name service (53)'+"\n"
                                            + '  finger     Finger (79)'+"\n"
                                            + '  ftp        File transfer protocol (21)'+"\n"
                                            + '  login      Login (rlogin, 513)'+"\n"
                                            + '  pop2       Post office protocol v2 (109)'+"\n"
                                            + '  pop3       Post office protocol v3 (110)'+"\n"
                                            + '  smtp       Simple mail transport protocol (25)'+"\n"
                                            + '  telnet     Telnet (23)'+"\n"
                                            + '  www        World wide web (HTTP, 80)'+"\n"
                                            + 'Some has specific means when port protocol type is UDP.'+"\n"
                                            + '  bootpc       Bootstrap protocol (BOOTP) client (68)'+"\n"
                                            + '  bootps       Bootstrap protocol (BOOTP) server (67)'+"\n"
                                            + '  domain       Domain name service (DNS, 53)'+"\n"
                                            + '  ntp          Network time protocol (123)'+"\n"
                                            + '  pim-auto-rp  PIM auto-RP (496)'+"\n"
                                            + '  rip          Routing information protocol (router, in.routed, 520)'+"\n"
                                            + '  snmp         Simple network management protocol (161)'+"\n"
                                            + '  snmptrap     SNMP traps (162)'+"\n"
                                            + '  tftp         Trivial file transfer protocol (69).'
                                              ;
                                  type uint16 {
                                    range 0..65535 ;
                                  }
                                  mandatory true ;
                                }
                              }
                            }
                            case src-port-range {
                              description 'Configure port range.'
                                          ;
                              container src-port-range {
                                description 'Configure port range.'
                                            ;
                                presence 'Configure port range'
                                         ;
                                leaf src-port-operator {
                                  description 'Operator type
range(7): match only packet on a given port range.'
                                              ;
                                  type enumeration {
                                    enum range {
                                      value 7 ;
                                      description Range. ;
                                    }
                                  }
                                  mandatory true ;
                                }
                                leaf src-port-range {
                                  description 'Port range, support <0-65535>-<0-65535>.'
                                              ;
                                  type acl-port-range ;
                                  mandatory true ;
                                }
                              }
                            }
                          }
                        }
                        choice dst-addr {
                          description 'Configure destination address.'
                                      ;
                          mandatory true ;
                          case addr-type {
                            description 'Configure destination address.'
                                        ;
                            leaf dst-address {
                              description 'Configure destination address.'
                                          ;
                              type ncd:ipv6-address ;
                              mandatory true ;
                            }
                            container dst-wildcard {
                              description 'Configure destination wildcard.'
                                          ;
                              choice wildcard-type {
                                description 'Configure destination wildcard.'
                                            ;
                                mandatory true ;
                                case wildcard-len {
                                  description 'Configure destination wildcard prefix length.'
                                              ;
                                  leaf dst-wildcard-len {
                                    description 'Configure destination wildcard prefix length.'
                                                ;
                                    type uint8 {
                                      range 0..128 ;
                                    }
                                    mandatory true ;
                                  }
                                }
                                case wildcard-bits {
                                  description 'Configure destination wildcard bits.'
                                              ;
                                  leaf dst-wildcard-bits {
                                    description 'Configure destination wildcard bits.'
                                                ;
                                    type ncd:ipv6-address ;
                                    mandatory true ;
                                  }
                                }
                              }
                            }
                          }
                          case any-type {
                            description 'Any destination address.'
                                        ;
                            leaf dst-any-addr {
                              description 'Any destination address.'
                                          ;
                              type empty ;
                              mandatory true ;
                            }
                          }
                        }
                        container destination-port {
                          description 'Specify destination port.'+"\n"
                                    + 'When the value of operator is invalid, i'
                                    + 't means match all port range,'+"\n"
                                    + 'the other value of operator means'+"\n"
                                    + 'eq(1)   : match only packets on a given '
                                    + 'port number'+"\n"
                                    + 'ge(2)   : match only packets with a no l'
                                    + 'ower port number'+"\n"
                                    + 'le(3)   : match only packets with a no g'
                                    + 'reater port number'+"\n"
                                    + 'range(7): match only packet on a given p'
                                    + 'ort range.'
                                      ;
                          presence 'Specify destination port'
                                   ;
                          choice destination-port {
                            description 'Specify destination port.'+"\n"
                                      + 'When the value of operator is invalid, it means match all port range,'+"\n"
                                      + 'the other value of operator means'+"\n"
                                      + 'eq(1)   : match only packets on a given port number'+"\n"
                                      + 'ge(2)   : match only packets with a no lower port number'+"\n"
                                      + 'le(3)   : match only packets with a no greater port number'+"\n"
                                      + 'range(7): match only packet on a given port range.'
                                        ;
                            mandatory true ;
                            case dst-port-value {
                              description 'Configure port number.'
                                          ;
                              container dst-port-value {
                                description 'Configure port number.'
                                            ;
                                presence 'Configure port number'
                                         ;
                                leaf dst-port-operator {
                                  description 'Operator type'+"\n"
                                            + 'eq(1)   : match only packets on a given port number'+"\n"
                                            + 'ge(2)   : match only packets with a no lower port number'+"\n"
                                            + 'le(3)   : match only packets with a no greater port number.'
                                              ;
                                  type enumeration {
                                    enum eq {
                                      value 1 ;
                                      description 'Equal to.'
                                                  ;
                                    }
                                    enum ge {
                                      value 2 ;
                                      description 'Great than or equal to.'
                                                  ;
                                    }
                                    enum le {
                                      value 3 ;
                                      description 'Less than or equal to.'
                                                  ;
                                    }
                                  }
                                  mandatory true ;
                                }
                                leaf dst-port-value {
                                  description 'Configure port number from 0 to 65535.'+"\n"
                                            + 'Some has specific means when port protocol type is TCP.'+"\n"
                                            + '  bgp        Border gateway protocol (179)'+"\n"
                                            + '  domain     Domain name service (53)'+"\n"
                                            + '  finger     Finger (79)'+"\n"
                                            + '  ftp        File transfer protocol (21)'+"\n"
                                            + '  login      Login (rlogin, 513)'+"\n"
                                            + '  pop2       Post office protocol v2 (109)'+"\n"
                                            + '  pop3       Post office protocol v3 (110)'+"\n"
                                            + '  smtp       Simple mail transport protocol (25)'+"\n"
                                            + '  telnet     Telnet (23)'+"\n"
                                            + '  www        World wide web (HTTP, 80)'+"\n"
                                            + 'Some has specific means when port protocol type is UDP.'+"\n"
                                            + '  bootpc       Bootstrap protocol (BOOTP) client (68)'+"\n"
                                            + '  bootps       Bootstrap protocol (BOOTP) server (67)'+"\n"
                                            + '  domain       Domain name service (DNS, 53)'+"\n"
                                            + '  ntp          Network time protocol (123)'+"\n"
                                            + '  pim-auto-rp  PIM auto-RP (496)'+"\n"
                                            + '  rip          Routing information protocol (router, in.routed, 520)'+"\n"
                                            + '  snmp         Simple network management protocol (161)'+"\n"
                                            + '  snmptrap     SNMP traps (162)'+"\n"
                                            + '  tftp         Trivial file transfer protocol (69).'
                                              ;
                                  type uint16 {
                                    range 0..65535 ;
                                  }
                                  mandatory true ;
                                }
                              }
                            }
                            case dst-port-range {
                              description 'Configure port range.'
                                          ;
                              container dst-port-range {
                                description 'Configure port range.'
                                            ;
                                presence 'Configure port range'
                                         ;
                                leaf dst-port-operator {
                                  description 'Operator type
range(7): match only packet on a given port range.'
                                              ;
                                  type enumeration {
                                    enum range {
                                      value 7 ;
                                      description Range. ;
                                    }
                                  }
                                  mandatory true ;
                                }
                                leaf dst-port-range {
                                  description 'Port range, support <0-65535>-<0-65535>.'
                                              ;
                                  type acl-port-range ;
                                  mandatory true ;
                                }
                              }
                            }
                          }
                        }
                      }
                    }
                    case ip {
                      description 'Configure protocol type of IPv6 VXLAN acl in'
                                + ' inner-layer as follows:'+"\n"
                                + 'IP protocol number(0-255)'+"\n"
                                + 'Some has specific mean:'+"\n"
                                + 'gre      Generic Routing Encapsulation (47)
'
                                + ''+"\n"
                                + 'icmp     Internet Control Message Protocol(5'
                                + '8)'+"\n"
                                + 'ospf     Open Shortest Path First Protocol ('
                                + '89)'+"\n"
                                + 'pim      Protocol Independent Multicast (103'
                                + ')'+"\n"
                                + 'vrrp     Virtual Router Redundancy Protocol '
                                + '(112)'+"\n"
                                + 'ip       Any IP protocol (65535).'
                                  ;
                      container ipv6-protocol {
                        description 'Configure protocol type of IPv6 VXLAN acl '
                                  + 'in inner-layer as follows:'+"\n"
                                  + 'IP protocol number(0-255)'+"\n"
                                  + 'Some has specific mean:'+"\n"
                                  + 'gre      Generic Routing Encapsulation (47'
                                  + ')'+"\n"
                                  + 'icmp     Internet Control Message Protocol'
                                  + ' (58)'+"\n"
                                  + 'ospf     Open Shortest Path First Protocol'
                                  + ' (89)'+"\n"
                                  + 'pim      Protocol Independent Multicast (1'
                                  + '03)'+"\n"
                                  + 'tcp      Transmission Control Protocol(6)
'
                                  + ''+"\n"
                                  + 'udp      User Datagram Protocol(17)'+"\n"
                                  + 'vrrp     Virtual Router Redundancy Protoco'
                                  + 'l (112)'+"\n"
                                  + 'ipv6     Any IP protocol (65535).'
                                    ;
                        leaf protocol-type {
                          description 'Configure protocol type of IPv6 VXLAN ac'
                                    + 'l in inner-layer as follows:'+"\n"
                                    + 'IP protocol number(0-255)'+"\n"
                                    + 'Some has specific mean:'+"\n"
                                    + 'gre      Generic Routing Encapsulation ('
                                    + '47)'+"\n"
                                    + 'icmp     Internet Control Message Protoc'
                                    + 'ol (58)'+"\n"
                                    + 'ospf     Open Shortest Path First Protoc'
                                    + 'ol (89)'+"\n"
                                    + 'pim      Protocol Independent Multicast '
                                    + '(103)'+"\n"
                                    + 'tcp      Transmission Control Protocol(6'
                                    + ')'+"\n"
                                    + 'udp      User Datagram Protocol(17)'+"\n"
                                    + 'vrrp     Virtual Router Redundancy Proto'
                                    + 'col (112)'+"\n"
                                    + 'ipv6     Any IP protocol (65535).'
                                      ;
                          type uint16 {
                            range '0..5 | 7..16 | 18..255 | 65535'
                                  ;
                          }
                          mandatory true ;
                        }
                        choice src-addr {
                          description 'Configure source address.'
                                      ;
                          mandatory true ;
                          case addr-type {
                            description 'Configure source address.'
                                        ;
                            leaf src-address {
                              description 'Configure source address.'
                                          ;
                              type ncd:ipv6-address ;
                              mandatory true ;
                            }
                            container src-wildcard {
                              description 'Configure source wildcard.'
                                          ;
                              choice wildcard-type {
                                description 'Configure source wildcard.'
                                            ;
                                mandatory true ;
                                case wildcard-len {
                                  description 'Configure source wildcard prefix length.'
                                              ;
                                  leaf src-wildcard-len {
                                    description 'Configure source wildcard prefix length.'
                                                ;
                                    type uint8 {
                                      range 0..128 ;
                                    }
                                    mandatory true ;
                                  }
                                }
                                case wildcard-bits {
                                  description 'Configure source wildcard bits.'
                                              ;
                                  leaf src-wildcard-bits {
                                    description 'Configure source wildcard bits.'
                                                ;
                                    type ncd:ipv6-address ;
                                    mandatory true ;
                                  }
                                }
                              }
                            }
                          }
                          case any-type {
                            description 'Any source address.'
                                        ;
                            leaf src-any-addr {
                              description 'Any source address.'
                                          ;
                              type empty ;
                              mandatory true ;
                            }
                          }
                        }
                        choice dst-addr {
                          description 'Configure destination address.'
                                      ;
                          mandatory true ;
                          case addr-type {
                            description 'Configure destination address.'
                                        ;
                            leaf dst-address {
                              description 'Configure destination address.'
                                          ;
                              type ncd:ipv6-address ;
                              mandatory true ;
                            }
                            container dst-wildcard {
                              description 'Configure destination wildcard.'
                                          ;
                              choice wildcard-type {
                                description 'Configure destination wildcard.'
                                            ;
                                mandatory true ;
                                case wildcard-len {
                                  description 'Configure destination wildcard prefix length.'
                                              ;
                                  leaf dst-wildcard-len {
                                    description 'Configure destination wildcard prefix length.'
                                                ;
                                    type uint8 {
                                      range 0..128 ;
                                    }
                                    mandatory true ;
                                  }
                                }
                                case wildcard-bits {
                                  description 'Configure destination wildcard bits.'
                                              ;
                                  leaf dst-wildcard-bits {
                                    description 'Configure destination wildcard bits.'
                                                ;
                                    type ncd:ipv6-address ;
                                    mandatory true ;
                                  }
                                }
                              }
                            }
                          }
                          case any-type {
                            description 'Any destination address.'
                                        ;
                            leaf dst-any-addr {
                              description 'Any destination address.'
                                          ;
                              type empty ;
                              mandatory true ;
                            }
                          }
                        }
                      }
                    }
                  }
                  leaf dscp {
                    description 'DSCP value.'
                                ;
                    type uint8 {
                      range 0..63 ;
                    }
                  }
                }
                container vni {
                  description 'VXLAN ID.'
                              ;
                  presence vni ;
                  leaf vxlan-id {
                    description 'VXLAN ID.'
                                ;
                    type uint32 {
                      range 1..16777215 ;
                    }
                    mandatory true ;
                  }
                }
                leaf vrf {
                  description 'VPN Routing/Forwarding instance name, support 1-'
                            + '32 characters.'
                              ;
                  type acl-vrf-name {
                    length 1..32 {
                      description 'VPN Routing/Forwarding instance name, suppor'
                                + 't 1-32 characters.'
                                  ;
                    }
                  }
                }
                leaf time-range {
                  description 'Specify the existed time-range name.'
                              ;
                  type string {
                    length 1..31 ;
                  }
                  ncd:revise-date 2021-04-02 ;
                }
                container l2-layer {
                  if-feature l2-layer ;
                  description 'L2 information.'
                              ;
                  presence l2-layer ;
                  container link-prot {
                    description 'Specify Link protocol type.'
                                ;
                    choice link-prot {
                      description 'Specify Link protocol type.'
                                  ;
                      case link-protocol {
                        description 'Specify Link protocol type.'
                                    ;
                        leaf link-protocol {
                          description 'Specify Link protocol type.'
                                      ;
                          type uint32 {
                            range 1536..65535 ;
                          }
                        }
                      }
                      case link-protocol-hex {
                        if-feature link-prot-hex-config ;
                        description 'Specify Link protocol type, hex.'
                                    ;
                        leaf link-protocol-hex {
                          description 'Specify Link protocol type, hex.'
                                      ;
                          type ncd:hex ;
                        }
                      }
                    }
                  }
                  container source-mac {
                    description 'Specify source MAC address.'
                                ;
                    choice src-mac-addr {
                      description 'Specify source MAC address.'
                                  ;
                      mandatory true ;
                      case src-mac-addr {
                        description 'MAC address.'
                                    ;
                        leaf src-mac-address {
                          description 'MAC address.'
                                      ;
                          type ncd:mac-address ;
                          mandatory true ;
                        }
                        leaf src-mac-wildcard {
                          description 'MAC address wildcard.'
                                      ;
                          type ncd:mac-address ;
                          mandatory true ;
                        }
                      }
                      case src-mac-any {
                        description 'Any MAC address.'
                                    ;
                        leaf src-mac-any {
                          description 'Any MAC address.'
                                      ;
                          type empty ;
                          mandatory true ;
                        }
                      }
                    }
                  }
                  container destination-mac {
                    description 'Specify destination MAC address.'
                                ;
                    choice dest-mac-addr {
                      description 'Specify destination MAC address.'
                                  ;
                      mandatory true ;
                      case dest-mac-addr {
                        description 'MAC address.'
                                    ;
                        leaf dest-mac-address {
                          description 'MAC address.'
                                      ;
                          type ncd:mac-address ;
                          mandatory true ;
                        }
                        leaf dest-mac-wildcard {
                          description 'MAC address wildcard.'
                                      ;
                          type ncd:mac-address ;
                          mandatory true ;
                        }
                      }
                      case dest-mac-any {
                        description 'Any MAC address.'
                                    ;
                        leaf dest-mac-any {
                          description 'Any MAC address.'
                                      ;
                          type empty ;
                          mandatory true ;
                        }
                      }
                    }
                  }
                  leaf inner-cos {
                    if-feature link-cos-value ;
                    description 'Value of inner CoS.'
                                ;
                    type uint8 {
                      range 0..7 ;
                    }
                  }
                  leaf outer-cos {
                    if-feature link-cos-value ;
                    description 'Value of outer CoS.'
                                ;
                    type uint8 {
                      range 0..7 ;
                    }
                  }
                  leaf inner-vlan-range {
                    description 'Specify range of inner VLAN.'
                                ;
                    type acl-vlan-range ;
                  }
                  leaf outer-vlan-range {
                    description 'Specify range of outer VLAN.'
                                ;
                    type acl-vlan-range ;
                  }
                  ncd:revise-date 2021-10-26 ;
                }
                leaf log {
                  if-feature log-config ;
                  description 'If log flag is set, the matching times of this r'
                            + 'ule will be recorded.'
                              ;
                  type boolean ;
                  default false ;
                  ncd:revise-date 2022-01-20 ;
                }
              }
            }
            container rules-transit-outer {
              description 'Configure rule of an IPv6 VXLAN ACL.'
                          ;
              list rule-transit-outer {
                description 'Configure rule of an IPv6 VXLAN ACL.'
                            ;
                key ruleid ;
                leaf ruleid {
                  description 'ID of this rule.'
                              ;
                  type uint32 {
                    range 1..2147483644 ;
                  }
                }
                choice permit-deny {
                  description 'Deny  :  Specify packets to reject'+"\n"
                            + 'Permit:  Specify packets to forward.'
                              ;
                  mandatory true ;
                  case deny {
                    description 'Deny:Specify packets to reject.'
                                ;
                    leaf deny {
                      description 'Deny:Specify packets to reject.'
                                  ;
                      type empty ;
                      mandatory true ;
                    }
                  }
                  case permit {
                    description 'Permit:  Specify packets to forward.'
                                ;
                    leaf permit {
                      description 'Permit:  Specify packets to forward.'
                                  ;
                      type empty ;
                      mandatory true ;
                    }
                  }
                }
                container vni {
                  description 'VXLAN ID.'
                              ;
                  presence vni ;
                  leaf vxlan-id {
                    description 'VXLAN ID.'
                                ;
                    type uint32 {
                      range 1..16777215 ;
                    }
                    mandatory true ;
                  }
                }
                container outer-layer {
                  description 'The outer-layer protocol of VXLAN.'
                              ;
                  leaf udp {
                    description 'Configure UDP protocol.'
                                ;
                    type empty ;
                    mandatory true ;
                  }
                  choice src-addr {
                    description 'Configure source address.'
                                ;
                    mandatory true ;
                    case addr-type {
                      description 'Configure source address.'
                                  ;
                      leaf src-address {
                        description 'Configure source address.'
                                    ;
                        type ncd:ipv6-address ;
                        mandatory true ;
                      }
                      container src-wildcard {
                        description 'Configure source wildcard.'
                                    ;
                        choice wildcard-type {
                          description 'Configure source wildcard.'
                                      ;
                          mandatory true ;
                          case wildcard-len {
                            description 'Configure source wildcard prefix length.'
                                        ;
                            leaf src-wildcard-len {
                              description 'Configure source wildcard prefix length.'
                                          ;
                              type uint8 {
                                range 0..128 ;
                              }
                              mandatory true ;
                            }
                          }
                          case wildcard-bits {
                            description 'Configure source wildcard bits.'
                                        ;
                            leaf src-wildcard-bits {
                              description 'Configure source wildcard bits.'
                                          ;
                              type ncd:ipv6-address ;
                              mandatory true ;
                            }
                          }
                        }
                      }
                    }
                    case any-type {
                      description 'Any source address.'
                                  ;
                      leaf src-any-addr {
                        description 'Any source address.'
                                    ;
                        type empty ;
                        mandatory true ;
                      }
                    }
                  }
                  container source-port {
                    description 'Specify source port.'+"\n"
                              + 'When the value of operator is invalid, it mean'
                              + 's match all port range,'+"\n"
                              + 'the other value of operator means'+"\n"
                              + 'eq(1)   : match only packets on a given port n'
                              + 'umber'+"\n"
                              + 'ge(2)   : match only packets with a no lower p'
                              + 'ort number'+"\n"
                              + 'le(3)   : match only packets with a no greater'
                              + ' port number'+"\n"
                              + 'range(7): match only packet on a given port ra'
                              + 'nge.'
                                ;
                    presence 'Specify source port'
                             ;
                    choice source-port {
                      description 'Specify source port.'+"\n"
                                + 'When the value of operator is invalid, it me'
                                + 'ans match all port range,'+"\n"
                                + 'the other value of operator means'+"\n"
                                + 'eq(1)   : match only packets on a given port'
                                + ' number'+"\n"
                                + 'ge(2)   : match only packets with a no lower'
                                + ' port number'+"\n"
                                + 'le(3)   : match only packets with a no great'
                                + 'er port number'+"\n"
                                + 'range(7): match only packet on a given port '
                                + 'range.'
                                  ;
                      mandatory true ;
                      case src-port-value {
                        description 'Configure port number.'
                                    ;
                        container src-port-value {
                          description 'Configure port number.'
                                      ;
                          presence 'Configure port number'
                                   ;
                          leaf src-port-operator {
                            description 'Operator type'+"\n"
                                      + 'eq(1)   : match only packets on a given port number'+"\n"
                                      + 'ge(2)   : match only packets with a no lower port number'+"\n"
                                      + 'le(3)   : match only packets with a no greater port number.'
                                        ;
                            type enumeration {
                              enum eq {
                                value 1 ;
                                description 'Equal to.'
                                            ;
                              }
                              enum ge {
                                value 2 ;
                                description 'Great than or equal to.'
                                            ;
                              }
                              enum le {
                                value 3 ;
                                description 'Less than or equal to.'
                                            ;
                              }
                            }
                            mandatory true ;
                          }
                          leaf src-port-value {
                            description 'Port number.'+"\n"
                                      + 'Some has specific means:'+"\n"
                                      + 'bootpc       Bootstrap protocol (BOOTP) client (68)'+"\n"
                                      + 'bootps       Bootstrap protocol (BOOTP) server (67)'+"\n"
                                      + 'domain       Domain name service (DNS, 53)'+"\n"
                                      + 'ntp          Network time protocol (123)'+"\n"
                                      + 'pim-auto-rp  PIM auto-RP (496)'+"\n"
                                      + 'rip          Routing information protocol (router, in.routed, 520)'+"\n"
                                      + 'snmp         Simple network management protocol (161)'+"\n"
                                      + 'snmptrap     SNMP traps (162)'+"\n"
                                      + 'tftp         Trivial file transfer protocol (69).'
                                        ;
                            type uint16 {
                              range 0..65535 ;
                            }
                            mandatory true ;
                          }
                        }
                      }
                      case src-port-range {
                        description 'Configure port range.'
                                    ;
                        container src-port-range {
                          description 'Configure port range.'
                                      ;
                          presence 'Configure port range'
                                   ;
                          leaf src-port-operator {
                            description 'Operator type
range(7): match only packet on a given port range.'
                                        ;
                            type enumeration {
                              enum range {
                                value 7 ;
                                description Range. ;
                              }
                            }
                            mandatory true ;
                          }
                          leaf src-port-range {
                            description 'Port range, support <0-65535>-<0-65535>.'
                                        ;
                            type acl-port-range ;
                            mandatory true ;
                          }
                        }
                      }
                    }
                  }
                  choice dst-addr {
                    description 'Configure destination address.'
                                ;
                    mandatory true ;
                    case addr-type {
                      description 'Configure destination address.'
                                  ;
                      leaf dst-address {
                        description 'Configure destination address.'
                                    ;
                        type ncd:ipv6-address ;
                        mandatory true ;
                      }
                      container dst-wildcard {
                        description 'Configure destination wildcard.'
                                    ;
                        choice wildcard-type {
                          description 'Configure destination wildcard.'
                                      ;
                          mandatory true ;
                          case wildcard-len {
                            description 'Configure destination wildcard prefix length.'
                                        ;
                            leaf dst-wildcard-len {
                              description 'Configure destination wildcard prefix length.'
                                          ;
                              type uint8 {
                                range 0..128 ;
                              }
                              mandatory true ;
                            }
                          }
                          case wildcard-bits {
                            description 'Configure destination wildcard bits.'
                                        ;
                            leaf dst-wildcard-bits {
                              description 'Configure destination wildcard bits.'
                                          ;
                              type ncd:ipv6-address ;
                              mandatory true ;
                            }
                          }
                        }
                      }
                    }
                    case any-type {
                      description 'Any destination address.'
                                  ;
                      leaf dst-any-addr {
                        description 'Any destination address.'
                                    ;
                        type empty ;
                        mandatory true ;
                      }
                    }
                  }
                  container destination-port {
                    description 'Specify destination port.'+"\n"
                              + 'When the value of operator is invalid, it mean'
                              + 's match all port range,'+"\n"
                              + 'the other value of operator means'+"\n"
                              + 'eq(1)   : match only packets on a given port n'
                              + 'umber'+"\n"
                              + 'ge(2)   : match only packets with a no lower p'
                              + 'ort number'+"\n"
                              + 'le(3)   : match only packets with a no greater'
                              + ' port number'+"\n"
                              + 'range(7): match only packet on a given port ra'
                              + 'nge.'
                                ;
                    presence 'Specify destination port'
                             ;
                    choice destination-port {
                      description 'Specify destination port.'+"\n"
                                + 'When the value of operator is invalid, it me'
                                + 'ans match all port range,'+"\n"
                                + 'the other value of operator means'+"\n"
                                + 'eq(1)   : match only packets on a given port'
                                + ' number'+"\n"
                                + 'ge(2)   : match only packets with a no lower'
                                + ' port number'+"\n"
                                + 'le(3)   : match only packets with a no great'
                                + 'er port number'+"\n"
                                + 'range(7): match only packet on a given port '
                                + 'range.'
                                  ;
                      mandatory true ;
                      case dst-port-value {
                        description 'Configure port number.'
                                    ;
                        container dst-port-value {
                          description 'Configure port number.'
                                      ;
                          presence 'Configure port number'
                                   ;
                          leaf dst-port-operator {
                            description 'Operator type'+"\n"
                                      + 'eq(1)   : match only packets on a given port number'+"\n"
                                      + 'ge(2)   : match only packets with a no lower port number'+"\n"
                                      + 'le(3)   : match only packets with a no greater port number.'
                                        ;
                            type enumeration {
                              enum eq {
                                value 1 ;
                                description 'Equal to.'
                                            ;
                              }
                              enum ge {
                                value 2 ;
                                description 'Great than or equal to.'
                                            ;
                              }
                              enum le {
                                value 3 ;
                                description 'Less than or equal to.'
                                            ;
                              }
                            }
                            mandatory true ;
                          }
                          leaf dst-port-value {
                            description 'Port number.'+"\n"
                                      + 'Some has specific means:'+"\n"
                                      + 'bootpc       Bootstrap protocol (BOOTP) client (68)'+"\n"
                                      + 'bootps       Bootstrap protocol (BOOTP) server (67)'+"\n"
                                      + 'domain       Domain name service (DNS, 53)'+"\n"
                                      + 'ntp          Network time protocol (123)'+"\n"
                                      + 'pim-auto-rp  PIM auto-RP (496)'+"\n"
                                      + 'rip          Routing information protocol (router, in.routed, 520)'+"\n"
                                      + 'snmp         Simple network management protocol (161)'+"\n"
                                      + 'snmptrap     SNMP traps (162)'+"\n"
                                      + 'tftp         Trivial file transfer protocol (69).'
                                        ;
                            type uint16 {
                              range 0..65535 ;
                            }
                            mandatory true ;
                          }
                        }
                      }
                      case dst-port-range {
                        description 'Configure port range.'
                                    ;
                        container dst-port-range {
                          description 'Configure port range.'
                                      ;
                          presence 'Configure port range'
                                   ;
                          leaf dst-port-operator {
                            description 'Operator type
range(7): match only packet on a given port range.'
                                        ;
                            type enumeration {
                              enum range {
                                value 7 ;
                                description Range. ;
                              }
                            }
                            mandatory true ;
                          }
                          leaf dst-port-range {
                            description 'Port range, support <0-65535>-<0-65535>.'
                                        ;
                            type acl-port-range ;
                            mandatory true ;
                          }
                        }
                      }
                    }
                  }
                  leaf dscp {
                    description 'DSCP value.'
                                ;
                    type uint8 {
                      range 0..63 ;
                    }
                  }
                }
                leaf vrf {
                  description 'VPN Routing/Forwarding instance name, support 1-'
                            + '32 characters.'
                              ;
                  type acl-vrf-name {
                    length 1..32 {
                      description 'VPN Routing/Forwarding instance name, suppor'
                                + 't 1-32 characters.'
                                  ;
                    }
                  }
                }
                leaf time-range {
                  description 'Specify the existed time-range name.'
                              ;
                  type string {
                    length 1..31 ;
                  }
                  ncd:revise-date 2021-04-02 ;
                }
              }
            }
            container rules-vtep-inner {
              description 'Configure rule of an IPv6 VXLAN ACL.'
                          ;
              list rule-vtep-inner {
                description 'Configure rule of an IPv6 VXLAN ACL.'
                            ;
                key ruleid ;
                leaf ruleid {
                  description 'ID of this rule.'
                              ;
                  type uint32 {
                    range 1..2147483644 ;
                  }
                }
                choice permit-deny {
                  description 'Deny  :  Specify packets to reject'+"\n"
                            + 'Permit:  Specify packets to forward.'
                              ;
                  mandatory true ;
                  case deny {
                    description 'Deny:Specify packets to reject.'
                                ;
                    leaf deny {
                      description 'Deny:Specify packets to reject.'
                                  ;
                      type empty ;
                      mandatory true ;
                    }
                  }
                  case permit {
                    description 'Permit:  Specify packets to forward.'
                                ;
                    leaf permit {
                      description 'Permit:  Specify packets to forward.'
                                  ;
                      type empty ;
                      mandatory true ;
                    }
                  }
                }
                container inner-layer {
                  description 'The inner-layer protocol of VXLAN.'
                              ;
                  presence inner-layer ;
                  choice protocol-type {
                    description 'Configure protocol type of IPv6 VXLAN acl in i'
                              + 'nner-layer as follows:'+"\n"
                              + 'IP protocol number(0-255)'+"\n"
                              + 'Some has specific mean:'+"\n"
                              + 'gre      Generic Routing Encapsulation (47)'+"\n"
                              + 'icmp     Internet Control Message Protocol (58'
                              + ')'+"\n"
                              + 'ospf     Open Shortest Path First Protocol (89'
                              + ')'+"\n"
                              + 'pim      Protocol Independent Multicast (103)
'
                              + ''+"\n"
                              + 'tcp      Transmission Control Protocol(6)'+"\n"
                              + 'udp      User Datagram Protocol(17)'+"\n"
                              + 'vrrp     Virtual Router Redundancy Protocol (1'
                              + '12)'+"\n"
                              + 'ipv6     Any IP protocol (65535).'
                                ;
                    mandatory true ;
                    case tcp-udp {
                      description 'Configure TCP or UDP protocol of IPv6 VXLAN '
                                + 'ACL.'+"\n"
                                + 'tcp      Transmission Control Protocol(6)'+"\n"
                                + 'udp      User Datagram Protocol(17)'
                                  ;
                      container tcp-udp {
                        description 'Configure protocol type of IPv6 VXLAN ACL.'
                                  + ''+"\n"
                                  + 'tcp      Transmission Control Protocol(6)
'
                                  + ''+"\n"
                                  + 'udp      User Datagram Protocol(17)'
                                    ;
                        leaf tcp-udp {
                          description 'Configure protocol type of IPv6 VXLAN AC'
                                    + 'L.'+"\n"
                                    + 'tcp      Transmission Control Protocol(6'
                                    + ')'+"\n"
                                    + 'udp      User Datagram Protocol(17)'
                                      ;
                          type enumeration {
                            enum tcp {
                              value 6 ;
                              description 'Transmission Control Protocol(6)'
                                          ;
                            }
                            enum udp {
                              value 17 ;
                              description 'User Datagram Protocol(17)'
                                          ;
                            }
                          }
                          mandatory true ;
                        }
                        choice src-addr {
                          description 'Configure source address.'
                                      ;
                          mandatory true ;
                          case addr-type {
                            description 'Configure source address.'
                                        ;
                            leaf src-address {
                              description 'Configure source address.'
                                          ;
                              type ncd:ipv6-address ;
                              mandatory true ;
                            }
                            container src-wildcard {
                              description 'Configure source wildcard.'
                                          ;
                              choice wildcard-type {
                                description 'Configure source wildcard.'
                                            ;
                                mandatory true ;
                                case wildcard-len {
                                  description 'Configure source wildcard prefix length.'
                                              ;
                                  leaf src-wildcard-len {
                                    description 'Configure source wildcard prefix length.'
                                                ;
                                    type uint8 {
                                      range 0..128 ;
                                    }
                                    mandatory true ;
                                  }
                                }
                                case wildcard-bits {
                                  description 'Configure source wildcard bits.'
                                              ;
                                  leaf src-wildcard-bits {
                                    description 'Configure source wildcard bits.'
                                                ;
                                    type ncd:ipv6-address ;
                                    mandatory true ;
                                  }
                                }
                              }
                            }
                          }
                          case any-type {
                            description 'Any source address.'
                                        ;
                            leaf src-any-addr {
                              description 'Any source address.'
                                          ;
                              type empty ;
                              mandatory true ;
                            }
                          }
                        }
                        container source-port {
                          description 'Specify source port.'+"\n"
                                    + 'When the value of operator is invalid, i'
                                    + 't means match all port range,'+"\n"
                                    + 'the other value of operator means'+"\n"
                                    + 'eq(1)   : match only packets on a given '
                                    + 'port number'+"\n"
                                    + 'ge(2)   : match only packets with a no l'
                                    + 'ower port number'+"\n"
                                    + 'le(3)   : match only packets with a no g'
                                    + 'reater port number'+"\n"
                                    + 'range(7): match only packet on a given p'
                                    + 'ort range.'
                                      ;
                          presence 'Specify source port'
                                   ;
                          choice source-port {
                            description 'Specify source port.'+"\n"
                                      + 'When the value of operator is invalid, it means match all port range,'+"\n"
                                      + 'the other value of operator means'+"\n"
                                      + 'eq(1)   : match only packets on a given port number'+"\n"
                                      + 'ge(2)   : match only packets with a no lower port number'+"\n"
                                      + 'le(3)   : match only packets with a no greater port number'+"\n"
                                      + 'range(7): match only packet on a given port range.'
                                        ;
                            mandatory true ;
                            case src-port-value {
                              description 'Configure port number.'
                                          ;
                              container src-port-value {
                                description 'Configure port number.'
                                            ;
                                presence 'Configure port number'
                                         ;
                                leaf src-port-operator {
                                  description 'Operator type'+"\n"
                                            + 'eq(1)   : match only packets on a given port number'+"\n"
                                            + 'ge(2)   : match only packets with a no lower port number'+"\n"
                                            + 'le(3)   : match only packets with a no greater port number.'
                                              ;
                                  type enumeration {
                                    enum eq {
                                      value 1 ;
                                      description 'Equal to.'
                                                  ;
                                    }
                                    enum ge {
                                      value 2 ;
                                      description 'Great than or equal to.'
                                                  ;
                                    }
                                    enum le {
                                      value 3 ;
                                      description 'Less than or equal to.'
                                                  ;
                                    }
                                  }
                                  mandatory true ;
                                }
                                leaf src-port-value {
                                  description 'Configure port number from 0 to 65535.'+"\n"
                                            + 'Some has specific means when port protocol type is TCP.'+"\n"
                                            + '  bgp        Border gateway protocol (179)'+"\n"
                                            + '  domain     Domain name service (53)'+"\n"
                                            + '  finger     Finger (79)'+"\n"
                                            + '  ftp        File transfer protocol (21)'+"\n"
                                            + '  login      Login (rlogin, 513)'+"\n"
                                            + '  pop2       Post office protocol v2 (109)'+"\n"
                                            + '  pop3       Post office protocol v3 (110)'+"\n"
                                            + '  smtp       Simple mail transport protocol (25)'+"\n"
                                            + '  telnet     Telnet (23)'+"\n"
                                            + '  www        World wide web (HTTP, 80)'+"\n"
                                            + 'Some has specific means when port protocol type is UDP.'+"\n"
                                            + '  bootpc       Bootstrap protocol (BOOTP) client (68)'+"\n"
                                            + '  bootps       Bootstrap protocol (BOOTP) server (67)'+"\n"
                                            + '  domain       Domain name service (DNS, 53)'+"\n"
                                            + '  ntp          Network time protocol (123)'+"\n"
                                            + '  pim-auto-rp  PIM auto-RP (496)'+"\n"
                                            + '  rip          Routing information protocol (router, in.routed, 520)'+"\n"
                                            + '  snmp         Simple network management protocol (161)'+"\n"
                                            + '  snmptrap     SNMP traps (162)'+"\n"
                                            + '  tftp         Trivial file transfer protocol (69).'
                                              ;
                                  type uint16 {
                                    range 0..65535 ;
                                  }
                                  mandatory true ;
                                }
                              }
                            }
                            case src-port-range {
                              description 'Configure port range.'
                                          ;
                              container src-port-range {
                                description 'Configure port range.'
                                            ;
                                presence 'Configure port range'
                                         ;
                                leaf src-port-operator {
                                  description 'Operator type
range(7): match only packet on a given port range.'
                                              ;
                                  type enumeration {
                                    enum range {
                                      value 7 ;
                                      description Range. ;
                                    }
                                  }
                                  mandatory true ;
                                }
                                leaf src-port-range {
                                  description 'Port range, support <0-65535>-<0-65535>.'
                                              ;
                                  type acl-port-range ;
                                  mandatory true ;
                                }
                              }
                            }
                          }
                        }
                        choice dst-addr {
                          description 'Configure destination address.'
                                      ;
                          mandatory true ;
                          case addr-type {
                            description 'Configure destination address.'
                                        ;
                            leaf dst-address {
                              description 'Configure destination address.'
                                          ;
                              type ncd:ipv6-address ;
                              mandatory true ;
                            }
                            container dst-wildcard {
                              description 'Configure destination wildcard.'
                                          ;
                              choice wildcard-type {
                                description 'Configure destination wildcard.'
                                            ;
                                mandatory true ;
                                case wildcard-len {
                                  description 'Configure destination wildcard prefix length.'
                                              ;
                                  leaf dst-wildcard-len {
                                    description 'Configure destination wildcard prefix length.'
                                                ;
                                    type uint8 {
                                      range 0..128 ;
                                    }
                                    mandatory true ;
                                  }
                                }
                                case wildcard-bits {
                                  description 'Configure destination wildcard bits.'
                                              ;
                                  leaf dst-wildcard-bits {
                                    description 'Configure destination wildcard bits.'
                                                ;
                                    type ncd:ipv6-address ;
                                    mandatory true ;
                                  }
                                }
                              }
                            }
                          }
                          case any-type {
                            description 'Any destination address.'
                                        ;
                            leaf dst-any-addr {
                              description 'Any destination address.'
                                          ;
                              type empty ;
                              mandatory true ;
                            }
                          }
                        }
                        container destination-port {
                          description 'Specify destination port.'+"\n"
                                    + 'When the value of operator is invalid, i'
                                    + 't means match all port range,'+"\n"
                                    + 'the other value of operator means'+"\n"
                                    + 'eq(1)   : match only packets on a given '
                                    + 'port number'+"\n"
                                    + 'ge(2)   : match only packets with a no l'
                                    + 'ower port number'+"\n"
                                    + 'le(3)   : match only packets with a no g'
                                    + 'reater port number'+"\n"
                                    + 'range(7): match only packet on a given p'
                                    + 'ort range.'
                                      ;
                          presence 'Specify destination port'
                                   ;
                          choice destination-port {
                            description 'Specify destination port.'+"\n"
                                      + 'When the value of operator is invalid, it means match all port range,'+"\n"
                                      + 'the other value of operator means'+"\n"
                                      + 'eq(1)   : match only packets on a given port number'+"\n"
                                      + 'ge(2)   : match only packets with a no lower port number'+"\n"
                                      + 'le(3)   : match only packets with a no greater port number'+"\n"
                                      + 'range(7): match only packet on a given port range.'
                                        ;
                            mandatory true ;
                            case dst-port-value {
                              description 'Configure port number.'
                                          ;
                              container dst-port-value {
                                description 'Configure port number.'
                                            ;
                                presence 'Configure port number'
                                         ;
                                leaf dst-port-operator {
                                  description 'Operator type'+"\n"
                                            + 'eq(1)   : match only packets on a given port number'+"\n"
                                            + 'ge(2)   : match only packets with a no lower port number'+"\n"
                                            + 'le(3)   : match only packets with a no greater port number.'
                                              ;
                                  type enumeration {
                                    enum eq {
                                      value 1 ;
                                      description 'Equal to.'
                                                  ;
                                    }
                                    enum ge {
                                      value 2 ;
                                      description 'Great than or equal to.'
                                                  ;
                                    }
                                    enum le {
                                      value 3 ;
                                      description 'Less than or equal to.'
                                                  ;
                                    }
                                  }
                                  mandatory true ;
                                }
                                leaf dst-port-value {
                                  description 'Configure port number from 0 to 65535.'+"\n"
                                            + 'Some has specific means when port protocol type is TCP.'+"\n"
                                            + '  bgp        Border gateway protocol (179)'+"\n"
                                            + '  domain     Domain name service (53)'+"\n"
                                            + '  finger     Finger (79)'+"\n"
                                            + '  ftp        File transfer protocol (21)'+"\n"
                                            + '  login      Login (rlogin, 513)'+"\n"
                                            + '  pop2       Post office protocol v2 (109)'+"\n"
                                            + '  pop3       Post office protocol v3 (110)'+"\n"
                                            + '  smtp       Simple mail transport protocol (25)'+"\n"
                                            + '  telnet     Telnet (23)'+"\n"
                                            + '  www        World wide web (HTTP, 80)'+"\n"
                                            + 'Some has specific means when port protocol type is UDP.'+"\n"
                                            + '  bootpc       Bootstrap protocol (BOOTP) client (68)'+"\n"
                                            + '  bootps       Bootstrap protocol (BOOTP) server (67)'+"\n"
                                            + '  domain       Domain name service (DNS, 53)'+"\n"
                                            + '  ntp          Network time protocol (123)'+"\n"
                                            + '  pim-auto-rp  PIM auto-RP (496)'+"\n"
                                            + '  rip          Routing information protocol (router, in.routed, 520)'+"\n"
                                            + '  snmp         Simple network management protocol (161)'+"\n"
                                            + '  snmptrap     SNMP traps (162)'+"\n"
                                            + '  tftp         Trivial file transfer protocol (69).'
                                              ;
                                  type uint16 {
                                    range 0..65535 ;
                                  }
                                  mandatory true ;
                                }
                              }
                            }
                            case dst-port-range {
                              description 'Configure port range.'
                                          ;
                              container dst-port-range {
                                description 'Configure port range.'
                                            ;
                                presence 'Configure port range'
                                         ;
                                leaf dst-port-operator {
                                  description 'Operator type
range(7): match only packet on a given port range.'
                                              ;
                                  type enumeration {
                                    enum range {
                                      value 7 ;
                                      description Range. ;
                                    }
                                  }
                                  mandatory true ;
                                }
                                leaf dst-port-range {
                                  description 'Port range, support <0-65535>-<0-65535>.'
                                              ;
                                  type acl-port-range ;
                                  mandatory true ;
                                }
                              }
                            }
                          }
                        }
                      }
                    }
                    case ip {
                      description 'Configure protocol type of IPv6 VXLAN acl in'
                                + ' inner-layer as follows:'+"\n"
                                + 'IP protocol number(0-255)'+"\n"
                                + 'Some has specific mean:'+"\n"
                                + 'gre      Generic Routing Encapsulation (47)
'
                                + ''+"\n"
                                + 'icmp     Internet Control Message Protocol(5'
                                + '8)'+"\n"
                                + 'ospf     Open Shortest Path First Protocol ('
                                + '89)'+"\n"
                                + 'pim      Protocol Independent Multicast (103'
                                + ')'+"\n"
                                + 'vrrp     Virtual Router Redundancy Protocol '
                                + '(112)'+"\n"
                                + 'ip       Any IP protocol (65535).'
                                  ;
                      container ipv6-protocol {
                        description 'Configure protocol type of IPv6 VXLAN acl '
                                  + 'in inner-layer as follows:'+"\n"
                                  + 'IP protocol number(0-255)'+"\n"
                                  + 'Some has specific mean:'+"\n"
                                  + 'gre      Generic Routing Encapsulation (47'
                                  + ')'+"\n"
                                  + 'icmp     Internet Control Message Protocol'
                                  + ' (58)'+"\n"
                                  + 'ospf     Open Shortest Path First Protocol'
                                  + ' (89)'+"\n"
                                  + 'pim      Protocol Independent Multicast (1'
                                  + '03)'+"\n"
                                  + 'tcp      Transmission Control Protocol(6)
'
                                  + ''+"\n"
                                  + 'udp      User Datagram Protocol(17)'+"\n"
                                  + 'vrrp     Virtual Router Redundancy Protoco'
                                  + 'l (112)'+"\n"
                                  + 'ipv6     Any IP protocol (65535).'
                                    ;
                        leaf protocol-type {
                          description 'Configure protocol type of IPv6 VXLAN ac'
                                    + 'l in inner-layer as follows:'+"\n"
                                    + 'IP protocol number(0-255)'+"\n"
                                    + 'Some has specific mean:'+"\n"
                                    + 'gre      Generic Routing Encapsulation ('
                                    + '47)'+"\n"
                                    + 'icmp     Internet Control Message Protoc'
                                    + 'ol (58)'+"\n"
                                    + 'ospf     Open Shortest Path First Protoc'
                                    + 'ol (89)'+"\n"
                                    + 'pim      Protocol Independent Multicast '
                                    + '(103)'+"\n"
                                    + 'tcp      Transmission Control Protocol(6'
                                    + ')'+"\n"
                                    + 'udp      User Datagram Protocol(17)'+"\n"
                                    + 'vrrp     Virtual Router Redundancy Proto'
                                    + 'col (112)'+"\n"
                                    + 'ipv6     Any IP protocol (65535).'
                                      ;
                          type uint16 {
                            range '0..5 | 7..16 | 18..255 | 65535'
                                  ;
                          }
                          mandatory true ;
                        }
                        choice src-addr {
                          description 'Configure source address.'
                                      ;
                          mandatory true ;
                          case addr-type {
                            description 'Configure source address.'
                                        ;
                            leaf src-address {
                              description 'Configure source address.'
                                          ;
                              type ncd:ipv6-address ;
                              mandatory true ;
                            }
                            container src-wildcard {
                              description 'Configure source wildcard.'
                                          ;
                              choice wildcard-type {
                                description 'Configure source wildcard.'
                                            ;
                                mandatory true ;
                                case wildcard-len {
                                  description 'Configure source wildcard prefix length.'
                                              ;
                                  leaf src-wildcard-len {
                                    description 'Configure source wildcard prefix length.'
                                                ;
                                    type uint8 {
                                      range 0..128 ;
                                    }
                                    mandatory true ;
                                  }
                                }
                                case wildcard-bits {
                                  description 'Configure source wildcard bits.'
                                              ;
                                  leaf src-wildcard-bits {
                                    description 'Configure source wildcard bits.'
                                                ;
                                    type ncd:ipv6-address ;
                                    mandatory true ;
                                  }
                                }
                              }
                            }
                          }
                          case any-type {
                            description 'Any source address.'
                                        ;
                            leaf src-any-addr {
                              description 'Any source address.'
                                          ;
                              type empty ;
                              mandatory true ;
                            }
                          }
                        }
                        choice dst-addr {
                          description 'Configure destination address.'
                                      ;
                          mandatory true ;
                          case addr-type {
                            description 'Configure destination address.'
                                        ;
                            leaf dst-address {
                              description 'Configure destination address.'
                                          ;
                              type ncd:ipv6-address ;
                              mandatory true ;
                            }
                            container dst-wildcard {
                              description 'Configure destination wildcard.'
                                          ;
                              choice wildcard-type {
                                description 'Configure destination wildcard.'
                                            ;
                                mandatory true ;
                                case wildcard-len {
                                  description 'Configure destination wildcard prefix length.'
                                              ;
                                  leaf dst-wildcard-len {
                                    description 'Configure destination wildcard prefix length.'
                                                ;
                                    type uint8 {
                                      range 0..128 ;
                                    }
                                    mandatory true ;
                                  }
                                }
                                case wildcard-bits {
                                  description 'Configure destination wildcard bits.'
                                              ;
                                  leaf dst-wildcard-bits {
                                    description 'Configure destination wildcard bits.'
                                                ;
                                    type ncd:ipv6-address ;
                                    mandatory true ;
                                  }
                                }
                              }
                            }
                          }
                          case any-type {
                            description 'Any destination address.'
                                        ;
                            leaf dst-any-addr {
                              description 'Any destination address.'
                                          ;
                              type empty ;
                              mandatory true ;
                            }
                          }
                        }
                      }
                    }
                  }
                  leaf dscp {
                    description 'DSCP value.'
                                ;
                    type uint8 {
                      range 0..63 ;
                    }
                  }
                }
                container vni {
                  description 'VXLAN ID.'
                              ;
                  presence vni ;
                  leaf vxlan-id {
                    description 'VXLAN ID.'
                                ;
                    type uint32 {
                      range 1..16777215 ;
                    }
                    mandatory true ;
                  }
                }
                leaf vrf {
                  description 'VPN Routing/Forwarding instance name, support 1-'
                            + '32 characters.'
                              ;
                  type acl-vrf-name {
                    length 1..32 {
                      description 'VPN Routing/Forwarding instance name, suppor'
                                + 't 1-32 characters.'
                                  ;
                    }
                  }
                }
                leaf time-range {
                  description 'Specify the existed time-range name.'
                              ;
                  type string {
                    length 1..31 ;
                  }
                  ncd:revise-date 2021-04-02 ;
                }
                container l2-layer {
                  if-feature l2-layer ;
                  description 'L2 information.'
                              ;
                  presence l2-layer ;
                  container link-prot {
                    description 'Specify Link protocol type.'
                                ;
                    choice link-prot {
                      description 'Specify Link protocol type.'
                                  ;
                      case link-protocol {
                        description 'Specify Link protocol type.'
                                    ;
                        leaf link-protocol {
                          description 'Specify Link protocol type.'
                                      ;
                          type uint32 {
                            range 1536..65535 ;
                          }
                        }
                      }
                      case link-protocol-hex {
                        if-feature link-prot-hex-config ;
                        description 'Specify Link protocol type, hex.'
                                    ;
                        leaf link-protocol-hex {
                          description 'Specify Link protocol type, hex.'
                                      ;
                          type ncd:hex ;
                        }
                      }
                    }
                  }
                  container source-mac {
                    description 'Specify source MAC address.'
                                ;
                    choice src-mac-addr {
                      description 'Specify source MAC address.'
                                  ;
                      mandatory true ;
                      case src-mac-addr {
                        description 'MAC address.'
                                    ;
                        leaf src-mac-address {
                          description 'MAC address.'
                                      ;
                          type ncd:mac-address ;
                          mandatory true ;
                        }
                        leaf src-mac-wildcard {
                          description 'MAC address wildcard.'
                                      ;
                          type ncd:mac-address ;
                          mandatory true ;
                        }
                      }
                      case src-mac-any {
                        description 'Any MAC address.'
                                    ;
                        leaf src-mac-any {
                          description 'Any MAC address.'
                                      ;
                          type empty ;
                          mandatory true ;
                        }
                      }
                    }
                  }
                  container destination-mac {
                    description 'Specify destination MAC address.'
                                ;
                    choice dest-mac-addr {
                      description 'Specify destination MAC address.'
                                  ;
                      mandatory true ;
                      case dest-mac-addr {
                        description 'MAC address.'
                                    ;
                        leaf dest-mac-address {
                          description 'MAC address.'
                                      ;
                          type ncd:mac-address ;
                          mandatory true ;
                        }
                        leaf dest-mac-wildcard {
                          description 'MAC address wildcard.'
                                      ;
                          type ncd:mac-address ;
                          mandatory true ;
                        }
                      }
                      case dest-mac-any {
                        description 'Any MAC address.'
                                    ;
                        leaf dest-mac-any {
                          description 'Any MAC address.'
                                      ;
                          type empty ;
                          mandatory true ;
                        }
                      }
                    }
                  }
                  leaf inner-cos {
                    if-feature link-cos-value ;
                    description 'Value of inner CoS.'
                                ;
                    type uint8 {
                      range 0..7 ;
                    }
                  }
                  leaf outer-cos {
                    if-feature link-cos-value ;
                    description 'Value of outer CoS.'
                                ;
                    type uint8 {
                      range 0..7 ;
                    }
                  }
                  leaf inner-vlan-range {
                    description 'Specify range of inner VLAN.'
                                ;
                    type acl-vlan-range ;
                  }
                  leaf outer-vlan-range {
                    description 'Specify range of outer VLAN.'
                                ;
                    type acl-vlan-range ;
                  }
                  ncd:revise-date 2021-10-26 ;
                }
                leaf log {
                  if-feature log-config ;
                  description 'If log flag is set, the matching times of this r'
                            + 'ule will be recorded.'
                              ;
                  type boolean ;
                  default false ;
                  ncd:revise-date 2022-01-20 ;
                }
              }
            }
            container rules-vtep-outer {
              description 'Configure rule of an IPv6 VXLAN ACL.'
                          ;
              list rule-vtep-outer {
                description 'Configure rule of an IPv6 VXLAN ACL.'
                            ;
                key ruleid ;
                leaf ruleid {
                  description 'ID of this rule.'
                              ;
                  type uint32 {
                    range 1..2147483644 ;
                  }
                }
                choice permit-deny {
                  description 'Deny  :  Specify packets to reject'+"\n"
                            + 'Permit:  Specify packets to forward.'
                              ;
                  mandatory true ;
                  case deny {
                    description 'Deny:Specify packets to reject.'
                                ;
                    leaf deny {
                      description 'Deny:Specify packets to reject.'
                                  ;
                      type empty ;
                      mandatory true ;
                    }
                  }
                  case permit {
                    description 'Permit:  Specify packets to forward.'
                                ;
                    leaf permit {
                      description 'Permit:  Specify packets to forward.'
                                  ;
                      type empty ;
                      mandatory true ;
                    }
                  }
                }
                container vni {
                  description 'VXLAN ID.'
                              ;
                  presence vni ;
                  leaf vxlan-id {
                    description 'VXLAN ID.'
                                ;
                    type uint32 {
                      range 1..16777215 ;
                    }
                    mandatory true ;
                  }
                }
                container outer-layer {
                  description 'The outer-layer protocol of VXLAN.'
                              ;
                  leaf udp {
                    description 'Configure UDP protocol.'
                                ;
                    type empty ;
                    mandatory true ;
                  }
                  choice src-addr {
                    description 'Configure source address.'
                                ;
                    mandatory true ;
                    case addr-type {
                      description 'Configure source address.'
                                  ;
                      leaf src-address {
                        description 'Configure source address.'
                                    ;
                        type ncd:ipv6-address ;
                        mandatory true ;
                      }
                      container src-wildcard {
                        description 'Configure source wildcard.'
                                    ;
                        choice wildcard-type {
                          description 'Configure source wildcard.'
                                      ;
                          mandatory true ;
                          case wildcard-len {
                            description 'Configure source wildcard prefix length.'
                                        ;
                            leaf src-wildcard-len {
                              description 'Configure source wildcard prefix length.'
                                          ;
                              type uint8 {
                                range 0..128 ;
                              }
                              mandatory true ;
                            }
                          }
                          case wildcard-bits {
                            description 'Configure source wildcard bits.'
                                        ;
                            leaf src-wildcard-bits {
                              description 'Configure source wildcard bits.'
                                          ;
                              type ncd:ipv6-address ;
                              mandatory true ;
                            }
                          }
                        }
                      }
                    }
                    case any-type {
                      description 'Any source address.'
                                  ;
                      leaf src-any-addr {
                        description 'Any source address.'
                                    ;
                        type empty ;
                        mandatory true ;
                      }
                    }
                  }
                  container source-port {
                    description 'Specify source port.'+"\n"
                              + 'When the value of operator is invalid, it mean'
                              + 's match all port range,'+"\n"
                              + 'the other value of operator means'+"\n"
                              + 'eq(1)   : match only packets on a given port n'
                              + 'umber'+"\n"
                              + 'ge(2)   : match only packets with a no lower p'
                              + 'ort number'+"\n"
                              + 'le(3)   : match only packets with a no greater'
                              + ' port number'+"\n"
                              + 'range(7): match only packet on a given port ra'
                              + 'nge.'
                                ;
                    presence 'Specify source port'
                             ;
                    choice source-port {
                      description 'Specify source port.'+"\n"
                                + 'When the value of operator is invalid, it me'
                                + 'ans match all port range,'+"\n"
                                + 'the other value of operator means'+"\n"
                                + 'eq(1)   : match only packets on a given port'
                                + ' number'+"\n"
                                + 'ge(2)   : match only packets with a no lower'
                                + ' port number'+"\n"
                                + 'le(3)   : match only packets with a no great'
                                + 'er port number'+"\n"
                                + 'range(7): match only packet on a given port '
                                + 'range.'
                                  ;
                      mandatory true ;
                      case src-port-value {
                        description 'Configure port number.'
                                    ;
                        container src-port-value {
                          description 'Configure port number.'
                                      ;
                          presence 'Configure port number'
                                   ;
                          leaf src-port-operator {
                            description 'Operator type'+"\n"
                                      + 'eq(1)   : match only packets on a given port number'+"\n"
                                      + 'ge(2)   : match only packets with a no lower port number'+"\n"
                                      + 'le(3)   : match only packets with a no greater port number.'
                                        ;
                            type enumeration {
                              enum eq {
                                value 1 ;
                                description 'Equal to.'
                                            ;
                              }
                              enum ge {
                                value 2 ;
                                description 'Great than or equal to.'
                                            ;
                              }
                              enum le {
                                value 3 ;
                                description 'Less than or equal to.'
                                            ;
                              }
                            }
                            mandatory true ;
                          }
                          leaf src-port-value {
                            description 'Port number.'+"\n"
                                      + 'Some has specific means:'+"\n"
                                      + 'bootpc       Bootstrap protocol (BOOTP) client (68)'+"\n"
                                      + 'bootps       Bootstrap protocol (BOOTP) server (67)'+"\n"
                                      + 'domain       Domain name service (DNS, 53)'+"\n"
                                      + 'ntp          Network time protocol (123)'+"\n"
                                      + 'pim-auto-rp  PIM auto-RP (496)'+"\n"
                                      + 'rip          Routing information protocol (router, in.routed, 520)'+"\n"
                                      + 'snmp         Simple network management protocol (161)'+"\n"
                                      + 'snmptrap     SNMP traps (162)'+"\n"
                                      + 'tftp         Trivial file transfer protocol (69).'
                                        ;
                            type uint16 {
                              range 0..65535 ;
                            }
                            mandatory true ;
                          }
                        }
                      }
                      case src-port-range {
                        description 'Configure port range.'
                                    ;
                        container src-port-range {
                          description 'Configure port range.'
                                      ;
                          presence 'Configure port range'
                                   ;
                          leaf src-port-operator {
                            description 'Operator type
range(7): match only packet on a given port range.'
                                        ;
                            type enumeration {
                              enum range {
                                value 7 ;
                                description Range. ;
                              }
                            }
                            mandatory true ;
                          }
                          leaf src-port-range {
                            description 'Port range, support <0-65535>-<0-65535>.'
                                        ;
                            type acl-port-range ;
                            mandatory true ;
                          }
                        }
                      }
                    }
                  }
                  choice dst-addr {
                    description 'Configure destination address.'
                                ;
                    mandatory true ;
                    case addr-type {
                      description 'Configure destination address.'
                                  ;
                      leaf dst-address {
                        description 'Configure destination address.'
                                    ;
                        type ncd:ipv6-address ;
                        mandatory true ;
                      }
                      container dst-wildcard {
                        description 'Configure destination wildcard.'
                                    ;
                        choice wildcard-type {
                          description 'Configure destination wildcard.'
                                      ;
                          mandatory true ;
                          case wildcard-len {
                            description 'Configure destination wildcard prefix length.'
                                        ;
                            leaf dst-wildcard-len {
                              description 'Configure destination wildcard prefix length.'
                                          ;
                              type uint8 {
                                range 0..128 ;
                              }
                              mandatory true ;
                            }
                          }
                          case wildcard-bits {
                            description 'Configure destination wildcard bits.'
                                        ;
                            leaf dst-wildcard-bits {
                              description 'Configure destination wildcard bits.'
                                          ;
                              type ncd:ipv6-address ;
                              mandatory true ;
                            }
                          }
                        }
                      }
                    }
                    case any-type {
                      description 'Any destination address.'
                                  ;
                      leaf dst-any-addr {
                        description 'Any destination address.'
                                    ;
                        type empty ;
                        mandatory true ;
                      }
                    }
                  }
                  container destination-port {
                    description 'Specify destination port.'+"\n"
                              + 'When the value of operator is invalid, it mean'
                              + 's match all port range,'+"\n"
                              + 'the other value of operator means'+"\n"
                              + 'eq(1)   : match only packets on a given port n'
                              + 'umber'+"\n"
                              + 'ge(2)   : match only packets with a no lower p'
                              + 'ort number'+"\n"
                              + 'le(3)   : match only packets with a no greater'
                              + ' port number'+"\n"
                              + 'range(7): match only packet on a given port ra'
                              + 'nge.'
                                ;
                    presence 'Specify destination port'
                             ;
                    choice destination-port {
                      description 'Specify destination port.'+"\n"
                                + 'When the value of operator is invalid, it me'
                                + 'ans match all port range,'+"\n"
                                + 'the other value of operator means'+"\n"
                                + 'eq(1)   : match only packets on a given port'
                                + ' number'+"\n"
                                + 'ge(2)   : match only packets with a no lower'
                                + ' port number'+"\n"
                                + 'le(3)   : match only packets with a no great'
                                + 'er port number'+"\n"
                                + 'range(7): match only packet on a given port '
                                + 'range.'
                                  ;
                      mandatory true ;
                      case dst-port-value {
                        description 'Configure port number.'
                                    ;
                        container dst-port-value {
                          description 'Configure port number.'
                                      ;
                          presence 'Configure port number'
                                   ;
                          leaf dst-port-operator {
                            description 'Operator type'+"\n"
                                      + 'eq(1)   : match only packets on a given port number'+"\n"
                                      + 'ge(2)   : match only packets with a no lower port number'+"\n"
                                      + 'le(3)   : match only packets with a no greater port number.'
                                        ;
                            type enumeration {
                              enum eq {
                                value 1 ;
                                description 'Equal to.'
                                            ;
                              }
                              enum ge {
                                value 2 ;
                                description 'Great than or equal to.'
                                            ;
                              }
                              enum le {
                                value 3 ;
                                description 'Less than or equal to.'
                                            ;
                              }
                            }
                            mandatory true ;
                          }
                          leaf dst-port-value {
                            description 'Port number.'+"\n"
                                      + 'Some has specific means:'+"\n"
                                      + 'bootpc       Bootstrap protocol (BOOTP) client (68)'+"\n"
                                      + 'bootps       Bootstrap protocol (BOOTP) server (67)'+"\n"
                                      + 'domain       Domain name service (DNS, 53)'+"\n"
                                      + 'ntp          Network time protocol (123)'+"\n"
                                      + 'pim-auto-rp  PIM auto-RP (496)'+"\n"
                                      + 'rip          Routing information protocol (router, in.routed, 520)'+"\n"
                                      + 'snmp         Simple network management protocol (161)'+"\n"
                                      + 'snmptrap     SNMP traps (162)'+"\n"
                                      + 'tftp         Trivial file transfer protocol (69).'
                                        ;
                            type uint16 {
                              range 0..65535 ;
                            }
                            mandatory true ;
                          }
                        }
                      }
                      case dst-port-range {
                        description 'Configure port range.'
                                    ;
                        container dst-port-range {
                          description 'Configure port range.'
                                      ;
                          presence 'Configure port range'
                                   ;
                          leaf dst-port-operator {
                            description 'Operator type
range(7): match only packet on a given port range.'
                                        ;
                            type enumeration {
                              enum range {
                                value 7 ;
                                description Range. ;
                              }
                            }
                            mandatory true ;
                          }
                          leaf dst-port-range {
                            description 'Port range, support <0-65535>-<0-65535>.'
                                        ;
                            type acl-port-range ;
                            mandatory true ;
                          }
                        }
                      }
                    }
                  }
                  leaf dscp {
                    description 'DSCP value.'
                                ;
                    type uint8 {
                      range 0..63 ;
                    }
                  }
                }
                leaf vrf {
                  description 'VPN Routing/Forwarding instance name, support 1-'
                            + '32 characters.'
                              ;
                  type acl-vrf-name {
                    length 1..32 {
                      description 'VPN Routing/Forwarding instance name, suppor'
                                + 't 1-32 characters.'
                                  ;
                    }
                  }
                }
                leaf time-range {
                  description 'Specify the existed time-range name.'
                              ;
                  type string {
                    length 1..31 ;
                  }
                  ncd:revise-date 2021-04-02 ;
                }
              }
            }
          }
          ncd:revise-date 2020-03-18 ;
        }
      }
      container port-acl {
        description 'Bind access-list to interface.'
                    ;
        container if-ipv4 {
          if-feature ipv4-feature ;
          description 'Bind IPv4 access-list to interface.'
                      ;
          list egress {
            description 'Bind IPv4 access-list to interface in egress.'
                        ;
            key if-name ;
            leaf if-name {
              description 'Interface name.'
                          ;
              type ncd:ifname ;
            }
            leaf acl-name {
              description 'Name of access-list.'
                          ;
              type acl-name-type ;
              mandatory true ;
            }
            leaf port-acl-description {
              description 'Description of a port acl, support 1-79 characters.'
                          ;
              type ncd:string-with-blank {
                length 1..79 {
                  description 'Description of a port acl, support 1-79 characte'
                            + 'rs.'
                              ;
                }
              }
              ncd:revise-date 2020-06-18 ;
            }
            leaf none-rule-default-action {
              if-feature none-rule-default-action ;
              description 'Configure default action in empty ACL.'
                          ;
              type enumeration {
                enum permit-any {
                  value 1 ;
                  description 'Configure default action is permit any in empty '
                            + 'ACL.'
                              ;
                }
                enum deny-any {
                  value 2 ;
                  description 'Configure default action is deny any in empty AC'
                            + 'L.'
                              ;
                }
              }
              ncd:revise-date 2021-11-23 ;
            }
          }
          list ingress {
            description 'Bind IPv4 access-list to interface in ingress.'
                        ;
            key if-name ;
            leaf if-name {
              description 'Interface name.'
                          ;
              type ncd:ifname ;
            }
            leaf acl-name {
              description 'Name of access-list.'
                          ;
              type acl-name-type ;
              mandatory true ;
            }
            leaf port-acl-description {
              description 'Description of a port acl, support 1-79 characters.'
                          ;
              type ncd:string-with-blank {
                length 1..79 {
                  description 'Description of a port acl, support 1-79 characte'
                            + 'rs.'
                              ;
                }
              }
              ncd:revise-date 2020-06-18 ;
            }
            leaf none-rule-default-action {
              if-feature none-rule-default-action ;
              description 'Configure default action in empty ACL.'
                          ;
              type enumeration {
                enum permit-any {
                  value 1 ;
                  description 'Configure default action is permit any in empty '
                            + 'ACL.'
                              ;
                }
                enum deny-any {
                  value 2 ;
                  description 'Configure default action is deny any in empty AC'
                            + 'L.'
                              ;
                }
              }
              ncd:revise-date 2021-11-23 ;
            }
          }
        }
        container vlan-ipv4 {
          if-feature ipv4-feature ;
          if-feature switchvlan-acl ;
          description 'Bind IPv4 access-list to VLAN interface.'
                      ;
          list egress {
            description 'Bind IPv4 access-list to VLAN interface in egress.'
                        ;
            key vlan-id ;
            leaf vlan-id {
              description 'VLAN ID.'
                          ;
              type uint16 {
                range 1..4094 ;
              }
            }
            leaf acl-name {
              description 'Name of access-list.'
                          ;
              type acl-name-type ;
              mandatory true ;
            }
            leaf port-acl-description {
              description 'Description of a port acl, support 1-79 characters.'
                          ;
              type ncd:string-with-blank {
                length 1..79 {
                  description 'Description of a port acl, support 1-79 characte'
                            + 'rs.'
                              ;
                }
              }
              ncd:revise-date 2020-06-29 ;
            }
          }
          list ingress {
            description 'Bind IPv4 access-list to VLAN interface in ingress.'
                        ;
            key vlan-id ;
            leaf vlan-id {
              description 'VLAN ID.'
                          ;
              type uint16 {
                range 1..4094 ;
              }
            }
            leaf acl-name {
              description 'Name of access-list.'
                          ;
              type acl-name-type ;
              mandatory true ;
            }
            leaf port-acl-description {
              description 'Description of a port acl, support 1-79 characters.'
                          ;
              type ncd:string-with-blank {
                length 1..79 {
                  description 'Description of a port acl, support 1-79 characte'
                            + 'rs.'
                              ;
                }
              }
              ncd:revise-date 2020-06-29 ;
            }
          }
        }
        container device-ipv4s {
          if-feature ipv4-feature ;
          if-feature statics-per-device ;
          description 'Bind IPv4 access-list to device.'
                      ;
          list device-ipv4 {
            description 'Bind IPv4 access-list to device.'
                        ;
            key direction ;
            leaf direction {
              description 'Specify the direction of device, as follows,'+"\n"
                        + '     egress  Direction egress'+"\n"
                        + '     ingress Direction ingress.'
                          ;
              type acl-if-direction ;
            }
            leaf acl-name {
              description 'Name of ACL.'
                          ;
              type acl-name-type ;
              mandatory true ;
            }
          }
          ncd:revise-date 2015-12-15 ;
        }
        container slot-ipv4s {
          if-feature ipv4-feature ;
          description 'Bind IPv4 access-list to specified slot.'
                      ;
          list slot-ipv4 {
            description 'Bind IPv4 access-list to specified slot.'
                        ;
            key 'slot-id direction'
                ;
            leaf slot-id {
              description 'Specify the slot id.'
                          ;
              type uint8 {
                range 0..255 ;
              }
            }
            leaf direction {
              description 'Specify the direction of slot, as follows,'+"\n"
                        + '  egress     Direction egress'+"\n"
                        + '  ingress    Direction ingress.'
                          ;
              type acl-if-direction ;
            }
            leaf acl-name {
              description 'Name of an IPv4 access list.'
                          ;
              type acl-name-type {
                length 1..31 {
                  description 'Name of an IPv4 access list.'
                              ;
                }
              }
              mandatory true ;
            }
          }
          ncd:revise-date 2020-01-20 ;
        }
        container if-ipv4-mixed {
          if-feature ipv4-mixed-feature ;
          description 'Bind IPv4 mixed access-list to interface.'
                      ;
          list egress {
            description 'Bind IPv4 mixed access-list to interface in egress.'
                        ;
            key if-name ;
            leaf if-name {
              description 'Interface name.'
                          ;
              type ncd:ifname ;
            }
            leaf acl-name {
              description 'Name of access-list.'
                          ;
              type acl-name-type ;
              mandatory true ;
            }
            leaf port-acl-description {
              description 'Description of a port acl, support 1-79 characters.'
                          ;
              type ncd:string-with-blank {
                length 1..79 {
                  description 'Description of a port acl, support 1-79 characte'
                            + 'rs.'
                              ;
                }
              }
              ncd:revise-date 2020-06-18 ;
            }
          }
          list ingress {
            description 'Bind IPv4 mixed access-list to interface in ingress.'
                        ;
            key if-name ;
            leaf if-name {
              description 'Interface name.'
                          ;
              type ncd:ifname ;
            }
            leaf acl-name {
              description 'Name of access-list.'
                          ;
              type acl-name-type ;
              mandatory true ;
            }
            leaf port-acl-description {
              description 'Description of a port acl, support 1-79 characters.'
                          ;
              type ncd:string-with-blank {
                length 1..79 {
                  description 'Description of a port acl, support 1-79 characte'
                            + 'rs.'
                              ;
                }
              }
              ncd:revise-date 2020-06-18 ;
            }
          }
        }
        container vlan-ipv4-mixed {
          if-feature ipv4-mixed-feature ;
          if-feature switchvlan-acl ;
          description 'Bind IPv4 mixed access-list to VLAN interface.'
                      ;
          list egress {
            description 'Bind IPv4 mixed access-list to VLAN interface in egres'
                      + 's.'
                        ;
            key vlan-id ;
            leaf vlan-id {
              description 'VLAN ID.'
                          ;
              type uint16 {
                range 1..4094 ;
              }
            }
            leaf acl-name {
              description 'Name of access-list.'
                          ;
              type acl-name-type ;
              mandatory true ;
            }
            leaf port-acl-description {
              description 'Description of a port acl, support 1-79 characters.'
                          ;
              type ncd:string-with-blank {
                length 1..79 {
                  description 'Description of a port acl, support 1-79 characte'
                            + 'rs.'
                              ;
                }
              }
              ncd:revise-date 2020-06-29 ;
            }
          }
          list ingress {
            description 'Bind IPv4 access-list to VLAN interface in ingress.'
                        ;
            key vlan-id ;
            leaf vlan-id {
              description 'VLAN ID.'
                          ;
              type uint16 {
                range 1..4094 ;
              }
            }
            leaf acl-name {
              description 'Name of access-list.'
                          ;
              type acl-name-type ;
              mandatory true ;
            }
            leaf port-acl-description {
              description 'Description of a port acl, support 1-79 characters.'
                          ;
              type ncd:string-with-blank {
                length 1..79 {
                  description 'Description of a port acl, support 1-79 characte'
                            + 'rs.'
                              ;
                }
              }
              ncd:revise-date 2020-06-29 ;
            }
          }
        }
        container device-ipv4-mixeds {
          if-feature ipv4-mixed-feature ;
          if-feature statics-per-device ;
          description 'Bind IPv4 mixed access-list to device.'
                      ;
          list device-ipv4-mixed {
            description 'Bind IPv4 mixed access-list to device.'
                        ;
            key direction ;
            leaf direction {
              description 'Specify the direction of device, as follows,'+"\n"
                        + '     egress  Direction egress'+"\n"
                        + '     ingress Direction ingress.'
                          ;
              type acl-if-direction ;
            }
            leaf acl-name {
              description 'Name of ACL.'
                          ;
              type acl-name-type ;
              mandatory true ;
            }
          }
          ncd:revise-date 2015-12-15 ;
        }
        container if-ipv6 {
          if-feature ipv6-feature ;
          description 'Bind IPv6 access-list to interface.'
                      ;
          list egress {
            description 'Bind IPv6 access-list to interface in egress.'
                        ;
            key if-name ;
            leaf if-name {
              description 'Interface name.'
                          ;
              type ncd:ifname ;
            }
            leaf acl-name {
              description 'Name of access-list.'
                          ;
              type acl-name-type ;
              mandatory true ;
            }
            leaf port-acl-description {
              description 'Description of a port acl, support 1-79 characters.'
                          ;
              type ncd:string-with-blank {
                length 1..79 {
                  description 'Description of a port acl, support 1-79 characte'
                            + 'rs.'
                              ;
                }
              }
              ncd:revise-date 2020-06-18 ;
            }
            leaf none-rule-default-action {
              if-feature none-rule-default-action ;
              description 'Configure default action in empty ACL.'
                          ;
              type enumeration {
                enum permit-any {
                  value 1 ;
                  description 'Configure default action is permit any in empty '
                            + 'ACL.'
                              ;
                }
                enum deny-any {
                  value 2 ;
                  description 'Configure default action is deny any in empty AC'
                            + 'L.'
                              ;
                }
              }
              ncd:revise-date 2021-11-23 ;
            }
          }
          list ingress {
            description 'Bind IPv6 access-list to interface in ingress.'
                        ;
            key if-name ;
            leaf if-name {
              description 'Interface name.'
                          ;
              type ncd:ifname ;
            }
            leaf acl-name {
              description 'Name of access-list.'
                          ;
              type acl-name-type ;
              mandatory true ;
            }
            leaf port-acl-description {
              description 'Description of a port acl, support 1-79 characters.'
                          ;
              type ncd:string-with-blank {
                length 1..79 {
                  description 'Description of a port acl, support 1-79 characte'
                            + 'rs.'
                              ;
                }
              }
              ncd:revise-date 2020-06-18 ;
            }
            leaf none-rule-default-action {
              if-feature none-rule-default-action ;
              description 'Configure default action in empty ACL.'
                          ;
              type enumeration {
                enum permit-any {
                  value 1 ;
                  description 'Configure default action is permit any in empty '
                            + 'ACL.'
                              ;
                }
                enum deny-any {
                  value 2 ;
                  description 'Configure default action is deny any in empty AC'
                            + 'L.'
                              ;
                }
              }
              ncd:revise-date 2021-11-23 ;
            }
          }
        }
        container vlan-ipv6 {
          if-feature ipv6-feature ;
          if-feature switchvlan-acl ;
          description 'Bind IPv6 access-list to VLAN interface.'
                      ;
          list egress {
            description 'Bind IPv6 access-list to VLAN interface in egress.'
                        ;
            key vlan-id ;
            leaf vlan-id {
              description 'VLAN ID.'
                          ;
              type uint16 {
                range 1..4094 ;
              }
            }
            leaf acl-name {
              description 'Name of access-list.'
                          ;
              type acl-name-type ;
              mandatory true ;
            }
            leaf port-acl-description {
              description 'Description of a port acl, support 1-79 characters.'
                          ;
              type ncd:string-with-blank {
                length 1..79 {
                  description 'Description of a port acl, support 1-79 characte'
                            + 'rs.'
                              ;
                }
              }
              ncd:revise-date 2020-06-29 ;
            }
          }
          list ingress {
            description 'Bind IPv6 access-list to VLAN interface in ingress.'
                        ;
            key vlan-id ;
            leaf vlan-id {
              description 'VLAN ID.'
                          ;
              type uint16 {
                range 1..4094 ;
              }
            }
            leaf acl-name {
              description 'Name of access-list.'
                          ;
              type acl-name-type ;
              mandatory true ;
            }
            leaf port-acl-description {
              description 'Description of a port acl, support 1-79 characters.'
                          ;
              type ncd:string-with-blank {
                length 1..79 {
                  description 'Description of a port acl, support 1-79 characte'
                            + 'rs.'
                              ;
                }
              }
              ncd:revise-date 2020-06-29 ;
            }
          }
        }
        container device-ipv6s {
          if-feature ipv6-feature ;
          if-feature statics-per-device ;
          description 'Bind IPv6 access-list to device.'
                      ;
          list device-ipv6 {
            description 'Bind IPv6 access-list to device.'
                        ;
            key direction ;
            leaf direction {
              description 'Specify the direction of device, as follows,'+"\n"
                        + '     egress  Direction egress'+"\n"
                        + '     ingress Direction ingress.'
                          ;
              type acl-if-direction ;
            }
            leaf acl-name {
              description 'Name of ACL.'
                          ;
              type acl-name-type ;
              mandatory true ;
            }
          }
          ncd:revise-date 2015-12-15 ;
        }
        container slot-ipv6s {
          if-feature ipv6-feature ;
          description 'Bind IPv6 access-list to specified slot.'
                      ;
          list slot-ipv6 {
            description 'Bind IPv6 access-list to specified slot.'
                        ;
            key 'slot-id direction'
                ;
            leaf slot-id {
              description 'Specify the slot id.'
                          ;
              type uint8 {
                range 0..255 ;
              }
            }
            leaf direction {
              description 'Specify the direction of slot, as follows,'+"\n"
                        + '  egress     Direction egress'+"\n"
                        + '  ingress    Direction ingress.'
                          ;
              type acl-if-direction ;
            }
            leaf acl-name {
              description 'Name of an IPv6 access list.'
                          ;
              type acl-name-type {
                length 1..31 {
                  description 'Name of an IPv6 access list.'
                              ;
                }
              }
              mandatory true ;
            }
          }
          ncd:revise-date 2020-01-20 ;
        }
        container if-ipv6-mixed {
          if-feature ipv6-mixed-feature ;
          description 'Bind IPv6 mixed access-list to interface.'
                      ;
          list egress {
            description 'Bind IPv6 mixed access-list to interface in egress.'
                        ;
            key if-name ;
            leaf if-name {
              description 'Interface name.'
                          ;
              type ncd:ifname ;
            }
            leaf acl-name {
              description 'Name of access-list.'
                          ;
              type acl-name-type ;
              mandatory true ;
            }
            leaf port-acl-description {
              description 'Description of a port acl, support 1-79 characters.'
                          ;
              type ncd:string-with-blank {
                length 1..79 {
                  description 'Description of a port acl, support 1-79 characte'
                            + 'rs.'
                              ;
                }
              }
              ncd:revise-date 2020-06-29 ;
            }
          }
          list ingress {
            description 'Bind IPv6 mixed access-list to interface in ingress.'
                        ;
            key if-name ;
            leaf if-name {
              description 'Interface name.'
                          ;
              type ncd:ifname ;
            }
            leaf acl-name {
              description 'Name of access-list.'
                          ;
              type acl-name-type ;
              mandatory true ;
            }
            leaf port-acl-description {
              description 'Description of a port acl, support 1-79 characters.'
                          ;
              type ncd:string-with-blank {
                length 1..79 {
                  description 'Description of a port acl, support 1-79 characte'
                            + 'rs.'
                              ;
                }
              }
              ncd:revise-date 2020-06-29 ;
            }
          }
        }
        container vlan-ipv6-mixed {
          if-feature ipv6-mixed-feature ;
          if-feature switchvlan-acl ;
          description 'Bind IPv6 mixed access-list to VLAN interface.'
                      ;
          list egress {
            description 'Bind IPv6 mixed access-list to VLAN interface in egres'
                      + 's.'
                        ;
            key vlan-id ;
            leaf vlan-id {
              description 'VLAN ID.'
                          ;
              type uint16 {
                range 1..4094 ;
              }
            }
            leaf acl-name {
              description 'Name of access-list.'
                          ;
              type acl-name-type ;
              mandatory true ;
            }
            leaf port-acl-description {
              description 'Description of a port acl, support 1-79 characters.'
                          ;
              type ncd:string-with-blank {
                length 1..79 {
                  description 'Description of a port acl, support 1-79 characte'
                            + 'rs.'
                              ;
                }
              }
              ncd:revise-date 2020-06-29 ;
            }
          }
          list ingress {
            description 'Bind IPv6 access-list to VLAN interface in ingress.'
                        ;
            key vlan-id ;
            leaf vlan-id {
              description 'VLAN ID.'
                          ;
              type uint16 {
                range 1..4094 ;
              }
            }
            leaf acl-name {
              description 'Name of access-list.'
                          ;
              type acl-name-type ;
              mandatory true ;
            }
            leaf port-acl-description {
              description 'Description of a port acl, support 1-79 characters.'
                          ;
              type ncd:string-with-blank {
                length 1..79 {
                  description 'Description of a port acl, support 1-79 characte'
                            + 'rs.'
                              ;
                }
              }
              ncd:revise-date 2020-06-29 ;
            }
          }
        }
        container device-ipv6-mixeds {
          if-feature ipv6-mixed-feature ;
          if-feature statics-per-device ;
          description 'Bind IPv6 mixed access-list to device.'
                      ;
          list device-ipv6-mixed {
            description 'Bind IPv6 mixed access-list to device.'
                        ;
            key direction ;
            leaf direction {
              description 'Specify the direction of device, as follows,'+"\n"
                        + '     egress  Direction egress'+"\n"
                        + '     ingress Direction ingress.'
                          ;
              type acl-if-direction ;
            }
            leaf acl-name {
              description 'Name of ACL.'
                          ;
              type acl-name-type ;
              mandatory true ;
            }
          }
          ncd:revise-date 2015-12-15 ;
        }
        container if-link {
          if-feature link-feature ;
          description 'Bind Link access-list to interface.'
                      ;
          list egress {
            description 'Bind Link access-list to interface in egress.'
                        ;
            key if-name ;
            leaf if-name {
              description 'Interface name.'
                          ;
              type ncd:ifname ;
            }
            leaf acl-name {
              description 'Name of access-list.'
                          ;
              type acl-name-type ;
              mandatory true ;
            }
            leaf none-rule-default-action {
              if-feature none-rule-default-action ;
              description 'Configure default action in empty ACL.'
                          ;
              type enumeration {
                enum permit-any {
                  value 1 ;
                  description 'Configure default action is permit any in empty '
                            + 'ACL.'
                              ;
                }
                enum deny-any {
                  value 2 ;
                  description 'Configure default action is deny any in empty AC'
                            + 'L.'
                              ;
                }
              }
              ncd:revise-date 2021-11-23 ;
            }
          }
          list ingress {
            description 'Bind Link access-list to interface in ingress.'
                        ;
            key if-name ;
            leaf if-name {
              description 'Interface name.'
                          ;
              type ncd:ifname ;
            }
            leaf acl-name {
              description 'Name of access-list.'
                          ;
              type acl-name-type ;
              mandatory true ;
            }
            leaf none-rule-default-action {
              if-feature none-rule-default-action ;
              description 'Configure default action in empty ACL.'
                          ;
              type enumeration {
                enum permit-any {
                  value 1 ;
                  description 'Configure default action is permit any in empty '
                            + 'ACL.'
                              ;
                }
                enum deny-any {
                  value 2 ;
                  description 'Configure default action is deny any in empty AC'
                            + 'L.'
                              ;
                }
              }
              ncd:revise-date 2021-11-23 ;
            }
          }
        }
        container vlan-link {
          if-feature link-feature ;
          if-feature switchvlan-acl ;
          description 'Bind Link access-list to VLAN interface.'
                      ;
          list egress {
            description 'Bind Link access-list to VLAN interface in egress.'
                        ;
            key vlan-id ;
            leaf vlan-id {
              description 'VLAN ID.'
                          ;
              type uint16 {
                range 1..4094 ;
              }
            }
            leaf acl-name {
              description 'Name of access-list.'
                          ;
              type acl-name-type ;
              mandatory true ;
            }
          }
          list ingress {
            description 'Bind Link access-list to VLAN interface in ingress.'
                        ;
            key vlan-id ;
            leaf vlan-id {
              description 'VLAN ID.'
                          ;
              type uint16 {
                range 1..4094 ;
              }
            }
            leaf acl-name {
              description 'Name of access-list.'
                          ;
              type acl-name-type ;
              mandatory true ;
            }
          }
        }
        container device-links {
          if-feature link-feature ;
          if-feature statics-per-device ;
          description 'Bind link access-list to device.'
                      ;
          list device-link {
            description 'Bind link access-list to device.'
                        ;
            key direction ;
            leaf direction {
              description 'Specify the direction of device, as follows,'+"\n"
                        + '     egress  Direction egress'+"\n"
                        + '     ingress Direction ingress.'
                          ;
              type acl-if-direction ;
            }
            leaf acl-name {
              description 'Name of ACL.'
                          ;
              type acl-name-type ;
              mandatory true ;
            }
          }
          ncd:revise-date 2015-12-15 ;
        }
        container device-user-defineds {
          if-feature statics-per-device ;
          if-feature user-defined-feature ;
          description 'Bind user-defined access-list to device.'
                      ;
          list device-user-defined {
            description 'Bind user-defined access-list to device.'
                        ;
            key direction ;
            leaf direction {
              description 'Specify the direction of device, as follows,'+"\n"
                        + '     egress  Direction egress'+"\n"
                        + '     ingress Direction ingress.'
                          ;
              type acl-if-direction ;
            }
            leaf acl-name {
              description 'Name of ACL.'
                          ;
              type acl-name-type ;
              mandatory true ;
            }
          }
          ncd:revise-date 2015-12-15 ;
        }
        container if-ipv4-vxlan {
          if-feature ipv4-vxlan-feature ;
          description 'Bind IPv4 VXLAN access-list to interface.'
                      ;
          container egresses {
            description 'Bind IPv4 VXLAN access-list to interface in egress.'
                        ;
            list egress {
              description 'Bind IPv4 VXLAN access-list to interface in egress.'
                          ;
              key if-name ;
              leaf if-name {
                description 'Interface name.'
                            ;
                type ncd:ifname ;
              }
              leaf acl-name {
                description 'Name of access-list.'
                            ;
                type acl-name-type ;
                mandatory true ;
              }
            }
            ncd:revise-date 2016-03-04 ;
          }
          container ingresses {
            description 'Bind IPv4 VXLAN access-list to interface in ingress.'
                        ;
            list ingress {
              description 'Bind IPv4 VXLAN access-list to interface in ingress.'
                          ;
              key if-name ;
              leaf if-name {
                description 'Interface name.'
                            ;
                type ncd:ifname ;
              }
              leaf acl-name {
                description 'Name of access-list.'
                            ;
                type acl-name-type ;
                mandatory true ;
              }
            }
            ncd:revise-date 2016-03-04 ;
          }
          ncd:revise-date 2016-03-04 ;
        }
        container vlan-ipv4-vxlan {
          if-feature switchvlan-acl ;
          if-feature ipv4-vxlan-feature ;
          description 'Bind IPv4 VXLAN access-list to switchvlan interface.'
                      ;
          container egresses {
            description 'Bind IPv4 VXLAN access-list to switchvlan interface in'
                      + ' egress.'
                        ;
            list egress {
              description 'Bind IPv4 VXLAN access-list to switchvlan interface '
                        + 'in egress.'
                          ;
              key vlan-id ;
              leaf vlan-id {
                description 'VLAN ID.'
                            ;
                type uint16 {
                  range 1..4094 ;
                }
              }
              leaf acl-name {
                description 'Name of access-list.'
                            ;
                type acl-name-type ;
                mandatory true ;
              }
            }
            ncd:revise-date 2016-03-04 ;
          }
          container ingresses {
            description 'Bind IPv4 VXLAN access-list to switchvlan interface in'
                      + ' ingress.'
                        ;
            list ingress {
              description 'Bind IPv4 VXLAN access-list to switchvlan interface '
                        + 'in ingress.'
                          ;
              key vlan-id ;
              leaf vlan-id {
                description 'VLAN ID.'
                            ;
                type uint16 {
                  range 1..4094 ;
                }
              }
              leaf acl-name {
                description 'Name of access-list.'
                            ;
                type acl-name-type ;
                mandatory true ;
              }
            }
            ncd:revise-date 2016-03-04 ;
          }
          ncd:revise-date 2016-03-04 ;
        }
        container device-ipv4-vxlans {
          if-feature statics-per-device ;
          if-feature ipv4-vxlan-feature ;
          description 'Bind IPv4 VXLAN access-list to device.'
                      ;
          list device-ipv4-vxlan {
            description 'Bind IPv4 access-list to device.'
                        ;
            key direction ;
            leaf direction {
              description 'Specify the direction of device, as follows,'+"\n"
                        + '  egress      Direction egress'+"\n"
                        + '  ingress     Direction ingress.'
                          ;
              type acl-if-direction ;
            }
            leaf acl-name {
              description 'Name of ACL.'
                          ;
              type acl-name-type ;
              mandatory true ;
            }
          }
          ncd:revise-date 2016-03-04 ;
        }
        container if-udf-template {
          if-feature udf-template-type ;
          description 'Bind user defined template access-list to interface.'
                      ;
          container egresses {
            description 'Bind user defined template access-list to interface in'
                      + ' egress.'
                        ;
            list egress {
              description 'Bind user defined template access-list to interface '
                        + 'in egress.'
                          ;
              key if-name ;
              leaf if-name {
                description 'Interface name.'
                            ;
                type ncd:ifname ;
              }
              leaf acl-name {
                description 'Name of access-list.'
                            ;
                type acl-name-type ;
                mandatory true ;
              }
            }
          }
          container ingresses {
            description 'Bind user defined template access-list to interface in'
                      + ' ingress.'
                        ;
            list ingress {
              description 'Bind user defined template access-list to interface '
                        + 'in ingress.'
                          ;
              key if-name ;
              leaf if-name {
                description 'Interface name.'
                            ;
                type ncd:ifname ;
              }
              leaf acl-name {
                description 'Name of access-list.'
                            ;
                type acl-name-type ;
                mandatory true ;
              }
            }
          }
          ncd:revise-date 2017-05-08 ;
        }
        container if-ipv6-vxlan {
          description 'Bind IPv6 VXLAN access-list to interface.'
                      ;
          container egresses {
            description 'Bind IPv6 VXLAN access-list to interface in egress.'
                        ;
            list egress {
              description 'Bind IPv6 VXLAN access-list to interface in egress.'
                          ;
              key if-name ;
              leaf if-name {
                description 'Interface name.'
                            ;
                type ncd:ifname ;
              }
              leaf acl-name {
                description 'Name of access-list.'
                            ;
                type acl-name-type ;
                mandatory true ;
              }
            }
          }
          container ingresses {
            description 'Bind IPv6 VXLAN access-list to interface in ingress.'
                        ;
            list ingress {
              description 'Bind IPv6 VXLAN access-list to interface in ingress.'
                          ;
              key if-name ;
              leaf if-name {
                description 'Interface name.'
                            ;
                type ncd:ifname ;
              }
              leaf acl-name {
                description 'Name of access-list.'
                            ;
                type acl-name-type ;
                mandatory true ;
              }
            }
          }
          ncd:revise-date 2020-03-18 ;
        }
        container vlan-ipv6-vxlan {
          description 'Bind IPv6 VXLAN access-list to switchvlan interface.'
                      ;
          container egresses {
            description 'Bind IPv6 VXLAN access-list to switchvlan interface in'
                      + ' egress.'
                        ;
            list egress {
              description 'Bind IPv6 VXLAN access-list to switchvlan interface '
                        + 'in egress.'
                          ;
              key vlan-id ;
              leaf vlan-id {
                description 'VLAN ID.'
                            ;
                type uint16 {
                  range 1..4094 ;
                }
              }
              leaf acl-name {
                description 'Name of access-list.'
                            ;
                type acl-name-type ;
                mandatory true ;
              }
            }
          }
          container ingresses {
            description 'Bind IPv6 VXLAN access-list to switchvlan interface in'
                      + ' ingress.'
                        ;
            list ingress {
              description 'Bind IPv6 VXLAN access-list to switchvlan interface '
                        + 'in ingress.'
                          ;
              key vlan-id ;
              leaf vlan-id {
                description 'VLAN ID.'
                            ;
                type uint16 {
                  range 1..4094 ;
                }
              }
              leaf acl-name {
                description 'Name of access-list.'
                            ;
                type acl-name-type ;
                mandatory true ;
              }
            }
          }
          ncd:revise-date 2020-03-18 ;
        }
        container device-ipv6-vxlans {
          description 'Bind IPv6 VXLAN access-list to device.'
                      ;
          list device-ipv6-vxlan {
            description 'Bind IPv6 VXLAN access-list to device.'
                        ;
            key direction ;
            leaf direction {
              description 'Specify the direction of device, as follows,'+"\n"
                        + '  egress      Direction egress'+"\n"
                        + '  ingress     Direction ingress.'
                          ;
              type acl-if-direction ;
            }
            leaf acl-name {
              description 'Name of ACL.'
                          ;
              type acl-name-type ;
              mandatory true ;
            }
          }
          ncd:revise-date 2020-03-18 ;
        }
      }
      container vni-acl {
        description 'Bind access-list to VXLAN instances.'
                    ;
        container vni-ipv4-vxlans {
          if-feature ipv4-vxlan-feature ;
          description 'Bind IPv4 VXLAN access-list to VXLAN instances.'
                      ;
          list vni-ipv4-vxlan {
            description 'Bind IPv4 VXLAN access-list to VXLAN instances.'
                        ;
            key 'vxlan-id direction'
                ;
            leaf vxlan-id {
              description 'VXLAN ID.'
                          ;
              type uint32 {
                range 1..16777215 {
                  description 'VXLAN ID.'
                              ;
                }
              }
            }
            leaf direction {
              description 'Specify the direction of VXLAN instance, as follows,'
                        + ''+"\n"
                        + '  egress     Direction egress'+"\n"
                        + '  ingress    Direction ingress.'
                          ;
              type acl-if-direction ;
            }
            leaf acl-name {
              description 'Name of an IPv4 VXLAN access list.'
                          ;
              type acl-name-type {
                length 1..31 {
                  description 'Name of an IPv4 VXLAN access list.'
                              ;
                }
              }
              mandatory true ;
            }
          }
        }
        ncd:revise-date 2016-03-04 ;
      }
      container statistics-switch {
        if-feature acl-statistics ;
        description 'Configure ACL log statistics switch.'
                    ;
        presence 'Configure ACL log statistics switch'
                 ;
        container ipv4-log-switchs {
          if-feature ipv4-feature ;
          description 'Configure IPv4 ACL log statistics switch.'
                      ;
          list ipv4-log-switch {
            description 'Configure IPv4 ACL log statistics switch.'
                        ;
            key 'if-name if-direction'
                ;
            leaf if-name {
              description 'Configure the name of the attaching interface.'
                          ;
              type ncd:ifname ;
            }
            leaf if-direction {
              description 'Specify the direction of interface, as follows,'+"\n"
                        + '     egress  Direction egress'+"\n"
                        + '     ingress Direction ingress.'
                          ;
              type acl-if-direction ;
            }
            choice switch-option {
              description 'Set acl log switch, '+"\n"
                        + '    off  Turn off ACL log switch'+"\n"
                        + '    on   Turn on ACL log switch.'
                          ;
              mandatory true ;
              case off {
                description 'Turn off ACL log switch.'
                            ;
                leaf off {
                  description 'Turn off ACL log switch.'
                              ;
                  type empty ;
                  mandatory true ;
                }
              }
              case on {
                description 'Turn on ACL log switch.'
                            ;
                leaf on {
                  description 'Turn on ACL log switch.'
                              ;
                  type empty ;
                  mandatory true ;
                }
                leaf action {
                  description 'Specify which action of ACL to turn on the log s'
                            + 'witch, as follows,'+"\n"
                            + '     permit  Enable permit ACL log'+"\n"
                            + '     deny    Enable deny ACL log'+"\n"
                            + '     all     Enable all ACL log.'
                              ;
                  type enumeration {
                    enum permit {
                      value 1 ;
                      description 'Enable permit ACL log.'
                                  ;
                    }
                    enum deny {
                      value 2 ;
                      description 'Enable deny ACL log.'
                                  ;
                    }
                    enum all {
                      value 3 ;
                      description 'Enable all ACL log.'
                                  ;
                    }
                  }
                  mandatory true ;
                }
              }
            }
          }
        }
        container ipv6-log-switchs {
          if-feature ipv6-feature ;
          description 'Configure IPv6 ACL log statistics switch.'
                      ;
          list ipv6-log-switch {
            description 'Configure IPv6 ACL log statistics switch.'
                        ;
            key 'if-name if-direction'
                ;
            leaf if-name {
              description 'Configure the name of the attaching interface.'
                          ;
              type ncd:ifname ;
            }
            leaf if-direction {
              description 'Specify the direction of interface, as follows,'+"\n"
                        + '     egress  Direction egress'+"\n"
                        + '     ingress Direction ingress.'
                          ;
              type acl-if-direction ;
            }
            choice switch-option {
              description 'Set acl log switch, '+"\n"
                        + '    off  Turn off ACL log switch'+"\n"
                        + '    on   Turn on ACL log switch.'
                          ;
              mandatory true ;
              case off {
                description 'Turn off ACL log switch.'
                            ;
                leaf off {
                  description 'Turn off ACL log switch.'
                              ;
                  type empty ;
                  mandatory true ;
                }
              }
              case on {
                description 'Turn on ACL log switch.'
                            ;
                leaf on {
                  description 'Turn on ACL log switch.'
                              ;
                  type empty ;
                  mandatory true ;
                }
                leaf action {
                  description 'Specify which action of ACL to turn on the log s'
                            + 'witch, as follows,'+"\n"
                            + '     permit  Enable permit ACL log'+"\n"
                            + '     deny    Enable deny ACL log'+"\n"
                            + '     all     Enable all ACL log.'
                              ;
                  type enumeration {
                    enum permit {
                      value 1 ;
                      description 'Enable permit ACL log.'
                                  ;
                    }
                    enum deny {
                      value 2 ;
                      description 'Enable deny ACL log.'
                                  ;
                    }
                    enum all {
                      value 3 ;
                      description 'Enable all ACL log.'
                                  ;
                    }
                  }
                  mandatory true ;
                }
              }
            }
          }
        }
        container link-log-switchs {
          if-feature link-log-config ;
          description 'Configure link ACL log statistics switch.'
                      ;
          list link-log-switch {
            description 'Configure link ACL log statistics switch.'
                        ;
            key 'if-name if-direction'
                ;
            leaf if-name {
              description 'Configure the name of the attaching interface.'
                          ;
              type ncd:ifname ;
            }
            leaf if-direction {
              description 'Specify the direction of interface, as follows,'+"\n"
                        + '     egress  Direction egress'+"\n"
                        + '     ingress Direction ingress.'
                          ;
              type acl-if-direction ;
            }
            choice switch-option {
              description 'Set acl log switch, '+"\n"
                        + '    off  Turn off ACL log switch'+"\n"
                        + '    on   Turn on ACL log switch.'
                          ;
              mandatory true ;
              case off {
                description 'Turn off ACL log switch.'
                            ;
                leaf off {
                  description 'Turn off ACL log switch.'
                              ;
                  type empty ;
                  mandatory true ;
                }
              }
              case on {
                description 'Turn on ACL log switch.'
                            ;
                leaf on {
                  description 'Turn on ACL log switch.'
                              ;
                  type empty ;
                  mandatory true ;
                }
                leaf action {
                  description 'Specify which action of ACL to turn on the log s'
                            + 'witch, as follows,'+"\n"
                            + '     permit  Enable permit ACL log'+"\n"
                            + '     deny    Enable deny ACL log'+"\n"
                            + '     all     Enable all ACL log.'
                              ;
                  type enumeration {
                    enum permit {
                      value 1 ;
                      description 'Enable permit ACL log.'
                                  ;
                    }
                    enum deny {
                      value 2 ;
                      description 'Enable deny ACL log.'
                                  ;
                    }
                    enum all {
                      value 3 ;
                      description 'Enable all ACL log.'
                                  ;
                    }
                  }
                  mandatory true ;
                }
              }
            }
          }
          ncd:revise-date 2019-10-08 ;
        }
        container ipv4-mixed-log-switchs {
          if-feature ipv4-mixed-log-config ;
          description 'Configure IPv4 mixed ACL log statistics switch.'
                      ;
          list ipv4-mixed-log-switch {
            description 'Configure IPv4 mixed ACL log statistics switch.'
                        ;
            key 'if-name if-direction'
                ;
            leaf if-name {
              description 'Configure the name of the attaching interface.'
                          ;
              type ncd:ifname ;
            }
            leaf if-direction {
              description 'Specify the direction of interface, as follows,'+"\n"
                        + '     egress  Direction egress'+"\n"
                        + '     ingress Direction ingress.'
                          ;
              type acl-if-direction ;
            }
            choice switch-option {
              description 'Set acl log switch, '+"\n"
                        + '    off  Turn off ACL log switch'+"\n"
                        + '    on   Turn on ACL log switch.'
                          ;
              mandatory true ;
              case off {
                description 'Turn off ACL log switch.'
                            ;
                leaf off {
                  description 'Turn off ACL log switch.'
                              ;
                  type empty ;
                  mandatory true ;
                }
              }
              case on {
                description 'Turn on ACL log switch.'
                            ;
                leaf on {
                  description 'Turn on ACL log switch.'
                              ;
                  type empty ;
                  mandatory true ;
                }
                leaf action {
                  description 'Specify which action of ACL to turn on the log s'
                            + 'witch, as follows,'+"\n"
                            + '     permit  Enable permit ACL log'+"\n"
                            + '     deny    Enable deny ACL log'+"\n"
                            + '     all     Enable all ACL log.'
                              ;
                  type enumeration {
                    enum permit {
                      value 1 ;
                      description 'Enable permit ACL log.'
                                  ;
                    }
                    enum deny {
                      value 2 ;
                      description 'Enable deny ACL log.'
                                  ;
                    }
                    enum all {
                      value 3 ;
                      description 'Enable all ACL log.'
                                  ;
                    }
                  }
                  mandatory true ;
                }
              }
            }
          }
          ncd:revise-date 2019-10-08 ;
        }
        container ipv6-mixed-log-switchs {
          if-feature ipv6-mixed-log-config ;
          description 'Configure IPv6 mixed ACL log statistics switch.'
                      ;
          list ipv6-mixed-log-switch {
            description 'Configure IPv6 mixed ACL log statistics switch.'
                        ;
            key 'if-name if-direction'
                ;
            leaf if-name {
              description 'Configure the name of the attaching interface.'
                          ;
              type ncd:ifname ;
            }
            leaf if-direction {
              description 'Specify the direction of interface, as follows,'+"\n"
                        + '     egress  Direction egress'+"\n"
                        + '     ingress Direction ingress.'
                          ;
              type acl-if-direction ;
            }
            choice switch-option {
              description 'Set acl log switch, '+"\n"
                        + '    off  Turn off ACL log switch'+"\n"
                        + '    on   Turn on ACL log switch.'
                          ;
              mandatory true ;
              case off {
                description 'Turn off ACL log switch.'
                            ;
                leaf off {
                  description 'Turn off ACL log switch.'
                              ;
                  type empty ;
                  mandatory true ;
                }
              }
              case on {
                description 'Turn on ACL log switch.'
                            ;
                leaf on {
                  description 'Turn on ACL log switch.'
                              ;
                  type empty ;
                  mandatory true ;
                }
                leaf action {
                  description 'Specify which action of ACL to turn on the log s'
                            + 'witch, as follows,'+"\n"
                            + '     permit  Enable permit ACL log'+"\n"
                            + '     deny    Enable deny ACL log'+"\n"
                            + '     all     Enable all ACL log.'
                              ;
                  type enumeration {
                    enum permit {
                      value 1 ;
                      description 'Enable permit ACL log.'
                                  ;
                    }
                    enum deny {
                      value 2 ;
                      description 'Enable deny ACL log.'
                                  ;
                    }
                    enum all {
                      value 3 ;
                      description 'Enable all ACL log.'
                                  ;
                    }
                  }
                  mandatory true ;
                }
              }
            }
          }
          ncd:revise-date 2021-06-03 ;
        }
        container ipv4-log-switchs-by-acl {
          description 'Configure IPv4 ACL log statistics switch.'
                      ;
          list ipv4-log-switch-by-acl {
            description 'Configure IPv4 ACL log statistics switch.'
                        ;
            key 'acl-name if-direction'
                ;
            leaf acl-name {
              description 'Configure the name of the attaching ACL.'
                          ;
              type acl-name-type ;
            }
            leaf if-direction {
              description 'Specify the direction, as follows,'+"\n"
                        + '     egress  Direction egress'+"\n"
                        + '     ingress Direction ingress.'
                          ;
              type acl-if-direction ;
            }
            leaf switch-action {
              description 'Specify which action of ACL to turn on the log switc'
                        + 'h, as follows,'+"\n"
                        + '     permit  Enable permit ACL log'+"\n"
                        + '     deny    Enable deny ACL log'+"\n"
                        + '     all     Enable all ACL log.'
                          ;
              type enumeration {
                enum permit {
                  value 1 ;
                  description 'Enable permit ACL log.'
                              ;
                }
                enum deny {
                  value 2 ;
                  description 'Enable deny ACL log.'
                              ;
                }
                enum all {
                  value 3 ;
                  description 'Enable all ACL log.'
                              ;
                }
              }
              mandatory true ;
            }
          }
          ncd:revise-date 2021-10-20 ;
        }
        container ipv6-log-switchs-by-acl {
          description 'Configure IPv6 ACL log statistics switch.'
                      ;
          list ipv6-log-switch-by-acl {
            description 'Configure IPv6 ACL log statistics switch.'
                        ;
            key 'acl-name if-direction'
                ;
            leaf acl-name {
              description 'Configure the name of the attaching ACL.'
                          ;
              type acl-name-type ;
            }
            leaf if-direction {
              description 'Specify the direction, as follows,'+"\n"
                        + '     egress  Direction egress'+"\n"
                        + '     ingress Direction ingress.'
                          ;
              type acl-if-direction ;
            }
            leaf switch-action {
              description 'Specify which action of ACL to turn on the log switc'
                        + 'h, as follows,'+"\n"
                        + '     permit  Enable permit ACL log'+"\n"
                        + '     deny    Enable deny ACL log'+"\n"
                        + '     all     Enable all ACL log.'
                          ;
              type enumeration {
                enum permit {
                  value 1 ;
                  description 'Enable permit ACL log.'
                              ;
                }
                enum deny {
                  value 2 ;
                  description 'Enable deny ACL log.'
                              ;
                }
                enum all {
                  value 3 ;
                  description 'Enable all ACL log.'
                              ;
                }
              }
              mandatory true ;
            }
          }
          ncd:revise-date 2021-10-20 ;
        }
        container link-log-switchs-by-acl {
          description 'Configure link ACL log statistics switch.'
                      ;
          list link-log-switch-by-acl {
            description 'Configure link ACL log statistics switch.'
                        ;
            key 'acl-name if-direction'
                ;
            leaf acl-name {
              description 'Configure the name of the attaching ACL.'
                          ;
              type acl-name-type ;
            }
            leaf if-direction {
              description 'Specify the direction, as follows,'+"\n"
                        + '     egress  Direction egress'+"\n"
                        + '     ingress Direction ingress.'
                          ;
              type acl-if-direction ;
            }
            leaf switch-action {
              description 'Specify which action of ACL to turn on the log switc'
                        + 'h, as follows,'+"\n"
                        + '     permit  Enable permit ACL log'+"\n"
                        + '     deny    Enable deny ACL log'+"\n"
                        + '     all     Enable all ACL log.'
                          ;
              type enumeration {
                enum permit {
                  value 1 ;
                  description 'Enable permit ACL log.'
                              ;
                }
                enum deny {
                  value 2 ;
                  description 'Enable deny ACL log.'
                              ;
                }
                enum all {
                  value 3 ;
                  description 'Enable all ACL log.'
                              ;
                }
              }
              mandatory true ;
            }
          }
          ncd:revise-date 2021-10-20 ;
        }
        container ipv4-mixed-log-switchs-by-acl {
          description 'Configure IPv4 mixed ACL log statistics switch.'
                      ;
          list ipv4-mixed-log-switch-by-acl {
            description 'Configure IPv4 mixed ACL log statistics switch.'
                        ;
            key 'acl-name if-direction'
                ;
            leaf acl-name {
              description 'Configure the name of the attaching ACL.'
                          ;
              type acl-name-type ;
            }
            leaf if-direction {
              description 'Specify the direction, as follows,'+"\n"
                        + '     egress  Direction egress'+"\n"
                        + '     ingress Direction ingress.'
                          ;
              type acl-if-direction ;
            }
            leaf switch-action {
              description 'Specify which action of ACL to turn on the log switc'
                        + 'h, as follows,'+"\n"
                        + '     permit  Enable permit ACL log'+"\n"
                        + '     deny    Enable deny ACL log'+"\n"
                        + '     all     Enable all ACL log.'
                          ;
              type enumeration {
                enum permit {
                  value 1 ;
                  description 'Enable permit ACL log.'
                              ;
                }
                enum deny {
                  value 2 ;
                  description 'Enable deny ACL log.'
                              ;
                }
                enum all {
                  value 3 ;
                  description 'Enable all ACL log.'
                              ;
                }
              }
              mandatory true ;
            }
          }
          ncd:revise-date 2021-10-20 ;
        }
        container ipv6-mixed-log-switchs-by-acl {
          description 'Configure IPv6 mixed ACL log statistics switch.'
                      ;
          list ipv6-mixed-log-switch-by-acl {
            description 'Configure IPv6 mixed ACL log statistics switch.'
                        ;
            key 'acl-name if-direction'
                ;
            leaf acl-name {
              description 'Configure the name of the attaching ACL.'
                          ;
              type acl-name-type ;
            }
            leaf if-direction {
              description 'Specify the direction, as follows,'+"\n"
                        + '     egress  Direction egress'+"\n"
                        + '     ingress Direction ingress.'
                          ;
              type acl-if-direction ;
            }
            leaf switch-action {
              description 'Specify which action of ACL to turn on the log switc'
                        + 'h, as follows,'+"\n"
                        + '     permit  Enable permit ACL log'+"\n"
                        + '     deny    Enable deny ACL log'+"\n"
                        + '     all     Enable all ACL log.'
                          ;
              type enumeration {
                enum permit {
                  value 1 ;
                  description 'Enable permit ACL log.'
                              ;
                }
                enum deny {
                  value 2 ;
                  description 'Enable deny ACL log.'
                              ;
                }
                enum all {
                  value 3 ;
                  description 'Enable all ACL log.'
                              ;
                }
              }
              mandatory true ;
            }
          }
          ncd:revise-date 2021-10-20 ;
        }
        container ipv4-vxlan-log-switches-by-acl {
          description 'Configure IPv4 VXLAN ACL log statistics switch.'
                      ;
          list ipv4-vxlan-log-switch-by-acl {
            description 'Configure IPv4 VXLAN ACL log statistics switch.'
                        ;
            key 'acl-name if-direction'
                ;
            leaf acl-name {
              description 'Configure the name of the attaching ACL.'
                          ;
              type acl-name-type ;
            }
            leaf if-direction {
              description 'Specify the direction, as follows,'+"\n"
                        + '     egress  Direction egress'+"\n"
                        + '     ingress Direction ingress.'
                          ;
              type acl-if-direction ;
            }
            leaf switch-action {
              description 'Specify which action of ACL to turn on the log switc'
                        + 'h, as follows,'+"\n"
                        + '     permit  Enable permit ACL log'+"\n"
                        + '     deny    Enable deny ACL log'+"\n"
                        + '     all     Enable all ACL log.'
                          ;
              type enumeration {
                enum permit {
                  value 1 ;
                  description 'Enable permit ACL log.'
                              ;
                }
                enum deny {
                  value 2 ;
                  description 'Enable deny ACL log.'
                              ;
                }
                enum all {
                  value 3 ;
                  description 'Enable all ACL log.'
                              ;
                }
              }
              mandatory true ;
            }
          }
          ncd:revise-date 2022-01-20 ;
        }
        container ipv6-vxlan-log-switches-by-acl {
          description 'Configure IPv6 VXLAN ACL log statistics switch.'
                      ;
          list ipv6-vxlan-log-switch-by-acl {
            description 'Configure IPv6 VXLAN ACL log statistics switch.'
                        ;
            key 'acl-name if-direction'
                ;
            leaf acl-name {
              description 'Configure the name of the attaching ACL.'
                          ;
              type acl-name-type ;
            }
            leaf if-direction {
              description 'Specify the direction, as follows,'+"\n"
                        + '     egress  Direction egress'+"\n"
                        + '     ingress Direction ingress.'
                          ;
              type acl-if-direction ;
            }
            leaf switch-action {
              description 'Specify which action of ACL to turn on the log switc'
                        + 'h, as follows,'+"\n"
                        + '     permit  Enable permit ACL log'+"\n"
                        + '     deny    Enable deny ACL log'+"\n"
                        + '     all     Enable all ACL log.'
                          ;
              type enumeration {
                enum permit {
                  value 1 ;
                  description 'Enable permit ACL log.'
                              ;
                }
                enum deny {
                  value 2 ;
                  description 'Enable deny ACL log.'
                              ;
                }
                enum all {
                  value 3 ;
                  description 'Enable all ACL log.'
                              ;
                }
              }
              mandatory true ;
            }
          }
          ncd:revise-date 2022-01-20 ;
        }
        container user-defined-template-log-switchs {
          if-feature udf-template-type ;
          description 'Configure user defined template ACL log statistics switc'
                    + 'h.'
                      ;
          list user-defined-template-log-switch {
            description 'Configure user defined template ACL log statistics swi'
                      + 'tch.'
                        ;
            key 'if-name if-direction'
                ;
            leaf if-name {
              description 'Configure the name of the attaching interface.'
                          ;
              type ncd:ifname ;
            }
            leaf if-direction {
              description 'Specify the direction of interface, as follows,'+"\n"
                        + '     egress  Direction egress'+"\n"
                        + '     ingress Direction ingress.'
                          ;
              type acl-if-direction ;
            }
            leaf action {
              description 'Specify which action of ACL to turn on the log switc'
                        + 'h, as follows,'+"\n"
                        + '     permit  Enable permit ACL log'+"\n"
                        + '     deny    Enable deny ACL log'+"\n"
                        + '     all     Enable all ACL log.'
                          ;
              type enumeration {
                enum permit {
                  value 1 ;
                  description 'Enable permit ACL log.'
                              ;
                }
                enum deny {
                  value 2 ;
                  description 'Enable deny ACL log.'
                              ;
                }
                enum all {
                  value 3 ;
                  description 'Enable all ACL log.'
                              ;
                }
              }
              mandatory true ;
            }
          }
          ncd:revise-date 2022-01-27 ;
        }
        ncd:revise-date 2015-06-08 ;
      }
    }
  }
  container operation {
    config false ;
    description 'Operation model.'
                ;
    container acl {
      description 'Operation about ACL.'
                  ;
      container ipv4-log-clears {
        if-feature ipv4-feature ;
        if-feature acl-statistics ;
        description 'Clear IPv4 ACL log statistics data.'
                    ;
        choice clear-type {
          description 'Type of clearing IPv4 ACL log statistics data.'
                      ;
          case specify-if {
            description 'Clear ACL statistics data with specified interface and'
                      + ' direction.'
                        ;
            list ipv4-log-clear {
              description 'Clear ACL statistics data with specified interface a'
                        + 'nd direction.'
                          ;
              key 'if-name if-direction'
                  ;
              leaf if-name {
                description 'Specify the name of the attaching interface.'
                            ;
                type ncd:ifname ;
              }
              leaf if-direction {
                description 'Specify the direction of interface, as follows,'+"\n"
                          + '     egress  Direction egress'+"\n"
                          + '     ingress Direction ingress.'
                            ;
                type acl-if-direction ;
              }
            }
          }
          case all-if {
            description 'Clear ACL statistics data in all interface.'
                        ;
            leaf ipv4-log-clear-all {
              description 'Clear ACL statistics data in all interface.'
                          ;
              type empty ;
              mandatory true ;
            }
            ncd:revise-date 2021-11-02 ;
          }
        }
      }
      container ipv6-log-clears {
        if-feature ipv6-feature ;
        if-feature acl-statistics ;
        description 'Clear IPv6 ACL log statistics data.'
                    ;
        choice clear-type {
          description 'Type of clearing IPv6 ACL log statistics data.'
                      ;
          case specify-if {
            description 'Clear ACL statistics data with specified interface and'
                      + ' direction.'
                        ;
            list ipv6-log-clear {
              description 'Clear ACL statistics data with specified interface a'
                        + 'nd direction.'
                          ;
              key 'if-name if-direction'
                  ;
              leaf if-name {
                description 'Specify the name of the attaching interface.'
                            ;
                type ncd:ifname ;
              }
              leaf if-direction {
                description 'Specify the direction of interface, as follows,'+"\n"
                          + '     egress  Direction egress'+"\n"
                          + '     ingress Direction ingress.'
                            ;
                type acl-if-direction ;
              }
            }
          }
          case all-if {
            description 'Clear ACL statistics data in all interface.'
                        ;
            leaf ipv6-log-clear-all {
              description 'Clear ACL statistics data in all interface.'
                          ;
              type empty ;
              mandatory true ;
            }
            ncd:revise-date 2021-11-02 ;
          }
        }
      }
      container link-log-clears {
        if-feature link-feature ;
        if-feature acl-statistics ;
        description 'Clear link ACL log statistics data.'
                    ;
        choice clear-type {
          description 'Type of clearing link ACL log statistics data.'
                      ;
          case specify-if {
            description 'Clear ACL statistics data with specified interface and'
                      + ' direction.'
                        ;
            list link-log-clear {
              description 'Clear ACL statistics data with specified interface a'
                        + 'nd direction.'
                          ;
              key 'if-name if-direction'
                  ;
              leaf if-name {
                description 'Specify the name of the attaching interface.'
                            ;
                type ncd:ifname ;
              }
              leaf if-direction {
                description 'Specify the direction of interface, as follows,'+"\n"
                          + '     egress  Direction egress'+"\n"
                          + '     ingress Direction ingress.'
                            ;
                type acl-if-direction ;
              }
            }
          }
          case all-if {
            description 'Clear ACL statistics data in all interface.'
                        ;
            leaf link-log-clear-all {
              description 'Clear ACL statistics data in all interface.'
                          ;
              type empty ;
              mandatory true ;
            }
            ncd:revise-date 2021-11-02 ;
          }
        }
      }
      container ipv4-mixed-log-clears {
        if-feature ipv4-mixed-log-config ;
        description 'Clear IPv4 mixed ACL log statistics data.'
                    ;
        choice clear-type {
          description 'Type of clearing IPv4 mixed ACL log statistics data.'
                      ;
          case specify-if {
            description 'Clear ACL statistics data with specified interface and'
                      + ' direction.'
                        ;
            list ipv4-mixed-log-clear {
              description 'Clear ACL statistics data with specified interface a'
                        + 'nd direction.'
                          ;
              key 'if-name if-direction'
                  ;
              leaf if-name {
                description 'Specify the name of the attaching interface.'
                            ;
                type ncd:ifname ;
              }
              leaf if-direction {
                description 'Specify the direction of interface, as follows,'+"\n"
                          + '     egress  Direction egress'+"\n"
                          + '     ingress Direction ingress.'
                            ;
                type acl-if-direction ;
              }
            }
          }
          case all-if {
            description 'Clear ACL statistics data in all interface.'
                        ;
            leaf ipv4-mixed-log-clear-all {
              description 'Clear ACL statistics data in all interface.'
                          ;
              type empty ;
              mandatory true ;
            }
            ncd:revise-date 2021-11-02 ;
          }
        }
        ncd:revise-date 2019-10-08 ;
      }
      container ipv6-mixed-log-clears {
        if-feature ipv6-mixed-log-config ;
        description 'Clear IPv6 mixed ACL log statistics data.'
                    ;
        list ipv6-mixed-log-clear {
          description 'Clear IPv6 mixed ACL log statistics data.'
                      ;
          key 'if-name if-direction'
              ;
          leaf if-name {
            description 'Specify the name of the attaching interface.'
                        ;
            type ncd:ifname ;
          }
          leaf if-direction {
            description 'Specify the direction of interface, as follows,'+"\n"
                      + '     egress  Direction egress'+"\n"
                      + '     ingress Direction ingress.'
                        ;
            type acl-if-direction ;
          }
        }
        ncd:revise-date 2021-06-03 ;
      }
      container ipv4-log-clears-by-acl {
        description 'Clear IPv4 ACL log statistics data.'
                    ;
        list ipv4-log-clear-by-acl {
          description 'Clear IPv4 ACL log statistics data.'
                      ;
          key 'acl-name if-direction'
              ;
          leaf acl-name {
            description 'Specify the name of the attaching ACL.'
                        ;
            type acl-name-type ;
          }
          leaf if-direction {
            description 'Specify the direction, as follows,'+"\n"
                      + '     egress  Direction egress'+"\n"
                      + '     ingress Direction ingress.'
                        ;
            type acl-if-direction ;
          }
        }
        ncd:revise-date 2021-10-20 ;
      }
      container ipv6-log-clears-by-acl {
        description 'Clear IPv6 ACL log statistics data.'
                    ;
        list ipv6-log-clear-by-acl {
          description 'Clear IPv6 ACL log statistics data.'
                      ;
          key 'acl-name if-direction'
              ;
          leaf acl-name {
            description 'Specify the name of the attaching ACL.'
                        ;
            type acl-name-type ;
          }
          leaf if-direction {
            description 'Specify the direction, as follows,'+"\n"
                      + '     egress  Direction egress'+"\n"
                      + '     ingress Direction ingress.'
                        ;
            type acl-if-direction ;
          }
        }
        ncd:revise-date 2021-10-20 ;
      }
      container link-log-clears-by-acl {
        description 'Clear link ACL log statistics data.'
                    ;
        list link-log-clear-by-acl {
          description 'Clear link ACL log statistics data.'
                      ;
          key 'acl-name if-direction'
              ;
          leaf acl-name {
            description 'Specify the name of the attaching ACL.'
                        ;
            type acl-name-type ;
          }
          leaf if-direction {
            description 'Specify the direction, as follows,'+"\n"
                      + '     egress  Direction egress'+"\n"
                      + '     ingress Direction ingress.'
                        ;
            type acl-if-direction ;
          }
        }
        ncd:revise-date 2021-10-20 ;
      }
      container ipv4-mixed-log-clears-by-acl {
        description 'Clear IPv4 mixed ACL log statistics data.'
                    ;
        list ipv4-mixed-log-clear-by-acl {
          description 'Clear IPv4 mixed ACL log statistics data.'
                      ;
          key 'acl-name if-direction'
              ;
          leaf acl-name {
            description 'Specify the name of the attaching ACL.'
                        ;
            type acl-name-type ;
          }
          leaf if-direction {
            description 'Specify the direction, as follows,'+"\n"
                      + '     egress  Direction egress'+"\n"
                      + '     ingress Direction ingress.'
                        ;
            type acl-if-direction ;
          }
        }
        ncd:revise-date 2021-10-20 ;
      }
      container ipv6-mixed-log-clears-by-acl {
        description 'Clear IPv6 mixed ACL log statistics data.'
                    ;
        list ipv6-mixed-log-clear-by-acl {
          description 'Clear IPv6 mixed ACL log statistics data.'
                      ;
          key 'acl-name if-direction'
              ;
          leaf acl-name {
            description 'Specify the name of the attaching ACL.'
                        ;
            type acl-name-type ;
          }
          leaf if-direction {
            description 'Specify the direction, as follows,'+"\n"
                      + '     egress  Direction egress'+"\n"
                      + '     ingress Direction ingress.'
                        ;
            type acl-if-direction ;
          }
        }
        ncd:revise-date 2021-10-20 ;
      }
      container ipv4-vxlan-log-clears-by-acl {
        description 'Clear IPv4 VXLAN ACL log statistics data.'
                    ;
        list ipv4-vxlan-log-clear-by-acl {
          description 'Clear IPv4 VXLAN ACL log statistics data.'
                      ;
          key 'acl-name if-direction'
              ;
          leaf acl-name {
            description 'Specify the name of the attaching ACL.'
                        ;
            type acl-name-type ;
          }
          leaf if-direction {
            description 'Specify the direction, as follows,'+"\n"
                      + '     egress  Direction egress'+"\n"
                      + '     ingress Direction ingress.'
                        ;
            type acl-if-direction ;
          }
        }
        ncd:revise-date 2022-01-20 ;
      }
      container ipv6-vxlan-log-clears-by-acl {
        description 'Clear IPv6 VXLAN ACL log statistics data.'
                    ;
        list ipv6-vxlan-log-clear-by-acl {
          description 'Clear IPv6 VXLAN ACL log statistics data.'
                      ;
          key 'acl-name if-direction'
              ;
          leaf acl-name {
            description 'Specify the name of the attaching ACL.'
                        ;
            type acl-name-type ;
          }
          leaf if-direction {
            description 'Specify the direction, as follows,'+"\n"
                      + '     egress  Direction egress'+"\n"
                      + '     ingress Direction ingress.'
                        ;
            type acl-if-direction ;
          }
        }
        ncd:revise-date 2022-01-20 ;
      }
      container user-defined-template-log-clears {
        if-feature udf-template-type ;
        if-feature acl-statistics ;
        description 'Clear user defined template ACL log statistics data.'
                    ;
        list user-defined-template-log-clear {
          description 'Clear user defined template ACL log statistics data.'
                      ;
          key 'if-name if-direction'
              ;
          leaf if-name {
            description 'Specify the name of the attaching interface.'
                        ;
            type ncd:ifname ;
          }
          leaf if-direction {
            description 'Specify the direction of interface, as follows,'+"\n"
                      + '     egress  Direction egress'+"\n"
                      + '     ingress Direction ingress.'
                        ;
            type acl-if-direction ;
          }
        }
        ncd:revise-date 2022-01-27 ;
      }
    }
    ncd:revise-date 2015-06-08 ;
  }
  container state {
    config false ;
    description 'State model.'
                ;
    container acl {
      description 'State about ACL.'
                  ;
      container acl-v4-statistics {
        if-feature ipv4-feature ;
        if-feature acl-statistics ;
        description 'Query IPv4 ACL statistics data.'
                    ;
        list acl-v4-statistic {
          description 'Query IPv4 ACL statistics data.'
                      ;
          key 'if-name if-direction acl-ruleid'
              ;
          leaf if-name {
            description 'The name of the attaching interface.'
                        ;
            type ncd:ifname ;
          }
          leaf if-direction {
            description 'The direction of interface, as follows,'+"\n"
                      + '     egress  Direction egress'+"\n"
                      + '     ingress Direction ingress.'
                        ;
            type acl-if-direction ;
          }
          leaf acl-ruleid {
            description 'ID of this rule.'
                        ;
            type uint32 {
              range 1..2147483644 {
                description 'ID of this rule.'
                            ;
              }
            }
          }
          leaf acl-name {
            description 'Name of ACL.'
                        ;
            type acl-name-type ;
          }
          leaf stats-bytes {
            description 'Matching packet bytes.'
                        ;
            type uint64 ;
            units byte ;
          }
          leaf stats-packets {
            description 'Matching packets.'
                        ;
            type uint64 ;
          }
          leaf stats-rate {
            description 'Matching packet rate.'
                        ;
            type uint64 ;
            units bps ;
          }
          ncd:select 'if-name if-direction'
                     ;
          ncd:select 'if-name if-direction acl-ruleid'
                     ;
        }
      }
      container acl-v6-statistics {
        if-feature ipv6-feature ;
        if-feature acl-statistics ;
        description 'Query IPv6 ACL statistics data.'
                    ;
        list acl-v6-statistic {
          description 'Query IPv6 ACL statistics data.'
                      ;
          key 'if-name if-direction acl-ruleid'
              ;
          leaf if-name {
            description 'The name of the attaching interface.'
                        ;
            type ncd:ifname ;
          }
          leaf if-direction {
            description 'The direction of interface, as follows,'+"\n"
                      + '     egress  Direction egress'+"\n"
                      + '     ingress Direction ingress.'
                        ;
            type acl-if-direction ;
          }
          leaf acl-ruleid {
            description 'ID of this rule.'
                        ;
            type uint32 {
              range 1..2147483644 {
                description 'ID of this rule.'
                            ;
              }
            }
          }
          leaf acl-name {
            description 'Name of ACL.'
                        ;
            type acl-name-type ;
          }
          leaf stats-bytes {
            description 'Matching packet bytes.'
                        ;
            type uint64 ;
            units byte ;
          }
          leaf stats-packets {
            description 'Matching packets.'
                        ;
            type uint64 ;
          }
          leaf stats-rate {
            description 'Matching packet rate.'
                        ;
            type uint64 ;
            units bps ;
          }
          ncd:select 'if-name if-direction'
                     ;
          ncd:select 'if-name if-direction acl-ruleid'
                     ;
        }
      }
      container acl-link-statistics {
        if-feature link-log-config ;
        description 'Query link ACL statistics data.'
                    ;
        list acl-link-statistic {
          description 'Query link ACL statistics data.'
                      ;
          key 'if-name if-direction acl-ruleid'
              ;
          leaf if-name {
            description 'The name of the attaching interface.'
                        ;
            type ncd:ifname ;
          }
          leaf if-direction {
            description 'The direction of interface, as follows,'+"\n"
                      + '     egress  Direction egress'+"\n"
                      + '     ingress Direction ingress.'
                        ;
            type acl-if-direction ;
          }
          leaf acl-ruleid {
            description 'ID of this rule.'
                        ;
            type uint32 {
              range 1..2147483644 {
                description 'ID of this rule.'
                            ;
              }
            }
          }
          leaf acl-name {
            description 'Name of ACL.'
                        ;
            type acl-name-type ;
          }
          leaf stats-bytes {
            description 'Matching packet bytes.'
                        ;
            type uint64 ;
            units byte ;
          }
          leaf stats-packets {
            description 'Matching packets.'
                        ;
            type uint64 ;
          }
          leaf stats-rate {
            description 'Matching packet rate.'
                        ;
            type uint64 ;
            units bps ;
          }
          ncd:select 'if-name if-direction'
                     ;
          ncd:select 'if-name if-direction acl-ruleid'
                     ;
        }
        ncd:revise-date 2019-10-08 ;
      }
      container acl-v4-mixed-statistics {
        if-feature ipv4-mixed-log-config ;
        description 'Query IPv4 mixed ACL statistics data.'
                    ;
        list acl-v4-mixed-statistic {
          description 'Query IPv4 mixed ACL statistics data.'
                      ;
          key 'if-name if-direction acl-ruleid'
              ;
          leaf if-name {
            description 'The name of the attaching interface.'
                        ;
            type ncd:ifname ;
          }
          leaf if-direction {
            description 'The direction of interface, as follows,'+"\n"
                      + '     egress  Direction egress'+"\n"
                      + '     ingress Direction ingress.'
                        ;
            type acl-if-direction ;
          }
          leaf acl-ruleid {
            description 'ID of this rule.'
                        ;
            type uint32 {
              range 1..2147483644 {
                description 'ID of this rule.'
                            ;
              }
            }
          }
          leaf acl-name {
            description 'Name of ACL.'
                        ;
            type acl-name-type ;
          }
          leaf stats-bytes {
            description 'Matching packet bytes.'
                        ;
            type uint64 ;
            units byte ;
          }
          leaf stats-packets {
            description 'Matching packets.'
                        ;
            type uint64 ;
          }
          leaf stats-rate {
            description 'Matching packet rate.'
                        ;
            type uint64 ;
            units bps ;
          }
          ncd:select 'if-name if-direction'
                     ;
          ncd:select 'if-name if-direction acl-ruleid'
                     ;
        }
        ncd:revise-date 2019-10-08 ;
      }
      container acl-v6-mixed-statistics {
        if-feature ipv6-mixed-log-config ;
        description 'Query IPv6 mixed ACL statistics data.'
                    ;
        list acl-v6-mixed-statistic {
          description 'Query IPv6 mixed ACL statistics data.'
                      ;
          key 'if-name if-direction acl-ruleid'
              ;
          leaf if-name {
            description 'The name of the attaching interface.'
                        ;
            type ncd:ifname ;
          }
          leaf if-direction {
            description 'The direction of interface, as follows,'+"\n"
                      + '     egress  Direction egress'+"\n"
                      + '     ingress Direction ingress.'
                        ;
            type acl-if-direction ;
          }
          leaf acl-ruleid {
            description 'ID of this rule.'
                        ;
            type uint32 {
              range 1..2147483644 {
                description 'ID of this rule.'
                            ;
              }
            }
          }
          leaf acl-name {
            description 'Name of ACL.'
                        ;
            type acl-name-type ;
          }
          leaf stats-bytes {
            description 'Matching packet bytes.'
                        ;
            type uint64 ;
            units byte ;
          }
          leaf stats-packets {
            description 'Matching packets.'
                        ;
            type uint64 ;
          }
          leaf stats-rate {
            description 'Matching packet rate.'
                        ;
            type uint64 ;
            units bps ;
          }
          ncd:select 'if-name if-direction'
                     ;
          ncd:select 'if-name if-direction acl-ruleid'
                     ;
        }
        ncd:revise-date 2021-06-03 ;
      }
      container acl-v4-statistics-by-acl {
        description 'Query IPv4 ACL statistics data.'
                    ;
        list acl-v4-statistic-by-acl {
          description 'Query IPv4 ACL statistics data.'
                      ;
          key 'acl-name if-direction acl-ruleid'
              ;
          leaf acl-name {
            description 'Name of ACL.'
                        ;
            type acl-name-type ;
          }
          leaf if-direction {
            description 'The direction, as follows,'+"\n"
                      + '     egress  Direction egress'+"\n"
                      + '     ingress Direction ingress.'
                        ;
            type acl-if-direction ;
          }
          leaf acl-ruleid {
            description 'ID of this rule.'
                        ;
            type uint32 {
              range 1..2147483644 {
                description 'ID of this rule.'
                            ;
              }
            }
          }
          leaf stats-bytes {
            description 'Matching packet bytes.'
                        ;
            type uint64 ;
            units byte ;
          }
          leaf stats-packets {
            description 'Matching packets.'
                        ;
            type uint64 ;
          }
          leaf stats-rate {
            description 'Matching packet rate.'
                        ;
            type uint64 ;
            units bps ;
          }
          ncd:select 'acl-name if-direction'
                     ;
          ncd:select 'acl-name if-direction acl-ruleid'
                     ;
        }
        ncd:revise-date 2021-10-20 ;
      }
      container acl-v6-statistics-by-acl {
        description 'Query IPv6 ACL statistics data.'
                    ;
        list acl-v6-statistic-by-acl {
          description 'Query IPv6 ACL statistics data.'
                      ;
          key 'acl-name if-direction acl-ruleid'
              ;
          leaf acl-name {
            description 'Name of ACL.'
                        ;
            type acl-name-type ;
          }
          leaf if-direction {
            description 'The direction, as follows,'+"\n"
                      + '     egress  Direction egress'+"\n"
                      + '     ingress Direction ingress.'
                        ;
            type acl-if-direction ;
          }
          leaf acl-ruleid {
            description 'ID of this rule.'
                        ;
            type uint32 {
              range 1..2147483644 {
                description 'ID of this rule.'
                            ;
              }
            }
          }
          leaf stats-bytes {
            description 'Matching packet bytes.'
                        ;
            type uint64 ;
            units byte ;
          }
          leaf stats-packets {
            description 'Matching packets.'
                        ;
            type uint64 ;
          }
          leaf stats-rate {
            description 'Matching packet rate.'
                        ;
            type uint64 ;
            units bps ;
          }
          ncd:select 'acl-name if-direction'
                     ;
          ncd:select 'acl-name if-direction acl-ruleid'
                     ;
        }
        ncd:revise-date 2021-10-20 ;
      }
      container acl-link-statistics-by-acl {
        description 'Query link ACL statistics data.'
                    ;
        list acl-link-statistic-by-acl {
          description 'Query link ACL statistics data.'
                      ;
          key 'acl-name if-direction acl-ruleid'
              ;
          leaf acl-name {
            description 'Name of ACL.'
                        ;
            type acl-name-type ;
          }
          leaf if-direction {
            description 'The direction, as follows,'+"\n"
                      + '     egress  Direction egress'+"\n"
                      + '     ingress Direction ingress.'
                        ;
            type acl-if-direction ;
          }
          leaf acl-ruleid {
            description 'ID of this rule.'
                        ;
            type uint32 {
              range 1..2147483644 {
                description 'ID of this rule.'
                            ;
              }
            }
          }
          leaf stats-bytes {
            description 'Matching packet bytes.'
                        ;
            type uint64 ;
            units byte ;
          }
          leaf stats-packets {
            description 'Matching packets.'
                        ;
            type uint64 ;
          }
          leaf stats-rate {
            description 'Matching packet rate.'
                        ;
            type uint64 ;
            units bps ;
          }
          ncd:select 'acl-name if-direction'
                     ;
          ncd:select 'acl-name if-direction acl-ruleid'
                     ;
        }
        ncd:revise-date 2021-10-20 ;
      }
      container acl-v4-mixed-statistics-by-acl {
        description 'Query IPv4 mixed ACL statistics data.'
                    ;
        list acl-v4-mixed-statistic-by-acl {
          description 'Query IPv4 mixed ACL statistics data.'
                      ;
          key 'acl-name if-direction acl-ruleid'
              ;
          leaf acl-name {
            description 'Name of ACL.'
                        ;
            type acl-name-type ;
          }
          leaf if-direction {
            description 'The direction, as follows,'+"\n"
                      + '     egress  Direction egress'+"\n"
                      + '     ingress Direction ingress.'
                        ;
            type acl-if-direction ;
          }
          leaf acl-ruleid {
            description 'ID of this rule.'
                        ;
            type uint32 {
              range 1..2147483644 {
                description 'ID of this rule.'
                            ;
              }
            }
          }
          leaf stats-bytes {
            description 'Matching packet bytes.'
                        ;
            type uint64 ;
            units byte ;
          }
          leaf stats-packets {
            description 'Matching packets.'
                        ;
            type uint64 ;
          }
          leaf stats-rate {
            description 'Matching packet rate.'
                        ;
            type uint64 ;
            units bps ;
          }
          ncd:select 'acl-name if-direction'
                     ;
          ncd:select 'acl-name if-direction acl-ruleid'
                     ;
        }
        ncd:revise-date 2021-10-20 ;
      }
      container acl-v6-mixed-statistics-by-acl {
        description 'Query IPv6 mixed ACL statistics data.'
                    ;
        list acl-v6-mixed-statistic-by-acl {
          description 'Query IPv6 mixed ACL statistics data.'
                      ;
          key 'acl-name if-direction acl-ruleid'
              ;
          leaf acl-name {
            description 'Name of ACL.'
                        ;
            type acl-name-type ;
          }
          leaf if-direction {
            description 'The direction, as follows,'+"\n"
                      + '     egress  Direction egress'+"\n"
                      + '     ingress Direction ingress.'
                        ;
            type acl-if-direction ;
          }
          leaf acl-ruleid {
            description 'ID of this rule.'
                        ;
            type uint32 {
              range 1..2147483644 {
                description 'ID of this rule.'
                            ;
              }
            }
          }
          leaf stats-bytes {
            description 'Matching packet bytes.'
                        ;
            type uint64 ;
            units byte ;
          }
          leaf stats-packets {
            description 'Matching packets.'
                        ;
            type uint64 ;
          }
          leaf stats-rate {
            description 'Matching packet rate.'
                        ;
            type uint64 ;
            units bps ;
          }
          ncd:select 'acl-name if-direction'
                     ;
          ncd:select 'acl-name if-direction acl-ruleid'
                     ;
        }
        ncd:revise-date 2021-10-20 ;
      }
      container acl-v4-vxlan-statistics-by-acl {
        description 'Query IPv4 VXLAN ACL statistics data.'
                    ;
        list acl-v4-vxlan-statistics-by-acl {
          description 'Query IPv4 VXLAN ACL statistics data.'
                      ;
          key 'acl-name if-direction acl-ruleid'
              ;
          leaf acl-name {
            description 'Name of ACL.'
                        ;
            type acl-name-type ;
          }
          leaf if-direction {
            description 'The direction, as follows,'+"\n"
                      + '     egress  Direction egress'+"\n"
                      + '     ingress Direction ingress.'
                        ;
            type acl-if-direction ;
          }
          leaf acl-ruleid {
            description 'ID of this rule.'
                        ;
            type uint32 {
              range 1..2147483644 {
                description 'ID of this rule.'
                            ;
              }
            }
          }
          leaf stats-bytes {
            description 'Matching packet bytes.'
                        ;
            type uint64 ;
            units byte ;
          }
          leaf stats-packets {
            description 'Matching packets.'
                        ;
            type uint64 ;
          }
          leaf stats-rate {
            description 'Matching packet rate.'
                        ;
            type uint64 ;
            units bps ;
          }
          ncd:select 'acl-name if-direction'
                     ;
          ncd:select 'acl-name if-direction acl-ruleid'
                     ;
        }
        ncd:revise-date 2022-01-20 ;
      }
      container acl-v6-vxlan-statistics-by-acl {
        description 'Query IPv6 VXLAN ACL statistics data.'
                    ;
        list acl-v6-vxlan-statistics-by-acl {
          description 'Query IPv6 VXLAN ACL statistics data.'
                      ;
          key 'acl-name if-direction acl-ruleid'
              ;
          leaf acl-name {
            description 'Name of ACL.'
                        ;
            type acl-name-type ;
          }
          leaf if-direction {
            description 'The direction, as follows,'+"\n"
                      + '     egress  Direction egress'+"\n"
                      + '     ingress Direction ingress.'
                        ;
            type acl-if-direction ;
          }
          leaf acl-ruleid {
            description 'ID of this rule.'
                        ;
            type uint32 {
              range 1..2147483644 {
                description 'ID of this rule.'
                            ;
              }
            }
          }
          leaf stats-bytes {
            description 'Matching packet bytes.'
                        ;
            type uint64 ;
            units byte ;
          }
          leaf stats-packets {
            description 'Matching packets.'
                        ;
            type uint64 ;
          }
          leaf stats-rate {
            description 'Matching packet rate.'
                        ;
            type uint64 ;
            units bps ;
          }
          ncd:select 'acl-name if-direction'
                     ;
          ncd:select 'acl-name if-direction acl-ruleid'
                     ;
        }
        ncd:revise-date 2022-01-20 ;
      }
    }
    ncd:revise-date 2015-06-08 ;
  }
}
