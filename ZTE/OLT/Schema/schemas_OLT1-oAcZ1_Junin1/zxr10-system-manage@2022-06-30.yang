module zxr10-system-manage {
  namespace 'http://www.zte.com.cn/zxr10/netconf/schema/rosng/system-manage'
            ;
  prefix system-manage ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The netconf module to describe system-manage. System-manage is o'
            + 'peration and configuration to the system.'
              ;
  revision 2022-06-30 {
    description "Add leaf node 'configuration/privileges/privilege/physical-mod"
              + "e-id';'state/logic-modes/logic-mode/physical-mode'"
                ;
  }
  revision 2022-01-21 {
    description 'Add the privileges configuration and the logic-modes state.'
                ;
  }
  revision 2021-06-19 {
    description 'Add the multi-user configuration.'
                ;
  }
  revision 2021-04-19 {
    description "(1)Extend the length range of node '/configuration/startrun-ba"
              + "ckup-to-ipv4-servers/startrun-backup-to-ipv4-server/ftp/passwo"
              + "rd' from 64 to 128.
\n(2)Extend the length range of node '/con"
              + "figuration/startrun-backup-to-ipv4-servers/startrun-backup-to-"
              + "ipv4-server/sftp/password' from 64 to 128.
\n(3)Extend the len"
              + "gth range of node '/configuration/startrun-backup-to-ipv6-serv"
              + "ers/startrun-backup-to-ipv6-server/ftp/password' from 64 to 12"
              + "8.
\n(4)Extend the length range of node '/configuration/startr"
              + "un-backup-to-ipv6-servers/startrun-backup-to-ipv6-server/sftp/"
              + "password' from 64 to 128.
\n(5)Extend the length range of node"
              + " '/operation/system-manage/startrun-download/remote/password' "
              + "from 64 to 128."
                ;
  }
  revision 2020-07-11 {
    description "(1)Change the node '/configuration/startrun-backup-to-ipv4-ser"
              + "vers/startrun-backup-to-ipv4-server/ftp/password' datatype fro"
              + "m 'chars' to \"plaintext\";
\n(2)Change the node '/configurati"
              + "on/startrun-backup-to-ipv4-servers/startrun-backup-to-ipv4-ser"
              + "ver/ftp/encrypted-password' datatype from 'chars' to \"ciphert"
              + "ext\";
\n(3)Change the node '/configuration/startrun-backup-to"
              + "-ipv4-servers/startrun-backup-to-ipv4-server/sftp/password' da"
              + "tatype from 'chars' to \"plaintext\";
\n(4)Change the node '/c"
              + "onfiguration/startrun-backup-to-ipv4-servers/startrun-backup-t"
              + "o-ipv4-server/sftp/encrypted-password' datatype from 'chars' t"
              + "o \"ciphertext\";
\n(5)Change the node '/configuration/startru"
              + "n-backup-to-ipv6-servers/startrun-backup-to-ipv6-server/ftp/pa"
              + "ssword' datatype from 'chars' to \"plaintext\";
\n(6)Change th"
              + "e node '/configuration/startrun-backup-to-ipv6-servers/startru"
              + "n-backup-to-ipv6-server/ftp/encrypted-password' datatype from "
              + "'chars' to \"ciphertext\";
\n(7)Change the node '/configuratio"
              + "n/startrun-backup-to-ipv6-servers/startrun-backup-to-ipv6-serv"
              + "er/sftp/password' datatype from 'chars' to \"plaintext\";
\n(8"
              + ")Change the node '/configuration/startrun-backup-to-ipv6-serve"
              + "rs/startrun-backup-to-ipv6-server/sftp/encrypted-password' dat"
              + "atype from 'chars' to \"ciphertext\";
\n(9)Extend the length r"
              + "ange of node '/configuration/startrun-backup-to-ipv4-servers/s"
              + "tartrun-backup-to-ipv4-server/ftp/encrypted-password' from 64,"
              + "128 to 64-240.
\n(10)Extend the length range of node '/configu"
              + "ration/startrun-backup-to-ipv4-servers/startrun-backup-to-ipv4"
              + "-server/sftp/encrypted-password' from 64,128 to 64-240.
\n(11)"
              + "Extend the length range of node '/configuration/startrun-backu"
              + "p-to-ipv6-servers/startrun-backup-to-ipv6-server/ftp/encrypted"
              + "-password' from 64,128 to 64-240.
\n(12)Extend the length rang"
              + "e of node '/configuration/startrun-backup-to-ipv6-servers/star"
              + "trun-backup-to-ipv6-server/sftp/encrypted-password' from 64,12"
              + "8 to 64-240."
                ;
  }
  revision 2020-06-03 {
    description 'Delete the if-feature. Path:/system-manage:configuration/syste'
              + 'm-manage:auto-save.'
                ;
  }
  revision 2019-09-24 {
    description '1.Add choice node. Path:/system-manage:configuration/system-ma'
              + 'nage:startrun-backup-to-ipv6-servers/system-manage:startrun-ba'
              + 'ckup-to-ipv6-server/system-manage:vrf-name.'+"\n"
              + '2.Add choice node. Path:/system-manage:configuration/system-ma'
              + 'nage:startrun-backup-to-ipv4-servers/system-manage:startrun-ba'
              + 'ckup-to-ipv4-server/system-manage:vrf-name.'+"\n"
              + '3.Add new feature:dcn-surpport-product.'
                ;
  }
  revision 2019-06-18 {
    description '1.Path:/system-manage:configuration/system-manage:startrun-bac'
              + 'kup-to-ipv4-servers/system-manage:startrun-backup-to-ipv4-serv'
              + 'er/system-manage:ftp/system-manage:encrypted-password. Data ty'
              + 'pe of this leaf node is changed from string-all to string.'+"\n"
              + '2.Path:/system-manage:configuration/system-manage:startrun-bac'
              + 'kup-to-ipv4-servers/system-manage:startrun-backup-to-ipv4-serv'
              + 'er/system-manage:ftp/system-manage:password. This leaf node is'
              + ' changed to mandatory.'
                ;
  }
  revision 2019-06-10 {
    description "(1)Change the length of node '/configuration/startrun-backup-t"
              + "o-ipv4-servers/startrun-backup-to-ipv4-server/ftp/password' fr"
              + "om 1-32 to 1-64. (2)Change the length of node '/configuration/"
              + "startrun-backup-to-ipv4-servers/startrun-backup-to-ipv4-server"
              + "/sftp/password' from 1-32 to 1-64. (3)Change the length of nod"
              + "e '/configuration/startrun-backup-to-ipv6-servers/startrun-bac"
              + "kup-to-ipv6-server/ftp/password' from 1-32 to 1-64. (4)Change "
              + "the length of node '/configuration/startrun-backup-to-ipv6-ser"
              + "vers/startrun-backup-to-ipv6-server/sftp/password' from 1-32 t"
              + "o 1-64. (5)Change the length of node '/configuration/startrun-"
              + "backup-to-ipv4-servers/startrun-backup-to-ipv4-server/ftp/encr"
              + "ypted-password' from 64 to 64 or 128. (6)Change the length of "
              + "node '/configuration/startrun-backup-to-ipv4-servers/startrun-"
              + "backup-to-ipv4-server/sftp/encrypted-password' from 64 to 64 o"
              + "r 128. (7)Change the length of node '/configuration/startrun-b"
              + "ackup-to-ipv6-servers/startrun-backup-to-ipv6-server/ftp/encry"
              + "pted-password' from 64 to 64 or 128. (8)Change the length of n"
              + "ode '/configuration/startrun-backup-to-ipv6-servers/startrun-b"
              + "ackup-to-ipv6-server/sftp/encrypted-password' from 64 to 64 or"
              + " 128.(9)Change the length of node '/operation/system-manage/st"
              + "artrun-download/remote/password' from 1-32 to 1-64."
                ;
  }
  revision 2019-02-27 {
    description 'Add unzip leaf node.'+"\n"
              + 'Add zip leaf node. Path:/system-manage:configuration/system-ma'
              + 'nage:startrun-backup-to-ipv4-servers/system-manage:startrun-ba'
              + 'ckup-to-ipv4-server/system-manage:zip and /system-manage:confi'
              + 'guration/system-manage:startrun-backup-to-ipv6-servers/system-'
              + 'manage:startrun-backup-to-ipv6-server/system-manage:zip'+"\n"
              + 'Add choice key node in startrun-backup-to-ipv6-server and star'
              + 'trun-backup-to-ipv4-server.'
                ;
  }
  revision 2018-09-04 {
    description 'Add startrun download function.'
                ;
  }
  revision 2018-06-08 {
    description "Add leaf node 'configuration/timestamp'"
                ;
  }
  revision 2017-07-03 {
    description 'Add automatic saving configuration function.'
                ;
  }
  revision 2014-08-05 {
    description 'Intial version'
                ;
  }
  feature auto-write ;
  feature startrun-download-dcn ;
  feature dcn-surpport-product ;
  container configuration {
    container auto-save {
      description 'Automatic saving configuration.'
                  ;
      choice policy {
        description 'Automatic saving configuration policy:delay-policy and eve'
                  + 'ryday-policy.'
                    ;
        case delay-policy {
          description 'Delay-policy of automatic saving configuration.'
                      ;
          leaf delay {
            description 'The hold off time interval of automatic saving configu'
                      + 'ration when configuration data is changed. Uint:minute'
                      + 's.Range:1-60.'
                        ;
            type uint32 {
              range 1..60 ;
            }
          }
        }
        case everyday-policy {
          description 'Everyday-policy of automatic saving configuration.'
                      ;
          leaf everyday {
            description 'The time of automatic saving configuration time everyd'
                      + 'ay. For example: HH:MM:SS.(02:22:33).'
                        ;
            type ncd:time ;
          }
        }
      }
      container auto-save-perf-para {
        description 'Automatic saving configuration will take effective interva'
                  + 'l xx minutes when cpu utilization reaches to upper limit.'
                    ;
        presence auto-save-perf-para ;
        leaf cpu-limit {
          description 'The CPU usage threshold of automatic saving configuratio'
                    + 'n.Range:1-90.'
                      ;
          type uint32 {
            range 1..90 ;
          }
          mandatory true ;
        }
        leaf interval {
          description 'The time interval of automatic saving configuration when'
                    + ' cpu utilization reaches to upper limit.Uint:minutes.Ran'
                    + 'ge:1-60.'
                      ;
          type uint32 {
            range 1..60 ;
          }
        }
      }
    }
    container startrun-backup-to-ipv4-servers {
      description 'Backup startrun to file servers with IPv4.'
                  ;
      list startrun-backup-to-ipv4-server {
        description 'Backup startrun to file server with IPv4.'
                    ;
        key ipv4-address ;
        leaf ipv4-address {
          description 'IPv4 address for server.'
                      ;
          type ncd:ipv4-address-none-zero ;
        }
        leaf port {
          description 'Listen port.'
                      ;
          type uint16 {
            range 1..65535 ;
          }
        }
        choice vrf-name {
          description 'VPN name.'
                      ;
          case normal-vrf {
            description 'VPN name without DCN.'
                        ;
            leaf vpn-instance-name {
              description 'VPN instance name.'
                          ;
              type string {
                length 1..32 ;
              }
            }
          }
          case dcn {
            if-feature dcn-surpport-product ;
            description 'Whether DCN VRF or not.'
                        ;
            leaf dcn {
              if-feature dcn-surpport-product ;
              description 'Whether DCN VRF or not.'
                          ;
              type empty ;
            }
            ncd:revise-date 2019-09-24 ;
          }
        }
        choice transport-type {
          description 'Transport type.'
                      ;
          mandatory true ;
          case ftp {
            description 'FTP server.'
                        ;
            container ftp {
              description 'FTP server.'
                          ;
              leaf user-name {
                description "FTP server's username."
                            ;
                type string {
                  length 1..65 ;
                }
                mandatory true ;
              }
              choice key {
                description 'FTP server key.'
                            ;
                mandatory true ;
                case password {
                  description 'Clear password, which display in encrypted passw'
                            + 'ord.'
                              ;
                  leaf password {
                    description "FTP server's password, which display in encryp"
                              + "ted password."
                                ;
                    type string {
                      length 1..128 ;
                    }
                    mandatory true ;
                  }
                }
                case encrypted-password {
                  description 'Encrypted password.'
                              ;
                  leaf encrypted-password {
                    description 'Encrypted password.'
                                ;
                    type string {
                      length 64..240 ;
                    }
                    mandatory true ;
                  }
                }
                ncd:revise-date 2019-02-27 ;
              }
            }
          }
          case sftp {
            description 'SFTP server.'
                        ;
            container sftp {
              description 'SFTP server.'
                          ;
              leaf user-name {
                description "SFTP server's username."
                            ;
                type string {
                  length 1..65 ;
                }
                mandatory true ;
              }
              choice key {
                description 'SFTP server key.'
                            ;
                mandatory true ;
                case password {
                  description "SFTP server's password, which display in encrypt"
                            + "ed-password."
                              ;
                  leaf password {
                    description "SFTP server's password, which display in encry"
                              + "pted-password."
                                ;
                    type string {
                      length 1..128 ;
                    }
                    mandatory true ;
                  }
                }
                case encrypted-password {
                  description 'Encrypted password.'
                              ;
                  leaf encrypted-password {
                    description 'Encrypted password.'
                                ;
                    type string {
                      length 64..240 ;
                    }
                    mandatory true ;
                  }
                }
                ncd:revise-date 2019-02-27 ;
              }
            }
          }
          case tftp {
            description 'TFTP server.'
                        ;
            leaf tftp {
              description 'TFTP server.'
                          ;
              type empty ;
              mandatory true ;
            }
          }
        }
        leaf path {
          description 'File path in server.'
                      ;
          type string {
            length 1..64 ;
          }
        }
        leaf zip {
          description 'Compress file before backuping it to server.'
                      ;
          type empty ;
          ncd:revise-date 2019-02-27 ;
        }
      }
    }
    container startrun-backup-to-ipv6-servers {
      description 'Backup startrun to file servers with IPv6.'
                  ;
      list startrun-backup-to-ipv6-server {
        description 'Backup startrun to file server with IPv6.'
                    ;
        key ipv6-address ;
        leaf ipv6-address {
          description 'IPV6 address for server.'
                      ;
          type ncd:ipv6-address ;
        }
        leaf port {
          description 'Listen port.'
                      ;
          type uint16 {
            range 1..65535 ;
          }
        }
        choice vrf-name {
          description 'VPN name.'
                      ;
          case normal-vrf {
            description 'VPN name without DCN.'
                        ;
            leaf vpn-instance-name {
              description 'VPN instance name.'
                          ;
              type string {
                length 1..32 ;
              }
            }
          }
          case dcn {
            if-feature dcn-surpport-product ;
            description 'Whether DCN VRF or not.'
                        ;
            leaf dcn {
              if-feature dcn-surpport-product ;
              description 'Whether DCN VRF or not.'
                          ;
              type empty ;
            }
            ncd:revise-date 2019-09-24 ;
          }
        }
        choice transport-type {
          description 'Transport type.'
                      ;
          mandatory true ;
          case ftp {
            description 'FTP server.'
                        ;
            container ftp {
              description 'FTP server.'
                          ;
              leaf user-name {
                description "FTP server's username."
                            ;
                type string {
                  length 1..65 ;
                }
                mandatory true ;
              }
              choice key {
                description 'FTP server key.'
                            ;
                mandatory true ;
                case password {
                  description "FTP server's password, which display in encrypte"
                            + "d password."
                              ;
                  leaf password {
                    description "FTP server's password, which display in encryp"
                              + "ted password."
                                ;
                    type string {
                      length 1..128 ;
                    }
                    mandatory true ;
                  }
                }
                case encrypted-password {
                  description 'Encrypted password.'
                              ;
                  leaf encrypted-password {
                    description 'Encrypted password.'
                                ;
                    type string {
                      length 64..240 ;
                    }
                    mandatory true ;
                  }
                }
                ncd:revise-date 2019-02-27 ;
              }
            }
          }
          case stfp {
            description 'SFTP server.'
                        ;
            container sftp {
              description 'SFTP server.'
                          ;
              leaf user-name {
                description "SFTP server's username."
                            ;
                type string {
                  length 1..65 ;
                }
                mandatory true ;
              }
              choice key {
                description 'SFTP server key.'
                            ;
                mandatory true ;
                case password {
                  description "SFTP server's password, which display in encrypt"
                            + "ed-password."
                              ;
                  leaf password {
                    description "SFTP server's password, which display in encry"
                              + "pted-password."
                                ;
                    type string {
                      length 1..128 ;
                    }
                    mandatory true ;
                  }
                }
                case encrypted-password {
                  description 'Encrypted password.'
                              ;
                  leaf encrypted-password {
                    description 'Encrypted password.'
                                ;
                    type string {
                      length 64..240 ;
                    }
                    mandatory true ;
                  }
                }
                ncd:revise-date 2019-02-27 ;
              }
            }
          }
          case tftp {
            description 'TFTP server.'
                        ;
            leaf tftp {
              description 'TFTP server.'
                          ;
              type empty ;
              mandatory true ;
            }
          }
        }
        leaf path {
          description 'File path in server.'
                      ;
          type string {
            length 1..64 ;
          }
        }
        leaf zip {
          description 'Compress file before backuping it to server.'
                      ;
          type empty ;
          ncd:revise-date 2019-02-27 ;
        }
      }
    }
    leaf timestamp {
      description "After the timestamp function is enabled, the system time is "
                + "printed first when the 'show' command is executed."
                  ;
      type enumeration {
        enum enable {
          value 1 ;
          description "Enable the system's timestamp function"
                      ;
        }
        enum disable {
          value 2 ;
          description "Disable the system's timestamp function"
                      ;
        }
      }
      default disable ;
    }
    container multi-user {
      description 'When the multi-user configure is enabled,the ohter client te'
                + 'rminal can use configuration mode.'
                  ;
      leaf configure {
        description 'When the multi-user configure is enabled,the ohter client '
                  + 'terminal can use configuration mode.There are default valu'
                  + 'es, which are different in different environments.'
                    ;
        type enumeration {
          enum enable {
            value 1 ;
            description 'Enable the multi-user configure function.'
                        ;
          }
          enum disable {
            value 0 ;
            description 'Disable the multi-user configure function.'
                        ;
          }
        }
      }
      ncd:revise-date 2021-06-19 ;
    }
    container privileges {
      description 'Set command privilege level.'
                  ;
      list privilege {
        max-elements 2000 ;
        key 'command-node all logic-mode-id physical-mode-id'
            ;
        leaf command-node {
          description 'The command to modify'
                      ;
          type ncd:string-with-blank {
            length 1..200 ;
          }
        }
        leaf all {
          description 'All suboption will be set to the same level'
                      ;
          type boolean ;
        }
        leaf logic-mode-id {
          description 'Command logic mode ID'
                      ;
          type uint16 ;
        }
        leaf physical-mode-id {
          description 'Command physical mode ID'
                      ;
          type uint16 ;
          ncd:revise-date 2022-06-30 ;
        }
        choice command-level {
          description 'Set privilege level of command'
                      ;
          mandatory true ;
          case level {
            description 'Command privilege level'
                        ;
            leaf level {
              type uint8 {
                range 2..15 ;
              }
            }
          }
          case default {
            description 'Default command privilege level.'
                        ;
            leaf default {
              type empty ;
            }
          }
        }
      }
      ncd:revise-date 2022-01-21 ;
    }
  }
  container operation {
    config false ;
    description 'The operation top node of system-manage'
                ;
    container system-manage {
      description 'The node of system-manage.'
                  ;
      container save-configuration {
        description 'The node to save configuration.'
                    ;
        presence save-configuration ;
        container target {
          description 'The target of configuration to be saved.'
                      ;
          choice type-choice {
            description 'The choice node of configuration saving type,such as t'
                      + 'xt or zdb.'
                        ;
            mandatory true ;
            case txt-type {
              description 'The txt type of configuration saving.'
                          ;
              leaf txt {
                description 'Configuration saved in txt type.'
                            ;
                type empty ;
              }
            }
            case zdb-type {
              description 'Configuration saved in zdb type.'
                          ;
              leaf zdb {
                description 'Configuration saved in zdb type.'
                            ;
                type empty ;
              }
            }
          }
        }
      }
      container startrun-download {
        description 'The operation of startrun download.'
                    ;
        choice copy-type {
          description 'The copy type of startrun download,such as local or remo'
                    + 'te.'
                      ;
          case local {
            description 'The local copy type of startrun download.'
                        ;
            container local {
              description 'The operation of local copy.'
                          ;
              leaf path {
                description 'Specify the local path of startrun download.'
                            ;
                type string {
                  length 1..159 ;
                }
                mandatory true ;
              }
            }
          }
          case remote {
            description 'The remote copy type of startrun download.'
                        ;
            container remote {
              description 'The operation of remote copy.'
                          ;
              choice transport-type {
                description 'Transport type'
                            ;
                mandatory true ;
                case ftp {
                  description 'The FTP copy type of startrun download.'
                              ;
                  leaf ftp {
                    description 'The FTP copy type of startrun download.'
                                ;
                    type empty ;
                  }
                }
                case sftp {
                  description 'The SFTP copy type of startrun download.'
                              ;
                  leaf sftp {
                    description 'The SFTP copy type of startrun download.'
                                ;
                    type empty ;
                  }
                }
              }
              choice copy-mode {
                description 'Specify the mode of file transmition.'
                            ;
                case dcn {
                  if-feature startrun-download-dcn ;
                  description 'To transmit file by DCN.'
                              ;
                  leaf dcn {
                    description 'DCN mode.'
                                ;
                    type empty ;
                  }
                }
                case vrf {
                  description 'To transmit file by VRF.'
                              ;
                  leaf vrf-name {
                    description 'Specify VRF name.'
                                ;
                    type string {
                      length 1..32 ;
                    }
                    mandatory true ;
                  }
                }
              }
              choice ip-address {
                description 'Specify the IP address.'
                            ;
                mandatory true ;
                case ipv4 {
                  description 'IPv4 address.'
                              ;
                  leaf ipv4 {
                    description 'IPv4 address.'
                                ;
                    type ncd:ipv4-address-none-zero ;
                  }
                }
                case ipv6 {
                  description 'IPv6 address.'
                              ;
                  leaf ipv6 {
                    description 'IPv6 address.'
                                ;
                    type ncd:ipv6-address ;
                  }
                }
              }
              leaf port {
                description 'Specify listen port.'
                            ;
                type uint16 {
                  range 1..65535 ;
                }
              }
              leaf username {
                description 'Specify username.'
                            ;
                type string {
                  length 1..65 ;
                }
                mandatory true ;
              }
              leaf password {
                description 'Specify password.'
                            ;
                type string {
                  length 1..128 ;
                }
                mandatory true ;
              }
              leaf path {
                description 'Specify the path of startrun download.'
                            ;
                type string {
                  length 1..159 ;
                }
                mandatory true ;
              }
            }
          }
        }
        leaf unzip {
          description 'Download file and uncompress it.'
                      ;
          type empty ;
          ncd:revise-date 2019-02-27 ;
        }
        ncd:revise-date 2018-09-04 ;
      }
    }
  }
  container state {
    config false ;
    container logic-modes {
      description 'Query logic mode info'
                  ;
      list logic-mode {
        description 'For query logic mode id. Query condition: (1) logic mode n'
                  + 'ame;(2)none for all.'
                    ;
        key logic-mode-name ;
        leaf logic-mode-name {
          description 'Logic mode name'
                      ;
          type string {
            length 1..32 ;
          }
        }
        leaf logic-mode-id {
          description 'Logic mode id'
                      ;
          type uint16 ;
        }
        list physical-mode {
          description 'For query physical mode id.'
                      ;
          key physical-mode-name ;
          leaf physical-mode-name {
            description 'Physical mode name'
                        ;
            type string ;
          }
          leaf physical-mode-id {
            description 'Physical mode id'
                        ;
            type uint16 ;
          }
          ncd:revise-date 2022-06-30 ;
        }
        ncd:select logic-mode-name ;
      }
    }
    ncd:revise-date 2022-01-21 ;
  }
}
