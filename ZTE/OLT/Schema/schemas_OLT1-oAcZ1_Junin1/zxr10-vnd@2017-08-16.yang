module zxr10-vnd {
  namespace urn:ietf:params:xml:ns:yang:zxr10-vnd ;
  prefix vnd ;
  revision 2017-08-16 {
    description 'Initial revision.'
                ;
    reference 'A YANG data model for VND resource profile'
              ;
  }
  container configuration {
    container zxr10-c600-vnd {
      container vnd-resource-objects {
        container vnd-resource-profile {
          list vnd-resource-profile-lists {
            description '"zxAnVndResourceProfileLists indexs include vnd-resour'
                      + 'ce-profile-name and vnd-resource-type"'
                        ;
            key 'vnd-resource-profile-name vnd-resource-type'
                ;
            unique 'vnd-resource-profile-name vnd-resource-type'
                   ;
            leaf vnd-resource-profile-name {
              description '"create VND resource profile name."'
                          ;
              type string {
                length 1..32 {
                  description 'The length of VND resource profile name is from '
                            + '1 to 32.'
                              ;
                }
              }
            }
            leaf vnd-resource-type {
              description '"VND Resource Type."'
                          ;
              type enumeration {
                enum vlan {
                  value 1 ;
                  description 'VND resource of vlan'
                              ;
                }
                enum igmp {
                  value 2 ;
                  description 'VND resource of igmp'
                              ;
                }
                enum mld {
                  value 3 ;
                  description 'VND resource of mld'
                              ;
                }
                enum mac {
                  value 4 ;
                  description 'VND resource of mac'
                              ;
                }
                enum vport {
                  value 5 ;
                  description 'VND resource of vport'
                              ;
                }
                enum onu {
                  value 6 ;
                  description 'VND resource of onu'
                              ;
                }
                enum 1:1vlan {
                  value 7 ;
                  description 'VND resource of vlan xconnect'
                              ;
                }
                enum service-port {
                  value 8 ;
                  description 'VND resource of sport'
                              ;
                }
                enum qos-cos-to-cos {
                  value 9 ;
                  description 'VND resource of qos cos-to-cos'
                              ;
                }
                enum qos-dscp-to-dscp {
                  value 10 ;
                  description 'VND resource of qos dscp-to-dscp'
                              ;
                }
                enum qos-dscp-to-cos {
                  value 11 ;
                  description 'VND resource of qos dscp-to-cos'
                              ;
                }
                enum acl-rule {
                  value 12 ;
                  description 'VND resource of acl rule'
                              ;
                }
                enum l2cp {
                  value 13 ;
                  description 'VND resource of l2cp'
                              ;
                }
                enum trafficPir {
                  value 14 ;
                  description 'VND resource of trafficPir'
                              ;
                }
                enum pppoe {
                  value 15 ;
                  description 'VND resource of pppoe'
                              ;
                }
                enum dhcpv4 {
                  value 16 ;
                  description 'VND resource of dhcpv4'
                              ;
                }
                enum dhcpv6 {
                  value 17 ;
                  description 'VND resource of dhcpv6'
                              ;
                }
                enum qos-queue-map {
                  value 18 ;
                   description 'VND resource of qos-queue-map'
                              ;
                }
                enum qos-traffic {
                  value 19 ;
                   description 'VND resource of qos-traffic'
                              ;
                }
                enum allDefault {
                  value 255 ;
                  description 'If enum name is 255, that means user only operat'
                            + 'e resource profile, include create and delete.'+"\n"
                            + 'Only creating or deleting VND resource profile, '
                            + 'no resource type.'
                              ;
                  reference 'If resource type is 255, that means creating or de'
                          + 'leting resource templates only.'
                            ;
                }
              }
            }
            leaf vnd-resource-upper-thresh {
              description '"VND resource number upper threshold. When vnd-resou'
                        + 'rce-type is vlan(1), the maximum value of vnd-resour'
                        + 'ce-upper-thresh is 4094. When vnd-resource-type is i'
                        + 'gmp(2) the maximum value of vnd-resource-upper-thres'
                        + 'h is 4096. When vnd-resource-type is mld(3) the maxi'
                        + 'mum value of vnd-resource-upper-thresh is 4096. When'
                        + ' vnd-resource-type is mac(4) the maximum value of vn'
                        + 'd-resource-upper-thresh is 1048576. When vnd-resourc'
                        + 'e-type is vport(5) the maximum value of vnd-resource'
                        + '-upper-thresh is 32768 in C600 and 65536 in C680. Wh'
                        + 'en vnd-resource-type is onu(6) the maximum value of '
                        + 'vnd-resource-upper-thresh is 32768 in C600 and 65536'
                        + ' in C680. When vnd-resource-type is vlanForwardingMo'
                        + 'de(7) the maximum value of vnd-resource-upper-thresh'
                        + ' is 32768. When vnd-resource-type is servicePort(8) '
                        + 'the maximum value of vnd-resource-upper-thresh is 13'
                        + '1072 in C600 and 262144 in C680. When vnd-resource-t'
                        + 'ype is qosCosToCos(9) the maximum value of vnd-resou'
                        + 'rce-upper-thresh is 239. When vnd-resource-type is q'
                        + 'osDscpToDscp(10) the maximum value of vnd-resource-u'
                        + 'pper-thresh is 238. The qosDscpToDscp and qosDscpToC'
                        + 'os prifile total number is 238. When vnd-resource-ty'
                        + 'pe is qosDscpToCos(11) the maximum value of vnd-reso'
                        + 'urce-upper-thresh is 238.The qosDscpToDscp and qosDs'
                        + 'cpToCos prifile total number is 238. When vnd-resour'
                        + 'ce-type is aclRule(12) the maximum value of vnd-reso'
                        + 'urce-upper-thresh is 8176. When vnd-resource-type is'
                        + ' l2cp(13) the maximum value of vnd-resource-upper-th'
                        + 'resh is 62.When zxAnVndResType is trafficPir(14) the'
                        + ' maximum value of zxAnVndResUpperThresh is 10000000.'
                        + 'When zxAnVndResType is qos-queue-map(18) the maximum'
                        + ' value of zxAnVndResUpperThresh is 16. When zxAnVndR'
                        + 'esType is qos-traffic(19) the maximum value of zxAnV'
                        + 'ndResUpperThresh is 1024.'
                        + '"'
                          ;
              type int32 ;
            }
          }
        }
        container vnd-resource-profile-bind {
          list vnd-resource-profile-bind-lists {
            description '"vnd-resource-profile-bind-lists index is vnd-name"'
                        ;
            key vnd-name ;
            unique vnd-name ;
            leaf vnd-name {
              description '"VND Name."'
                          ;
              type string {
                length 1..31 {
                  description '"VND name."'
                              ;
                }
              }
            }
            leaf vnd-bind-resource-profile {
              description '"VND resource profile name."'
                          ;
              type string {
                length 1..32 ;
              }
            }
          }
        }
      }
    }
  }
  container state {
    config false ;
    container vnd-curr-resource-objects {
      container vnd-curr-resource-stats {
        list vnd-curr-resource-lists {
          key vnd-resource-type ;
          unique vnd-resource-type ;
          leaf vnd-resource-type {
            description '"VND Resource Type."'
                        ;
            type enumeration {
              enum vlan {
                value 1 ;
              }
              enum igmp {
                value 2 ;
              }
              enum mld {
                value 3 ;
              }
              enum mac {
                value 4 ;
              }
              enum vport {
                value 5 ;
              }
              enum onu {
                value 6 ;
              }
              enum 1:1vlan {
                value 7 ;
              }
              enum service-port {
                value 8 ;
              }
              enum qos-cos-to-cos {
                value 9 ;
              }
              enum qos-dscp-to-dscp {
                value 10 ;
              }
              enum qos-dscp-to-cos {
                value 11 ;
              }
              enum acl-rule {
                value 12 ;
              }
              enum l2cp {
                value 13 ;
              }
              enum trafficPir {
                value 14 ;
              }
              enum pppoe {
                value 15 ;
              }
              enum dhcpv4 {
                value 16 ;
              }
              enum dhcpv6 {
                value 17 ;
              }
              enum qos-queue-map {
                value 18 ;
              }
              enum qos-traffic {
                value 19 ;
              }
            }
          }
          leaf vnd-curr-resource-stats-usednum {
            description '"Current Used Resources."'
                        ;
            type int32 ;
          }
          leaf vnd-curr-resource-stats-availablenum {
            description '"Current Available Resources."'
                        ;
            type int32 ;
          }
        }
      }
    }
    container vnd-resource-stats {
      list vnd-resource-stats-lists {
        key 'vnd-name vnd-resource-type'
            ;
        unique 'vnd-name vnd-resource-type'
               ;
        leaf vnd-name {
          description '"VND Name."'
                      ;
          type string {
            length 1..31 ;
          }
        }
        leaf vnd-resource-type {
          description '"VND Resource Type."'
                      ;
          type enumeration {
            enum vlan {
              value 1 ;
            }
            enum igmp {
              value 2 ;
            }
            enum mld {
              value 3 ;
            }
            enum mac {
              value 4 ;
            }
            enum vport {
              value 5 ;
            }
            enum onu {
              value 6 ;
            }
            enum 1:1vlan {
              value 7 ;
            }
            enum service-port {
              value 8 ;
            }
            enum qos-cos-to-cos {
              value 9 ;
            }
            enum qos-dscp-to-dscp {
              value 10 ;
            }
            enum qos-dscp-to-cos {
              value 11 ;
            }
            enum acl-rule {
              value 12 ;
            }
            enum l2cp {
              value 13 ;
            }
            enum trafficPir {
              value 14 ;
            }
            enum pppoe {
              value 15 ;
            }
            enum dhcpv4 {
              value 16 ;
            }
            enum dhcpv6 {
              value 17 ;
            }
            enum qos-queue-map {
              value 18 ;
            }
            enum qos-traffic {
              value 19 ;
            }
          }
        }
        leaf vnd-resourcestats-totalnum {
          description '"Total resources. This object is valid only in VND 0."'
                      ;
          type int32 ;
        }
        leaf vnd-resourcestats-usednum {
          description '"Used Resources."'
                      ;
          type int32 ;
        }
        leaf vnd-resourcestats-availablenum {
          description '"Available Resources."'
                      ;
          type int32 ;
        }
      }
    }
  }
}
