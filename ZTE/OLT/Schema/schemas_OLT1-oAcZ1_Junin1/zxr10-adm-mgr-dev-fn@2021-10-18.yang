module zxr10-adm-mgr-dev-fn {
  namespace 'http://www.zte.com.cn/zxr10/netconf/schema/rosng/adm-mgr-dev-fn'
            ;
  prefix adm-mgr-dev-fn ;
  yang-version 1 ;
  import zxr10-adm-mgr {
    prefix adm-mgr ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  revision 2021-10-18 {
    description "V6000(vRouter/CDB),MSE(M6000) project support the range of lea"
              + "f node 'password-duration' from 0 to 360"
                ;
  }
  revision 2021-09-27 {
    description "65V5,6700 project support the range of leaf node 'password-dur"
              + "ation' from 0 to 360"
                ;
  }
  revision 2021-07-01 {
    description "SWITCH(99X/5960X) 'password-duration' do not support 1-360"
                ;
  }
  revision 2021-02-18 {
    description "15K, vBRAS-C and T8000 project support the range of leaf node "
              + "'password-duration' from 0 to 360"
                ;
  }
  revision 2019-04-22 {
    description "MW(NR8000) project need support the range of leaf node 'passwo"
              + "rd-duration' from 0 to 360"
                ;
  }
  revision 2019-01-03 {
    description "OTN(7000/8700/9700/M721) project need support the range of lea"
              + "f node 'password-duration' from 0 to 360"
                ;
  }
  revision 2018-03-26 {
    description "C600 project need support the range of leaf node 'password-dur"
              + "ation' from 0 to 360"
                ;
  }
  deviation '/adm-mgr:configuration/adm-mgr:adm-mgr/adm-mgr:usernames/adm-mgr:u'
          + 'sername/adm-mgr:password-duration'
            {
    description 'Configuration password validity period'
                ;
    deviate replace {
      type uint16 {
        range 0..360 ;
      }
    }
  }
}
