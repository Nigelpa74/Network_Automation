module zte-an-qos-trafficprf {
    namespace 'http://www.zte.com.cn/zxr10/netconf/schema/rosng/zx-qos-trafficprf';
    prefix zx-qos-trafficprf;
    import zxr10-netconf-defs {
        prefix ncd;
        revision-date 2017-08-15;
    }
    organization "ZTE Corporation";
    contact "Luo Feima     ZTE Corporation
                    Mail : luo.feima@zte.com.cn
                    Tel  : +86-21-68896470.";
    description "This MIB defines ZTE Access Node QoS Traffic managed objects.";
    revision 2011-09-22 {
        description "Modification of some spelling error for this MIB module.";
    }
    revision 2011-08-25 {
        description "Modification of the descriptions for this MIB module.";
    }
    revision 2011-08-19 {
        description "Modification of the comments for this MIB module.";
    }
    revision 2011-07-05 {
        description "Conformance supplement for this MIB module.";
    }
    revision 2010-10-28 {
        description "Initial version of this MIB module.";
    }
    container zxAnQosTraffic {
        description "";
        container zxAnQosTrafficObjects {
            description "";
            container zxAnQosTrafficPrfTable {
                description "This table contains information about traffic controlling.
                             An entry in this table reflects a profile defined which can be
                             used to configure an interface.";
                list zxAnQosTrafficPrfEntry {
                    description "zxAnQosTrafficPrfTable entry.
                                 
                                 The multi-variables binding rule should be complied with when a
                                 manager creates an entry. According to this rule, all the related
                                 mib variables must be included in one SNMP set operation.
                                 
                                 There are two types of variables: mandatory and optional.
                                 All of the mandatory variables must be included in one SNMP set 
                                 operation. Optional variables may be included in one SNMP set 
                                 operation with the mandatory variables, but must not be used alone.
                                 
                                 To create an entry, the mandatory and optional variables are as
                                 follows:
                                 mandatory: zxAnQosTrafficPrfCir, zxAnQosTrafficPrfCbs, 
                                 zxAnQosTrafficPrfPir, zxAnQosTrafficPrfPbs,
                                 zxAnQosTrafficPrfDiscardMode, zxAnQosTrafficPrfColorMode,
                                 zxAnQosTrafficPrfPolicerType,
                                 zxAnQosTrafficPrfCouplingEn,
                                 zxAnQosTrafficPrfRowStatus.
                                 optional : none.
                                 
                                 To delete an entry, only zxAnQosTrafficPrfRowStatus is needed in
                                 one SNMP setOperation.
                                 
                                 After an entry is created, variables zxAnQosTrafficPrfCir, 
                                 zxAnQosTrafficPrfCbs, zxAnQosTrafficPrfPir, zxAnQosTrafficPrfPbs, 
                                 zxAnQosTrafficPrfDiscardMode, zxAnQosTrafficPrfColorMode,
                                 zxAnQosTrafficPrfPolicerType and zxAnQosTrafficPrfCouplingEn
                                 can be modified alone.
                                 
                                 Make sure that zxAnQosTrafficPrfPir is not less than 
                                 zxAnQosTrafficPrfCir, and zxAnQosTrafficPrfPbs is not less than
                                 zxAnQosTrafficPrfCbs when to create or modify an entry. ";
                    max-elements 256;
                    key "zxAnQosTrafficPrfName";
                    leaf zxAnQosTrafficPrfName {
                        description "Traffic profile name which can be applied to an interface.";
                        type string {
                            length 1..32;
                        }
                    }
                    leaf zxAnQosTrafficPrfCir {
                        description "Committed Information Rate(CIR) in kbps.";
                        type enumeration {
                        }
                    }
                    leaf zxAnQosTrafficPrfCbs {
                        description "Committed Burst Size(CBS) in kbytes.";
                        type enumeration {
                        }
                    }
                    leaf zxAnQosTrafficPrfPir {
                        description "Peak Information Rate(PIR) in kbps.";
                        type enumeration {
                        }
                    }
                    leaf zxAnQosTrafficPrfPbs {
                        description "Peak Burst Size(PBS) in kbyte.";
                        type enumeration {
                        }
                    }
                    leaf zxAnQosTrafficPrfDiscardMode {
                        description "The discard mode is used when the traffic exceeds the limit.
                                     noDistinction(1)    -- discard extra flow equally.
                                     lowPriorityFirst(2) -- discard low priority flow firstly.";
                        type enumeration {
                            enum noDistinction {
                                value 1;
                                description "";
                            }
                            enum lowPriorityFirst {
                                value 2;
                                description "";
                            }
                        }
                    }
                    leaf zxAnQosTrafficPrfColorMode {
                        description "Color mode.
                                     aware(1)  -- color aware mode.
                                     blind(2)  -- color blind mode.
                                     ";
                        type enumeration {
                            enum aware {
                                value 1;
                                description "";
                            }
                            enum blind {
                                value 2;
                                description "";
                            }
                        }
                        default blind;
                    }
                    leaf zxAnQosTrafficPrfPolicerType {
                        description "Policer type.";
                        type enumeration {
                            enum enhancedMef {
                                value 1;
                                description "";
                            }
                            enum mef {
                                value 2;
                                description "";
                            }
                            enum rfc {
                                value 3;
                                description "";
                            }
                            enum multipleThresholds {
                                value 4;
                                description "";
                            }
                        }
                        default enhancedMef;
                    }
                    leaf zxAnQosTrafficPrfCouplingEn {
                        description "Enables or disables the coupling enabling.";
                        type enumeration {
                            enum enabled {
                                value 1;
                                description "";
                            }
                            enum disabled {
                                value 2;
                                description "";
                            }
                        }
                        default enabled;
                    }
                }
            }
        }
    }
}
