module zxr10-test {
  namespace 'http://www.zte.com.cn/zxr10/netconf/schema/rosng/test'
            ;
  prefix GponOnu ;
  import zxr10-netconf-defs {
    prefix ncd ;
    revision-date 2017-03-30 ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  revision 2017-08-23 ;
  container configuration {
    list onulist {
      key 'ifIndex zxAnPonOnuIndex'
          ;
      unique zxAnPonOnuIndex ;
      leaf ifIndex {
        type uint32 ;
      }
      leaf zxAnPonOnuIndex {
        type uint32 ;
      }
      leaf zxAnGponOnuMgmtTypeName {
        type string ;
      }
      leaf zxAnGponOnuMgmtName {
        type string ;
      }
      leaf zxAnGponOnuMgmtDesc {
        type string {
          length 0..200 ;
        }
      }
      leaf zxAnGponOnuMgmtOpticalLineSn {
        type string {
          length 0..64 ;
        }
      }
      leaf zxAnGponOnuMgmtRegMode {
        type enumeration {
          enum regModeSn {
            value 1 ;
          }
          enum regModePwd {
            value 2 ;
          }
          enum regModeSnPlusPwd {
            value 3 ;
          }
          enum regModeRegisterId {
            value 4 ;
          }
          enum regModeRegisterIdPlus8021x {
            value 5 ;
          }
          enum regModeRegisterIdPlusMutual {
            value 6 ;
          }
          enum regModeHexPwd {
            value 7 ;
          }
          enum regModeSnPlusHexPwd {
            value 8 ;
          }
          enum regModeLoid {
            value 9 ;
          }
          enum regModeLoidPlusPwd {
            value 10 ;
          }
          enum regModeSnPlusRegisterId {
            value 11 ;
          }
          enum regModePsk {
            value 12 ;
          }
        }
      }
      leaf zxAnGponOnuMgmtSn {
        type string {
          length 12 ;
        }
      }
      leaf zxAnGponOnuMgmtLoid {
        type string {
          length 0..24 ;
        }
      }
      leaf zxAnGponOnuMgmtPwd {
        type string {
          length 0..10 ;
        }
      }
      leaf zxAnGponOnuMgmtTargetStatus {
        type enumeration {
          enum deactive {
            value 1 ;
          }
          enum omccReady {
            value 2 ;
          }
        }
      }
      leaf zxAnGponOnuMgmtVportMode {
        type enumeration {
          enum gemport {
            value 1 ;
          }
          enum manual {
            value 3 ;
          }
        }
      }
      leaf zxAnGponOnuMgmtDbaMode {
        type enumeration {
          enum sr {
            value 1 ;
          }
          enum nsr {
            value 2 ;
          }
          enum hybrid {
            value 3 ;
          }
        }
      }
      leaf zxAnGponOnuMgmtOmccBwPrfName {
        type string {
          length 0..64 ;
        }
      }
      leaf zxAnGponOnuMgmtEnableWithSn {
        type enumeration {
          enum disabled {
            value 2 ;
          }
          enum enabled {
            value 1 ;
          }
        }
      }
      leaf zxAnGponOnuMgmtAuthPassCtrl {
        type int32 {
          range 0..10 ;
        }
      }
      leaf zxAnGponOnuMgmtUsFecEnable {
        type enumeration {
          enum enabled {
            value 1 ;
          }
          enum disabled {
            value 2 ;
          }
          enum auto {
            value 3 ;
          }
        }
      }
      leaf zxAnGponOnuMgmtReonlineAuthInfo {
        type enumeration {
          enum snAndAuthValue {
            value 1 ;
          }
          enum sn {
            value 2 ;
          }
          enum authValue {
            value 3 ;
          }
        }
      }
      leaf zxAnGponOnuMgmtRegistrationInfo {
        type string {
          length 0..255 ;
        }
      }
      leaf zxAnGponOnuMgmtOmccEncryptEnable {
        type enumeration {
          enum enbaled {
            value 1 ;
          }
          enum disabled {
            value 2 ;
          }
        }
      }
      leaf zxAnGponOnuMgmtBerInterval {
        type int32 {
          range 1..536870911 ;
        }
      }
      leaf zxAnGponOnuMgmtToDEnable {
        type enumeration {
          enum enabled {
            value 1 ;
          }
          enum disabled {
            value 2 ;
          }
        }
      }
      leaf zxAnGponOnuMcastEncryptEnable {
        type enumeration {
          enum enabled {
            value 1 ;
          }
          enum disabled {
            value 2 ;
          }
        }
      }
      leaf zxAnGponOnuMgmtChannelId {
        type int32 {
          range 0..8 ;
        }
        default 0 ;
      }
      leaf zxAnGponOnuMgmtLoidPwd {
        type string {
          length 0..12 ;
        }
      }
    }
    list onuBindList {
      key 'ifIndex onuIndex onuProfileType'
          ;
      leaf ifIndex {
        type int32 ;
      }
      leaf onuIndex {
        type int32 ;
      }
      leaf onuProfileName {
        type string ;
      }
      leaf onuProfileType {
        type enumeration {
          enum onuLinePrf {
            value 1 ;
          }
          enum onuServicePrf {
            value 2 ;
          }
        }
      }
    }
    list tcontprf {
      key zxAnGponSrvBwPrfName ;
      leaf zxAnGponSrvBwPrfName {
        type string {
          length 1..64 ;
        }
      }
      leaf zxAnGponSrvBwPrfFixed {
        type int32 {
          range 0..9953280 ;
        }
      }
      leaf zxAnGponSrvBwPrfAssured {
        type int32 {
          range 0..9953280 ;
        }
      }
      leaf zxAnGponSrvBwPrfMaximum {
        type int32 {
          range 0..9953280 ;
        }
      }
      leaf zxAnGponSrvBwPrfType {
        type int32 {
          range 1..5 ;
        }
      }
      leaf zxAnGponSrvBwPrfPriority {
        type int32 {
          range 0..4 ;
        }
      }
      leaf zxAnGponSrvBwPrfWeight {
        type int32 {
          range 0..1000 ;
        }
      }
    }
    list tcontlist {
      key 'ifIndex zxAnPonOnuIndex zxAnGponOnuTcontIndex'
          ;
      unique zxAnGponOnuTcontIndex ;
      leaf ifIndex {
        type int32 ;
      }
      leaf zxAnPonOnuIndex {
        type int32 ;
      }
      leaf zxAnGponOnuTcontIndex {
        type int32 ;
      }
      leaf zxAnGponSrvTcontAllocId {
        type int32 {
          range 0..4095 ;
        }
      }
      leaf zxAnGponSrvTcontDbaGapMode {
        type enumeration {
          enum mode0 {
            value 1 ;
          }
          enum mode1 {
            value 2 ;
          }
          enum mode2 {
            value 3 ;
          }
          enum mode3 {
            value 4 ;
          }
          enum default {
            value 11 ;
          }
        }
      }
      leaf zxAnGponSrvTcontName {
        type string ;
      }
      leaf zxAnGponSrvTcontBwPrfName {
        type string ;
      }
    }
    list gemportlist {
      key 'ifIndex zxAnPonOnuIndex zxAnGponOnuGemportIndex'
          ;
      unique zxAnGponOnuGemportIndex ;
      leaf ifIndex {
        type int32 ;
      }
      leaf zxAnPonOnuIndex {
        type int32 ;
      }
      leaf zxAnGponOnuGemportIndex {
        type int32 ;
      }
      leaf zxAnGponSrvGemPortName {
        type string ;
      }
      leaf zxAnGponSrvGemPortTcontIndex {
        type int32 ;
      }
      leaf zxAnGponSrvGemPortPortId {
        type int32 ;
      }
      leaf zxAnGponSrvGemPortQueueOfTcont {
        type int32 {
          range 0..7 ;
        }
        default 0 ;
      }
      leaf zxAnGponSrvGemPortEnable {
        type enumeration {
          enum enabled {
            value 1 ;
          }
          enum disabled {
            value 2 ;
          }
        }
        default enabled ;
      }
      leaf zxAnGponSrvGemPortEncrypt {
        type enumeration {
          enum downstreamEncrypt {
            value 1 ;
          }
          enum noEncrypt {
            value 2 ;
          }
          enum bothDirectEncrypt {
            value 3 ;
          }
        }
        default noEncrypt ;
      }
    }
    list tcontSchPrf {
      key zxAnGponRmTrffcSchedPrfName ;
      leaf zxAnGponRmTrffcSchedPrfName {
        type string {
          length 1..64 ;
        }
      }
      leaf zxAnGponRmTrffcSchedMode {
        type int32 ;
      }
      leaf zxAnGponRmTrffcSchedQueueMap0 {
        type int32 ;
      }
      leaf zxAnGponRmTrffcSchedQueueMap1 {
        type int32 ;
      }
      leaf zxAnGponRmTrffcSchedQueueMap2 {
        type int32 ;
      }
      leaf zxAnGponRmTrffcSchedQueueMap3 {
        type int32 ;
      }
      leaf zxAnGponRmTrffcSchedQueueMap4 {
        type int32 ;
      }
      leaf zxAnGponRmTrffcSchedQueueMap5 {
        type int32 ;
      }
      leaf zxAnGponRmTrffcSchedQueueMap6 {
        type int32 ;
      }
      leaf zxAnGponRmTrffcSchedQueueMap7 {
        type int32 ;
      }
    }
    list onuTcontSchPrf {
      key 'ifIndex zxAnPonOnuIndex zxAnGponRmTcontIndex'
          ;
      leaf ifIndex {
        type int32 ;
      }
      leaf zxAnPonOnuIndex {
        type int32 ;
      }
      leaf zxAnGponRmTcontIndex {
        type int32 ;
      }
      leaf gponRmTcontQueueSchedPrfName {
        type string {
          length 1..64 ;
        }
      }
    }
    list ponList {
      key ifIndex ;
      leaf ifIndex {
        type int32 ;
      }
      leaf zxAnGponSrvPonIdFormat {
        type int32 ;
      }
      leaf zxAnGponSrvPonId {
        type string {
          length 0..7 ;
        }
      }
    }
    list vportlist {
      key 'ifIndex zxAnPonOnuIndex zxAnGponSrvVportIndex'
          ;
      leaf ifIndex {
        type uint32 ;
      }
      leaf zxAnPonOnuIndex {
        type uint32 ;
      }
      leaf zxAnGponSrvVportIndex {
        type int32 ;
      }
      leaf zxAnGponSrvVportName {
        type string ;
      }
      leaf zxAnGponSrvVportMapType {
        type enumeration {
          enum cos {
            value 1 ;
          }
          enum vlan {
            value 2 ;
          }
          enum cos+vlan {
            value 3 ;
          }
          enum 1:1 {
            value 4 ;
          }
        }
      }
    }
    list vportmaplist {
      key 'ifIndex zxAnPonOnuIndex zxAnGponSrvVportIndex zxAnGponSrvGemportInde'
        + 'x zxAnGponSrvVportmapCos zxAnGponSrvVportmapVlan'
          ;
      leaf ifIndex {
        type uint32 ;
      }
      leaf zxAnPonOnuIndex {
        type uint32 ;
      }
      leaf zxAnGponSrvVportIndex {
        type int32 ;
      }
      leaf zxAnGponSrvGemportIndex {
        type int32 ;
      }
      leaf zxAnGponSrvVportmapCos {
        type int32 {
          range 0..7 ;
        }
      }
      leaf zxAnGponSrvVportmapVlan {
        type int32 ;
      }
    }
    list rmservice {
      key 'ifIndex zxAnPonOnuIndex zxAnGponRmServiceName'
          ;
      leaf ifIndex {
        type uint32 ;
      }
      leaf zxAnPonOnuIndex {
        type uint32 ;
      }
      leaf zxAnGponRmServiceName {
        type string {
          length 1..32 ;
        }
      }
      leaf zxAnGponRmServiceGemPort {
        type int32 ;
      }
      leaf zxAnGponRmServiceMapVidString {
        type string {
          length 0..64 ;
        }
      }
      leaf zxAnGponRmServiceMapType {
        type int32 ;
      }
      leaf zxAnGponRmServiceUntag {
        type int32 ;
      }
    }
    list onuAdminState {
      key 'ifIndex zxAnPonOnuIndex'
          ;
      leaf ifIndex {
        type uint32 ;
      }
      leaf zxAnPonOnuIndex {
        type uint32 ;
      }
      leaf zxAnGponSrvOnuAdminStatus {
        type enumeration {
          enum enabled {
            value 1 ;
          }
          enum disabled {
            value 2 ;
          }
        }
      }
    }
    list rmmvlan {
      key 'ifIndex zxAnPonOnuIndex zxAnGponRmMVid'
          ;
      leaf ifIndex {
        type uint32 ;
      }
      leaf zxAnPonOnuIndex {
        type uint32 ;
      }
      leaf zxAnGponRmMVid {
        type uint32 ;
      }
    }
    list epononulist {
      key 'ifIndex zxAnPonOnuIndex'
          ;
      unique zxAnPonOnuIndex ;
      leaf ifIndex {
        type uint32 ;
      }
      leaf zxAnPonOnuIndex {
        type uint32 ;
      }
      leaf onuType {
        type string ;
      }
      leaf onuAdminState {
        type enumeration {
          enum enabled {
            value 1 ;
          }
          enum disabled {
            value 2 ;
          }
          enum auto {
            value 3 ;
          }
        }
      }
      leaf onuAuthMACAddress {
        type ncd:mac-address-none-zero ;
      }
      leaf onuAuthLoid {
        type string {
          length 0..24 ;
        }
      }
      leaf onuAuthPassword {
        type string {
          length 0..10 ;
        }
      }
    }
    list epononuslaprofile {
      key profileName ;
      leaf profileName {
        type string {
          length 1..64 ;
        }
      }
      leaf upBwProfileFixedBw {
        type int32 {
          range 0..9953280 ;
        }
      }
      leaf upBwProfileAssuredBw {
        type int32 {
          range 0..9953280 ;
        }
      }
      leaf upBwProfileMaximumBw {
        type int32 {
          range 0..9953280 ;
        }
      }
      leaf upBwProfilePri {
        type int32 {
          range 0..4 ;
        }
      }
    }
    list epononuslabind {
      key 'ifIndex zxAnPonOnuIndex zxAnGponOnuVportIndex'
          ;
      leaf ifIndex {
        type uint32 ;
      }
      leaf zxAnPonOnuIndex {
        type uint32 ;
      }
      leaf bindSlaProfileName {
        type string {
          length 1..64 ;
        }
      }
      leaf zxAnGponOnuVportIndex {
        type int32 ;
      }
    }
  }
  container state {
    config false ;
    list onuStatus {
      key 'ifIndex zxAnPonOnuIndex'
          ;
      unique zxAnPonOnuIndex ;
      leaf ifIndex {
        type uint32 ;
      }
      leaf zxAnPonOnuIndex {
        type uint32 ;
      }
      leaf zxAnGponSrvOnuPhaseStatus {
        type enumeration {
          enum logging {
            value 1 ;
          }
          enum los {
            value 2 ;
          }
          enum syncMib {
            value 3 ;
          }
          enum working {
            value 4 ;
          }
          enum dyingGasp {
            value 5 ;
          }
          enum authFailed {
            value 6 ;
          }
          enum offline {
            value 7 ;
          }
          enum unknown {
            value 0 ;
          }
        }
      }
    }
    list tcontOper {
      key 'ifIndex zxAnPonOnuIndex zxAnGponOnuTcontIndex'
          ;
      unique zxAnGponOnuTcontIndex ;
      leaf ifIndex {
        type uint32 ;
      }
      leaf zxAnPonOnuIndex {
        type uint32 ;
      }
      leaf zxAnGponOnuTcontIndex {
        type uint32 ;
      }
      leaf zxAnGponSrvTcontAllocId {
        type int32 {
          range 0..4095 ;
        }
      }
      leaf zxAnGponSrvTcontName {
        type string ;
      }
    }
    list gemportoper {
      key 'ifIndex zxAnPonOnuIndex zxAnGponOnuGemportIndex'
          ;
      unique zxAnGponOnuGemportIndex ;
      leaf ifIndex {
        type int32 ;
      }
      leaf zxAnPonOnuIndex {
        type int32 ;
      }
      leaf zxAnGponOnuGemportIndex {
        type int32 ;
      }
      leaf zxAnGponSrvGemPortName {
        type string ;
      }
      leaf zxAnGponSrvGemPortPortId {
        type int32 ;
        default 0 ;
      }
    }
  }
}
