module bbf-hardware-transceiver-identities {
  yang-version 1.1;

  namespace "urn:bbf:yang:bbf-hardware-transceiver-identities";

  prefix bbf-hw-xcvr-id;

  organization
    "Broadband Forum <https://www.broadband-forum.org>
     Common YANG Project Stream";

  contact
    "Comments or questions about this Broadband Forum YANG module
     should be directed to <mailto:help@broadband-forum.org>.

     Editor:      

     Editor:      
     
     PS Leader:   Michael Shaffer, Nokia
                  <mailto:michael.shaffer@nokia.com>

     PS Leader:   William Lupton, Broadband Forum
                  <mailto:wlupton@broadband-forum.org>";

  description
    "This module contains a collection of YANG definitions for 
     supporting the Broadband Forum requirements on hardware 
     management as applicable to access network equipment. 
     As such, this module is specific to access network equipment 
     (e.g., BBF-specified Access Nodes and FTTdp DPUs).

     Specifically, this module defines identities used in the 
     management of compact transceivers.
    
     Copyright (c) 2017, Broadband Forum
     All rights reserved.

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383; see
     the TR itself for full legal notices.";

  revision 2017-04-25 {
    description
      "Initial revision.
       * Approval Date:    see revision date above.
       * Publication Date: yyyy-mm-dd.";
    reference
      "TR-383: Common YANG Modules
               <https://www.broadband-forum.org/technical/download/
                        TR-383.pdf>";
  }

  // Alarm/warning flags
  identity alarm-warning {
    description
      "Base identity for the alarm and warning flags of the
       transceiver.";
  }
  
  identity transceiver-alarm-warning {
    base alarm-warning;
    description
      "Base identity for the basic alarm and warning flags of the
       transceiver.";
  }
  
  identity temperature-high {
    base transceiver-alarm-warning;
    description
      "Present when internal temperature has exceeded the 
       high level threshold.";
  }
  
  identity temperature-low {
    base transceiver-alarm-warning;
    description
      "Present when internal temperature has dropped below the 
       low level threshold.";
  }
  
  identity supply-voltage-high {
    base transceiver-alarm-warning;
    description
      "Present when internal supply voltage has exceeded the 
       high level threshold.";
  }
  
  identity supply-voltage-low {
    base transceiver-alarm-warning;
    description
      "Present when internal supply voltage has dropped below 
       the low level threshold.";
  }
  
  identity link-alarm-warning {
    base alarm-warning;
    description
      "Base identity for the physical links of alarm and warning flags
       of the transceiver.";
  }

  identity tx-bias-high {
    base link-alarm-warning;
    description
      "Present when TX bias current has exceeded the high 
       level threshold.";
  }
  
  identity tx-bias-low {
    base link-alarm-warning;
    description
      "Present when TX bias current has dropped below the low 
       level threshold.";
  }
  
  identity tx-power-high {
    base link-alarm-warning;
    description
      "Present when TX output power has exceeded the high 
       level threshold.";
  }
  
  identity tx-power-low {
    base link-alarm-warning;
    description
      "Present when TX output power has dropped below the low 
       level threshold.";
  }
  
  identity rx-power-high {
    base link-alarm-warning;
    description
      "Present when RX output power has exceeded the high 
       level threshold.";
  }
  
  identity rx-power-low {
    base link-alarm-warning;
    description
      "Present when RX output power has dropped below the low 
       level threshold.";
  }
  
  identity laser-temperature-high {
    base link-alarm-warning;
    description
      "Present when laser temperature has exceeded the high 
       level threshold.";
  }
  
  identity laser-temperature-low {
    base link-alarm-warning;
    description
      "Present when laser temperature has dropped below the low 
       level threshold.";
  }

  identity tec-current-high {
    base link-alarm-warning;
    description
      "Present when Thermoelectric Cooler (TEC) current has exceeded 
       the high level threshold.";
  }
  
  identity tec-current-low {
    base link-alarm-warning;
    description
      "Present when Thermoelectric Cooler (TEC) current has exceeded 
       the low level threshold.";
  }



  //Physical Device Identifiers
  identity physical-device {
    description
      "Identifies the physical device.";
    reference
      "SFF-8472 Revision 12.2, Section 5.1 - Physical Device 
       Identifier Values";
  }
  
  identity unknown-physical-device {
    base physical-device;
    description
      "Unknown or unspecified.";
    reference
      "SFF-8472 Revision 12.2, Table 5-1, Value 00h;
       SFF-8024 Revision 4.1, Table 4-1, Value 04h";
  }
  
  identity gbic {
    base physical-device;
    description
      "GBIC.";
    reference
      "SFF-8472 Revision 12.2, Table 5-1, Value 01h;
       SFF-8024 Revision 4.1, Table 4-1, Value 04h";
  }
  
  identity sff {
    base physical-device;
    description
      "Module/connector soldered to a motherboard (using SFF-8472).";
    reference
      "SFF-8472 Revision 12.2, Table 5-1, Value 02h;
       SFF-8024 Revision 4.1, Table 4-1, Value 04h";
  }

  identity sfp {
    base physical-device;
    description
      "SFP/SFP+/SFP28.";
    reference
      "SFF-8472 Revision 12.2, Table 5-1, Value 03h;
       SFF-8024 Revision 4.1, Table 4-1, Value 04h";
  }
  
  identity xbi-300-pin {
    base physical-device;
    description
      "300 pin XBI.";
    reference
      "SFF-8024 Revision 4.1, Table 4-1, Value 04h";
  }
  
  identity xenpak {
    base physical-device;
    description
      "XENPAK.";
    reference
      "SFF-8024 Revision 4.1, Table 4-1, Value 05h";
  }
  
  identity xfp {
    base physical-device;
    description
      "XFP.";
    reference
      "SFF-8024 Revision 4.1, Table 4-1, Value 06h";
  }
  
  identity xff {
    base physical-device;
    description
      "XFF.";
    reference
      "SFF-8024 Revision 4.1, Table 4-1, Value 07h";
  }
  
  identity xfp-e {
    base physical-device;
    description
      "XFP-E.";
    reference
      "SFF-8024 Revision 4.1, Table 4-1, Value 08h";
  }

  identity xpak {
    base physical-device;
    description
      "XPAK.";
    reference
      "SFF-8024 Revision 4.1, Table 4-1, Value 09h";
  }
  
  identity x2 {
    base physical-device;
    description
      "X2.";
    reference
      "SFF-8024 Revision 4.1, Table 4-1, Value 0Ah";
  }
  
  identity dwdm-sfp {
    base physical-device;
    description
      "DWDM-SFP/SFP+ (not using SFF-8472).";
    reference
      "SFF-8024 Revision 4.1, Table 4-1, Value 0Bh";
  }
  
  identity qsfp {
    base physical-device;
    description
      "QSFP (INF-8438).";
    reference
      "SFF-8024 Revision 4.1, Table 4-1, Value 0Ch";
  }
  
  identity qsfp-plus-or-later {
    base physical-device;
    description
      "QSFP+ or later (SFF-8436, SFF-8635, SFF-8665, SFF-8685
       et al).";
    reference
      "SFF-8024 Revision 4.1, Table 4-1, Value 0Dh";
  }
  
  identity cxp-or-later {
    base physical-device;
    description
      "CXP or later.";
    reference
      "SFF-8024 Revision 4.1, Table 4-1, Value 0Eh";
  }
  
  identity shielded-mini-multilane-hd-4x  {
    base physical-device;
    description
      "Shielded Mini Multilane HD 4x.";
    reference
      "SFF-8024 Revision 4.1, Table 4-1, Value 0Fh";
  }
  
  identity shielded-mini-multilane-hd-8x  {
    base physical-device;
    description
      "Shielded Mini Multilane HD 8x.";
    reference
      "SFF-8024 Revision 4.1, Table 4-1, Value 10h";
  }
  
  identity qsfp28-or-later {
    base physical-device;
    description
      "QSFP28 or later (SFF-8665).";
    reference
      "SFF-8024 Revision 4.1, Table 4-1, Value 11h";
  }
  
  identity cxp2-or-later {
    base physical-device;
    description
      "CXP2 (aka CXP28) or later.";
    reference
      "SFF-8024 Revision 4.1, Table 4-1, Value 12h";
  }
  
  identity cdfp-style1-style2 {
    base physical-device;
    description
      "CDFP (Style 1/Style 2).";
    reference
      "SFF-8024 Revision 4.1, Table 4-1, Value 13h";
  }
  
  identity shielded-mini-multilane-hd-4x-fanout-cable  {
    base physical-device;
    description
      "Shielded Mini Multilane HD 4x Fanout Cable.";
    reference
      "SFF-8024 Revision 4.1, Table 4-1, Value 14h";
  }

  identity shielded-mini-multilane-hd-8x-fanout-cable  {
    base physical-device;
    description
      "Shielded Mini Multilane HD 8x Fanout Cable.";
    reference
      "SFF-8024 Revision 4.1, Table 4-1, Value 15h";
  }
  
  identity cdfp-style3 {
    base physical-device;
    description
      "CDFP (Style 3).";
    reference
      "SFF-8024 Revision 4.1, Table 4-1, Value 16h";
  }
  
  identity micro-qsfp {
    base physical-device;
    description
      "Micro QSFP.";
    reference
      "SFF-8024 Revision 4.1, Table 4-1, Value 17h";
  }
  
  identity qsfp-dd {
    base physical-device;
    description
      "QSFP-DD Double Density 8X Pluggable Transceiver (INF-8628).";
    reference
      "SFF-8024 Revision 4.1, Table 4-1, Value 18h";
  }
  
  identity vendor-specific {
    base physical-device;
    description
      "Vendor specfic physical device. A vendor may derive specific
       idenities from this one.";
    reference
      "SFF-8024 Revision 4.1, Table 4-1, Values 80h-FFh";
  }
  
  
  
  
  //Connector Types
  identity connector-type {
    description
      "Indentifies the external optical or electrical cable 
       connector provided as the media interface.";
    reference
      "SFF-8472 Revision 12.2, Section 5.3 - Connector Values.";
  }

  identity unknown-connector-type {
    base connector-type;
    description
      "Unknown or unspecified.";
    reference
      "SFF-8024 Revision 4.1, Table 4-3, Value 00h";
  }
  
  identity subscriber-connector {
    base connector-type;
    description
      "SC (Subscriber Connector).";
    reference
      "SFF-8024 Revision 4.1, Table 4-3, Value 01h";
  }
  
  identity fibre-channel-style-1-copper {
    base connector-type;
    description
      "Fibre Channel Style 1 copper connector.";
    reference
      "SFF-8024 Revision 4.1, Table 4-3, Value 02h";
  }
  
  identity fibre-channel-style-2-copper {
    base connector-type;
    description
      "Fibre Channel Style 2 copper connector.";
    reference
      "SFF-8024 Revision 4.1, Table 4-3, Value 03h";
  }
  
  identity bnc-tnc {
    base connector-type;
    description
      "BNC/TNC (Bayonet/Threaded Neill-Concelman).";
    reference
      "SFF-8024 Revision 4.1, Table 4-3, Value 04h";
  }
  
  identity fibre-channel-coax-headers {
    base connector-type;
    description
      "Fibre Channel coax headers.";
    reference
      "SFF-8024 Revision 4.1, Table 4-3, Value 05h";
  }
  
  identity fibre-jack {
    base connector-type;
    description
      "Fibre Jack.";
    reference
      "SFF-8024 Revision 4.1, Table 4-3, Value 06h";
  }
  
  identity lucent-connector {
    base connector-type;
    description
      "LC (Lucent Connector).";
    reference
      "SFF-8024 Revision 4.1, Table 4-3, Value 07h";
  }
  
  identity mt-rj {
    base connector-type;
    description
      "MT-RJ (Mechanical Transfer - Registered Jack).";
    reference
      "SFF-8024 Revision 4.1, Table 4-3, Value 08h";
  }
  
  identity mu {
    base connector-type;
    description
      "MU (Multiple Optical).";
    reference
      "SFF-8024 Revision 4.1, Table 4-3, Value 09h";
  }
  
  identity sg {
    base connector-type;
    description
      "SG.";
    reference
      "SFF-8024 Revision 4.1, Table 4-3, Value 0Ah";
  }
  
  identity optical-pigtail {
    base connector-type;
    description
      "Optical Pigtail.";
    reference
      "SFF-8024 Revision 4.1, Table 4-3, Value 0Bh";
  }
  
  identity mpo-1x12 {
    base connector-type;
    description
      "MPO 1x12 (Multifiber Parallel Optic).";
    reference
      "SFF-8024 Revision 4.1, Table 4-3, Value 0Ch";
  }
  
  identity mpo-2x16 {
    base connector-type;
    description
      "MPO 2x16 (Multifiber Parallel Optic).";
    reference
      "SFF-8024 Revision 4.1, Table 4-3, Value 0Dh";
  }
  
  identity hssdc-ii {
    base connector-type;
    description
      "HSSDC II (High Speed Serial Data Connector).";
    reference
      "SFF-8024 Revision 4.1, Table 4-3, Value 20h";
  }
  
  identity copper-pigtail {
    base connector-type;
    description
      "Copper Pigtail.";
    reference
      "SFF-8024 Revision 4.1, Table 4-3, Value 21h";
  }
  
  identity rj45 {
    base connector-type;
    description
      "RF45 (Registered Jack).";
    reference
      "SFF-8024 Revision 4.1, Table 4-3, Value 22h";
  }
  
  identity no-separable-connector {
    base connector-type;
    description
      "No separable connector.";
    reference
      "SFF-8024 Revision 4.1, Table 4-3, Value 23h";
  }
  
  identity mxc-2x16 {
    base connector-type;
    description
      "MXC 2x16.";
    reference
      "SFF-8024 Revision 4.1, Table 4-3, Value 24h";
  }
  
}
