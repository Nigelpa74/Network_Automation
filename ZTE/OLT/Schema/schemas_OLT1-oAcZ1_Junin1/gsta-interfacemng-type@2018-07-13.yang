submodule gsta-interfacemng-type {
    belongs-to gsta-interfacemng {
        prefix ifm;
    }
          
    organization
        "China Telecom Group - Guangdong Telecom Research Institute";
    contact
        "China Telecom Corporation Guangdong Research Institute (hereinafter referred to as:Guangzhou Research Institute)";
    description
        "Defination DataType";
      
    revision 2018-07-13 {
        description
          "Initial modeling.";
        reference
          "GSTA IP-RAN 5G Common Yang Model.";
    }
    
    typedef InterfaceNameType {
		type string {
          length "1..63";
        }
		description "ifName is like ethernet1/1/1/1";
	}
	typedef MacAddressType {
        type string {
           pattern '[0-9a-fA-F]{2}(:[0-9a-fA-F]{2}){5}';
        }
        description
           "A MAC address in standard notation";
    }
    typedef ifmcommIfClassType {
        type enumeration {
          enum "mainInterface" {
            description
              "Main Interface.";
          }
          enum "subInterface" {
            description
              "Sub-interface.";
          }
        }
        description
          "Interface Class Type";
    }
    typedef ifmcommPhyType {
        type enumeration {
          enum "Ethernet" {
            description
              "Ethernet interface.";
          }
          enum "GigabitEthernet" {
            description
              "GigabitEthernet interface.";
          }
          enum "Eth-Trunk" {
            description
              "Eth-Trunk interface.";
          }
          enum "Ip-Trunk" {
            description
              "IP-Trunk interface.";
          }
          enum "Pos" {
            description
              "POS interface.";
          }
          enum "Tunnel" {
            description
              "Tunnel interface.";
          }
          enum "NULL" {
            description
              "Null interface.";
          }
          enum "LoopBack" {
            description
              "Loopback interface.";
          }
          enum "Vlanif" {
            description
              "VLANIF interface.";
          }
          enum "100GE" {
            description
              "100 GigabitEthernet interface.";
          }
          enum "200GE" {
            description
              "200 GigabitEthernet interface.";
          }
          enum "40GE" {
            description
              "40 GigabitEthernet interface.";
          }
          enum "MTunnel" {
            description
              "MTunnel interface.";
          }
          enum "10GE" {
            description
              "10 GigabitEthernet interface.";
          }
          enum "GEBrief" {
            description
              "GigabitEthernet interface.";
          }
          enum "MEth" {
            description
              "Management Ethernet interface.";
          }
          enum "IMEth" {
            description
              "Inner Management Ethernet interface.";
          }
          enum "Stack-Port" {
            description
              "Stack-port interface.";
          }
          enum "Sip" {
            description
              "System interconnect port.";
          }
          enum "Cpos" {
            description
              "CPOS controller.";
          }
          enum "E1" {
            description
              "E1 controller.";
          }
          enum "Serial" {
            description
              "Serial interface.";
          }
          enum "Mp-group" {
            description
              "MP-group interface.";
          }
          enum "Virtual-Ethernet" {
            description
              "Virtual-Ethernet interface.";
          }
          enum "VMEth" {
            description
              "Virtual management Ethernet interface.";
          }
          enum "Ima-group" {
            description
              "IMA-group interface.";
          }
          enum "Remote-Ap" {
            description
              "Virtual cluster access remote access point interface.";
          }
          enum "VBridge" {
            description
              "Virtual cluster access bridge interface.";
          }
          enum "Atm-Bundle" {
            description
              "ATM-Bundle interface.";
          }
          enum "Fiber-Channel" {
            description
              "Fiber-Channel interface.";
          }
          enum "Infiniband" {
            description
              "Infiniband interface.";
          }
          enum "Lmpif" {
            description
              "Lmpif interface.";
          }
          enum "T1" {
            description
              "T1 controller.";
          }
          enum "T3" {
            description
              "T3 controller.";
          }
          enum "Global-VE" {
            description
              "Global-VE interface.";
          }
          enum "VC4" {
            description
              "VC4 interface.";
          }
          enum "VC12" {
            description
              "VC12 interface.";
          }
          enum "Vbdif" {
            description
              "VBDIF interface.";
          }
          enum "Fabric-Port" {
            description
              "Fabric-Port interface.";
          }
          enum "E3" {
            description
              "E3 controller.";
          }
          enum "Otn" {
            description
              "OTN controller.";
          }
          enum "Vp" {
            description
              "VP interface.";
          }
          enum "DcnInterface" {
            description
              "DCN interface.";
          }
          enum "Cpos-Trunk" {
            description
              "Cpos-Trunk interface.";
          }
          enum "Pos-Trunk" {
            description
              "Pos-Trunk interface.";
          }
          enum "Trunk-Serial" {
            description
              "Trunk-Serial interface.";
          }
          enum "Global-Ima-Group" {
            description
              "Global-Ima-Group interface.";
          }
          enum "Global-Mp-Group" {
            description
              "Global-Mp-Group interface.";
          }
          enum "Gmpls-Uni" {
            description
              "Gmpls-Uni interface.";
          }
          enum "Wdm" {
            description
              "Wdm controller.";
          }
          enum "Nve" {
            description
              "NVE interface.";
          }
          enum "FCoE-Port" {
            description
              "FCoE-Port Interface.";
          }
          enum "Virtual-Template" {
            description
              "Virtual-Template Interface.";
          }
          enum "FC" {
            description
              "FC Interface.";
          }
          enum "4x10GE" {
            description
              "4x10 GigabitEthernet interface.";
          }
          enum "10x10GE" {
            description
              "10x10 GigabitEthernet interface.";
          }
          enum "3x40GE" {
            description
              "3x40 GigabitEthernet interface.";
          }
          enum "4x25GE" {
            description
              "4x25 GigabitEthernet interface.";
          }
          enum "25GE" {
            description
              "25 GigabitEthernet interface.";
          }
          enum "ATM" {
            description
              "Atm interface.";
          }
          enum "XGigabitEthernet" {
            description
              "XGigabitEthernet interface.";
          }
          enum "ServiceIf" {
            description
              "ServiceIf interface.";
          }
          enum "Virtual-ODUk" {
            description
              "Virtual-ODUk interface.";
          }
          enum "FlexE" {
            description
              "FlexE interface.";
          }
          enum "FlexE-200GE" {
            description
              "FlexE-200GE interface.";
          }
          enum "50|100GE" {
            description
              "50|100 GigabitEthernet interface.";
          }
          enum "50GE" {
            description
              "50 GigabitEthernet interface.";
          }
          enum "FlexE-50G" {
            description
              "FlexE-50G interface.";
          }
          enum "FlexE-100G" {
            description
              "FlexE-100G interface.";
          }
          enum "FlexE-50|100G" {
            description
              "FlexE-50|100G interface.";
          }
          enum "PW-VE" {
            description
              "PW-VE interface.";
          }
          enum "Virtual-Serial" {
            description
              "Virtual-Serial interface.";
          }
          enum "400GE" {
            description
              "400GE interface.";
          }
          enum "VX-Tunnel" {
            description
              "VX-Tunnel interface.";
          }
        }
        description
          "Interface Physical Type";
    }
    typedef ifmcommAdminStaType {
        type enumeration {
          enum "up" {
            description
              "Administratively Up.";
          }
          enum "down" {
            description
              "Administratively Down.";
          }
        }
        description
          "Interface Admin State Type";
    }
    typedef ifmcommStatMode {
        type enumeration {
          enum "baseInterface" {
            description
              "Statistics are collected based on interfaces.";
          }
          enum "baseVlanGroup" {
            description
              "Statistics are collected based on VLANs.";
          }
        }
        description
          "Interface Statistic Mode";
    }
    typedef ifmcommPortMode {
        type enumeration {
          enum "Mix" {
            description
              "Mix Port Mode";
          }
          enum "L2" {
            description
              "L2 Port Mode";
          }
          enum "L3" {
            description
              "L3 Port Mode";
          }
        }
        description
          "Interface Port Mode";
    }
    typedef ifmcommServiceType {
        type enumeration {
          enum "None" {
            description
              "None.";
          }
          enum "TrunkMember" {
            description
              "Trunk member.";
          }
          enum "StackMember" {
            description
              "Stack member.";
          }
          enum "MpMember" {
            description
              "MP-Group Member.";
          }
          enum "VbridgeMember" {
            description
              "VBridge member.";
          }
          enum "ImaMember" {
            description
              "IMA member.";
          }
          enum "BundleMember" {
            description
              "Bundle member.";
          }
          enum "FabricMember" {
            description
              "Fabric member";
          }
          enum "LagMasterMember" {
            description
              "Master member in a LAG.";
          }
          enum "LagSlaveMember" {
            description
              "Slave member in a LAG.";
          }
          enum "CposTrunkMember" {
            description
              "Cpos-Trunk Member.";
          }
          enum "PosTrunkMember" {
            description
              "Pos-Trunk Member.";
          }
          enum "GlobalMpMember" {
            description
              "Global-Mp-group Member.";
          }
          enum "GlobalImaMember" {
            description
              "Global-Ima-group Member.";
          }
        }
        description
          "Interface Service Type";
    }
  typedef ifmam4CfgType {
	type enumeration {
	  enum "config" {
		description
		  "Configured address.";
	  }
	  enum "negotiation" {
		description
		  "Negotiated address.";
	  }
	  enum "unnumbered" {
		description
		  "Unnumbered address.";
	  }
	}
	description
	  "Am4 Config Type";
  }
  typedef ifmIpv4Mask {
    type string {
      length "9..15";
      pattern '((([1-9]?[0-9]|1[0-9][0-9]|2[0-4][0-9]|25[0-5])\.){3}([1-9]?[0-9]|1[0-9][0-9]|2[0-4][0-9]|25[0-5]))';
    }
    description
      "ipv4Mask support mask format";
  }
  typedef ifmam6IpAddr6Type {
    type enumeration {
      enum "global" {
        description
          "Global unicast address.";
      }
      enum "linkLocal" {
        description
          "Link local address.";
      }
      enum "ndPrefix" {
        description
          "ND prefix.";
      }
      enum "eui64" {
        description
          "EUI 64.";
      }
      enum "anycast" {
        description
          "Anycast address.";
      }
    }
    description
      "Ipv6 Address Type";
  }
  typedef ifmam4IpAddrType {
    type enumeration {
      enum "main" {
        description
          "Primary address of an interface.";
      }
      enum "sub" {
        description
          "Secondary address of an interface.";
      }
      enum "neg" {
        description
          "Negotiated address of an interface.";
      }
      enum "neg_remote" {
        description
          "Remotely negotiated address of an interface.";
      }
      enum "unnumber" {
        description
          "Unnumbered address of an interface.";
      }
      enum "nap" {
        description
          "Negotiated address using the Neighbor access protocol.";
      }
    }
    description
      "Ip Address Type";
  }
  typedef ifmam6IDGenType {
    type enumeration {
      enum "none" {
        description
          "none.";
      }
      enum "cga" {
        description
          "CGA.";
      }
      enum "eui64" {
        description
          "EUI 64.";
      }
    }
    description
      "Ipv6 Address Algorithm Type";
  }

}
