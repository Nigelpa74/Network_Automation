module zxr10-qos-dev-15k {
  namespace 'http://www.zte.com.cn/zxr10/netconf/schema/rosng/qos-dev-15k'
            ;
  prefix qos-dev-15k ;
  import zxr10-qos {
    prefix qos ;
    revision-date 2022-03-18 ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  revision 2022-03-19 {
    description 'Create project 15K deviation function,replace this node:'+"\n"
              + '/qos:configuration/qos:qos/qos:queue-if-stats/qos:stats-switch'
              + 'es/qos:stats-switch/qos:status'
                ;
  }
  deviation '/qos:configuration/qos:qos/qos:queue-if-stats/qos:stats-switches/q'
          + 'os:stats-switch/qos:status'
            {
    description 'Switch status.'
                ;
    deviate replace {
      mandatory true ;
      type enumeration {
        enum on {
          value 0 ;
          description 'swtich on'
                      ;
        }
        enum off {
          value 1 ;
          description 'swtich off'
                      ;
        }
      }
    }
  }
}
