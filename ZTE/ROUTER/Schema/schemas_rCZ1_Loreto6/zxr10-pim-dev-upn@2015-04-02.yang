module zxr10-pim-dev-upn {
  namespace 'http://www.zte.com.cn/zxr10/netconf/schema/rosng/router-pim' ;
  prefix router-pim ;
  import zxr10-pim {
    prefix pim ;
  }
  organization 'ZTE Corporation' ;
  contact "ZTE Corporation  
\n"
        + "   Nanjing Institute of ZTE Corporation 
\n"
        + "   No.68 Zijinghua Rd. Yuhuatai District, Nanjing, China 
\n"
        + '   Tel: +86-25-52870000'
          ;
  revision 2015-04-02 {
    description 'Delete the revision date of the import.' ;
  }
  revision 2014-02-26 {
    description 'Initial version.' ;
  }
  deviation "/pim:configuration/pim:router-pim/pim:vrf-pims/pim:vrf-pim/pim:bid"
          + "ir-pim"
            {
    description 'PIM bidir is not supported for router.' ;
    deviate not-supported ;
  }
  deviation "/pim:configuration/pim:router-pim/pim:vrf-pims/pim:vrf-pim/pim:int"
          + "fs/pim:intf/pim:dr-ignore"
            {
    description 'DR ignore is not supported for router.' ;
    deviate not-supported ;
  }
  deviation "/pim:configuration/pim:router-pim/pim:vrf-pims/pim:vrf-pim/pim:crp"
          + "s/pim:crp/pim:bidir-pim"
            {
    description 'BIDIR of C-RP is not supported for router.' ;
    deviate not-supported ;
  }
  deviation "/pim:configuration/pim:router-pim/pim:vrf-pims/pim:vrf-pim/pim:srp"
          + "s/pim:srp/pim:bidir-pim"
            {
    description 'BIDIR of S-RP is not supported for router.' ;
    deviate not-supported ;
  }
  deviation /pim:configuration/pim:router-pim/pim:pim/pim:global/pim:bidir-pim {
    description 'PIM bidir is not supported for router.' ;
    deviate not-supported ;
  }
  deviation "/pim:configuration/pim:router-pim/pim:pim/pim:intfs/pim:intf/pim:d"
          + "r-ignore"
            {
    description 'DR ignore is not supported for router.' ;
    deviate not-supported ;
  }
  deviation "/pim:configuration/pim:router-pim/pim:pim/pim:crps/pim:crp/pim:bid"
          + "ir-pim"
            {
    description 'BIDIR of C-RP is not supported for router.' ;
    deviate not-supported ;
  }
  deviation "/pim:configuration/pim:router-pim/pim:pim/pim:srps/pim:srp/pim:bid"
          + "ir-pim"
            {
    description 'BIDIR of S-RP is not supported for router.' ;
    deviate not-supported ;
  }
}
