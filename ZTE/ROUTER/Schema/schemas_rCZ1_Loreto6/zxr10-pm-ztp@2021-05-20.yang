module zxr10-pm-ztp {
  namespace 'http://www.zte.com.cn/zxr10/netconf/schema/rosng/pm-ztp'
            ;
  prefix pm-ztp ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  revision 2021-05-20 {
    description 'Add ztp-event'
                ;
  }
  revision 2021-03-22 {
    description 'Add satellite-ztp-status and satellite-ztp-event'
                ;
  }
  container state {
    config false ;
    container satellite-ztp-status {
      list satellite-ztp-status {
        key peid ;
        leaf peid {
          description 'Satellite id'
                      ;
          type uint32 ;
        }
        leaf process {
          description 'Satellite ZTP process'
                      ;
          type ncd:string-all ;
        }
        leaf mac {
          description 'Satellite MAC address'
                      ;
          type ncd:mac-address ;
        }
      }
    }
  }
  notification event {
    container satellite-ztp-events {
      config false ;
      list satellite-ztp-event {
        key peid ;
        leaf peid {
          description 'Satellite id'
                      ;
          type uint32 ;
        }
        leaf process {
          description 'Satellite ZTP process'
                      ;
          type ncd:string-all ;
        }
        leaf mac {
          description 'Satellite MAC address'
                      ;
          type ncd:mac-address ;
        }
      }
    }
    container ztp-event {
      config false ;
      leaf process {
        description 'ZTP process'
                    ;
        type ncd:string-all ;
      }
      leaf mac {
        description 'MAC address'
                    ;
        type ncd:mac-address ;
      }
      ncd:revise-date 2021-05-20 ;
    }
  }
}
