module zxr10-lldp {
  namespace "http://www.zte.com.cn/zxr10/netconf/schema/rosng/lldp" ;
  prefix lldp ;
  yang-version 1 ;
  import zxr10-netconf-defs {
    prefix ncd ;
    revision-date 2013-11-22 ;
  }

  organization "ZTE Corporation" ;
  contact "ZTE Corporation
  Nanjing Institute of ZTE Corporation
  No.68 Zijinghua Rd. Yuhuatai District, Nanjing, China
  Tel: +86-25-52870000" ;
  description 'The netconf module to describe the LLDP.' ;
  revision 2024-11-27 {
    description "description 'modify the following contents:
    Modify the leaf type /lldp:lldp-neighbor/lldp:neighbor/lldp:neighbor-info/lldp:rem-chassis-id from string-all to standard string
    Modify the leaf type /lldp:lldp-neighbor/lldp:neighbor/lldp:neighbor-info/lldp:rem-port-id from string-all to standard string
    Modify the leaf type /lldp:lldp-neighbor/lldp:neighbor/lldp:neighbor-info/lldp:rem-man-addresses/lldp:rem-man-address/lldp:man-address from string-all to standard string
    Modify the leaf type /lldp:state/lldp:lldp/lldp:localsystemdata/lldp:system-desc from string-all to standard string
    Modify the leaf type /lldp:state/lldp:lldp/lldp:localsystemdata/lldp:system-name from string-all to standard string
    Modify the leaf type /lldp:state/lldp:lldp/lldp:localsystemdata/lldp:chassis-id from string-all to standard string
    Modify the leaf type /lldp:state/lldp:lldp/lldp:portstate/lldp:local-ports/lldp:local-port/lldp:port-desc from string-all to standard string
    Modify the leaf type /lldp:state/lldp:lldp/lldp:portstate/lldp:detailed-neighbor-info/lldp:rem-man-addresses/lldp:rem-man-address/lldp:man-address from string-all to standard string
    Modify the leaf type /lldp:state/lldp:lldp/lldp:portstate/lldp:detailed-neighbor-info/lldp:rem-link-aggregation from string-all to standard string
    Modify the leaf type /lldp:state/lldp:lldp/lldp:portstate/lldp:detailed-neighbor-info/lldp:rem-man-addr from string-all to standard string' ;" ;
  }
  revision 2024-03-11 {
    description "1.Add Container 'configuration/lldp/glbcfgs/lnof-oui'.
    2.Add List 'configuration/lldp/glbcfgs/lnof-oui/lnof-oui'.
    3.Add Leaf 'configuration/lldp/glbcfgs/lnof-oui/lnof-oui/oui-type1'.
    4.Add Leaf 'configuration/lldp/glbcfgs/lnof-oui/lnof-oui/oui-type2'.
    5.Add Leaf 'configuration/lldp/glbcfgs/lnof-oui/lnof-oui/oui-type3'.
    6.Add Leaf 'configuration/lldp/glbcfgs/lnof-oui/lnof-oui/subtype'." ;
  }

  revision 2024-01-23 {
    description 'Add leaf state/lldp/portstate/detailed-neighbor-info/last-update.';
  }
  revision 2023-04-24 {
    description 'Change type from ncd:string-all to string of leaf state/lldp/portstate/basic-neighbor-info/rem-chassis-id, rem-sys-desc, rem-port-id, rem-host-name and leaf state/lldp/portstate/detailed-neighbor-info/rem-chassis-id, rem-port-id, rem-port-desc, rem-sys-name, rem-sys-desc, rem-host-name.' ;
  }

  revision 2023-02-28 {
    description "1.Add Container 'configuration/lldp/glbcfgs/tlvcheck'.
    2.Add Leaf 'configuration/lldp/glbcfgs/tlvcheck/port-vlan-id'.
    3.Add container 'configuration/lldp/portcfgs/portcfg/tlvcheck'.
    4.Add Leaf 'configuration/lldp/portcfgs/portcfg/tlvcheck/port-vlan-id'." ;
  }

  revision 2022-12-15 {
    description 'Add list dot3-neighbor-info.' ;
  }

  revision 2022-10-28 {
    description 'Add leaf configuration/lldp/glbcfgs/tlvoption/sd-info and leaf configuration/lldp/portcfgs/portcfg/tlvoption/sd-info.' ;
  }

  revision 2022-07-01 {
    description 'Add leaf configuration/lldp/glbcfgs/tlvoption/port-description,system-name,system-description,system-capabilities,manage-address,mac-physic,power,link-aggregation,max-frame-size and leaf configuration/lldp/portcfgs/tlvoption/port-description,system-name,system-description,system-capabilities,manage-address,mac-physic,power,link-aggregation,max-frame-size.' ;
  }

  revision 2022-04-29 {
    description 'Add leaf state/lldp/portstate/detailed-neighbor-info/rem-sys-cap-enabled and container state/lldp/portstate/local-ports.
Change type from string to ncd:string-all of leaf state/lldp/portstate/basic-neighbor-info/rem-chassis-id, rem-sys-desc, rem-port-id, rem-host-name and leaf state/lldp/portstate/detailed-neighbor-info/rem-chassis-id, rem-port-id, rem-port-desc, rem-sys-name, rem-sys-desc, rem-host-name.' ;
  }

  revision 2021-09-15 {
    description '1.Delete SWITCH(89) and OTN(9700/8700/7000) from feature neighbor-notification.
2.Add PTN(65V5/6700) and OTN(9700/8700/7000) to feature transparent.
3.Add feature ztp, and add if-feature ztp to node zxr10-lldp/configuration/lldp/glbcfgs/ztp-status, zxr10-lldp/configuration/lldp/glbcfgs/tlvoption/ztp and zxr10-lldp/configuration/lldp/portcfgs/portcfg/tlvoption/ztp.
4.Add feature pfc,and add if-feature pfc to node zxr10-lldp/configuration/lldp/portcfgs/portcfg/tlvoption/dcb-pfc-cfg.
5.Delete default value of node zxr10-lldp/configuration/lldp/glbcfgs/maxneighbor.' ;
  }

  revision 2021-03-16 {
    description '1 Add OTN.M721 9700 8700 7000 to feature node neighbor-notification.
2 Modify default value of configuration/lldp/glbcfgs/neighborreport to per-code.' ;
  }

  revision 2021-01-21 {
    description "1. Add Leaf 'configuration/lldp/glbcfgs/ztp-status'.
    2. Add Container 'configuration/lldp/glbcfgs/tlvoption'.
    3. Add Leaf 'configuration/lldp/glbcfgs/tlvoption/ztp'.
    4. Add Leaf 'configuration/lldp/portcfgs/portcfg/tlvoption/ztp'.
    5. Add list 'configuration/lldp/portcfgs/portcfgv2'." ;
  }

  revision 2020-10-30 {
    description "1. Add List 'lldp-neighbor/neighbor/neighbor-info/rem-man-addresses/rem-man-address/man-address'." ;
  }

  revision 2020-09-17 {
    description 'Add container zxr10-lldp\configuration\lldp\portcfgs\portcfg\tlvOption.' ;
  }

  revision 2019-10-16 {
    description 'Add MW.NR8000 to feature node neighbor-notification.' ;
  }

  revision 2019-09-02 {
    description "modify the following contents:
    Add a leaf rem-sys-name on zxr10-lldp\lldp-neighbor
    eighbor
    eighbor-info.
    Add enum value 'update' for leaf action on zxr10-lldp\lldp-neighbor
    eighbor
    eighbor-info.
    Delete feature neighbor-notification of lldp-neighbor notification table." ;
  }

  revision 2019-03-30 {
    description 'modify the following contents:
Modify the leaf type zxr10-lldp\state\lldp\portstate\detail-neighbor-info\rem-chassis-id from string-all to standard string
Modify the leaf type zxr10-lldp\state\lldp\portstate\detail-neighbor-info\rem-port-id from string-all to standard string
Modify the leaf type zxr10-lldp\state\lldp\portstate\detail-neighbor-info\rem-port-desc from string-all to standard string
Modify the leaf type zxr10-lldp\state\lldp\portstate\detail-neighbor-info\rem-sys-desc from string-all to standard string
Modify the leaf type zxr10-lldp\state\lldp\portstate\detail-neighbor-info\rem-host-name from string-all to standard string
Modify the leaf type zxr10-lldp\state\lldp\portstate\detail-neighbor-info\rem-sys-name from string-all to standard string
Modify the leaf type zxr10-lldp\state\lldp\portstate\basic-neighbor-info\rem-chassis-id from string-all to standard string
Modify the leaf type zxr10-lldp\state\lldp\portstate\basic-neighbor-info\rem-sys-desc from string-all to standard string
Modify the leaf type zxr10-lldp\state\lldp\portstate\basic-neighbor-info\rem-port-id from string-all to standard string
Modify the leaf type zxr10-lldp\state\lldp\portstate\basic-neighbor-info\rem-host-name from string-all to standard string' ;
  }

  revision 2019-03-21 {
    description 'delete the default value of the following nodes:
zxr10-lldp\configuration\lldp\glbcfgs\adminstatus;
zxr10-lldp\configuration\lldp\portcfgs\portcfg\adminstatus.' ;
  }

  revision 2018-11-07 {
    description 'modify the following contents:
  Add a container rem-man-addresses on zxr10-lldp\state\lldp\portstate\detailed-neighbor-info.
  Modify the length scope of notification leaf rem-chassis-id.
  Modify the length scope of notification leaf rem-port-id.
  Modify the leaf type zxr10-lldp\state\lldp\portstate\basic-neighbor-info\rem-sys-des from string to string-all
  Modify the leaf type zxr10-lldp\state\lldp\portstate\detail-neighbor-info\rem-port-id from string to string-all
  Modify the leaf type zxr10-lldp\state\lldp\portstate\detail-neighbor-info\rem-sys-des from string to string-all' ;
  }

  revision 2018-07-11 {
    description 'revision "2018-07-11"
    Add SWITCH.89 label for neighbor-notification feature node.' ;
  }

  revision 2016-05-11 {
    description 'modify the followin contents:
    (1)Add a new leaf on zxr10-lldp\configuration\lldp\glbcfgs\reinitdelay;
    (2)Add a new leaf on zxr10-lldp\configuration\lldp\portcfgs\portcfg\notification.' ;
  }

  revision 2016-03-22 {
    description 'modify the followin contents:
    (1)Add a leaf node neighborreport of glbcfgs container
    (2)Add a notification node lldp-neighbor
    (3)Add feature node neighbor-notification for LLDP neighbor report netconf function' ;
  }

  revision 2015-10-20 {
    description 'Change default max value of glbcfgs maxneighbor .
Change type of glbcfgs maxneighbor from uint16 to uint32.
Change unit of hellotime and msgfast.
Change max value of portcfgs maxneighbor .
Change type of portcfgs maxneighbor from uint16 to uint32.
Change unit of hellotime and msgfast.
Change type of basic-neighbor-info rem-sys-desc and detailed-neighbor-info rem-sys-desc .' ;
  }

  revision 2014-05-05 {
    description "revision \"2014-05-05\"
    modify the following contents:
    (1)Add a container of state,use it to get LLDP's local system data." ;
  }

  revision 2014-04-11 {
    description 'revision "2014-04-11"
    modify the following contents:
            (1)Modify the description of some nodes;
            (2)Add range of neighbor-id node;
            (3)Modify rem-plat-desc node name to rem-sys-desc.' ;
  }

  revision 2014-03-17 {
    description 'revision "2014-03-17"
    modify the following contents:
	    (1)Add state container node' ;
  }

  revision 2014-03-12 {
    description 'revision "2014-03-12"
    modify the following contents:
	    (1)Add if-filter-id for portname node in list portcfg
	    (2)Modify the description of some nodes' ;
  }

  revision 2014-02-11 {
    description 'revision "2014-02-11"
    modify the following contents:
	    (1)Add glbcfg container node
	    (2)Add feature node for transparent function' ;
  }

  revision 2013-09-05 {
    description 'revision "2013-9-5"
    modify the following contents:
	    (1)Modify the MimDataType for MimMap of hellotime node
	    (2)Modify the AttributeId for MimMap of holdtime node
	    (3)Add ValueMaps for MimMap transparent node' ;
  }

  revision 2013-07-10 {
    description 'Initial version.
revision "2013-09-05"
    modify the following contents:
	    (1)Modify the MimDataType for MimMap of hellotime node
	    (2)Modify the AttributeId for MimMap of holdtime node
	    (3)Add ValueMaps for MimMap transparent node' ;
  }

  feature transparent {
    description 'This node is used to distinguish whether the transparent node can be enabled' ;
  }

  feature neighbor-notification {
    description 'This node is used to distinguish whether the LLDP neighbor notification function can be enabled.' ;
  }

  feature ztp {
    description 'The LLDP ZTE function.' ;
    ncd:revise-date 2021-09-15 ;
  }

  feature pfc {
    description 'The PFC TLV function.' ;
    ncd:revise-date 2021-09-15 ;
  }

  feature tlv-optional {
    description 'This node is used to distinguish whether the tlv-optional node can be enabled' ;
    ncd:revise-date 2022-07-01 ;
  }

  feature tlv-check {
    description 'This node is used to distinguish whether the tlv check node can be enabled' ;
    ncd:revise-date 2023-02-28 ;
  }

  feature lnof-oui {
    description 'This node is used to distinguish whether the LNOF OUI node can be configured.' ;
    ncd:revise-date 2024-03-11 ;
  }

  container configuration {
    description 'Configuration model information.' ;
    container lldp {
      description 'Configure LLDP parameters.' ;
      container glbcfgs {
        description 'Configure LLDP global parameters.' ;
        leaf adminstatus {
          description "The administratively desired status of the local LLDP agent.If the associated rt-enable node has a value of 'txOnly(1)', then LLDP agent can transmit LLDP frames on all ports and it will not store any information about the remote systems connected.If the associated rt-enable node has a value of 'rxOnly(2)', then the LLDP agent can receive,but it will not transmit LLDP frames on all ports. If the associated rt-enable node has a value of 'txAndRx(3)', then the LLDP agent can transmit and receive LLDP frames on all ports.If the associated rt-enable node has a value of 'disabled(4)', then LLDP agent will not transmit or receive LLDP frames on all ports. If there is remote systems information which is received and stored, before rt-enable becomes disabled, then the information will naturally age out. This leaf has a default value, but value depends on the OS and the device." ;
          type enumeration {
            enum txOnly {
              value 1 ;
              description 'Enable transmit function only.' ;
            }

            enum rxOnly {
              value 2 ;
              description 'Enable receive function only.' ;
            }

            enum txAndRx {
              value 3 ;
              description 'Enable receive and transmit function.' ;
            }

            enum disabled {
              value 4 ;
              description 'Disable receive and transmit function.' ;
            }

          }

        }

        leaf hellotime {
          description 'The interval at which LLDP frames are transmitted on behalf of this LLDP agent. The default value for hellotime node is 30 seconds. The value of this object must be restored from non-volatile storage after a re-initialization of the management system' ;
          type uint16 {
            range 5..32768 ;

          }

          units second ;
          default 30 ;
        }

        leaf holdtime {
          description "The time-to-live value expressed as a multiple of the hellotime node. The actual time-to-live value used in LLDP frames, transmitted on behalf of this LLDP agent,can be expressed by the following formula: TTL = min(65535,(lldpMessageTxInterval * lldpMessageTxHoldMultiplier)) For example, if the value of lldpMessageTxInterval is '30', and the value of holdtime is '4', then the value '120' is encoded in the TTL field in the LLDP header.
          The default value for lldpMessageTxHoldMultiplier object is 4.
          The value of this object must be restored from non-volatile storage after a re-initialization of the management system." ;
          type uint8 {
            range 2..10 {
              description 'Default value is 4.' ;
            }

          }

          default 4 ;
        }

        leaf maxneighbor {
          description "The max number of the neighbor to save. It's default value and max value depends on ability of the device." ;
          type uint32 {
            range 1..2000 ;

          }

        }

        leaf msgfast {
          description 'The interval at which LLDP frames are transmitted on behalf of this LLDP agent during fast transmission period (e.g. when a new neighbor is detected).The default value for msgfast node is 1 second. The value of this object is restored from non-volatile storage after a re-initialization of the management system.' ;
          type uint16 {
            range 1..3600 ;

          }

          units second ;
          default 1 ;
        }

        leaf txcreditmax {
          description 'The maximum number of consecutive LLDP PDUs that can be transmitted at any time. The default value for txcreditmax object is 5 PDUs.The value of this object is restored from non-volatile storage after a re-initialization of the management system.' ;
          type uint8 {
            range 1..10 ;

          }

          units PDUs ;
          default 5 ;
        }

        leaf txfastinit {
          description 'The initial value used to initialize the txFast variable which determines the number of transmissions that are made in fast transmission mode.The default value for txfastinit node is 4.The value of this node is restored from non-volatile storage after a re-initialization of the management system.' ;
          type uint8 {
            range 1..8 ;

          }

          default 4 ;
        }

        leaf neighborreport {
          if-feature neighbor-notification ;

          description 'Set LLDP neighbor report netconf notification enable or disable.' ;
          type enumeration {
            enum disable {
              value 0 ;
              description 'Set LLDP neighbor netconf report disable.' ;
            }

            enum enable {
              value 1 ;
              description 'Set LLDP neighbor netconf report enable.' ;
            }

          }
          ncd:revise-date 2016-03-22 ;
        }

        leaf reinitdelay {
          description "The lldpReinitDelay indicates the delay (in units of seconds) from when lldpPortConfigAdminStatus object of a particular port becomes 'disabled' until re-initialization will be attempted." ;
          type uint8 {
            range 1..10 {
              description 'in units of seconds' ;
            }

          }

          units second ;
          default 2 ;
          ncd:revise-date 2016-05-11 ;
        }

        leaf ztp-status {
          if-feature ztp {
            ncd:revise-date 2021-09-15 ;
          }
          description 'Configure ZTP status.' ;
          type enumeration {
            enum enable {
              value 1 ;
              description 'Enable ZTP status.' ;
            }

            enum disable {
              value 2 ;
              description 'Disable ZTP status.' ;
            }

          }

          default disable ;
          ncd:revise-date 2021-01-21 ;
        }

        container tlvoption {
          description 'Configure whether TLVs are allowed to be transmitted.' ;
          leaf ztp {
            if-feature ztp {
              ncd:revise-date 2021-09-15 ;
            }
            description 'Configure whether ZTP TLV is allowed to be transmitted.' ;
            type enumeration {
              enum enable {
                value 1 ;
                description 'Enable ZTP TLV transmission.' ;
              }

              enum disable {
                value 2 ;
                description 'Disable ZTP TLV transmission.' ;
              }

            }

            default enable ;
          }

          leaf port-description {
            if-feature tlv-optional ;

            description 'Configure whether port description TLV is allowed to be transmitted.' ;
            type enumeration {
              enum enable {
                value 1 ;
                description 'Enable port description TLV transmission.' ;
              }

              enum disable {
                value 0 ;
                description 'Disable port description TLV transmission.' ;
              }

            }

            default enable ;
            ncd:revise-date 2022-07-01 ;
          }

          leaf system-name {
            if-feature tlv-optional ;

            description 'Configure whether system name TLV is allowed to be transmitted.' ;
            type enumeration {
              enum enable {
                value 1 ;
                description 'Enable system name TLV transmission.' ;
              }

              enum disable {
                value 0 ;
                description 'Disable system name TLV transmission.' ;
              }

            }

            default enable ;
            ncd:revise-date 2022-07-01 ;
          }

          leaf system-description {
            if-feature tlv-optional ;

            description 'Configure whether system description TLV is allowed to be transmitted.' ;
            type enumeration {
              enum enable {
                value 1 ;
                description 'Enable system description TLV transmission.' ;
              }

              enum disable {
                value 0 ;
                description 'Disable system description TLV transmission.' ;
              }

            }

            default enable ;
            ncd:revise-date 2022-07-01 ;
          }

          leaf system-capabilities {
            if-feature tlv-optional ;

            description 'Configure whether system capabilities TLV is allowed to be transmitted.' ;
            type enumeration {
              enum enable {
                value 1 ;
                description 'Enable port capabilities TLV transmission.' ;
              }

              enum disable {
                value 0 ;
                description 'Disable port capabilities TLV transmission.' ;
              }

            }

            default enable ;
            ncd:revise-date 2022-07-01 ;
          }

          leaf manage-address {
            if-feature tlv-optional ;

            description 'Configure whether manage address TLV is allowed to be transmitted.' ;
            type enumeration {
              enum enable {
                value 1 ;
                description 'Enable manage address TLV transmission.' ;
              }

              enum disable {
                value 0 ;
                description 'Disable manage address TLV transmission.' ;
              }

            }

            default enable ;
            ncd:revise-date 2022-07-01 ;
          }

          leaf mac-physic {
            if-feature tlv-optional ;

            description 'Configure whether mac physic TLV is allowed to be transmitted.' ;
            type enumeration {
              enum enable {
                value 1 ;
                description 'Enable mac physic TLV transmission.' ;
              }

              enum disable {
                value 0 ;
                description 'Disable mac physic TLV transmission.' ;
              }

            }

            default enable ;
            ncd:revise-date 2022-07-01 ;
          }

          leaf power {
            if-feature tlv-optional ;

            description 'Configure whether power TLV is allowed to be transmitted.' ;
            type enumeration {
              enum enable {
                value 1 ;
                description 'Enable power TLV transmission.' ;
              }

              enum disable {
                value 0 ;
                description 'Disable power TLV transmission.' ;
              }

            }

            default enable ;
            ncd:revise-date 2022-07-01 ;
          }

          leaf link-aggregation {
            if-feature tlv-optional ;

            description 'Configure whether link aggregation TLV is allowed to be transmitted.' ;
            type enumeration {
              enum enable {
                value 1 ;
                description 'Enable link aggregation TLV transmission.' ;
              }

              enum disable {
                value 0 ;
                description 'Disable link aggregation TLV transmission.' ;
              }

            }

            default enable ;
            ncd:revise-date 2022-07-01 ;
          }

          leaf max-frame-size {
            if-feature tlv-optional ;

            description 'Configure whether max frame size TLV is allowed to be transmitted.' ;
            type enumeration {
              enum enable {
                value 1 ;
                description 'Enable max frame size TLV transmission.' ;
              }

              enum disable {
                value 0 ;
                description 'Disable max frame size TLV transmission.' ;
              }

            }

            default enable ;
            ncd:revise-date 2022-07-01 ;
          }

          leaf sd-info {
            description 'Configure whether sd info TLV is allowed to be transmitted.' ;
            type enumeration {
              enum enable {
                value 1 ;
                description 'Enable power TLV transmission.' ;
              }

              enum disable {
                value 0 ;
                description 'Disable power TLV transmission.' ;
              }

            }

            default enable ;
            ncd:revise-date 2022-10-28 ;
          }
          ncd:revise-date 2021-01-21 ;
        }

        container tlvcheck {
          description 'Configure whether TLVs are allowed to be checked.' ;
          leaf port-vlan-id {
            if-feature tlv-check ;

            default disable ;
            description 'Set LLDP port VLAN ID TLV check enable or disable.' ;
            type enumeration {
              enum enable {
                value 1 ;
                description 'Enable LLDP port VLAN ID TLV check.' ;
              }

              enum disable {
                value 2 ;
                description 'Disable LLDP port VLAN ID TLV check.' ;
              }

            }

            ncd:revise-date 2023-02-28 ;
          }
          ncd:revise-date 2023-02-28 ;
        }

        container lnof-oui {
          description 'Configuring LNOF OUI.' ;
          presence lnof-oui ;
          config true ;
          list lnof-oui {
            leaf oui-type1 {
              type ncd:hex {
                length 3..4 ;

              }

              description 'OUI Type 1(1 octets).' ;


            }

            leaf oui-type2 {
              type ncd:hex {
                length 3..4 ;

              }

              description 'OUI Type 2(1 octets).' ;


            }

            leaf oui-type3 {
              type ncd:hex {
                length 3..4 ;

              }

              description 'OUI Type 3(1 octets).' ;


            }

            leaf subtype {
              type uint8 {
                range 1..255 ;

              }

              description 'Configuring LNOF subtype.' ;

	            
            }

            description 'Configuring LNOF OUI.' ;
            key 'oui-type1 oui-type2 oui-type3 subtype' ;
            config true ;
            
          }

          if-feature lnof-oui {
            ncd:revise-date 2024-03-11 ;
          }

          ncd:revise-date 2024-03-11 ;
        }

      }

      container portcfgs {
        description 'Configure LLDP parameters for interfaces.' ;
        list portcfg {
          description 'Configure LLDP interface parameters.' ;
          key "portname" ;
          leaf portname {
            description 'The port name used to identify the port component(contained in the local chassis with the LLDP agent)associated with this entry.' ;
            type ncd:ifname ;

          }

          leaf adminstatus {
            description "The administratively desired status of the local LLDP agent.If the associated rt-enable node has a value of 'txOnly(1)', then LLDP agent will transmit LLDP frames on this port and it will not store any information about the remote systems connected.If the associated rt-enable node object has a value of 'rxOnly(2)', then the LLDP agent will receive,but it will not transmit LLDP frames on this port.If the associated rt-enable node object has a value of 'txAndRx(3)', then the LLDP agent will transmit and receive LLDP frames on this port.If the associated lldpPortConfigAdminStatus object has a value of 'disabled(4)', then LLDP agent will not transmit or receive LLDP frames on this port.  If there is remote systems information which is received on this port and stored in other tables, before the port's rt-enable node becomes disabled, then the information will naturally age out. This leaf has a default value, but value depends on the OS and the device." ;
            type enumeration {
              enum txOnly {
                value 1 ;
                description 'Enable transmit function only.' ;
              }

              enum rxOnly {
                value 2 ;
                description 'Enable receive function only.' ;
              }

              enum txAndRx {
                value 3 ;
                description 'Enable transmit and receive function.' ;
              }

              enum disabled {
                value 4 ;
                description 'Disable transmit and receive function.' ;
              }

            }

          }

          leaf maxneighbor {
            description "The max number of the neighbor of the port.It's max value depends on ability of the device. The default value is 8." ;
            type uint32 {
              range 1..50 ;

            }

            default 8 ;
          }

          leaf transparent {
            if-feature transparent ;

            description 'The transparent control, on a per port basis, whether or not the received packets are forwarded. The value enable(1) means that the port will forward the received packets; the value disable(2) means that the port will not forward the received packets.' ;
            type enumeration {
              enum enable {
                value 1 ;
                description 'Enable transparent function.' ;
              }

              enum disable {
                value 2 ;
                description 'Disable transparent function.' ;
              }

            }

            default disable ;
          }

          leaf notification {
            description 'Whether or not notifications from the agent are enabled.' ;
            type enumeration {
              enum enable {
                value 1 ;
                description 'Enable notification function.' ;
              }

              enum disable {
                value 2 ;
                description 'Disable notification function.' ;
              }

            }

            default disable ;
            ncd:revise-date 2016-05-11 ;
          }

          container tlvoption {
            description 'Configure whether TLVs are allowed to be transmitted.' ;
            leaf dcb-pfc-cfg {
              if-feature pfc {
                ncd:revise-date 2021-09-15 ;
              }
              description 'Configure whether PFC configuration TLV is allowed to be transmitted.' ;
              type enumeration {
                enum enable {
                  value 1 ;
                  description 'Enable PFC configuration TLV transmission.' ;
                }

                enum disable {
                  value 2 ;
                  description 'Disable PFC configuration TLV transmission.' ;
                }

              }

              default disable ;
            }

            leaf ztp {
              if-feature ztp {
                ncd:revise-date 2021-09-15 ;
              }
              description 'Configure whether ZTP TLV is allowed to be transmitted.' ;
              type enumeration {
                enum enable {
                  value 1 ;
                  description 'Enable ZTP TLV transmission.' ;
                }

                enum disable {
                  value 2 ;
                  description 'Disable ZTP TLV transmission.' ;
                }

              }

              default disable ;
              ncd:revise-date 2021-01-21 ;
            }

            leaf port-description {
              if-feature tlv-optional ;

              description 'Configure whether port description TLV is allowed to be transmitted.' ;
              type enumeration {
                enum enable {
                  value 1 ;
                  description 'Enable port description TLV transmission.' ;
                }

                enum disable {
                  value 0 ;
                  description 'Disable port description TLV transmission.' ;
                }

              }

              default enable ;
              ncd:revise-date 2022-07-01 ;
            }

            leaf system-name {
              if-feature tlv-optional ;

              description 'Configure whether system name TLV is allowed to be transmitted.' ;
              type enumeration {
                enum enable {
                  value 1 ;
                  description 'Enable system name TLV transmission.' ;
                }

                enum disable {
                  value 0 ;
                  description 'Disable system name TLV transmission.' ;
                }

              }

              default enable ;
              ncd:revise-date 2022-07-01 ;
            }

            leaf system-description {
              if-feature tlv-optional ;

              description 'Configure whether system description TLV is allowed to be transmitted.' ;
              type enumeration {
                enum enable {
                  value 1 ;
                  description 'Enable system description TLV transmission.' ;
                }

                enum disable {
                  value 0 ;
                  description 'Disable system description TLV transmission.' ;
                }

              }

              default enable ;
              ncd:revise-date 2022-07-01 ;
            }

            leaf system-capabilities {
              if-feature tlv-optional ;

              description 'Configure whether system capabilities TLV is allowed to be transmitted.' ;
              type enumeration {
                enum enable {
                  value 1 ;
                  description 'Enable port capabilities TLV transmission.' ;
                }

                enum disable {
                  value 0 ;
                  description 'Disable port capabilities TLV transmission.' ;
                }

              }

              default enable ;
              ncd:revise-date 2022-07-01 ;
            }

            leaf manage-address {
              if-feature tlv-optional ;

              description 'Configure whether manage address TLV is allowed to be transmitted.' ;
              type enumeration {
                enum enable {
                  value 1 ;
                  description 'Enable manage address TLV transmission.' ;
                }

                enum disable {
                  value 0 ;
                  description 'Disable manage address TLV transmission.' ;
                }

              }

              default enable ;
              ncd:revise-date 2022-07-01 ;
            }

            leaf mac-physic {
              if-feature tlv-optional ;

              description 'Configure whether mac physic TLV is allowed to be transmitted.' ;
              type enumeration {
                enum enable {
                  value 1 ;
                  description 'Enable mac physic TLV transmission.' ;
                }

                enum disable {
                  value 0 ;
                  description 'Disable mac physic TLV transmission.' ;
                }

              }

              default enable ;
              ncd:revise-date 2022-07-01 ;
            }

            leaf power {
              if-feature tlv-optional ;

              description 'Configure whether power TLV is allowed to be transmitted.' ;
              type enumeration {
                enum enable {
                  value 1 ;
                  description 'Enable power TLV transmission.' ;
                }

                enum disable {
                  value 0 ;
                  description 'Disable power TLV transmission.' ;
                }

              }

              default enable ;
              ncd:revise-date 2022-07-01 ;
            }

            leaf link-aggregation {
              if-feature tlv-optional ;

              description 'Configure whether link aggregation TLV is allowed to be transmitted.' ;
              type enumeration {
                enum enable {
                  value 1 ;
                  description 'Enable link aggregation TLV transmission.' ;
                }

                enum disable {
                  value 0 ;
                  description 'Disable link aggregation TLV transmission.' ;
                }

              }

              default enable ;
              ncd:revise-date 2022-07-01 ;
            }

            leaf max-frame-size {
              if-feature tlv-optional ;

              description 'Configure whether max frame size TLV is allowed to be transmitted.' ;
              type enumeration {
                enum enable {
                  value 1 ;
                  description 'Enable max frame size TLV transmission.' ;
                }

                enum disable {
                  value 0 ;
                  description 'Disable max frame size TLV transmission.' ;
                }

              }

              default enable ;
              ncd:revise-date 2022-07-01 ;
            }

            leaf sd-info {
              description 'Configure whether sd info TLV is allowed to be transmitted.' ;
              type enumeration {
                enum enable {
                  value 1 ;
                  description 'Enable power TLV transmission.' ;
                }

                enum disable {
                  value 0 ;
                  description 'Disable power TLV transmission.' ;
                }

              }

              default enable ;
              ncd:revise-date 2022-10-28 ;
            }
            ncd:revise-date 2020-09-17 ;

          }

          container tlvcheck {
            description 'Configure whether TLVs are allowed to be checked.' ;
            leaf port-vlan-id {
              if-feature tlv-check ;

              default enable ;
              description 'Set LLDP port VLAN ID TLV  check enable or disable.' ;
              type enumeration {
                enum enable {
                  value 1 ;
                  description 'ENABLE LLDP port VLAN ID TLV check.' ;
                }

                enum disable {
                  value 2 ;
                  description 'DISABLE LLDP port VLAN ID TLV  check.' ;
                }

              }

              ncd:revise-date 2023-02-28 ;
            }
            ncd:revise-date 2023-02-28 ;
          }

        }

        list portcfgv2 {
          description 'Configuring interface parameters of LLDP Version 2.' ;
          key "portname destmactype" ;
          leaf portname {
            description 'The port name used to identify the port component(contained in the local chassis with the LLDP agent)associated with this entry.' ;
            type ncd:ifname ;

          }

          leaf destmactype {
            description "The value used to identify the standard group MAC addresses that can be used by LLDP. The choice of address used determines the scope of propagation of LLDPDUs within a bridged LAN. If the node is set to a value of 'nearest-non-tpmr-bridge', then LLDP agent transmits LLDPframes with the destination address 01-80-C2-00-00-03. If the node is set to a value of 'nearest-customer-bridge', then LLDP agent transmits LLDPframes with the destination address 01-80-C2-00-00-00." ;
            type enumeration {
              enum nearest-non-tpmr-bridge {
                value 2 ;
                description 'Propagation constrained by all bridges other than TPMRs; intended for use within provider bridged networks.' ;
              }

              enum nearest-customer-bridge {
                value 3 ;
                description 'Propagation constrained by customer bridges; this gives the same coverage as a customer-customer MACSec connection.' ;
              }

            }

          }

          leaf adminstatus {
            description "The administratively desired status of the local LLDP agent. If the node is set to a value of 'txOnly(1)', then LLDP agent transmits LLDPframes on this port and it does not store any information about the remote systems connected. If the node is set to a value of 'rxOnly(2)', then the LLDP agent receives, but it does not transmit LLDP frames on this port. If the node is set to a value of 'txAndRx(3)', then the LLDP agent transmits and receives LLDP frames on this port. If the node is set to a value of 'disabled(4)', then LLDP agent does not transmit or receive LLDP frames on this port." ;
            type enumeration {
              enum txOnly {
                value 1 ;
                description 'Enable transmit function only.' ;
              }

              enum rxOnly {
                value 2 ;
                description 'Enable receive function only.' ;
              }

              enum txAndRx {
                value 3 ;
                description 'Enable transmit and receive function.' ;
              }

              enum disabled {
                value 4 ;
                description 'Disable transmit and receive function.' ;
              }

            }

          }
          ncd:revise-date 2021-01-21 ;
        }

      }

    }

  }

  container state {
    config false ;
    description 'State model information.' ;
    container lldp {
      description 'LLDP state information.' ;
      container glbstatics {
        description 'Global statics information.' ;
        leaf tx-frames-total {
          description 'Global count of sent lldp packets.' ;
          type uint32 ;

        }

        leaf rx-frames-total {
          description 'Global count of received lldp packets.' ;
          type uint32 ;

        }

        leaf rx-frames-errors {
          description 'Global count of received error lldp packets.' ;
          type uint32 ;

        }

        leaf rx-frames-discard {
          description 'Global count of discarded lldp packets.' ;
          type uint32 ;

        }

        leaf rx-tlvs-discard {
          description 'Global count of discarded TLVs of lldp packets.' ;
          type uint32 ;

        }

        leaf rx-tlvs-unrecognized {
          description 'Global count of unrecognized TLVs of lldp packets.' ;
          type uint32 ;

        }

        leaf neighbor-add {
          description 'Global count of having been added new neighbors.' ;
          type uint32 ;

        }

        leaf neighbor-delete {
          description 'Global count of having been deleted neighbors.' ;
          type uint32 ;

        }

        leaf neighbor-ageout {
          description 'Global count of having been aged neighbors.' ;
          type uint32 ;

        }

        leaf neighbor-drop {
          description 'Global count of having been dropped neighbors.' ;
          type uint32 ;

        }

      }

      container portstate {
        description 'Port state information.' ;
        list portstatics {
          description 'Port statics information.' ;
          key "local-ifname" ;
          leaf local-ifname {
            description 'Local port name.' ;
            type ncd:ifname ;

          }

          leaf tx-frames-total {
            description 'Count of sent lldp packets of port.' ;
            type uint32 ;

          }

          leaf rx-frames-total {
            description 'Count of received lldp packets of port.' ;
            type uint32 ;

          }

          leaf rx-frames-errors {
            description 'Count of received error lldp packets of port.' ;
            type uint32 ;

          }

          leaf rx-frames-discard {
            description 'Count of discarded lldp packets of port.' ;
            type uint32 ;

          }

          leaf rx-tlvs-discard {
            description 'Count of discarded TLVs of lldp packets of port.' ;
            type uint32 ;

          }

          leaf rx-tlvs-unrecognized {
            description 'Count of unrecognized TLVs of lldp packets of port.' ;
            type uint32 ;

          }

          leaf neighbor-add {
            description 'Count of having been added new neighbors.' ;
            type uint32 ;

          }

          leaf neighbor-delete {
            description 'Count of having been deleted new neighbors.' ;
            type uint32 ;

          }

          leaf neighbor-ageout {
            description 'Count of having been aged new neighbors' ;
            type uint32 ;

          }

          leaf neighbor-drop {
            description 'Count of having been dropped new neighbors.' ;
            type uint32 ;

          }

          ncd:select local-ifname ;
        }

        list basic-neighbor-info {
          description 'Basic information of neighbors.' ;
          key "local-ifname neighbor-id" ;
          leaf local-ifname {
            description 'Local port name.' ;
            type ncd:ifname ;

          }

          leaf neighbor-id {
            description 'Neighbor ID.' ;
            type uint32 {
              range 1..4294967295 ;

            }

          }

          leaf rem-chassis-id {
            type string ;

            description 'Value to indicate basis identifier in chassis ID field.' ;
          }

          leaf ttl {
            description 'Hold on time of neighbor keeping alive.' ;
            type uint16 ;

          }

          leaf rem-sys-cap {
            description 'Capability of system of remote neighbor.' ;
            type uint16 ;

          }

          leaf rem-sys-desc {
            type string ;

            description 'Description of remote system of remote neighbor.' ;
          }

          leaf rem-port-id {
            type string ;

            description 'Remote port name in neighbor.' ;
          }

          leaf rem-host-name {
            type string ;

            description 'Host name of remote neighbor.' ;
          }

          ncd:select local-ifname ;
          ncd:select "local-ifname neighbor-id" ;
        }

        list detailed-neighbor-info {
          description 'Detailed information of neighbors.' ;
          key "local-ifname neighbor-id" ;
          leaf local-ifname {
            description 'Local port name.' ;
            type ncd:ifname ;

          }

          leaf neighbor-id {
            description 'Neighbor ID.' ;
            type uint32 {
              range 1..4294967295 ;

            }

          }

          leaf rem-chassis-id {
            type string ;

            description 'Value to indicate basis identifier in chassis ID field.' ;
          }

          leaf rem-chassis-id-subtype {
            description 'Subtype of the chassis ID of remote neighbor.' ;
            type uint16 ;

          }

          leaf rem-port-id {
            type string ;

            description 'Identifier in port ID field of neighbor. Value according to PortIdSubType.' ;
          }

          leaf rem-port-id-subtype {
            description 'Value to indicate basis identifier in port ID field.' ;
            type uint16 ;

          }

          leaf ttl {
            description 'Hold on time of neighbor keeping alive.' ;
            type uint16 ;

          }

          leaf rem-port-desc {
            type string ;

            description 'Description of port of remote neighbor.' ;
          }

          leaf rem-sys-name {
            type string ;

            description 'System name of remote neighbor.' ;
          }

          leaf rem-sys-desc {
            type string ;

            description 'Description of remote system of remote neighbor.' ;
          }

          leaf rem-sys-cap {
            description 'Capability of system of remote neighbor.' ;
            type uint16 ;

          }

          leaf rem-man-addr {
            type string ;

            description 'Management address of remote neighbor.' ;
            ncd:revise-date 2024-11-27 ;
          }

          leaf rem-link-aggregation {
            type string ;

            description 'Link aggregation information of port of remote neighbor.' ;
            ncd:revise-date 2024-11-27 ;
          }

          leaf rem-host-name {
            type string ;

            description 'Host name of remote neighbor.' ;
          }

          container rem-man-addresses {
            description 'Management address of remote neighbor.' ;
            list rem-man-address {
              description 'Management address of remote neighbor.' ;
              key "man-addr-subtype man-address" ;
              leaf man-addr-subtype {
                description "Subtype of the management address.
                The value '1' indicates the IPv4 address.
                The value '2' indicates the IPv6 address.
                For the definition of other values, refer to IANA-ADDRESS-FAMILY-NUMBERS-MIB." ;
                type uint8 {
                  range 0..255 ;

                }

              }

              leaf man-address {
                type string ;

                description 'Management address of remote neighbor.' ;
                ncd:revise-date 2024-11-27 ;
              }

              ncd:select "man-addr-subtype man-address" ;
            }
            ncd:revise-date 2018-11-07 ;
          }

          leaf rem-sys-cap-enabled {
            description 'Enabled capability of system of remote neighbor.' ;
            type uint16 ;
            ncd:revise-date 2022-04-29 ;
          }

          leaf last-update {
            type uint16 ;

            description 'Seconds since last update received.' ;
            ncd:revise-date 2024-01-23 ;
          }

          ncd:select local-ifname ;
          ncd:select "local-ifname neighbor-id" ;
        }

        container local-ports {
          description 'Port list of local system.' ;
          list local-port {
            description 'Port list of local system.' ;
            key "if-name" ;
            leaf if-name {
              description 'Interface name.' ;
              type ncd:ifname ;

            }

            leaf port-id-subtype {
              description 'Value to indicate basis identifier in port ID field.' ;
              type uint16 ;

            }

            leaf port-id {
              description 'Identifier in port ID field of local port. Value according to port-id-subtype.' ;
              type string ;

            }

            leaf port-desc {
              type string ;

              description 'Description of port of local port.' ;
              ncd:revise-date 2024-11-27 ;
            }

            leaf port-cap {
              description 'The capability of local port mode.
The bit 0 indicates eth.
The bit 1 indicates mtn-termination.
The bit 2 indicates flexe-termination.
The bit 3 indicates mtn-aware.
The bit 4 indicates flexe-aware.' ;
              type uint16 ;

            }

            leaf port-state {
              description 'The state of local port mode.
The value has the same meaning as port-cap.' ;
              type uint16 ;

            }

          }
          ncd:revise-date 2022-04-29 ;
        }

        list dot3-neighbor-info {
          description 'Dot3 information of neighbors.' ;
          key "local-ifname neighbor-id mac-type" ;
          leaf local-ifname {
            description 'Local port name.' ;
            type ncd:ifname ;

          }

          leaf neighbor-id {
            description 'Neighbor ID.' ;
            type uint32 {
              range 1..4294967295 ;

            }

          }

          leaf mac-type {
            description 'Mac Type.' ;
            type enumeration {
              enum Nearest-Bridge {
                value 1 ;
                description 'Mac type is Nearest Bridge.' ;
              }

              enum Nearest-Non-TPMR-Bridge {
                value 2 ;
                description 'Mac type is Nearest non-TPMR Bridge.' ;
              }

              enum Nearest-Customer-Bridge {
                value 3 ;
                description 'Mac type is Nearest Customer Bridge.' ;
              }

            }

          }

          leaf rem-aggregation-capability {
            description 'Aggregation capability of Link Aggregation of remote neighbor.' ;
            type enumeration {
              enum Supported {
                value 1 ;
                description 'Aggregation capability is supported.' ;
              }

              enum Not-supported {
                value 0 ;
                description 'Aggregation capability is not supported.' ;
              }

            }

          }

          leaf rem-aggregation-status {
            description 'Aggregation status of Link Aggregation of remote neighbor.' ;
            type enumeration {
              enum Enabled {
                value 1 ;
                description 'Aggregation status is enabled.' ;
              }

              enum Disabled {
                value 0 ;
                description 'Aggregation status is not disabled.' ;
              }

            }

          }

          leaf rem-aggregation-port-id {
            description 'Aggregation port ID of Link Aggregation of remote neighbor.' ;
            type uint32 ;

          }

          leaf rem-auto-negotiation-capability {
            description 'Auto-Negotiation Support/Status of MAC/PHY Cfg/Status of remote neighbor.' ;
            type enumeration {
              enum "Capability:Not-supported,Status:Disabled" {
                value 0 ;
                description 'Auto-Negotiation capability is not supported,Auto-Negotiation status is disabled.' ;
              }

              enum "Capability:Supported,Status:Disabled" {
                value 1 ;
                description 'Auto-Negotiation capability is supported,Auto-Negotiation status is disabled.' ;
              }

              enum "Capability:Not-supported,Status:Enabled" {
                value 2 ;
                description 'Auto-Negotiation capability is not supported,Auto-Negotiation status is enabled.' ;
              }

              enum "Capability:Supported,Status:Enabled" {
                value 3 ;
                description 'Auto-Negotiation capability is supported,Auto-Negotiation status is enabled.' ;
              }

            }

          }

          leaf rem-advertised-capability {
            description 'Auto-Negotiation Advertised Capability of MAC/PHY Cfg/Status of remote neighbor.' ;
            type enumeration {
              enum Other-0 {
                value 0 ;
                description 'Advertised capability is Other-0.' ;
              }

              enum 10baseT-1 {
                value 1 ;
                description 'Advertised capability is not 10baseT-1.' ;
              }

              enum 10baseTFD-2 {
                value 2 ;
                description 'Advertised capability is not 10baseTFD-2.' ;
              }

              enum 100baseT4-3 {
                value 3 ;
                description 'Advertised capability is not 100baseT4-3.' ;
              }

              enum 100baseTX-4 {
                value 4 ;
                description 'Advertised capability is not 100baseTX-4.' ;
              }

              enum 100baseTXFD-5 {
                value 5 ;
                description 'Advertised capability is not 100baseTXFD-5.' ;
              }

              enum 100baseT2-6 {
                value 6 ;
                description 'Advertised capability is not 100baseT2-6.' ;
              }

              enum 100baseT2FD-7 {
                value 7 ;
                description 'Advertised capability is not 100baseT2FD-7.' ;
              }

              enum FdxPause-8 {
                value 8 ;
                description 'Advertised capability is not FdxPause-8.' ;
              }

              enum FdxAPause-9 {
                value 9 ;
                description 'Advertised capability is not FdxAPause-9.' ;
              }

              enum FdxSPause-10 {
                value 10 ;
                description 'Advertised capability is not FdxSPause-10.' ;
              }

              enum FdxBPause-11 {
                value 11 ;
                description 'Advertised capability is not FdxBPause-11.' ;
              }

              enum 1000baseX-12 {
                value 12 ;
                description 'Advertised capability is not 1000baseX-12.' ;
              }

              enum 1000baseXFD-13 {
                value 13 ;
                description 'Advertised capability is not 1000baseXFD-13.' ;
              }

              enum 1000baseT-14 {
                value 14 ;
                description 'Advertised capability is not 1000baseT-14.' ;
              }

              enum 1000baseTFD-15 {
                value 15 ;
                description 'Advertised capability is not 1000baseTFD-15.' ;
              }

            }

          }

          leaf rem-operational-mau-type {
            description 'Operational MAU Type of MAC/PHY Cfg/Status of remote neighbor.' ;
            type enumeration {
              enum Other-0 {
                value 0 ;
                description 'Operational MAU type is Other-0.' ;
              }

              enum AUI-1 {
                value 1 ;
                description 'Operational MAU type is AUI-1.' ;
              }

              enum 10Base5-2 {
                value 2 ;
                description 'Operational MAU type is 10Base5-2.' ;
              }

              enum Foirl-3 {
                value 3 ;
                description 'Operational MAU type is Foirl-3.' ;
              }

              enum 10Base2-4 {
                value 4 ;
                description 'Operational MAU type is 10Base2-4.' ;
              }

              enum 10BaseT-5 {
                value 5 ;
                description 'Operational MAU type is 10BaseT-5.' ;
              }

              enum 10BaseFP-6 {
                value 6 ;
                description 'Operational MAU type is 10BaseFP-6.' ;
              }

              enum 10BaseFB-7 {
                value 7 ;
                description 'Operational MAU type is 10BaseFB-7.' ;
              }

              enum 10BaseFL-8 {
                value 8 ;
                description 'Operational MAU type is 10BaseFL-8.' ;
              }

              enum 10Broad36-9 {
                value 9 ;
                description 'Operational MAU type is 10Broad36-9.' ;
              }

              enum 10BaseTHD-10 {
                value 10 ;
                description 'Operational MAU type is 10BaseTHD-10.' ;
              }

              enum 10BaseTFD-11 {
                value 11 ;
                description 'Operational MAU type is 10BaseTFD-11.' ;
              }

              enum 10BaseFLHD-12 {
                value 12 ;
                description 'Operational MAU type is 10BaseFLHD-12.' ;
              }

              enum 10BaseFLFD-13 {
                value 13 ;
                description 'Operational MAU type is 10BaseFLFD-13.' ;
              }

              enum 100BaseT4-14 {
                value 14 ;
                description 'Operational MAU type is 100BaseT4-14.' ;
              }

              enum 100BaseTXHD-15 {
                value 15 ;
                description 'Operational MAU type is 100BaseTXHD-15.' ;
              }

              enum 100BaseTXFD-16 {
                value 16 ;
                description 'Operational MAU type is 100BaseTXFD-16.' ;
              }

              enum 100BaseFXHD-17 {
                value 17 ;
                description 'Operational MAU type is 100BaseFXHD-17.' ;
              }

              enum 100BaseFXFD-18 {
                value 18 ;
                description 'Operational MAU type is 100BaseFXFD-18.' ;
              }

              enum 100BaseT2HD-19 {
                value 19 ;
                description 'Operational MAU type is 100BaseT2HD-19.' ;
              }

              enum 100BaseT2FD-20 {
                value 20 ;
                description 'Operational MAU type is 100BaseT2FD-20.' ;
              }

              enum 1000BaseXHD-21 {
                value 21 ;
                description 'Operational MAU type is 1000BaseXHD-21.' ;
              }

              enum 1000BaseXFD-22 {
                value 22 ;
                description 'Operational MAU type is 1000BaseXFD-22.' ;
              }

              enum 1000BaseLXHD-23 {
                value 23 ;
                description 'Operational MAU type is 1000BaseLXHD-23.' ;
              }

              enum 1000BaseLXFD-24 {
                value 24 ;
                description 'Operational MAU type is 1000BaseLXFD-24.' ;
              }

              enum 1000BaseSXHD-25 {
                value 25 ;
                description 'Operational MAU type is 1000BaseSXHD-25.' ;
              }

              enum 1000BaseSXFD-26 {
                value 26 ;
                description 'Operational MAU type is 1000BaseSXFD-26.' ;
              }

              enum 1000BaseCXHD-27 {
                value 27 ;
                description 'Operational MAU type is 1000BaseCXHD-27.' ;
              }

              enum 1000BaseCXFD-28 {
                value 28 ;
                description 'Operational MAU type is 1000BaseCXFD-28.' ;
              }

              enum 1000BaseTHD-29 {
                value 29 ;
                description 'Operational MAU type is 1000BaseTHD-29.' ;
              }

              enum 1000BaseTFD-30 {
                value 30 ;
                description 'Operational MAU type is 1000BaseTFD-30.' ;
              }

              enum 10GigBaseX-31 {
                value 31 ;
                description 'Operational MAU type is 10GigBaseX-31.' ;
              }

              enum 10GigBaseLX4-32 {
                value 32 ;
                description 'Operational MAU type is 10GigBaseLX4-32.' ;
              }

              enum 10GigBaseR-33 {
                value 33 ;
                description 'Operational MAU type is 10GigBaseR-33.' ;
              }

              enum 10GigBaseER-34 {
                value 34 ;
                description 'Operational MAU type is 10GigBaseER-34.' ;
              }

              enum 10GigBaseLR-35 {
                value 35 ;
                description 'Operational MAU type is 10GigBaseLR-35.' ;
              }

              enum 10GigBaseSR-36 {
                value 36 ;
                description 'Operational MAU type is 10GigBaseSR-36.' ;
              }

              enum 10GigBaseW-37 {
                value 37 ;
                description 'Operational MAU type is 10GigBaseW-37.' ;
              }

              enum 10GigBaseEW-38 {
                value 38 ;
                description 'Operational MAU type is 10GigBaseEW-38.' ;
              }

              enum 10GigBaseLW-39 {
                value 39 ;
                description 'Operational MAU type is 10GigBaseLW-39.' ;
              }

              enum 10GigBaseSW-40 {
                value 40 ;
                description 'Operational MAU type is 10GigBaseSW-40.' ;
              }

              enum 10GigBaseCX4-41 {
                value 41 ;
                description 'Operational MAU type is 10GigBaseCX4-41.' ;
              }

              enum 2BaseTL-42 {
                value 42 ;
                description 'Operational MAU type is 2BaseTL-42.' ;
              }

              enum 10PassTS-43 {
                value 43 ;
                description 'Operational MAU type is 10PassTS-43.' ;
              }

              enum 100BaseBX10D-44 {
                value 44 ;
                description 'Operational MAU type is 100BaseBX10D-44.' ;
              }

              enum 100BaseBX10U-45 {
                value 45 ;
                description 'Operational MAU type is 100BaseBX10U-45.' ;
              }

              enum 100BaseLX10-46 {
                value 46 ;
                description 'Operational MAU type is 100BaseLX10-46.' ;
              }

              enum 1000BaseBX10D-47 {
                value 47 ;
                description 'Operational MAU type is 1000BaseBX10D-47.' ;
              }

              enum 1000BaseBX10U-48 {
                value 48 ;
                description 'Operational MAU type is 1000BaseBX10U-48.' ;
              }

              enum 1000BaseLX10-49 {
                value 49 ;
                description 'Operational MAU type is 1000BaseLX10-49.' ;
              }

              enum 1000BasePX10D-50 {
                value 50 ;
                description 'Operational MAU type is 1000BasePX10D-50.' ;
              }

              enum 1000BasePX10U-51 {
                value 51 ;
                description 'Operational MAU type is 1000BasePX10U-51.' ;
              }

              enum 1000BasePX20D-52 {
                value 52 ;
                description 'Operational MAU type is 1000BasePX20D-52.' ;
              }

              enum 1000BasePX20U-53 {
                value 53 ;
                description 'Operational MAU type is 1000BasePX20U-53.' ;
              }

              enum 10GbaseT-54 {
                value 54 ;
                description 'Operational MAU type is 10GbaseT-54.' ;
              }

              enum 10GbaseLRM-55 {
                value 55 ;
                description 'Operational MAU type is 10GbaseLRM-55.' ;
              }

              enum 1000baseKX-56 {
                value 56 ;
                description 'Operational MAU type is 1000baseKX-56.' ;
              }

              enum 10GbaseKX4-57 {
                value 57 ;
                description 'Operational MAU type is 10GbaseKX4-57.' ;
              }

              enum 10GbaseKR-58 {
                value 58 ;
                description 'Operational MAU type is 10GbaseKR-58.' ;
              }

              enum 10G1GbasePRXD1-59 {
                value 59 ;
                description 'Operational MAU type is 10G1GbasePRXD1-59.' ;
              }

              enum 10G1GbasePRXD2-60 {
                value 60 ;
                description 'Operational MAU type is 10G1GbasePRXD2-60.' ;
              }

              enum 10G1GbasePRXD3-61 {
                value 61 ;
                description 'Operational MAU type is 10G1GbasePRXD3-61.' ;
              }

              enum 10G1GbasePRXU1-62 {
                value 62 ;
                description 'Operational MAU type is 10G1GbasePRXU1-62.' ;
              }

              enum 10G1GbasePRXU2-63 {
                value 63 ;
                description 'Operational MAU type is 10G1GbasePRXU2-63.' ;
              }

              enum 10G1GbasePRXU3-64 {
                value 64 ;
                description 'Operational MAU type is 10G1GbasePRXU3-64.' ;
              }

              enum 10GbasePRD1-65 {
                value 65 ;
                description 'Operational MAU type is 10GbasePRD1-65.' ;
              }

              enum 10GbasePRD2-66 {
                value 66 ;
                description 'Operational MAU type is 10GbasePRD2-66.' ;
              }

              enum 10GbasePRD3-67 {
                value 67 ;
                description 'Operational MAU type is 10GbasePRD3-67.' ;
              }

              enum 10GbasePRU1-68 {
                value 68 ;
                description 'Operational MAU type is 10GbasePRU1-68.' ;
              }

              enum 10GbasePRU3-69 {
                value 69 ;
                description 'Operational MAU type is 10GbasePRU3-69.' ;
              }

              enum 40GbaseKR4-70 {
                value 70 ;
                description 'Operational MAU type is 40GbaseKR4-70.' ;
              }

              enum 40GbaseCR4-71 {
                value 71 ;
                description 'Operational MAU type is 40GbaseCR4-71.' ;
              }

              enum 40GbaseSR4-72 {
                value 72 ;
                description 'Operational MAU type is 40GbaseSR4-72.' ;
              }

              enum 40GbaseFR-73 {
                value 73 ;
                description 'Operational MAU type is 40GbaseFR-73.' ;
              }

              enum 40GbaseLR4-74 {
                value 74 ;
                description 'Operational MAU type is 40GbaseLR4-74.' ;
              }

              enum 100GbaseCR10-75 {
                value 75 ;
                description 'Operational MAU type is 100GbaseCR10-75.' ;
              }

              enum 100GbaseSR10-76 {
                value 76 ;
                description 'Operational MAU type is 100GbaseSR10-76.' ;
              }

              enum 100GbaseLR4-77 {
                value 77 ;
                description 'Operational MAU type is 100GbaseLR4-77.' ;
              }

              enum 100GbaseER4-78 {
                value 78 ;
                description 'Operational MAU type is 100GbaseER4-78.' ;
              }

              enum 1000baseT1-79 {
                value 79 ;
                description 'Operational MAU type is 1000baseT1-79.' ;
              }

              enum 1000basePX30D-80 {
                value 80 ;
                description 'Operational MAU type is 1000basePX30D-80.' ;
              }

              enum 1000basePX30U-81 {
                value 81 ;
                description 'Operational MAU type is 1000basePX30U-81.' ;
              }

              enum 1000basePX40D-82 {
                value 82 ;
                description 'Operational MAU type is 1000basePX40D-82.' ;
              }

              enum 1000basePX40U-83 {
                value 83 ;
                description 'Operational MAU type is 1000basePX40U-83.' ;
              }

              enum 10G1GbasePRXD4-84 {
                value 84 ;
                description 'Operational MAU type is 10G1GbasePRXD4-84.' ;
              }

              enum 10G1GbasePRXU4-85 {
                value 85 ;
                description 'Operational MAU type is 10G1GbasePRXU4-85.' ;
              }

              enum 10GbasePRD4-86 {
                value 86 ;
                description 'Operational MAU type is 10GbasePRD4-86.' ;
              }

              enum 10GbasePRU4-87 {
                value 87 ;
                description 'Operational MAU type is 10GbasePRU4-87.' ;
              }

              enum 25GbaseCR-88 {
                value 88 ;
                description 'Operational MAU type is 25GbaseCR-88.' ;
              }

              enum 25GbaseCRS-89 {
                value 89 ;
                description 'Operational MAU type is 25GbaseCRS-89.' ;
              }

              enum 25GbaseKR-90 {
                value 90 ;
                description 'Operational MAU type is 25GbaseKR-90.' ;
              }

              enum 25GbaseKRS-91 {
                value 91 ;
                description 'Operational MAU type is 25GbaseKRS-91.' ;
              }

              enum 25GbaseR-92 {
                value 92 ;
                description 'Operational MAU type is 25GbaseR-92.' ;
              }

              enum 25GbaseSR-93 {
                value 93 ;
                description 'Operational MAU type is 25GbaseSR-93.' ;
              }

              enum 25GbaseT-94 {
                value 94 ;
                description 'Operational MAU type is 25GbaseT-94.' ;
              }

              enum 40GbaseER4-95 {
                value 95 ;
                description 'Operational MAU type is 40GbaseER4-95.' ;
              }

              enum 40GbaseR-96 {
                value 96 ;
                description 'Operational MAU type is 40GbaseR-96.' ;
              }

              enum 40GbaseT-97 {
                value 97 ;
                description 'Operational MAU type is 40GbaseT-97.' ;
              }

              enum 100GbaseCR4-98 {
                value 98 ;
                description 'Operational MAU type is 100GbaseCR4-98.' ;
              }

              enum 100GbaseKR4-99 {
                value 99 ;
                description 'Operational MAU type is 100GbaseKR4-99.' ;
              }

              enum 100GbaseKP4-100 {
                value 100 ;
                description 'Operational MAU type is 100GbaseKP4-100.' ;
              }

              enum 100GbaseR-101 {
                value 101 ;
                description 'Operational MAU type is 100GbaseR-101.' ;
              }

              enum 100GbaseSR4-102 {
                value 102 ;
                description 'Operational MAU type is 100GbaseSR4-102.' ;
              }

            }

          }

          leaf rem-power-port-class {
            description 'Power Class of Power Via MDI of remote neighbor.' ;
            type enumeration {
              enum "Power-port-class:PD,Power-supported:Not-supported,Power-state:Disabled,Power-ability:Not-controlled" {
                value 0 ;
                description 'Power Class is PD, MDI power support is not supported, MDI power state is disabled, MDI power ability is not controlled.' ;
              }

              enum "Power-port-class:PSE,Power-supported:Not-supported,Power-state:Disabled,Power-ability:Not-controlled" {
                value 1 ;
                description 'Power Class is PSE, MDI power support is not supported, MDI power state is disabled, MDI power ability is not controlled.' ;
              }

              enum "Power-port-class:PD,Power-supported:Supported,Power-state:Disabled,Power-ability:Not-controlled" {
                value 2 ;
                description 'Power Class is PD, MDI power support is supported, MDI power state is disabled, MDI power ability is not controlled.' ;
              }

              enum "Power-port-class:PSE,Power-supported:Supported,Power-state:Disabled,Power-ability:Not-controlled" {
                value 3 ;
                description 'Power Class is PSE, MDI power support is supported, MDI power state is disabled, MDI power ability is not controlled.' ;
              }

              enum "Power-port-class:PD,Power-supported:Not-supported,Power-state:Enabled,Power-ability:Not-controlled" {
                value 4 ;
                description 'Power Class is PD, MDI power support is not supported, MDI power state is enabled, MDI power ability is not controlled.' ;
              }

              enum "Power-port-class:PSE,Power-supported:Not-supported,Power-state:Enabled,Power-ability:Not-controlled" {
                value 5 ;
                description 'Power Class is PSE, MDI power support is not supported, MDI power state is enabled, MDI power ability is controlled.' ;
              }

              enum "Power-port-class:PD,Power-supported:Supported,Power-state:Enabled,Power-ability:Not-controlled" {
                value 6 ;
                description 'Power Class is PD, MDI power support is supported, MDI power state is enabled, MDI power ability is not controlled.' ;
              }

              enum "Power-port-class:PSE,Power-supported:Supported,Power-state:Enabled,Power-ability:Not-controlled" {
                value 7 ;
                description 'Power Class is PSE, MDI power support is supported, MDI power state is enabled, MDI power ability is not controlled.' ;
              }

              enum "Power-port-class:PD,Power-supported:Not-supported,Power-state:Disabled,Power-ability:Controlled" {
                value 8 ;
                description 'Power Class is PD, MDI power support is not supported, MDI power state is disabled, MDI power ability is controlled.' ;
              }

              enum "Power-port-class:PSE,Power-supported:Not-supported,Power-state:Disabled,Power-ability:Controlled" {
                value 9 ;
                description 'Power Class is PSE, MDI power support is not supported, MDI power state is disabled, MDI power ability is controlled.' ;
              }

              enum "Power-port-class:PD,Power-supported:Supported,Power-state:Disabled,Power-ability:Controlled" {
                value 10 ;
                description 'Power Class is PD, MDI power support is supported, MDI power state is disabled, MDI power ability is controlled.' ;
              }

              enum "Power-port-class:PSE,Power-supported:Supported,Power-state:Disabled,Power-ability:Controlled" {
                value 11 ;
                description 'Power Class is PSE, MDI power support is supported, MDI power state is disabled, MDI power ability is controlled.' ;
              }

              enum "Power-port-class:PD,Power-supported:Not-supported,Power-state:Enabled,Power-ability:Controlled" {
                value 12 ;
                description 'Power Class is PD, MDI power support is not supported, MDI power state is enabled, MDI power ability is controlled.' ;
              }

              enum "Power-port-class:PSE,Power-supported:Not-supported,Power-state:Enabled,Power-ability:Controlled" {
                value 13 ;
                description 'Power Class is PSE, MDI power support is not supported, MDI power state is enabled, MDI power ability is controlled.' ;
              }

              enum "Power-port-class:PD,Power-supported:Supported,Power-state:Enabled,Power-ability:Controlled" {
                value 14 ;
                description 'Power Class is PD, MDI power support is supported, MDI power state is enabled, MDI power ability is controlled.' ;
              }

              enum "Power-port-class:PSE,Power-supported:Supported,Power-state:Enabled,Power-ability:Controlled" {
                value 15 ;
                description 'Power Class is PSE, MDI power support is supported, MDI power state is enabled, MDI power ability is controlled.' ;
              }

            }

          }

          leaf rem-pse-power-pair {
            description 'PSE power pair of Power Via MDI of remote neighbor.' ;
            type enumeration {
              enum Unknown {
                value 0 ;
                description 'MDI power pair is Unknown.' ;
              }

              enum Signal {
                value 1 ;
                description 'MDI power pair is Signal.' ;
              }

              enum Spare {
                value 2 ;
                description 'MDI power pair is Spare.' ;
              }

            }

          }

          leaf rem-port-power-class {
            description 'Power Class of Power Via MDI of remote neighbor.' ;
            type enumeration {
              enum Unknown {
                value 0 ;
                description 'MDI power class is Unknown.' ;
              }

              enum Class0 {
                value 1 ;
                description 'MDI power class is Class0.' ;
              }

              enum Class1 {
                value 2 ;
                description 'MDI power class is Class1.' ;
              }

              enum Class2 {
                value 3 ;
                description 'MDI power class is Class2.' ;
              }

              enum Class3 {
                value 4 ;
                description 'MDI power class is Class3.' ;
              }

              enum Class4 {
                value 5 ;
                description 'MDI power class is Class4.' ;
              }

            }

          }

          leaf rem-maximum-frame-size {
            description 'Maximum Frame Size of remote neighbor.' ;
            type uint16 ;

          }

          ncd:select local-ifname ;
          ncd:select "local-ifname mac-type" ;
          ncd:select "local-ifname mac-type neighbor-id" ;
          ncd:revise-date 2022-12-15 ;
        }

      }

      container localsystemdata {
        description 'Local system data information of LLDP.' ;
        leaf chassis-id-subtype {
          description 'Chassis ID subtype of LLDP local system data.' ;
          type enumeration {
            enum macAddress {
              value 4 ;
              description 'MAC address.' ;
            }

          }

        }

        leaf chassis-id {
          type string ;

          description 'Chassis ID of LLDP local system data.' ;
          ncd:revise-date 2024-11-27 ;
        }

        leaf system-name {
          type string ;

          description 'System name of LLDP local system data.' ;
          ncd:revise-date 2024-11-27 ;
        }

        leaf system-desc {
          type string ;

          description 'System description of LLDP local system data.' ;
          ncd:revise-date 2024-11-27 ;
        }

      }

    }

  }

  notification lldp-neighbor {
    description 'The LLDP notification when neighbor is added or deleted.' ;
    container neighbor {
      config false ;
      description 'The LLDP notification when neighbor is added or deleted.' ;
      list neighbor-info {
        description 'The LLDP notification when neighbor is added or deleted.' ;
        key "local-ifname neighbor-id" ;
        leaf local-ifname {
          description 'Local port name.' ;
          type ncd:ifname {
            length 1..31 ;

          }

        }

        leaf neighbor-id {
          description 'Neighbor ID.' ;
          type uint32 {
            range 1..4294967295 ;

          }

        }

        leaf rem-chassis-id {
          type string ;

          description 'Value to indicate basis identifier in chassis ID field.' ;
          ncd:revise-date 2024-11-27 ;
        }

        leaf rem-port-id {
          type string ;

          description 'Remote port name in neighbor.' ;
          ncd:revise-date 2024-11-27 ;
        }

        leaf action {
          description 'LLDP neighbor action type, add or delete.' ;
          type enumeration {
            enum add {
              value 1 ;
              description 'LLDP neighbor add.' ;
            }

            enum delete {
              value 2 ;
              description 'LLDP neighbor delete.' ;
            }

            enum update {
              value 3 ;
              description 'LLDP neighbor update.' ;
            }

          }

        }

        leaf rem-sys-name {
          description 'System name of remote neighbor.' ;
          type string ;
          ncd:revise-date 2019-09-02 ;
        }

        container rem-man-addresses {
          description 'Management address of remote neighbor.' ;
          list rem-man-address {
            description 'Management address of remote neighbor.' ;
            key "man-addr-subtype man-address" ;
            leaf man-addr-subtype {
              description "Subtype of the management address.
              The value '1' indicates the IPv4 address.
              The value '2' indicates the IPv6 address.
              For the definition of other values, refer to IANA-ADDRESS-FAMILY-NUMBERS-MIB." ;
              type uint8 {
                range 0..255 ;

              }

            }

            leaf man-address {
              type string ;

              description 'Management address of remote neighbor.' ;
              ncd:revise-date 2024-11-27 ;
            }

            ncd:select "man-addr-subtype man-address" ;
          }
          ncd:revise-date 2020-10-30 ;
        }

      }

    }

  }

}
