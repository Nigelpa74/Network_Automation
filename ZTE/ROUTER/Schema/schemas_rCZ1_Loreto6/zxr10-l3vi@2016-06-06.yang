module zxr10-l3vi {
  namespace 'http://www.zte.com.cn/zxr10/netconf/schema/rosng/l3vi'
            ;
  prefix l3vi ;
  import zxr10-netconf-defs {
    prefix ncd ;
    revision-date 2013-11-22 ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The netconf module to describe the Interface Relation.Like the b'
            + 'inding relation between l3vi interface and ac interface.'
              ;
  revision 2016-06-06 {
    description 'The initial version'
                ;
  }
  container configuration {
    description 'Configure the binding relation between interfaces'
                ;
    container l3vi {
      description 'Describe the parameters of l3vi interface relation to be con'
                + 'figured'
                  ;
      container l3vi-bind {
        description 'Describe the parameters of l3vi interface binding relation'
                  + ' to be configured'
                    ;
        list interface {
          description 'The list of interfaces for configuring parameters'
                      ;
          key l3vi-interface ;
          leaf l3vi-interface {
            description 'l3vi interface name'
                        ;
            type ncd:ifname ;
          }
          leaf bind-interface {
            description 'bindind interface name'
                        ;
            type ncd:ifname ;
            mandatory true ;
          }
        }
      }
    }
  }
}
