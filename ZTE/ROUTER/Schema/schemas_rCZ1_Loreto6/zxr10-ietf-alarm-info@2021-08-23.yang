module zxr10-ietf-alarm-info {
  namespace 'http://www.zte.com.cn/zxr10/netconf/schema/rosng/ietf-alarm-info'
            ;
  prefix zxr10-al ;
  import ietf-alarms {
    prefix al ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'This module defines an interface for ietf alarm.'
              ;
  revision 2021-08-23 {
    description 'Initial revision.'
                ;
  }
  identity zxr10-al-alarm-type-id {
    base al:alarm-type-id ;
  }
  identity equipment-alarm {
    base zxr10-al-alarm-type-id ;
  }
  identity environmental-alarm {
    base zxr10-al-alarm-type-id ;
  }
  identity communications-alarm {
    base zxr10-al-alarm-type-id ;
  }
  identity quality-of-service-alarm {
    base zxr10-al-alarm-type-id ;
  }
  identity processing-error-alarm {
    base zxr10-al-alarm-type-id ;
  }
  identity device-event {
    base zxr10-al-alarm-type-id ;
  }
}
