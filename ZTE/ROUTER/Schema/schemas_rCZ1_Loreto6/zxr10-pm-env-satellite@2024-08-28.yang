module zxr10-pm-env-satellite {
  namespace "http://www.zte.com.cn/zxr10/netconf/schema/rosng/pm-env-satellite" ;
  prefix pm-env-satellite ;
  yang-version 1 ;
  import zxr10-netconf-defs {
    prefix ncd ;
  }

  organization "ZTE Corporation" ;
  contact "ZTE Corporation
  Nanjing Institute of ZTE Corporation
  No.68 Zijinghua Rd. Yuhuatai District, Nanjing, China
  Tel: +86-25-52870000" ;
  revision 2024-08-28 {
    description 'add redundancy' ;
  }

  revision 2024-08-23 {
    description 'add boards and reload-slot container' ;
  }

  revision 2024-07-18 {
    description 'add container power-on-off' ;
  }

  revision 2023-05-29 {
    description 'add list:smartgroup' ;
  }

  revision 2023-02-10 {
    description 'add leaf:
speed,power-type,power-status,major-threshold' ;
  }

  revision 2022-09-05 {
    description 'State optical add leaf:
recv-wavelength,current,temperature,voltage 3.3,voltage 5,sensitivity,overload,power-range,authentication,authentication-code,product-s/n,product-date,optical-stand' ;
  }

  revision 2022-08-25 {
    description 'Leaf peid max value add perfcode.' ;
  }

  revision 2022-05-18 {
    description 'Add optical Rx Tx warning threshold.' ;
  }

  revision 2021-05-18 {
    description 'Change vendor-name,vendor-pn,vendor-sn,vendor-rev Length to 24.' ;
  }

  revision 2021-03-03 {
    description 'add reload system.' ;
  }

  revision 2021-02-02 {
    description 'add fan temp sa' ;
  }

  revision 2021-01-29 {
    description 'Initialize version.' ;
  }

  container state {
    config false ;
    container env {
      container opticals {
        list optical {
          key 'peid if-name' ;
          leaf peid {
            type uint32 {
              range 1..250 ;

            }

          }

          leaf if-name {
            type string ;

          }

          leaf optical-status {
            type enumeration {
              enum offline {
                value 0 ;
                description 'The optical is offline.' ;
              }

              enum online {
                value 1 ;
                description 'The optical is online.' ;
              }

            }

            default offline ;
          }

          leaf optical-electric-mode {
            type uint8 ;

          }

          leaf transceiver-type {
            type ncd:string-all ;

          }

          leaf single-fiber-double-orient {
            type uint8 ;

          }

          leaf work-speed {
            type uint32 ;

            ncd:revise-date 2022-09-05 ;
          }

          leaf media-type {
            type uint8 ;

          }

          leaf send-wavelength {
            type uint32 ;

          }

          leaf recv-wavelength {
            type uint32 ;

            ncd:revise-date 2022-09-05 ;
          }

          leaf length-9um-smf {
            type uint32 ;

          }

          leaf length-50um-om2 {
            type uint32 ;

          }

          leaf length-62um-om1 {
            type uint32 ;

          }

          leaf length-50um-om3 {
            type uint32 ;

          }

          leaf copper-line {
            type uint32 ;

            description 'Copper cable length, unit: m.
If the optical module belongs to the 8472 protocol or 8436 protocol and is in fiber mode, then this field is multiplexed as the length of the optical cable. For the optical module of the 8472 protocol, this value needs to be multiplied by 10 times,For the optical module of the 8436 protocol, this value needs to be multiplied by 2 times. When connecting to Active Optical Fiber, there is no need to multiply by a factor.' ;
          }

          leaf sonet-codes {
            type ncd:string-all ;

          }

          leaf ethernet-codes {
            type ncd:string-all ;

          }

          leaf vendor-name {
            type ncd:string-all ;

          }

          leaf vendor-pn {
            type ncd:string-all ;

          }

          leaf vendor-sn {
            type ncd:string-all ;

          }

          leaf vendor-rev {
            type ncd:string-all ;

          }

          leaf send-power {
            type ncd:string-all ;

          }

          leaf receive-power {
            type ncd:string-all ;

          }

          leaf channel-number {
            type uint8 ;

          }

          leaf connector-type {
            type ncd:string-all ;

          }

          leaf high-warning-threshold-rx {
            type ncd:string-all ;

            ncd:revise-date 2022-05-18 ;
          }

          leaf low-warning-threshold-rx {
            type ncd:string-all ;

            ncd:revise-date 2022-05-18 ;
          }

          leaf high-warning-threshold-tx {
            type ncd:string-all ;

            ncd:revise-date 2022-05-18 ;
          }

          leaf low-warning-threshold-tx {
            type ncd:string-all ;

            ncd:revise-date 2022-05-18 ;
          }

          leaf current {
            type ncd:string-all ;

            ncd:revise-date 2022-09-05 ;
          }

          leaf temperature {
            type ncd:string-all ;

            ncd:revise-date 2022-09-05 ;
          }

          leaf voltage3.3 {
            type ncd:string-all ;

            ncd:revise-date 2022-09-05 ;
          }

          leaf voltage5 {
            type ncd:string-all ;

            ncd:revise-date 2022-09-05 ;
          }

          leaf sensitivity {
            type ncd:string-all ;

            ncd:revise-date 2022-09-05 ;
          }

          leaf overload {
            type ncd:string-all ;

            ncd:revise-date 2022-09-05 ;
          }

          leaf power-range-tx {
            type ncd:string-all ;

            ncd:revise-date 2022-09-05 ;
          }

          leaf authentication {
            type ncd:string-all ;

            ncd:revise-date 2022-09-05 ;
          }

          leaf authentication-code {
            type ncd:string-all ;

            ncd:revise-date 2022-09-05 ;
          }

          leaf product-serial-number {
            type ncd:string-all ;

            ncd:revise-date 2022-09-05 ;
          }

          leaf product-date {
            type ncd:string-all ;

            ncd:revise-date 2022-09-05 ;
          }

          leaf optical-stand {
            type uint8 ;

            ncd:revise-date 2022-09-05 ;
          }

        }

        list smartgroup {
          key 'peid if-name' ;
          leaf peid {
            type uint32 {
              range 1..250 ;

            }

          }

          leaf if-name {
            type string ;

          }

          leaf optical-status {
            type enumeration {
              enum offline {
                value 0 ;
                description 'The optical is offline.' ;
              }

              enum online {
                value 1 ;
                description 'The optical is online.' ;
              }

            }

            default offline ;
          }

          leaf optical-electric-mode {
            type uint8 ;

          }

          leaf transceiver-type {
            type ncd:string-all ;

          }

          leaf single-fiber-double-orient {
            type uint8 ;

          }

          leaf work-speed {
            type uint32 ;

          }

          leaf media-type {
            type uint8 ;

          }

          leaf send-wavelength {
            type uint32 ;

          }

          leaf recv-wavelength {
            type uint32 ;

          }

          leaf length-9um-smf {
            type uint32 ;

          }

          leaf length-50um-om2 {
            type uint32 ;

          }

          leaf length-62um-om1 {
            type uint32 ;

          }

          leaf length-50um-om3 {
            type uint32 ;

          }

          leaf copper-line {
            type uint32 ;

            description 'Copper cable length, unit: m.
If the optical module belongs to the 8472 protocol or 8436 protocol and is in fiber mode, then this field is multiplexed as the length of the optical cable. For the optical module of the 8472 protocol, this value needs to be multiplied by 10 times,For the optical module of the 8436 protocol, this value needs to be multiplied by 2 times. When connecting to Active Optical Fiber, there is no need to multiply by a factor.' ;
          }

          leaf sonet-codes {
            type ncd:string-all ;

          }

          leaf ethernet-codes {
            type ncd:string-all ;

          }

          leaf vendor-name {
            type ncd:string-all ;

          }

          leaf vendor-pn {
            type ncd:string-all ;

          }

          leaf vendor-sn {
            type ncd:string-all ;

          }

          leaf vendor-rev {
            type ncd:string-all ;

          }

          leaf send-power {
            type ncd:string-all ;

          }

          leaf receive-power {
            type ncd:string-all ;

          }

          leaf channel-number {
            type uint8 ;

          }

          leaf connector-type {
            type ncd:string-all ;

          }

          leaf high-warning-threshold-rx {
            type ncd:string-all ;

          }

          leaf low-warning-threshold-rx {
            type ncd:string-all ;

          }

          leaf high-warning-threshold-tx {
            type ncd:string-all ;

          }

          leaf low-warning-threshold-tx {
            type ncd:string-all ;

          }

          leaf current {
            type ncd:string-all ;

          }

          leaf temperature {
            type ncd:string-all ;

          }

          leaf voltage3.3 {
            type ncd:string-all ;

          }

          leaf voltage5 {
            type ncd:string-all ;

          }

          leaf sensitivity {
            type ncd:string-all ;

          }

          leaf overload {
            type ncd:string-all ;

          }

          leaf power-range-tx {
            type ncd:string-all ;

          }

          leaf authentication {
            type ncd:string-all ;

          }

          leaf authentication-code {
            type ncd:string-all ;

          }

          leaf product-serial-number {
            type ncd:string-all ;

          }

          leaf product-date {
            type ncd:string-all ;

          }

          leaf optical-stand {
            type uint8 ;

          }

          ncd:revise-date 2023-05-29 ;
        }

      }

      container temperatures {
        list temperature {
          key peid ;
          leaf peid {
            type uint32 {
              range 1..250 ;

            }

          }

          leaf shelf {
            description 'Shelf no.' ;
            type uint8 ;

          }

          leaf slot {
            description 'Slot no.' ;
            type uint8 ;

          }

          leaf current-temperature {
            type int32 ;

          }

          leaf fatal-threshold {
            type uint32 ;

          }

          leaf major-threshold {
            type uint32 ;

            ncd:revise-date 2023-02-10 ;
          }

        }

        ncd:revise-date 2021-02-02 ;
      }

      container fans {
        list fan {
          key peid ;
          leaf peid {
            type uint32 {
              range 1..250 ;

            }

          }

          leaf shelf {
            description 'Shelf no.' ;
            type uint8 ;

          }

          leaf group {
            description 'Slot no.' ;
            type uint8 ;

          }

          leaf index {
            description 'Shelf no.' ;
            type uint8 ;

          }

          leaf fan-present {
            type uint8 ;

          }

          leaf work-status {
            type uint8 ;

          }

          leaf speed {
            description 'Fan run speed.' ;
            type uint8 ;

            ncd:revise-date 2023-02-10 ;
          }

        }

        ncd:revise-date 2021-02-02 ;
      }

      container powers {
        list power {
          key peid ;
          leaf peid {
            type uint32 {
              range 1..250 ;

            }

          }

          leaf shelf {
            description 'Shelf no.' ;
            type uint8 ;

          }

          leaf group-num {
            description 'Group number' ;
            type uint8 ;

          }

          leaf group-name {
            description 'Group name' ;
            type ncd:string-all ;

          }

          leaf power-used {
            description 'Power used' ;
            type ncd:string-all ;

          }

          leaf outputorInput1-voltage {
            description 'Output or input voltage.' ;
            type uint32 ;

          }

          leaf outputorInput1-current {
            description 'Output or input current.' ;
            type uint32 ;

          }

          leaf power-type {
            description 'power type.' ;
            type enumeration {
              enum "N/A" {
                value 0 ;
              }

              enum DC {
                value 1 ;
              }

              enum AC {
                value 2 ;
              }

            }

            ncd:revise-date 2023-02-10 ;
          }

          leaf phy-status {
            description 'phy status.' ;
            type enumeration {
              enum online {
                value 0 ;
              }

              enum offline {
                value 1 ;
              }

              enum unknown {
                value 255 ;
              }

            }

            ncd:revise-date 2023-02-10 ;
          }

          leaf power-status {
            type enumeration {
              enum normal {
                value 0 ;
              }

              enum abnormal {
                value 1 ;
              }

              enum unknown {
                value 255 ;
              }

            }

            ncd:revise-date 2023-02-10 ;
          }

          leaf output-voltage {
            description 'Output voltage.' ;
            type ncd:string-all ;

            ncd:revise-date 2023-02-10 ;
          }

          leaf output-current {
            description 'Output current.' ;
            type ncd:string-all ;

            ncd:revise-date 2023-02-10 ;
          }

          leaf module-num {
            description 'Module number' ;
            type uint8 ;

            ncd:revise-date 2023-02-10 ;
          }

        }

        ncd:revise-date 2021-05-18 ;
      }
	  container boards {
        list board {
          key 'peid shelf slot subslot'
              ;
          leaf peid {
            description 'Peid.' ;
            type uint32 {
              range 1..250 ;
            }
          }
          leaf shelf {
            description 'Shelf number.' ;
            type uint8 {
              range 0..255 ;
            }
          }
          leaf slot {
            description 'Slot number.' ;
            type uint8 {
              range 0..255 ;
            }
          }
          leaf subslot {
            description 'Subslot number.' ;
            type uint8 {
              range 0..255 ;
            }
          }
          leaf board-status {
            description 'Board status.' ;
            type enumeration {
              enum online-work {
                value 0 ;
              }
              enum online-poweroff {
                value 1 ;
              }
              enum offline {
                value 2 ;
              }
              enum abnormal {
                value 3 ;
              }
            }
          }

          ncd:select peid ;
          ncd:select "peid shelf" ;
          ncd:select "peid shelf slot" ;
          ncd:select "peid shelf slot subslot" ;
        }
        ncd:revise-date 2024-08-23 ;
      }
    }

  }

  container operation {
    config false ;
    container env {
      container reload-systems {
        list reload-system {
          key peid ;
          leaf peid {
            description 'Peid.' ;
            type uint32 {
              range 1..250 ;

            }

          }

          leaf reload-mode {
            description 'Reload mode.' ;
            type enumeration {
              enum force {
                value 0 ;
              }

            }

          }

          ncd:select peid ;
        }

      }

      container power-on-off {
        container boards {
          list board {
            leaf peid {
              type uint32 {
                range 1..250 ;

              }

              description 'Peid.' ;
            }

            leaf shelf {
              type uint8 {
                range 0..255 {
                  description 'shelf range.' ;
                }

              }

            }

            leaf slot {
              type uint8 {
                range 0..255 {
                  description 'slot range.' ;
                }

              }

            }

            choice power-mode {
              case board-on {
                leaf board-power-on {
                  type enumeration {
                    enum on {
                      value 1 ;
                    }

                  }

                  mandatory true ;
                }

              }

              case board-off {
                leaf board-power-off {
                  type enumeration {
                    enum off {
                      value 0 ;
                    }

                  }

                  mandatory true ;
                }

                leaf set-mode {
                  type enumeration {
                    enum force {
                      value 0 ;
                    }

                    enum grace {
                      value 1 ;
                    }

                  }

                  mandatory true ;
                }

              }

              case sub-board {
                leaf subslot {
                  type uint8 {
                    range 0..3 ;

                  }

                  mandatory true ;
                }

                leaf power-status {
                  type enumeration {
                    enum off {
                      value 0 ;
                    }

                    enum on {
                      value 1 ;
                    }

                  }

                  mandatory true ;
                }

              }

              mandatory true ;
            }

            key 'peid shelf slot' ;
          }

          ncd:revise-date 2024-07-18 ;
        }

      }
      container reload-slot {
        leaf peid {
          type uint32 {
            range 1..250 {
              description 'Peid.'
                          ;
            }
          }

          mandatory true ;
        }

        leaf shelf {
          type uint8 {
            range 0..255 {
              description 'Shelf number.'
                          ;
            }
          }

          mandatory true ;
        }
        leaf slot {
          type uint8 {
            range 0..255 {
              description 'Slot number.'
                          ;
            }
          }

          mandatory true ;
        }
        leaf reload-mode {
          type enumeration {
            enum force {
              value 0 ;
            }
            enum grace {
              value 1 ;
            }
          }

        }

        presence reload-slot ;
        ncd:revise-date 2024-08-23 ;
      }

      container redundancy {
        leaf peid {
          type uint32 {
            range 1..250 {
              description 'Peid.' ;
            }

          }

        }

        choice granularityctrl {
          case netelement {
            leaf name {
              type enumeration {
                enum sc {
                  value 1 ;
                }

              }

            }

          }

        }

        leaf mode {
          type enumeration {
            enum force {
              value 0 ;
            }

            enum grace {
              value 1 ;
            }

          }

        }

        ncd:revise-date 2024-08-28 ;
      }

    }

    ncd:revise-date 2021-03-03 ;
  }

}
