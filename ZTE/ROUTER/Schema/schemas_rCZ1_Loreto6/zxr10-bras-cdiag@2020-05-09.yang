module zxr10-bras-cdiag {
  namespace 'http://www.zte.com.cn/zxr10/netconf/schema/rosng/bras-cdiag'
            ;
  prefix bras-cdiag ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The netconf module to describe cdiag.'
              ;
  revision 2020-05-09 {
    description 'Add the node cdiag-uni-log mode'
                ;
  }
  revision 2020-04-14 {
    description 'Initial version'
                ;
  }
  container configuration {
    description 'Configuration mode'
                ;
    container bras-cdiag {
      description 'Configuration for cdiag mode'
                  ;
      container cdiag-high-perf-log {
        description 'Enter context diagnose high perf log mode'
                    ;
        leaf high-perf-log-isEnable {
          description 'High performance log isEnable'
                      ;
          type enumeration {
            enum disable {
              value 0 ;
              description 'Disable high performance log'
                          ;
            }
            enum enable {
              value 1 ;
              description 'Enable high performance log'
                          ;
            }
          }
          default enable ;
        }
        leaf write-period {
          description 'Congfig high performance log write period'
                      ;
          type uint32 {
            range 1..2592000 {
              description 'Write period(s)'
                          ;
            }
          }
          default 300 ;
        }
      }
      container cdiag-uni-log {
        description 'Enter context diagnose uni log mode'
                    ;
        leaf uni-log-isEnable {
          description 'UniLog isEnable'
                      ;
          type enumeration {
            enum disable {
              value 0 ;
              description 'Disable uni log'
                          ;
            }
            enum enable {
              value 1 ;
              description 'Enable uni log'
                          ;
            }
          }
          default enable ;
        }
        ncd:revise-date 2020-05-09 ;
      }
    }
  }
}
