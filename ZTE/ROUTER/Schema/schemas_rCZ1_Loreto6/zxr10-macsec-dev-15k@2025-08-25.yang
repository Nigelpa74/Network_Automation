module zxr10-macsec-dev-15k {
  namespace 'http://www.zte.com.cn/zxr10/netconf/schema/rosng/macsec-dev-15k'
            ;
  prefix macsec-dev-15k ;
  import zxr10-macsec {
    prefix macsec ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The deviation file for 15k.'
              ;
  revision 2025-08-25 {
    description 'update project label'
                ;
  }
  deviation "/macsec:configuration/macsec:macsec/macsec:interfaces/macsec:macsecs/macsec:macsec/macsec:cipher-suite" {
    deviate replace {
      type enumeration {
        enum gcm-aes-128 {
          value 1 ;
        }

        enum gcm-aes-xpn-128 {
          value 2 ;
        }

        enum gcm-aes-256 {
          value 3 ;
        }
        
        enum gcm-aes-xpn-256 {
          value 4 ;
        }
        
        enum gcm-sm4-128 {
          value 5 ;
        }
        
        enum gcm-sm4-xpn-128 {
          value 6 ;
        }
      }
    }
  }
}
