module zxr10-prefix-list {
  namespace 'http://www.zte.com.cn/zxr10/netconf/schema/rosng/prefix-list'
            ;
  prefix pfl ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The netconf module to describe prefix-list.'
              ;
  revision 2020-04-23 {
    description 'Modify the range of leaf:/configuration/prefix-list/ipv4/ipv4-'
              + 'pfls/ipv4-pfl/name;'+"\n"
              + '/configuration/prefix-list/ipv4/ipv4-descriptions/ipv4-descrip'
              + 'tion/name;'+"\n"
              + '/configuration/prefix-list/ipv6/ipv6-pfls/ipv6-pfl/name;'+"\n"
              + '/configuration/prefix-list/ipv6/ipv6-descriptions/ipv6-descrip'
              + 'tion/name.'
                ;
  }
  revision 2013-12-02 {
    description 'Initial version'
                ;
  }
  container configuration {
    description "IP prefix-list's configuration."
                ;
    container prefix-list {
      description "IPv4/6-prefix-list's configuration."
                  ;
      container ipv4 {
        description "IPv4-prefix-list's configuration."
                    ;
        container ipv4-pfls {
          description "IPv4-prefix-list's configuration."
                      ;
          list ipv4-pfl {
            description "IPv4-prefix-list's configuration."
                        ;
            key 'name sequence'
                ;
            leaf name {
              description 'Name of the prefix list.'
                          ;
              type string {
                length 1..169 {
                  description 'The length of name of prefix-list is from 1 to 1'
                            + '69 chars.'
                              ;
                }
              }
            }
            leaf sequence {
              description 'The sequence number for the prefix list.'
                          ;
              type uint32 {
                range 1..4294967294 {
                  description 'The range of sequence number for the prefix list'
                            + ' is from 1 to 4294967294.'
                              ;
                }
              }
            }
            leaf deny-permit {
              description 'Deny:Specify packets to reject;'+"\n"
                        + 'Permit:Specify packets to permit.'
                          ;
              type enumeration {
                enum deny {
                  value 0 ;
                  description 'Deny:Specify packets to reject.'
                              ;
                }
                enum permit {
                  value 1 ;
                  description 'Permit:Specify packets to permit.'
                              ;
                }
              }
              mandatory true ;
            }
            leaf ipv4-address {
              description 'Set the network number,for example:A.B.C.D.'
                          ;
              type ncd:ipv4-address ;
              mandatory true ;
            }
            leaf mask-length {
              description 'The length (in bits) of the network mask.'
                          ;
              type ncd:ipv4-mask-length ;
              mandatory true ;
            }
            leaf ge {
              description 'Minimum mask length to be matched.'+"\n"
                        + 'Normally,range of the value is :mask-length(ipv4-mas'
                        + 'k)<ge-mask<=le-mask<=32.'
                          ;
              type uint8 {
                range 1..32 {
                  description 'The range of minimum mask length is from 1 to 32.'
                              ;
                }
              }
            }
            leaf le {
              description 'Maximum mask length to be matched.'+"\n"
                        + 'Normally ,range of the value is :mask-length(ipv4-ma'
                        + 'sk)<ge-mask<=le-mask<=32.'
                          ;
              type uint8 {
                range 1..32 {
                  description 'The range of maximum mask length is from 1 to 32.'
                              ;
                }
              }
            }
          }
        }
        container ipv4-descriptions {
          description "IPv4 prefix-list's description."
                      ;
          list ipv4-description {
            description "IPv4 prefix-list's description."
                        ;
            key name ;
            leaf name {
              description 'Name of the prefix list.'
                          ;
              type string {
                length 1..169 {
                  description 'The length of name of prefix-list is from 1 to 1'
                            + '69 chars.'
                              ;
                }
              }
            }
            leaf description {
              description 'Text description of the prefix list (1-79).'
                          ;
              type ncd:string-with-blank {
                length 1..79 {
                  description 'The length of description of prefix-list is from'
                            + ' 1 to 79.'
                              ;
                }
              }
              mandatory true ;
            }
          }
        }
      }
      container ipv6 {
        description "IPv6-prefix-list's configuration."
                    ;
        container ipv6-pfls {
          description "IPv6-prefix-list's configuration."
                      ;
          list ipv6-pfl {
            description "IPv6-prefix-list's configuration."
                        ;
            key 'name sequence'
                ;
            leaf name {
              description 'Name of the prefix list.'
                          ;
              type string {
                length 1..169 {
                  description 'The length of name of prefix-list is from 1 to 1'
                            + '69 chars.'
                              ;
                }
              }
            }
            leaf sequence {
              description 'The sequence number for the prefix list.'
                          ;
              type uint32 {
                range 1..4294967294 {
                  description 'The range of sequence number for the prefix list'
                            + ' is from 1 to 4294967294.'
                              ;
                }
              }
            }
            leaf deny-permit {
              description 'Deny:Specify packets to reject;'+"\n"
                        + 'Permit:Specify packets to permit.'
                          ;
              type enumeration {
                enum deny {
                  value 0 ;
                  description 'Deny:Specify packets to reject.'
                              ;
                }
                enum permit {
                  value 1 ;
                  description 'Permit:Specify packets to permit.'
                              ;
                }
              }
              mandatory true ;
            }
            leaf ipv6-address {
              description "IPv6's Source address. For example:<X:X::X:X>."
                          ;
              type ncd:ipv6-address ;
              mandatory true ;
            }
            leaf mask-length {
              description 'The length (in bits) of the network mask.'
                          ;
              type ncd:ipv6-mask-length ;
              mandatory true ;
            }
            leaf ge {
              description 'Minimum mask length to be matched.'+"\n"
                        + 'Normally,range of the value is :ipv6-mask<ge-mask<=l'
                        + 'e-mask<=128.'
                          ;
              type uint8 {
                range 1..128 {
                  description 'The range of minimum mask length is from 1 to 12'
                            + '8.'
                              ;
                }
              }
            }
            leaf le {
              description 'Maximum mask length to be matched.'+"\n"
                        + 'Normally,range of the value is :ipv6-mask<ge-mask<=l'
                        + 'e-mask<=128.'
                          ;
              type uint8 {
                range 1..128 {
                  description 'The range of maximum mask length is from 1 to 12'
                            + '8.'
                              ;
                }
              }
            }
          }
        }
        container ipv6-descriptions {
          description "IPv6 prefix-list's description."
                      ;
          list ipv6-description {
            description "IPv6 prefix-list's description."
                        ;
            key name ;
            leaf name {
              description 'Name of the prefix list.'
                          ;
              type string {
                length 1..169 {
                  description 'The length of name of prefix-list is from 1 to 1'
                            + '69 chars.'
                              ;
                }
              }
            }
            leaf description {
              description 'Text description of the prefix list (1-79).'
                          ;
              type ncd:string-with-blank {
                length 1..79 {
                  description 'The length of description of prefix-list is from'
                            + ' 1 to 79.'
                              ;
                }
              }
              mandatory true ;
            }
          }
        }
      }
    }
  }
}
