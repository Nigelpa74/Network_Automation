module zxr10-interfaces {
  namespace "http://www.zte.com.cn/zxr10/netconf/schema/rosng/interfaces" ;
  prefix interface ;
  yang-version 1 ;
  import zxr10-netconf-defs {
    prefix ncd ;
  }

  organization "ZTE Corporation" ;
  contact "ZTE Corporation
  Nanjing Institute of ZTE Corporation
  No.68 Zijinghua Rd. Yuhuatai District, Nanjing, China
  Tel: +86-25-52870000" ;
  description 'The netconf module to describe the Interface Management' ;
  revision 2025-03-16 {
    description 'Add container to configure counter smooth and add new feature counter-smooth.' ;
  }
  revision 2025-01-06 {
    description 'add container /interface:configuration/interface:interfaces/interface:interface-statistics/interface:traffic-statistics-change,
add container /interface:configuration/interface:interfaces/interface:interface-configuration/interface:interface/interface:interface-statistics/interface:traffic-statistics-change,
add leaf /interface:configuration/interface:interfaces/interface:interface-configuration/interface:interface/interface:interface-statistics/interface:threshold-rate-drop/interface:rate-drop/interface:check-rate-threshold,
add leaf /interface:configuration/interface:interfaces/interface:interface-configuration/interface:interface/interface:interface-statistics/interface:threshold-rate-drop/interface:rate-drop/interface:check-utilization-threshold,
add leaf /interface:configuration/interface:interfaces/interface:interface-configuration/interface:interface/interface:interface-statistics/interface:threshold-rate-drop/interface:rate-drop/interface:change-ratio-threshold,
change status of leaf /interface:configuration/interface:interfaces/interface:interface-configuration/interface:interface/interface:interface-statistics/interface:threshold-rate-drop/interface:rate-drop/interface:normal-threshold into obsolete,
change status of leaf /interface:configuration/interface:interfaces/interface:interface-configuration/interface:interface/interface:interface-statistics/interface:threshold-rate-drop/interface:rate-drop/interface:alarm-threshold into obsolete.' ;
  }

  revision 2024-08-20 {
    description 'Change the leaf /configuration/interfaces/interface-configuration/interface/interface-statistics/threshold-utilization-change/utilization-change/check-threshold from 0-100 to 1-100.
Change the leaf /configuration/interfaces/interface-configuration/interface/interface-statistics/threshold-utilization-change/utilization-change/range-threshold from 0-100 to 1-100.' ;
  }

  revision 2023-12-11 {
    description 'Add new feature alarm-input-fcserrors;
Add new container /configuration/interfaces/interface-configuration/interface/interface-statistics/alarm-input-fcserrors;
Add new leaf /configuration/interfaces/interface-configuration/interface/interface-statistics/alarm-input-fcserrors/period;' ;
  }

  revision 2023-08-16 {
    description 'Add new container /state/vrfs
Add new list /state/vrfs/vrf
Add new leaf /state/vrfs/vrf/vrf-name
Add new container /state/vrfs/vrf/interfaces
Add new list /state/vrfs/vrf/interfaces/interface
Add new leaf /state/vrfs/vrf/interfaces/interface/name' ;
  }

  revision 2023-07-25 {
    description 'Add new feature extra-mc-lag-address;
Add new leaf /configuration/interfaces/interface-configuration/interface/ipv4/addresses/address/is-extra-mc-lag;
Add new leaf /configuration/interfaces/interface-configuration/interface/ipv6/addresses/address/is-extra-mc-lag;' ;
  }

  revision 2023-04-07 {
    description 'Change the leaf /configuration/interfaces/interface-configuration/interface/channale-bandwidth/bandwidth from 1-1000000 to 0-1000000.' ;
  }

  revision 2023-03-03 {
    description 'Add new feature threshold-rate-drop;
Add new feature threshold-utilization-change;
Add new container /configuration/interfaces/interface-configuration/interface/interface-statistics/threshold-rate-drop;
Add new leaf /configuration/interfaces/interface-configuration/interface/interface-statistics/threshold-rate-drop/alarm-type;
Add new leaf /configuration/interfaces/interface-configuration/interface/interface-statistics/threshold-rate-drop/normal-threshold;
Add new leaf /configuration/interfaces/interface-configuration/interface/interface-statistics/threshold-rate-drop/alarm-threshold;
Add new container /configuration/interfaces/interface-configuration/interface/interface-statistics/threshold-utilization-change;
Add new leaf /configuration/interfaces/interface-configuration/interface/interface-statistics/threshold-utilization-change/alarm-type;
Add new leaf /configuration/interfaces/interface-configuration/interface/interface-statistics/threshold-utilization-change/check-threshold;
Add new leaf /configuration/interfaces/interface-configuration/interface/interface-statistics/threshold-utilization-change/range-threshold;' ;
  }

  revision 2022-11-18 {
    description 'Change the leaf /configuration/interfaces/interface-configuration/interface/chinese-description from 238 into 242;
Change the leaf /configuration/interfaces/interface-configuration/interface/description from 238 into 242;
Add new leaf /state/interfaces/interface/interface-statistics/stream-counters/mc-statistics/in-bier-bytes;
Add new leaf /state/interfaces/interface/interface-statistics/stream-counters/mc-statistics/in-bier-pkts;
Add new leaf /state/interfaces/interface/interface-statistics/stream-counters/mc-statistics/e-bier-bytes;
Add new leaf /state/interfaces/interface/interface-statistics/stream-counters/mc-statistics/e-bier-pkts;
Add new leaf /state/interfaces/interface/interface-statistics/stream-counters/subport-statistics/in-bier-bytes;
Add new leaf /state/interfaces/interface/interface-statistics/stream-counters/subport-statistics/in-bier-pkts;
Add new leaf /state/interfaces/interface/interface-statistics/stream-counters/subport-statistics/e-bier-bytes;
Add new leaf /state/interfaces/interface/interface-statistics/stream-counters/subport-statistics/e-bier-pkts;' ;
  }

  revision 2022-11-14 {
    description 'The IPv4 addresses, IPv6 enable, IPv6 addresses will be deleted when the deleting operation of the leaf ip-vrf-forwarding is performed.' ;
  }

  revision 2022-10-31 {
    description 'Add new leaf /state/interfaces/interface/interface-statistics/stream-counters/mc-statistics/in-urpf-drop-pkts;
Add new leaf /state/interfaces/interface/interface-statistics/stream-counters/subport-statistics/in-urpf-drop-pkts;' ;
  }

  revision 2022-09-19 {
    description 'Add new feature threshold-upsend-car-drop;
Add new feature global-threshold;
Add new container /configuration/interfaces/interface-configuration/interface/interface-statistics/threshold-upsend-car-drop;
Add new leaf /configuration/interfaces/interface-configuration/interface/interface-statistics/threshold-upsend-car-drop/limit-ratio;
Add new leaf /state/interfaces/interface/interface-statistics/stream-counters/mc-statistics/in-upsendcarpkts;
Add new leaf /state/interfaces/interface/interface-statistics/stream-counters/subport-statistics/in-upsendcarpkts;
Add new leaf /state/interfaces/interface/interface-statistics/stream-counters/ulei-statistics/in-upsendcarpkts;
Add new leaf /state/interfaces/interface/interface-statistics/stream-counters/spi-statistics/in-upsendcarpkts;
Add new leaf /state/interfaces/interface/interface-statistics/stream-counters/spi-statistics/in-upsendcar-drop;
Add new leaf /state/interfaces/interface/interface-statistics/stream-counters/irb-statistics/in-upsendcarpkts;
Add new container /configuration/interfaces/interface-statistics/global-threshold;
Add new list /configuration/interfaces/interface-statistics/global-threshold/ratio-threshold;
Add new list /configuration/interfaces/interface-statistics/global-threshold/count-threshold;
Add new leaf /configuration/interfaces/interface-statistics/global-threshold/ratio-threshold/alarm-type;
Add new leaf /configuration/interfaces/interface-statistics/global-threshold/ratio-threshold/limit-ratio-low;
Add new leaf /configuration/interfaces/interface-statistics/global-threshold/ratio-threshold/limit-ratio-high;
Add new leaf /configuration/interfaces/interface-statistics/global-threshold/count-threshold/alarm-type;
Add new leaf /configuration/interfaces/interface-statistics/global-threshold/count-threshold/limit-count-low;
Add new leaf /configuration/interfaces/interface-statistics/global-threshold/count-threshold/limit-count-high;
Add new container /state/interfaces/interface/interface-statistics/hw-counters/sat-statistics;
Add new leaf /state/interfaces/interface/interface-statistics/hw-counters/sat-statistics/in-byte-speed;
Add new leaf /state/interfaces/interface/interface-statistics/hw-counters/sat-statistics/in-bytes;
Add new leaf /state/interfaces/interface/interface-statistics/hw-counters/sat-statistics/in-pkts;
Add new leaf /state/interfaces/interface/interface-statistics/hw-counters/sat-statistics/in-byteok;
Add new leaf /state/interfaces/interface/interface-statistics/hw-counters/sat-statistics/in-pktok;
Add new leaf /state/interfaces/interface/interface-statistics/hw-counters/sat-statistics/in-pause;
Add new leaf /state/interfaces/interface/interface-statistics/hw-counters/sat-statistics/in-singcollision;
Add new leaf /state/interfaces/interface/interface-statistics/hw-counters/sat-statistics/in-multcollision;
Add new leaf /state/interfaces/interface/interface-statistics/hw-counters/sat-statistics/in-Latecollision;
Add new leaf /state/interfaces/interface/interface-statistics/hw-counters/sat-statistics/in-excecollision;
Add new leaf /state/interfaces/interface/interface-statistics/hw-counters/sat-statistics/in-crc-error;
Add new leaf /state/interfaces/interface/interface-statistics/hw-counters/sat-statistics/in-alignerror;
Add new leaf /state/interfaces/interface/interface-statistics/hw-counters/sat-statistics/in-symbolerror;
Add new leaf /state/interfaces/interface/interface-statistics/hw-counters/sat-statistics/in-error;
Add new leaf /state/interfaces/interface/interface-statistics/hw-counters/sat-statistics/in-unicasts;
Add new leaf /state/interfaces/interface/interface-statistics/hw-counters/sat-statistics/in-broadcasts;
Add new leaf /state/interfaces/interface/interface-statistics/hw-counters/sat-statistics/in-multicasts;
Add new leaf /state/interfaces/interface/interface-statistics/hw-counters/sat-statistics/in-byteall;
Add new leaf /state/interfaces/interface/interface-statistics/hw-counters/sat-statistics/in-packetall;
Add new leaf /state/interfaces/interface/interface-statistics/hw-counters/sat-statistics/in-undersize;
Add new leaf /state/interfaces/interface/interface-statistics/hw-counters/sat-statistics/in-oversize;
Add new leaf /state/interfaces/interface/interface-statistics/hw-counters/sat-statistics/in-fragments;
Add new leaf /state/interfaces/interface/interface-statistics/hw-counters/sat-statistics/in-jabbers;
Add new leaf /state/interfaces/interface/interface-statistics/hw-counters/sat-statistics/in-64b;
Add new leaf /state/interfaces/interface/interface-statistics/hw-counters/sat-statistics/in-65-127b;
Add new leaf /state/interfaces/interface/interface-statistics/hw-counters/sat-statistics/in-128-255b;
Add new leaf /state/interfaces/interface/interface-statistics/hw-counters/sat-statistics/in-256-511b;
Add new leaf /state/interfaces/interface/interface-statistics/hw-counters/sat-statistics/in-512-1023b;
Add new leaf /state/interfaces/interface/interface-statistics/hw-counters/sat-statistics/in-1024-1518b;
Add new leaf /state/interfaces/interface/interface-statistics/hw-counters/sat-statistics/in-1519-maxb;
Add new leaf /state/interfaces/interface/interface-statistics/hw-counters/sat-statistics/in-dropevents;
Add new leaf /state/interfaces/interface/interface-statistics/hw-counters/sat-statistics/e-byte-speed;
Add new leaf /state/interfaces/interface/interface-statistics/hw-counters/sat-statistics/e-bytes;
Add new leaf /state/interfaces/interface/interface-statistics/hw-counters/sat-statistics/e-packets;
Add new leaf /state/interfaces/interface/interface-statistics/hw-counters/sat-statistics/e-byteok;
Add new leaf /state/interfaces/interface/interface-statistics/hw-counters/sat-statistics/e-packetok;
Add new leaf /state/interfaces/interface/interface-statistics/hw-counters/sat-statistics/e-pause;
Add new leaf /state/interfaces/interface/interface-statistics/hw-counters/sat-statistics/e-singcollision;
Add new leaf /state/interfaces/interface/interface-statistics/hw-counters/sat-statistics/e-multcollision;
Add new leaf /state/interfaces/interface/interface-statistics/hw-counters/sat-statistics/e-Latecollision;
Add new leaf /state/interfaces/interface/interface-statistics/hw-counters/sat-statistics/e-excecollision;
Add new leaf /state/interfaces/interface/interface-statistics/hw-counters/sat-statistics/e-crc-error;
Add new leaf /state/interfaces/interface/interface-statistics/hw-counters/sat-statistics/e-alignerror;
Add new leaf /state/interfaces/interface/interface-statistics/hw-counters/sat-statistics/e-symbolerror;
Add new leaf /state/interfaces/interface/interface-statistics/hw-counters/sat-statistics/e-error;
Add new leaf /state/interfaces/interface/interface-statistics/hw-counters/sat-statistics/e-unicasts;
Add new leaf /state/interfaces/interface/interface-statistics/hw-counters/sat-statistics/e-broadcasts;
Add new leaf /state/interfaces/interface/interface-statistics/hw-counters/sat-statistics/e-multicasts;
Add new leaf /state/interfaces/interface/interface-statistics/hw-counters/sat-statistics/e-byteall;
Add new leaf /state/interfaces/interface/interface-statistics/hw-counters/sat-statistics/e-packetall;
Add new leaf /state/interfaces/interface/interface-statistics/hw-counters/sat-statistics/e-undersize;
Add new leaf /state/interfaces/interface/interface-statistics/hw-counters/sat-statistics/e-oversize;
Add new leaf /state/interfaces/interface/interface-statistics/hw-counters/sat-statistics/e-fragments;
Add new leaf /state/interfaces/interface/interface-statistics/hw-counters/sat-statistics/e-jabbers;
Add new leaf /state/interfaces/interface/interface-statistics/hw-counters/sat-statistics/e-64b;
Add new leaf /state/interfaces/interface/interface-statistics/hw-counters/sat-statistics/e-65-127b;
Add new leaf /state/interfaces/interface/interface-statistics/hw-counters/sat-statistics/e-128-255b;
Add new leaf /state/interfaces/interface/interface-statistics/hw-counters/sat-statistics/e-256-511b;
Add new leaf /state/interfaces/interface/interface-statistics/hw-counters/sat-statistics/e-512-1023b;
Add new leaf /state/interfaces/interface/interface-statistics/hw-counters/sat-statistics/e-1024-1518b;
Add new leaf /state/interfaces/interface/interface-statistics/hw-counters/sat-statistics/e-1519-maxb;
Add new leaf /state/interfaces/interface/interface-statistics/hw-counters/sat-statistics/e-dropevents;
Add new leaf /state/interfaces/interface/interface-statistics/hw-counters/sat-statistics/in-macrxerror;
Add new leaf /state/interfaces/interface/interface-statistics/hw-counters/sat-statistics/in-overrun;
Add new leaf /state/interfaces/interface/interface-statistics/hw-counters/sat-statistics/in-pktsdrop;
Add new leaf /state/interfaces/interface/interface-statistics/hw-counters/sat-statistics/in-pktserror;
Add new leaf /state/interfaces/interface/interface-statistics/hw-counters/sat-statistics/e-pktsdrop;
Add new leaf /state/interfaces/interface/interface-statistics/hw-counters/sat-statistics/e-pktserror;' ;
  }

  revision 2022-02-24 {
    description 'Add new leaf /configuration/interfaces/interface-statistics/traffic-statistics-store-switch;' ;
  }

  revision 2021-10-12 {
    description 'Add new leaf /configuration/interfaces/interface-configuration/interface/channale-bandwidth/bandwidth;' ;
  }

  revision 2021-08-13 {
    description 'Add new leaf /state/interfaces/interface/interface-statistics/common-statistics/input-bytes;
Add new leaf /state/interfaces/interface/interface-statistics/common-statistics/input-pkts;
Add new leaf /state/interfaces/interface/interface-statistics/common-statistics/output-bytes;
Add new leaf /state/interfaces/interface/interface-statistics/common-statistics/output-pkts;' ;
  }

  revision 2021-07-26 {
    description 'Add label 61V5-1 to the feature name of anycast-mac-address.' ;
  }

  revision 2021-03-29 {
    description 'Add new leaf /state/interfaces/interface/interface-statistics/stream-counters/mc-statistics/e-notteuti-bytes;
Add new leaf /state/interfaces/interface/interface-statistics/stream-counters/mc-statistics/e-notteuti-pkts;
Add new leaf /state/interfaces/interface/interface-statistics/stream-counters/subport-statistics/e-notteuti-bytes;
Add new leaf /state/interfaces/interface/interface-statistics/stream-counters/subport-statistics/e-notteuti-pkts;' ;
  }

  revision 2021-03-03 {
    description 'Add new leaf /configuration/interfaces/interface-configuration/interface/ipv4/addresses/address/is-mclag;
Add new leaf /configuration/interfaces/interface-configuration/interface/ipv6/addresses/address/is-mclag;' ;
  }

  revision 2021-02-03 {
    description 'Add new leaf /state/interfaces/interface/interface-statistics/common-statistics/mpls-input-bytes-rate;
Add new leaf /state/interfaces/interface/interface-statistics/common-statistics/mpls-input-pkts-rate;
Add new leaf /state/interfaces/interface/interface-statistics/common-statistics/mpls-output-bytes-rate;
Add new leaf /state/interfaces/interface/interface-statistics/common-statistics/mpls-output-pkts-rate;
Add new leaf /state/interfaces/interface/interface-statistics/common-statistics/mpls-input-rate-peak;
Add new leaf /state/interfaces/interface/interface-statistics/common-statistics/mpls-input-rate-peak-time;
Add new leaf /state/interfaces/interface/interface-statistics/common-statistics/mpls-output-rate-peak;
Add new leaf /state/interfaces/interface/interface-statistics/common-statistics/mpls-output-rate-peak-time;
Add new leaf /state/interfaces/interface/interface-statistics/common-statistics/mpls-input-utilization;
Add new leaf /state/interfaces/interface/interface-statistics/common-statistics/mpls-output-utilization;
Add new leaf /state/interfaces/interface/interface-statistics/stream-counters/mc-statistics/in-v4bytes-l1;
Add new leaf /state/interfaces/interface/interface-statistics/stream-counters/mc-statistics/e-v4bytes-l1;
Add new leaf /state/interfaces/interface/interface-statistics/stream-counters/mc-statistics/in-v6bytes-l1;
Add new leaf /state/interfaces/interface/interface-statistics/stream-counters/mc-statistics/e-v6bytes-l1;
Add new leaf /state/interfaces/interface/interface-statistics/stream-counters/mc-statistics/in-mpls-bytes;
Add new leaf /state/interfaces/interface/interface-statistics/stream-counters/mc-statistics/e-mpls-bytes;
Add new leaf /state/interfaces/interface/interface-statistics/stream-counters/mc-statistics/in-mpls-pkts;
Add new leaf /state/interfaces/interface/interface-statistics/stream-counters/mc-statistics/e-mpls-pkts;
Add new leaf /state/interfaces/interface/interface-statistics/stream-counters/mc-statistics/in-mpls-bytes-l1;
Add new leaf /state/interfaces/interface/interface-statistics/stream-counters/mc-statistics/e-mpls-bytes-l1;
Add new leaf /state/interfaces/interface/interface-statistics/stream-counters/subport-statistics/in-v4bytes-l1;
Add new leaf /state/interfaces/interface/interface-statistics/stream-counters/subport-statistics/e-v4bytes-l1;
Add new leaf /state/interfaces/interface/interface-statistics/stream-counters/subport-statistics/in-v6bytes-l1;
Add new leaf /state/interfaces/interface/interface-statistics/stream-counters/subport-statistics/e-v6bytes-l1;
Add new leaf /state/interfaces/interface/interface-statistics/stream-counters/subport-statistics/in-mpls-bytes;
Add new leaf /state/interfaces/interface/interface-statistics/stream-counters/subport-statistics/e-mpls-bytes;
Add new leaf /state/interfaces/interface/interface-statistics/stream-counters/subport-statistics/in-mpls-pkts;
Add new leaf /state/interfaces/interface/interface-statistics/stream-counters/subport-statistics/e-mpls-pkts;
Add new leaf /state/interfaces/interface/interface-statistics/stream-counters/subport-statistics/in-mpls-bytes-l1;
Add new leaf /state/interfaces/interface/interface-statistics/stream-counters/subport-statistics/e-mpls-bytes-l1;' ;
  }

  revision 2021-01-14 {
    description 'Add new container /state/interfaces/interface/interface-statistics/defque-counters;
Add new container /state/interfaces/interface/interface-statistics/defque-counters/ethdefque-statistics;
Add new leaf /state/interfaces/interface/interface-statistics/defque-counters/ethdefque-statistics/in-bytes-tm;
Add new leaf /state/interfaces/interface/interface-statistics/defque-counters/ethdefque-statistics/in-pkts-tm;
Add new leaf /state/interfaces/interface/interface-statistics/defque-counters/ethdefque-statistics/in-dropbytes-tm;
Add new leaf /state/interfaces/interface/interface-statistics/defque-counters/ethdefque-statistics/in-droppkts-tm;
Add new leaf /state/interfaces/interface/interface-statistics/defque-counters/ethdefque-statistics/e-bytes-tm;
Add new leaf /state/interfaces/interface/interface-statistics/defque-counters/ethdefque-statistics/e-pkts-tm;
Add new leaf /state/interfaces/interface/interface-statistics/defque-counters/ethdefque-statistics/e-dropbytes-tm;
Add new leaf /state/interfaces/interface/interface-statistics/defque-counters/ethdefque-statistics/e-droppkts-tm;' ;
  }

  revision 2020-12-11 {
    description 'Add new leaf /state/interfaces/interface/interface-statistics/stream-counters/mc-statistics/in-acl-drop;
Add new leaf /state/interfaces/interface/interface-statistics/stream-counters/mc-statistics/in-car-drop;
Add new leaf /state/interfaces/interface/interface-statistics/stream-counters/mc-statistics/in-l3-rtmiss-drop;
Add new leaf /state/interfaces/interface/interface-statistics/stream-counters/mc-statistics/in-vlanmiss-drop;
Add new leaf /state/interfaces/interface/interface-statistics/stream-counters/mc-statistics/in-mplsmiss-drop;
Add new leaf /state/interfaces/interface/interface-statistics/stream-counters/mc-statistics/in-notfinde-drop;
Add new leaf /state/interfaces/interface/interface-statistics/stream-counters/mc-statistics/in-broadcast-drop;
Add new leaf /state/interfaces/interface/interface-statistics/stream-counters/mc-statistics/in-l2-proto-drop;
Add new leaf /state/interfaces/interface/interface-statistics/stream-counters/mc-statistics/in-remaining-drop;
Add new leaf /state/interfaces/interface/interface-statistics/stream-counters/mc-statistics/e-acl-drop;
Add new leaf /state/interfaces/interface/interface-statistics/stream-counters/mc-statistics/e-notfinde-drop;
Add new leaf /state/interfaces/interface/interface-statistics/stream-counters/mc-statistics/e-remaining-drop;
Add new leaf /state/interfaces/interface/interface-statistics/stream-counters/subport-statistics/in-acl-drop;
Add new leaf /state/interfaces/interface/interface-statistics/stream-counters/subport-statistics/in-car-drop;
Add new leaf /state/interfaces/interface/interface-statistics/stream-counters/subport-statistics/in-l3-rtmiss-drop;
Add new leaf /state/interfaces/interface/interface-statistics/stream-counters/subport-statistics/in-vlanmiss-drop;
Add new leaf /state/interfaces/interface/interface-statistics/stream-counters/subport-statistics/in-mplsmiss-drop;
Add new leaf /state/interfaces/interface/interface-statistics/stream-counters/subport-statistics/in-notfinde-drop;
Add new leaf /state/interfaces/interface/interface-statistics/stream-counters/subport-statistics/in-broadcast-drop;
Add new leaf /state/interfaces/interface/interface-statistics/stream-counters/subport-statistics/in-l2-proto-drop;
Add new leaf /state/interfaces/interface/interface-statistics/stream-counters/subport-statistics/in-remaining-drop;
Add new leaf /state/interfaces/interface/interface-statistics/stream-counters/subport-statistics/e-acl-drop;
Add new leaf /state/interfaces/interface/interface-statistics/stream-counters/subport-statistics/e-notfinde-drop;
Add new leaf /state/interfaces/interface/interface-statistics/stream-counters/subport-statistics/e-remaining-drop;' ;
  }

  revision 2020-10-16 {
    description 'Add new leaf /state/interfaces/interface/type' ;
  }

  revision 2020-06-29 {
    description 'Add new container shutdown-interface.' ;
  }

  revision 2020-06-15 {
    description 'Add new container /configuration/interfaces/interface-configuration/interface/interface-statistics/subport/subport-v4;
Add new leaf /configuration/interfaces/interface-configuration/interface/interface-statistics/subport/subport-v4/subport-v4-switch;
Add new container /configuration/interfaces/interface-configuration/interface/interface-statistics/subport/subport-v6;
Add new leaf /configuration/interfaces/interface-configuration/interface/interface-statistics/subport/subport-v6/subport-v6-switch;
Add new feature subport-v4-traffic-statics
Add new feature subport-v6-traffic-statics
Add new leaf /state/interfaces/interface/interface-statistics/common-statistics/v4-input-bytes-rate;
Add new leaf /state/interfaces/interface/interface-statistics/common-statistics/v4-input-pkts-rate;
Add new leaf /state/interfaces/interface/interface-statistics/common-statistics/v4-output-bytes-rate;
Add new leaf /state/interfaces/interface/interface-statistics/common-statistics/v4-output-pkts-rate;
Add new leaf /state/interfaces/interface/interface-statistics/common-statistics/v6-input-bytes-rate;
Add new leaf /state/interfaces/interface/interface-statistics/common-statistics/v6-input-pkts-rate;
Add new leaf /state/interfaces/interface/interface-statistics/common-statistics/v6-output-bytes-rate;
Add new leaf /state/interfaces/interface/interface-statistics/common-statistics/v6-output-pkts-rate;
Add new leaf /state/interfaces/interface/interface-statistics/common-statistics/v4-input-rate-peak;
Add new leaf /state/interfaces/interface/interface-statistics/common-statistics/v4-input-rate-peak-time;
Add new leaf /state/interfaces/interface/interface-statistics/common-statistics/v4-output-rate-peak;
Add new leaf /state/interfaces/interface/interface-statistics/common-statistics/v4-output-rate-peak-time;
Add new leaf /state/interfaces/interface/interface-statistics/common-statistics/v6-input-rate-peak;
Add new leaf /state/interfaces/interface/interface-statistics/common-statistics/v6-input-rate-peak-time;
Add new leaf /state/interfaces/interface/interface-statistics/common-statistics/v6-output-rate-peak;
Add new leaf /state/interfaces/interface/interface-statistics/common-statistics/v6-output-rate-peak-time;
Add new leaf /state/interfaces/interface/interface-statistics/common-statistics/v4-input-utilization;
Add new leaf /state/interfaces/interface/interface-statistics/common-statistics/v4-output-utilization;
Add new leaf /state/interfaces/interface/interface-statistics/common-statistics/v6-input-utilization;
Add new leaf /state/interfaces/interface/interface-statistics/common-statistics/v6-output-utilization;' ;
  }

  revision 2020-05-27 {
    description 'Change the range of leaf /configuration/interfaces/interface-configuration/interface/port-limit/high/cbs from 16-20000 to 16-100000
Change the range of leaf /configuration/interfaces/interface-configuration/interface/port-limit/low/cbs from 16-20000  to 16-100000
Change the range of leaf /configuration/interfaces/interface-configuration/interface/port-limit/high/cir from 0-200000 to 0-1000000
Change the range of leaf /configuration/interfaces/interface-configuration/interface/port-limit/low/cir from 0-200000 to 0-1000000' ;
  }

  revision 2020-04-08 {
    description 'The Container /configuration/interfaces/interface-configuration/interface add new select leaf /configuration/interfaces/interface-configuration/interface/index' ;
  }

  revision 2020-02-14 {
    description 'Add new container /state/interfaces/interface/interface-statistics/hw-counters/vei-statistics' ;
  }

  revision 2019-08-13 {
    description 'Add new leaf /configuration/interfaces/interface-configuration/interface/bandwidth-set/bandwidth;' ;
  }

  revision 2019-07-02 {
    description 'Add new leaf /configuration/interfaces/interface-configuration/interface/chinese-description;' ;
  }

  revision 2019-04-30 {
    description 'Add new leaf /state/interfaces/logic-interface-summary/config-limited-number' ;
  }

  revision 2019-02-18 {
    description 'Add new container ip-address for ip address primary-secondary mode.' ;
  }

  revision 2019-01-09 {
    description 'Change the range of leaf /configuration/interfaces/interface-configuration/interface/mtu from 0-9600 to 0-9700.
Change the range of leaf /state/interfaces/interface/mtu from 0-9600 to 0-9700.' ;
  }

  revision 2018-09-13 {
    description 'Add new container /state/interfaces/interface/interface-statistics/stream-counters/ipsectunnel-statistics' ;
  }

  revision 2018-06-22 {
    description 'Add new container /configuration/interfaces/interface-configuration/interface/byname-set;
Add new leaf /configuration/interfaces/interface-configuration/interface/byname-set/byname;' ;
  }

  revision 2017-12-19 {
    description 'Add new leaf /state/interfaces/interface/interface-statistics/stream-counters/irb-statistics/in-discards;
Add new leaf /state/interfaces/interface/interface-statistics/stream-counters/irb-statistics/in-upsendcar-drop;
Add new leaf /state/interfaces/interface/interface-statistics/stream-counters/irb-statistics/in-v4bytes;
Add new leaf /state/interfaces/interface/interface-statistics/stream-counters/irb-statistics/in-v4pkts;
Add new leaf /state/interfaces/interface/interface-statistics/stream-counters/irb-statistics/in-v6bytes;
Add new leaf /state/interfaces/interface/interface-statistics/stream-counters/irb-statistics/in-v6pkts;
Add new leaf /state/interfaces/interface/interface-statistics/stream-counters/irb-statistics/in-multicastbytes;
Add new leaf /state/interfaces/interface/interface-statistics/stream-counters/irb-statistics/in-multicastpkts;
Add new leaf /state/interfaces/interface/interface-statistics/stream-counters/irb-statistics/in-broadcastbytes;
Add new leaf /state/interfaces/interface/interface-statistics/stream-counters/irb-statistics/in-broadcastpkts;
Add new leaf /state/interfaces/interface/interface-statistics/stream-counters/irb-statistics/in-urpf-v4drppkts;
Add new leaf /state/interfaces/interface/interface-statistics/stream-counters/irb-statistics/in-urpf-v6drppkts;
Add new leaf /state/interfaces/interface/interface-statistics/stream-counters/irb-statistics/e-discards;
Add new leaf /state/interfaces/interface/interface-statistics/stream-counters/irb-statistics/e-v4bytes;
Add new leaf /state/interfaces/interface/interface-statistics/stream-counters/irb-statistics/e-v4pkts;
Add new leaf /state/interfaces/interface/interface-statistics/stream-counters/irb-statistics/e-v6bytes;
Add new leaf /state/interfaces/interface/interface-statistics/stream-counters/irb-statistics/e-v6pkts;
Add new leaf /state/interfaces/interface/interface-statistics/stream-counters/irb-statistics/e-multicastbytes;
Add new leaf /state/interfaces/interface/interface-statistics/stream-counters/irb-statistics/e-multicastpkts;
Add new leaf /state/interfaces/interface/interface-statistics/stream-counters/irb-statistics/e-broadcastbytes;
Add new leaf /state/interfaces/interface/interface-statistics/stream-counters/irb-statistics/e-broadcastpkts;
Add new leaf /state/interfaces/interface/interface-statistics/stream-counters/irb-statistics/e-upsendcar-drop;' ;
  }

  revision 2017-09-09 {
    description 'Add new container /configuration/interfaces/interface-configuration/interface/mode' ;
  }

  revision 2017-07-25 {
    description 'Add new container /configuration/interfaces/interface-statistics/rate-statistics.' ;
  }

  revision 2017-07-18 {
    description 'Add new leaf /state/interfaces/interface/interface-statistics/hw-counters/cpos-tdm-statistics/e-bufundcont
Add new leaf /state/interfaces/interface/interface-statistics/hw-counters/cpos-tdm-statistics/e-farsqdpcont
Add new leaf /state/interfaces/interface/interface-statistics/hw-counters/cpos-tdm-statistics/e-farowincont' ;
  }

  revision 2017-04-10 {
    description 'Add new leaf /configuration/interfaces/interface-configuration/interface/index' ;
  }

  revision 2017-02-15 {
    description 'Add new leaf /state/interfaces/interface/interface-statistics/stream-counters/tetunnel-statistics/in-pnodebytes
Add new leaf /state/interfaces/interface/interface-statistics/stream-counters/tetunnel-statistics/in-pnodepkts
Add new leaf /state/interfaces/interface/interface-statistics/stream-counters/tetunnel-statistics/e-pnodebytes
Add new leaf /state/interfaces/interface/interface-statistics/stream-counters/tetunnel-statistics/e-pnodepkts' ;
  }

  revision 2017-01-16 {
    description 'Add new container /configuration/interfaces/interface-configuration/interface/interface-statistics/rate-statistics. And add a feature named rate-statistics for this function.' ;
  }

  revision 2016-12-26 {
    description "Add a feature of 'MCG-5000' for 'global-traffic-statistics'.

    Add a feature of 'MCG-5000' for 'one-minute-peak'.

    Add a feature of 'MCG-5000' for 'logic-traffic-statistics'.

    Add a feature of 'MCG-5000' for 'subport-traffic-statistics'.

    Add a feature of 'MCG-5000' for 'threshold'." ;
  }

  revision 2016-12-13 {
    description 'Add new container /state/interfaces/interface/interface-statistics/stream-counters/tegtunnel-statistics.
Add new container /state/interfaces/interface/interface-statistics/stream-counters/gtunnelgroup-statistics' ;
  }

  revision 2016-11-23 {
    description 'Add new container /state/interfaces/interface/interface-statistics/stream-counters/svi-statistics' ;
  }

  revision 2016-11-11 {
    description 'Add a feature for anycast mac address function.
Add a new leaf /configuration/interfaces/interface-configuration/interface/is-anycast.' ;
  }

  revision 2016-09-14 {
    description 'Add new leaf /state/interfaces/interface/interface-statistics/stream-counters/spi-statistics/in-pktsdrop
Add new leaf /state/interfaces/interface/interface-statistics/stream-counters/spi-statistics/e-pktsdrop' ;
  }

  revision 2016-08-28 {
    description 'Add new container /state/interfaces/interface/interface-statistics/stream-counters/irb-statistics' ;
  }

  revision 2016-06-22 {
    description 'Add new container /state/interfaces/interface/interface-statistics/stream-counters/spi-statistics' ;
  }

  revision 2016-06-06 {
    description 'Add the enum type value eos and ces of the leaf /configuration/interfaces/interface-configuration/interface/encapsulation/type.' ;
  }

  revision 2016-06-01 {
    description 'Change the range of leaf /configuration/interfaces/interface-configuration/interface/mtu from 1500-9600 to 0-9600.
Change the range of leaf /configuration/interfaces/interface-configuration/interface/ipv4/mtu from 68-9600 to 0-9600.
Change the range of leaf /state/interfaces/interface/mtu from 1500-9600 to 0-9600.
Change the range of leaf /state/interfaces/interface/ip-mtu from 68-9600 to 0-9600.' ;
  }

  revision 2016-03-15 {
    description 'Add new container /configuration/interfaces/interface-configuration/interface/interface-statistics/effective-time-threshold.' ;
  }

  revision 2015-12-17 {
    description 'Change the units of leaf /configuration/interfaces/interface-configuration/interface/port-limit/high/cbs to KB.
Change the units of leaf /configuration/interfaces/interface-configuration/interface/port-limit/low/cbs to KB.
Change the units of leaf /configuration/interfaces/interface-configuration/interface/vlan-limit/high/cbs to KB.
Change the units of leaf /configuration/interfaces/interface-configuration/interface/vlan-limit/low/cbs to KB.' ;
  }

  revision 2015-11-18 {
    description 'Add new container /state/interfaces/interface/interface-statistics/hw-counters/bep-statistics' ;
  }

  revision 2015-11-05 {
    description 'Change the leaves of container /state/interfaces/interface/interface-statistics/stream-conters/tetunnel-statistics.
Change the leaf name from e_bytes into e-bytes.
Change the leaf name from e_packets into e-packets.
Change the leaf name from e_bytes_pri0 into e-bytes-pri0;
Change the leaf name from e_packets_pri0 into e-packets-pri0.

Change the leaf name from e_bytes_pri1 into e-bytes-pri1.
Change the leaf name from e_packets_pri1 into e-packets-pri1.

Change the leaf name from e_bytes_pri2 into e-bytes-pri2.
Change the leaf name from e_packets_pri2 into e-packets-pri2.

Change the leaf name from e_bytes_pri3 into e-bytes-pri3.
Change the leaf name from e_packets_pri3 into e-packets-pri3.

Change the leaf name from e_bytes_pri4 into e-bytes-pri4.
Change the leaf name from e_packets_pri4 into e-packets-pri4.

Change the leaf name from e_packets_pri5 into e-packets-pri5.

Change the leaf name from e_bytes_pri6 into e-bytes-pri6.
Change the leaf name from e_packets_pri6 into e-packets-pri6.

Change the leaf name from e_bytes_pri7 into e-bytes-pri7.
Change the leaf name from e_packets_pri7 into e-packets-pri7.

Change the leaf name from in_packets into in-packets.
Change the leaf name from in_bytes into in-bytes.
Change the leaf name from in_discbytes into in-discbytes.
Change the leaf name from in_discpkts into in-discpkts.
Change the leaf name from e_discbytes into e-discbytes.
Change the leaf name from e_discpkts into e-discpkts.' ;
  }

  revision 2015-10-16 {
    description 'Change the range of leaf /configuration/interfaces/interface-configuration/interface/mtu from 1500-9216 to 1500-9600.
Change the range of leaf /configuration/interfaces/interface-configuration/interface/mpls-mtu from 68-9216 to 68-9600.
Change the range of leaf /configuration/interfaces/interface-configuration/interface/ipv4/mtu from 68-9216 to 68-9600.
Change the range of leaf /configuration/interfaces/interface-configuration/interface/ipv6/mtu from 1280-9216 to 1280-9600.
Change the range of leaf /state/interfaces/interface/mtu from 1500-9216 to 1500-9600.
Change the range of leaf /state/interfaces/interface/mpls-mtu from 68-9216 to 68-9600.
Change the range of leaf /state/interfaces/interface/ip-mtu from 68-9216 to 68-9600.
Change the range of leaf /state/interfaces/interface/ipv6-mtu from 1280-9216 to 1280-9600.' ;
  }

  revision 2015-08-27 {
    description 'Add new container /state/interfaces/interface/interface-statistics/stream-counters/vxlantunnel-statistics' ;
  }

  revision 2015-08-04 {
    description 'Delete the config tag of container /operation' ;
  }

  revision 2015-07-14 {
    description 'Add new container /state/interfaces/interface/interface-statistics/stream-counters/null-statistics
Add new container /state/interfaces/interface/interface-statistics/stream-counters/loopback-statistics' ;
  }

  revision 2015-07-07 {
    description 'Add data range 1-4294967295 of the leaf /configuration/interfaces/interface-configuration/interface/load-sharing/bandwidth.' ;
  }

  revision 2015-05-19 {
    description 'Add leaf /state/interfaces/interface/interface-statistics/hw-counters/l3vlan-statistics/in-pktsdrop
Add leaf /state/interfaces/interface/interface-statistics/hw-counters/l3vlan-statistics/in-bytesdrop
Add leaf /state/interfaces/interface/interface-statistics/hw-counters/l3vlan-statistics/e-pktsdrop
Add leaf /state/interfaces/interface/interface-statistics/hw-counters/l3vlan-statistics/e-bytesdrop

Add leaf /state/interfaces/interface/interface-statistics/hw-counters/eth-statistics/in-pktsdrop
Add leaf /state/interfaces/interface/interface-statistics/hw-counters/eth-statistics/in-pktserror
Add leaf /state/interfaces/interface/interface-statistics/hw-counters/eth-statistics/e-pktsdrop
Add leaf /state/interfaces/interface/interface-statistics/hw-counters/eth-statistics/e-pktserror

Add leaf /state/interfaces/interface/interface-statistics/hw-counters/pos-statistics/in-pktsdrop
Add leaf /state/interfaces/interface/interface-statistics/hw-counters/pos-statistics/in-pktserror
Add leaf /state/interfaces/interface/interface-statistics/hw-counters/pos-statistics/e-pktsdrop
Add leaf /state/interfaces/interface/interface-statistics/hw-counters/pos-statistics/e-pktserror

Add leaf /state/interfaces/interface/interface-statistics/hw-counters/atm-statistics/in-pktsdrop
Add leaf /state/interfaces/interface/interface-statistics/hw-counters/atm-statistics/in-pktserror
Add leaf /state/interfaces/interface/interface-statistics/hw-counters/atm-statistics/e-pktsdrop
Add leaf /state/interfaces/interface/interface-statistics/hw-counters/atm-statistics/e-pktserror

Add leaf /state/interfaces/interface/interface-statistics/hw-counters/smartgroup-statistics/in-pktsdrop
Add leaf /state/interfaces/interface/interface-statistics/hw-counters/smartgroup-statistics/in-pktserror
Add leaf /state/interfaces/interface/interface-statistics/hw-counters/smartgroup-statistics/e-pktsdrop
Add leaf /state/interfaces/interface/interface-statistics/hw-counters/smartgroup-statistics/e-pktserror

Add leaf /state/interfaces/interface/interface-statistics/hw-counters/posgroup-statistics/in-pktsdrop
Add leaf /state/interfaces/interface/interface-statistics/hw-counters/posgroup-statistics/in-pktserror
Add leaf /state/interfaces/interface/interface-statistics/hw-counters/posgroup-statistics/e-pktsdrop
Add leaf /state/interfaces/interface/interface-statistics/hw-counters/posgroup-statistics/e-pktserror

Add leaf /state/interfaces/interface/interface-statistics/hw-counters/cpos-statistics/in-pktsdrop
Add leaf /state/interfaces/interface/interface-statistics/hw-counters/cpos-statistics/in-pktserror
Add leaf /state/interfaces/interface/interface-statistics/hw-counters/cpos-statistics/e-pktsdrop
Add leaf /state/interfaces/interface/interface-statistics/hw-counters/cpos-statistics/e-pktserror

Add leaf /state/interfaces/interface/interface-statistics/stream-counters/mc-statistics/in-pktsdrop
Add leaf /state/interfaces/interface/interface-statistics/stream-counters/mc-statistics/in-pktserror
Add leaf /state/interfaces/interface/interface-statistics/stream-counters/mc-statistics/e-pktsdrop
Add leaf /state/interfaces/interface/interface-statistics/stream-counters/mc-statistics/e-pktserror

Add leaf /state/interfaces/interface/interface-statistics/stream-counters/subport-statistics/in-pktsdrop
Add leaf /state/interfaces/interface/interface-statistics/stream-counters/subport-statistics/in-pktserror
Add leaf /state/interfaces/interface/interface-statistics/stream-counters/subport-statistics/e-pktsdrop
Add leaf /state/interfaces/interface/interface-statistics/stream-counters/subport-statistics/e-pktserror

Add leaf /state/interfaces/interface/interface-statistics/stream-counters/supervlan-statistics/in-pktsdrop
Add leaf /state/interfaces/interface/interface-statistics/stream-counters/supervlan-statistics/in-pktserror
Add leaf /state/interfaces/interface/interface-statistics/stream-counters/supervlan-statistics/e-pktsdrop
Add leaf /state/interfaces/interface/interface-statistics/stream-counters/supervlan-statistics/e-pktserror
Add new container /state/interfaces/interface/interface-statistics/stream-counters/pvcgroup-statistics' ;
  }

  revision 2015-01-30 {
    description 'Change the leaf name from in-urpf-discpkts into in-urpf-v4drppkts
	in /state/interfaces/interface/interface-statistics/stream-counters/mc-statistics
	and /state/interfaces/interface/interface-statistics/stream-counters/subport-statistics
	and /state/interfaces/interface/interface-statistics/stream-counters/supervlan-statistics
	and /state/interfaces/interface/interface-statistics/stream-counters/ulei-statistics
	Change the leaf name from e-urpf-discpkts into in-urpf-v6drppkts
	in /state/interfaces/interface/interface-statistics/stream-counters/mc-statistics
	and /state/interfaces/interface/interface-statistics/stream-counters/subport-statistics
	and /state/interfaces/interface/interface-statistics/stream-counters/supervlan-statistics
	and /state/interfaces/interface/interface-statistics/stream-counters/ulei-statistics' ;
  }

  revision 2015-01-08 {
    description 'Add leaf /state/interfaces/interface/interface-statistics/hw-counters/eth-statistics/in-overrun
Add leaf /state/interfaces/interface/interface-statistics/hw-counters/pos-statistics/in-overrun
Add leaf /state/interfaces/interface/interface-statistics/hw-counters/smartgroup-statistics/in-overrun
Add leaf /state/interfaces/interface/interface-statistics/hw-counters/posgroup-statistics/in-overrun' ;
  }

  revision 2014-11-20 {
    description 'Add container /configuration/interfaces/interface-configuration/interface/off-line
Add leaf /configuration/interfaces/interface-configuration/interface/off-line/off-line' ;
  }

  revision 2014-11-11 {
    description 'Add leaf /configuration/interfaces/interface-configuration/interface/type
Set leaf /configuration/interfaces/interface-configuration/interface/name as selects of list /configuration/interfaces/interface-configuration/interface
Set leaf /configuration/interfaces/interface-configuration/interface/type as seclects of list /configuration/interfaces/interface-configuration/interface' ;
  }

  revision 2014-09-25 {
    description 'modify the ifname type of leaf /operation/interfaces/interface-statistics/clear/one-minute-peak/name
modify the ifname type of leaf /operation/interfaces/interface-statistics/clear/interface-statistics/name' ;
  }

  revision 2014-07-02 {
    description 'Set the lenth of the leaf name in logic-interface-summary from 1 to 31' ;
  }

  revision 2014-06-16 {
    description 'Add leaf /state/interfaces/interface/interface-statistics/stream-counters/mc-statistics/in-urpf-discpkts
Add leaf /state/interfaces/interface/interface-statistics/stream-counters/mc-statistics/e-urpf-discpkts
Add leaf /state/interfaces/interface/interface-statistics/stream-counters/subport-statistics/in-urpf-discpkts
Add leaf /state/interfaces/interface/interface-statistics/stream-counters/subport-statistics/e-urpf-discpkts
Add leaf /state/interfaces/interface/interface-statistics/stream-counters/supervlan-statistics/in-multicastbytes
Add leaf /state/interfaces/interface/interface-statistics/stream-counters/supervlan-statistics/e-multicastbytes
Add leaf /state/interfaces/interface/interface-statistics/stream-counters/supervlan-statistics/e-broadcastbytes
Add leaf /state/interfaces/interface/interface-statistics/stream-counters/supervlan-statistics/in-urpf-discpkts
Add leaf /state/interfaces/interface/interface-statistics/stream-counters/supervlan-statistics/e-urpf-discpkts
Add leaf /state/interfaces/interface/interface-statistics/stream-counters/ulei-statistics/in-urpf-discpkts
Add leaf /state/interfaces/interface/interface-statistics/stream-counters/ulei-statistics/e-urpf-discpkts' ;
  }

  revision 2014-06-10 {
    description 'Add new container pw-configuration to configure pseudo wires.' ;
  }

  revision 2014-05-09 {
    description 'Add new leaf input-crcerrors-ratio in container common-statistics.
Add new leaf output-crcerrors-ratio in container common-statistics.' ;
  }

  revision 2014-04-29 {
    description 'Set the leaf is-group in container track-trigger mandatory, and delete its default value.
Add five features for interface-statistics function.' ;
  }

  revision 2014-04-09 {
    description 'Change the type of the leaf name in logic-interface-summary' ;
  }

  revision 2014-03-20 {
    description 'Add new leaf period in container track-trigger.' ;
  }

  revision 2014-03-04 {
    description 'Add new leaf alarm-threshold in container interface-statistics.' ;
  }

  revision 2014-02-10 {
    description "Add new container one-minute-peak-all, set leaf one-minute-peak-all become it's sub leaf." ;
  }

  revision 2014-01-25 {
    description "Add new list logic-interface-summary, set leaf name and leaf number become it's sub leaves.

    Add new container track-trigger, set leaf name ,leaf track-status and leaf is-group become it's sub leaves." ;
  }

  revision 2014-01-20 {
    description 'Add new container atm-statistics in container hw-counters.
Add new container posgroup-statistics in container hw-counters.
Add new container serial-statistics in container hw-counters.

Add new container cpos-statistics in container hw-counters.
Add new container cpos-fr-statistics in container hw-counters.
Add new container cpos-tdm-statistics in container hw-counters.
Add new container stream-counters in container interface-statistics.' ;
  }

  revision 2014-01-15 {
    description "Add new container switch-attribute, set leaf switch-attribute become it's sub leaf.

    Set the derivedtype of the leaf name tobe dcn:ifname." ;
  }

  revision 2014-01-09 {
    description 'Change the derivedtype of the leaf input-rate-peak-time from datetime to string-with-blank.
Change the derivedtype of the leaf output-rate-peak-time from datetime to string-with-blank.' ;
  }

  revision 2013-12-19 {
    description 'Change the type of the leaf is-gateway-interface from boolean to empty, and delete its default value. As long as the leaf has value, the interface is gateway interface.
Change the type of the leaf enable from boolean to empty, and delete its default value. As long as the leaf has value, the interface is enabled its IPv6 protocol.
Change the leaf prefix-len to non mandatory.
Change name of the leaf offset into mac-address-offset' ;
  }

  revision 2013-12-05 {
    description "Add new leaf one-minute-peak-all in container interface-statistics.

    Add new container one-minute-peak, set leaf one-minute-peak become it's sub leaf.

    Add new container threshold, set list ratio-threshold and count-threshold become it's sub list.

    Add new leaves ipv4-oper-status, ipv6-oper-status, phys-address, photo-electricity in state.

    Add new container interface-statistics in state, set container common-statistics and hw-counters become it's sub container.

    Add new container interface-statistics in operation,set leaf clear-one-minute-peak-all and clear-interface-statistics-all become it's sub leaf, set container clear become it's sub container." ;
  }

  revision 2013-11-15 {
    description 'Change the type of leaf description from string to ncd:string-with-blank.' ;
  }

  revision 2013-10-28 {
    description 'Set leaf is-group mandatory true, and delete the default value of the leaf.' ;
  }

  revision 2013-09-09 {
    description "Add new container interface-statistics, set leaf traffic-statistics-switch become it's sub leaf.

    Add new container subport, set leaf subport-switch become it's sub leaf.

    Add new container interface-configuration, set list interface become it's sub leaf

    Add new container gateway, set leaf is-gateway-interface become it's sub leaf.

    Add new container vrf, set leaf ip-vrf-forwarding become it's sub leaf.

    Add new container ip-unnumber, set leaf ip-unnumber-name become it's sub leaf.

    Add new container multicase-ecmp, set leaf multicase-ecmp-cost become it's sub leaf.

    Add new container if-track, set list track become it's sub list.

    Delete the \"mandatory true\" of leaf name(list interface), address,mask,primary(list address), leaf address,flag(list address), leaf name,type(list track).

    Delete the default value of leaf primary-or-secondly and leaf flag.

    Move leaf mtu,mpls-mtu to container gateway.

    Exchange the position of leaf flag and leaf prefix-len.

    Change the length of leaf name(list interface) from 1..32 to 1..31.

    Add new default value of leaf traffic-statistics-switch.

    Add new default value of leaf is-gateway-interface." ;
  }

  revision 2013-07-02 {
    description 'The initial version' ;
  }

  feature global-traffic-statistics {
    description 'The global traffic statistics function.' ;
  }

  feature one-minute-peak {
    description 'The one-minute peak statistcs function.' ;
  }

  feature logic-traffic-statistics {
    description 'The VLAN/Te-tunnel Port traffic-statistics function.' ;
  }

  feature subport-traffic-statistics {
    description 'The SubPort traffic-statistics function.' ;
  }

  feature alarm-input-fcserrors {
    description 'The configuration for input-fcserrors alarm function.' ;
    ncd:revise-date 2023-12-11 ;
  }

  feature threshold {
    description 'The threashold configuration for alarm function.' ;
  }

  feature effective-time-threshold {
    description 'The effective-time-threshold configuration for alarm function.' ;
  }

  feature anycast-mac-address {
    description 'The anycast-mac-address configuration for configure MAC address to be anycast.' ;
  }

  feature rate-statistics {
    description 'The interface rate count period set function.' ;
  }

  feature global-rate-statistics {
    description 'The global interface rate count period set function.' ;
  }

  feature ip-address-primary-sec {
    description 'IP address primary-secondary function.' ;
  }

  feature config-limited-number ;

  feature chinese-desc {
    description 'Set the chinese description of interface.' ;
  }

  feature subport-v4-traffic-statics {
    description 'The SubPort v4-traffic-statistics function.' ;
  }

  feature subport-v6-traffic-statics {
    description 'The SubPort v6-traffic-statistics function.' ;
  }

  feature shutdown-interface-alarm-shield {
    description 'shutdown-interface alarm-shield configration.' ;
  }

  feature mc-lag-address {
    description 'The multi-chassis link aggregation group function.' ;
  }

  feature extra-mc-lag-address {
    description 'The extra-multi-chassis link aggregation group function.' ;
    ncd:revise-date 2023-07-25 ;
  }

  feature channel-bandwidth {
    description 'channel bandwidth configration.' ;
    ncd:revise-date 2021-10-12 ;
  }

  feature traffic-statistics-store {
    ncd:revise-date 2022-02-24 ;
  }

  feature threshold-upsend-car-drop {
    description 'The upsend car drop threashold configuration for alarm function.' ;
    ncd:revise-date 2022-09-19 ;
  }

  feature global-threshold {
    description 'The global threashold configuration for alarm function.' ;
    ncd:revise-date 2022-09-19 ;
  }

  feature threshold-rate-drop {
    description 'The rate drop threashold configuration for alarm function.' ;
    ncd:revise-date 2023-03-03 ;
  }

  feature threshold-utilization-change {
    description 'The utilization change threashold configuration for alarm function.' ;
    ncd:revise-date 2023-03-03 ;
  }

  feature traffic-statistics-change {
    description 'The traffic statistics change configuration.' ;
    ncd:revise-date 2025-01-06 ;
  }

  feature counter-smooth {
    description 'The period attribute of the counter-smooth.' ;
    ncd:revise-date 2025-03-16 ;
  }

  container configuration {
    description 'Describe the configuration of interfaces' ;
    container interfaces {
      description 'Describe the parameters of interfaces to be configured' ;
      container interface-statistics {
        description 'Describe the parameters of interface statistics to be configured' ;
        leaf traffic-statistics-switch {
          if-feature global-traffic-statistics ;

          description 'Enable or disable the global traffic statistics. When this switch is disabled, the traffic statistics of all interfaces in the device is disabled. Otherwise it depends on the switch on the particular interface.' ;
          type enumeration {
            enum disable {
              value 0 ;
              description 'Disable the global traffic statistics' ;
            }

            enum enable {
              value 1 ;
              description 'Enable the global traffic statistics' ;
            }

          }

          default enable ;
        }

        leaf traffic-statistics-store-switch {
          if-feature traffic-statistics-store ;

          description 'The storage of traffic statistics. When this switch is enabled, The traffic statistics will be stored in the local disk.' ;
          type enumeration {
            enum disable {
              value 0 ;
              description 'Disable storing traffic statistics' ;
            }

            enum enable {
              value 1 ;
              description 'Enable storing traffic statistics' ;
            }

          }

          default disable ;
          ncd:revise-date 2022-02-24 ;
        }

        container one-minute-peak-all {
          if-feature one-minute-peak ;

          description 'Describe the one-minute-peak-value statistics to be configed for all eth-port.' ;
          leaf one-minute-peak-all {
            description 'Enable or disable one-minute-peak-value statistics for all eth-port.' ;
            type enumeration {
              enum disable {
                value 0 ;
                description 'disable one-minute-peak function.' ;
              }

              enum enable {
                value 1 ;
                description 'enable one-minute-peak function.' ;
              }

            }

            default disable ;
          }

        }

        leaf alarm-threshold {
          description 'Enable or disable the global threshold alarm.Only act on alarm type with bandwidth utilization and fcserrors.Only act on those interfaces who have not configured threshold.' ;
          type enumeration {
            enum disable {
              value 0 ;
              description 'Disable the global threshold alarm' ;
            }

            enum enable {
              value 1 ;
              description 'Enable the global threshold alarm' ;
            }

          }

          default enable ;
        }

        container rate-statistics {
          if-feature global-rate-statistics ;

          description 'Describe the parameters of rate count to be configured.' ;
          leaf period {
            description 'The interface rate count period.
Rate period which is a multiple of 10 (sec).' ;
            type uint32 {
              range 10..600 ;

            }

            units seconds ;
          }

          ncd:revise-date 2017-07-25 ;
        }

        container global-threshold {
          if-feature global-threshold ;

          description 'Describe the parameters of global threshold to be configured' ;
          list ratio-threshold {
            description 'Describe the parameters of percent-type global threshold to be configured.' ;
            key alarm-type ;
            leaf alarm-type {
              description 'The type of alarm.' ;
              type enumeration {
                enum input-utilization {
                  value 1 ;
                }

                enum output-utilization {
                  value 2 ;
                }

                enum input-fcsratio {
                  value 4 ;
                }

              }

            }

            leaf limit-ratio-low {
              description 'The lower limit range of alarm thresholds.' ;
              type uint32 {
                range 0..99 ;

              }

              default 0 ;
            }

            leaf limit-ratio-high {
              description 'The higher limit range of alarm thresholds.' ;
              type uint32 {
                range 1..100 ;

              }

            }

          }

          list count-threshold {
            description 'Describe the parameters of count-type global threshold to be configured.' ;
            key alarm-type ;
            leaf alarm-type {
              description 'The type of alarm.' ;
              type enumeration {
                enum input-fcserrors {
                  value 3 ;
                }

              }

            }

            leaf limit-count-low {
              description 'The lower limit range of alarm thresholds.' ;
              type uint32 {
                range 0..4294967294 ;

              }

              default 0 ;
            }

            leaf limit-count-high {
              description 'The higher limit range of alarm thresholds.' ;
              type uint32 {
                range 1..4294967295 ;

              }

            }

          }

          ncd:revise-date 2022-09-19 ;
        }

        container traffic-statistics-change {
          leaf rate-drop-switch {
            type enumeration {
              enum enable {
                value 1 ;
                description 'Enable the global rate drop alarm function' ;
              }

              enum disable {
                value 0 ;
                description 'Disable the global rate drop alarm function' ;
              }

            }

            description 'Enable or disable the global rate drop alarm function. When this switch is disabled, the rate drop alarm function of all interfaces in the device is disabled. Otherwise it depends on the switch on the particular interface.' ;
            default enable ;
          }

          leaf utilization-change-switch {
            type enumeration {
              enum enable {
                description 'Enable the global utilization change notice function' ;
                value 1 ;
              }

              enum disable {
                description 'Disable the global utilization change notice function' ;
                value 0 ;
              }

            }

            description 'Enable or disable the global utilization change notice function. When this switch is disabled, the utilization change notice function of all interfaces in the device is disabled. Otherwise it depends on the switch on the particular interface.' ;
            default enable ;
          }

          leaf period {
            type uint32 {
              range 120..600 ;

            }

            description 'The traffic statistics change period, which is a multiple of 10 (sec).' ;
            units seconds ;
            default 120 ;
          }

          if-feature traffic-statistics-change ;

          description 'Describe the parameters of global traffic statistics change to be configured' ;
          ncd:revise-date 2025-01-06 ;
        }

        container counter-smooths {
          description 'Interface counting smooth period configurations.' ;
          list counter-smooth {
            leaf termianl-type {
              type enumeration {
                enum mib {
                  value 1 ;
                }

                enum telemetry {
                  value 2 ;
                }

                enum netconf {
                  value 3 ;
                }

                enum cli {
                  value 4 ;
                }

              }

              description 'Terminal type of interface counting smooth period configuration.' ;
            }

            leaf counter-smooth-period {
              type uint32 {
                range 10..120 ;

              }

              description 'Smooth period which is a multiple of 10 (sec).' ;
              mandatory true ;
            }

            description 'Interface counting smooth period configuration.' ;
            key termianl-type ;
            max-elements 4 ;
          }

          if-feature counter-smooth ;

          ncd:revise-date 2025-03-16 ;
        }

      }

      container interface-configuration {
        description 'Describe the parameters of interfaces to be configured' ;
        list interface {
          description 'The list of interfaces for configuring parameters' ;
          key name ;
          leaf name {
            description 'The name of the interface.

This leaf MAY be mapped to ifName by an implementation. Such an implementation MUST restrict the values for this leaf so that it matches the restrictions of ifName.' ;
            reference "RFC 2863: The Interfaces Group MIB - ifName" ;
            type ncd:ifname ;

          }

          leaf description {
            description 'A textual description of the interface.This string should include the name of the
manufacturer, the product name and the version of the interface hardware/software.

This leaf has the same semantics as ifDescr.' ;
            reference "RFC 2863: The Interfaces Group MIB - ifDescr" ;
            type ncd:string-with-blank {
              length 1..242 ;

            }

          }

          leaf admin-status {
            description 'This leaf contains the configured, desired state of the interface.

This leaf has the same semantics as ifAdminStatus.' ;
            reference "RFC 2863: The Interfaces Group MIB - ifAdminStatus" ;
            type enumeration {
              enum disable {
                value 0 ;
                description 'Disable the desired state of the interface' ;
              }

              enum enable {
                value 1 ;
                description 'Enable the desired state of the interface' ;
              }

            }

          }

          leaf link-up-down-trap-enable {
            description 'Indicates whether linkUp/linkDown traps should be generated for this interface.

This leaf has the same semantics as ifLinkUpDownTrapEnable.' ;
            reference "RFC 2863: The Interfaces Group MIB ifLinkUpDownTrapEnable" ;
            type boolean ;

          }

          container interface-statistics {
            description 'Describe the parameters of interface statistics to be configured' ;
            leaf switch {
              if-feature logic-traffic-statistics ;

              description 'Enable or disable the current interface traffic statistics. Only when the current interface is VLAN interface or TE tunnel, the switch is effective.

Only particular interfaces can configure this traffic statistics switch. For those one can not configure this switch, the leaf of this container are not present.' ;
              type enumeration {
                enum disable {
                  value 0 ;
                  description 'Disable the current interface traffic statistics' ;
                }

                enum enable {
                  value 1 ;
                  description 'Enable the current interface traffic statistics' ;
                }

              }

            }

            container alarm-input-fcserrors {
              description 'Describe the parameters of interface input-fcserrors alarm to be configured' ;
              if-feature alarm-input-fcserrors {
                ncd:revise-date 2023-12-11 ;
              }

              leaf period {
                type uint32 {
                  range 10..65530 ;

                }

                description 'The interface input-fcserrors alarm period.
Alarm period which is an multiple of 10 (sec).' ;
                default 10 ;
                units seconds ;
              }

              ncd:revise-date 2023-12-11 ;
            }

            container subport {
              if-feature subport-traffic-statistics ;

              description 'Describe the parameters of interface statistics to be configured' ;
              leaf subport-switch {
                description 'Enable or disable subinterface traffic statistics. If the current interface is a subinterface, the subport-switch discribes enable or disable the current interface traffic statistics. Otherwise it discribes enable of disable all subinterface(s) of the current interface traffic statistics.
Whether the currnet interface enable traffic statistics, or its parent interface enable all subinterfaces traffic statistics, the traffic statistics of it is enabled. 
Only when the current interface disable traffic statistics, and its parent interface disable all subinterfaces traffic statistics, the traffic statistics of it is disabled.

Only particular interfaces can configure this traffic statistics switch. For those one can not configure this switch, the leaf of this container are not present.' ;
                type enumeration {
                  enum disable {
                    value 0 ;
                    description 'Disable subinterface traffic statistics' ;
                  }

                  enum enable {
                    value 1 ;
                    description 'Enable subinterface traffic statistics' ;
                  }

                }

              }

              container subport-v4 {
                if-feature subport-v4-traffic-statics ;

                description 'Describe the parameters of interface statistics to be configured' ;
                leaf subport-v4-switch {
                  description 'Enable or disable subinterface  v4 traffic statistics. If the current interface is a subinterface, the subport-switch discribes enable or disable the current interface v4 traffic statistics. Otherwise it discribes enable of disable all subinterface(s) of the current interface v4 traffic statistics.
Only when the currnet interface enable v4 traffic statistics, and its parent interface enable all subinterfaces v4 traffic statistics, the v4 traffic statistics of it is enabled. 
Whether the current interface disable v4 traffic statistics, or its parent interface disable all subinterfaces v4 traffic statistics, the v4 traffic statistics of it is disabled.' ;
                  type enumeration {
                    enum enable {
                      value 1 ;
                    }

                    enum disable {
                      value 0 ;
                    }

                  }

                }

                ncd:revise-date 2020-06-15 ;
              }

              container subport-v6 {
                if-feature subport-v6-traffic-statics ;

                description 'Describe the parameters of interface statistics to be configured' ;
                leaf subport-v6-switch {
                  description 'Enable or disable subinterface  v6 traffic statistics. If the current interface is a subinterface, the subport-switch discribes enable or disable the current interface v6 traffic statistics. Otherwise it discribes enable of disable all subinterface(s) of the current interface v6 traffic statistics.
Only when the currnet interface enable v6 traffic statistics, and its parent interface enable all subinterfaces v6 traffic statistics, the v6 traffic statistics of it is enabled. 
Whether the current interface disable v6 traffic statistics, or its parent interface disable all subinterfaces v6 traffic statistics, the v6 traffic statistics of it is disabled.' ;
                  type enumeration {
                    enum enable {
                      value 1 ;
                    }

                    enum disable {
                      value 0 ;
                    }

                  }

                }

                ncd:revise-date 2020-06-15 ;
              }

            }

            container one-minute-peak {
              if-feature one-minute-peak ;

              description 'Describe the one-minute-peak-value statistics to be configed' ;
              leaf one-minute-peak {
                description 'Enable or disable one-minute-peak-value statistics for single eth-port.' ;
                type enumeration {
                  enum disable {
                    value 0 ;
                  }

                  enum enable {
                    value 1 ;
                  }

                }

                default disable ;
              }

            }

            container threshold {
              if-feature threshold ;

              description 'Describe the parameters of interface threshold to be configured' ;
              list ratio-threshold {
                description 'Describe the parameters of percent-type interface threshold  to be configured.' ;
                key alarm-type ;
                leaf alarm-type {
                  description 'The type of alarm.' ;
                  type enumeration {
                    enum input-utilization {
                      value 1 ;
                    }

                    enum output-utilization {
                      value 2 ;
                    }

                    enum input-fcsratio {
                      value 4 ;
                    }

                  }

                }

                leaf limit-ratio-low {
                  description 'The lower limit range of alarm thresholds.' ;
                  type uint32 {
                    range 0..99 ;

                  }

                  default 0 ;
                }

                leaf limit-ratio-high {
                  description 'The higher limit range of alarm thresholds.' ;
                  type uint32 {
                    range 1..100 ;

                  }

                }

              }

              list count-threshold {
                description 'Describe the parameters of count-type interface threshold  to be configured.' ;
                key alarm-type ;
                leaf alarm-type {
                  description 'The type of alarm.' ;
                  type enumeration {
                    enum input-fcserrors {
                      value 3 ;
                    }

                  }

                }

                leaf limit-count-low {
                  description 'The lower limit range of alarm thresholds.' ;
                  type uint32 {
                    range 0..4294967294 ;

                  }

                  default 0 ;
                }

                leaf limit-count-high {
                  description 'The higher limit range of alarm thresholds.' ;
                  type uint32 {
                    range 1..4294967295 ;

                  }

                }

              }

            }

            container threshold-upsend-car-drop {
              if-feature threshold-upsend-car-drop ;

              description 'Describe the parameters of interface upsend car drop threshold to be configured' ;
              leaf limit-ratio {
                description 'The portlimit of alarm thresholds.' ;
                type uint32 {
                  range 0..100 ;

                }

              }

              ncd:revise-date 2022-09-19 ;
            }

            container effective-time-threshold {
              if-feature effective-time-threshold ;

              description 'Describe the parameters of interface effective-time-threshold to be configured' ;
              list ratio-threshold {
                description 'Describe the parameters of percent-type interface threshold to be configured.' ;
                key alarm-type ;
                leaf alarm-type {
                  description 'The type of alarm.' ;
                  type enumeration {
                    enum input-utilization {
                      value 1 ;
                    }

                    enum output-utilization {
                      value 2 ;
                    }

                    enum input-fcsratio {
                      value 4 ;
                    }

                  }

                }

                leaf limit-ratio-low {
                  description 'The lower limit range of alarm thresholds.' ;
                  type uint32 {
                    range 0..99 ;

                  }

                  mandatory true ;
                }

                leaf limit-begin-date {
                  description 'The begin date of effective-time-threshold configuration' ;
                  type ncd:date ;

                }

                leaf limit-begin-time {
                  description 'The begin time of effective-time-threshold configuration' ;
                  type ncd:time ;

                  mandatory true ;
                }

                leaf limit-end-date {
                  description 'The end date of effective-time-threshold configuration' ;
                  type ncd:date ;

                }

                leaf limit-end-time {
                  description 'The end time of effective-time-threshold configuration' ;
                  type ncd:time ;

                  mandatory true ;
                }

              }

              list count-threshold {
                description 'Describe the parameters of count-type interface threshold  to be configured.' ;
                key alarm-type ;
                leaf alarm-type {
                  description 'The type of alarm.' ;
                  type enumeration {
                    enum input-fcserrors {
                      value 3 ;
                    }

                  }

                }

                leaf limit-count-low {
                  description 'The lower limit range of alarm thresholds.' ;
                  type uint32 {
                    range 0..4294967294 ;

                  }

                  mandatory true ;
                }

                leaf limit-begin-date {
                  description 'The begin date of effective-time-threshold configuration' ;
                  type ncd:date ;

                }

                leaf limit-begin-time {
                  description 'The begin time of effective-time-threshold configuration' ;
                  type ncd:time ;

                  mandatory true ;
                }

                leaf limit-end-date {
                  description 'The end date of effective-time-threshold configuration' ;
                  type ncd:date ;

                }

                leaf limit-end-time {
                  description 'The end time of effective-time-threshold configuration' ;
                  type ncd:time ;

                  mandatory true ;
                }

              }

              ncd:revise-date 2016-03-15 ;
            }

            container rate-statistics {
              if-feature rate-statistics ;

              description 'Describe the parameters of rate count to be configured.' ;
              leaf period {
                description 'The interface rate count period.
Rate period which is an multiple of 10 (sec).' ;
                type uint32 {
                  range 10..600 ;

                }

                units seconds ;
              }

              ncd:revise-date 2017-01-16 ;
            }

            container threshold-rate-drop {
              if-feature threshold-rate-drop ;

              description 'Describe the parameters of interface rate drop threshold to be configured' ;
              list rate-drop {
                description 'Describe the parameters of rate-type interface threshold to be configured.' ;
                key alarm-type ;
                leaf alarm-type {
                  description 'The type of alarm.' ;
                  type enumeration {
                    enum input {
                      value 1 ;
                    }

                    enum output {
                      value 2 ;
                    }

                  }

                }

                leaf normal-threshold {
                  type uint32 {
                    range 0..4294967295 ;

                  }

                  description 'The normal threshold of rate drop alarm.' ;
                  status obsolete {
                    ncd:revise-date 2025-01-06 ;
                  }
                }

                leaf alarm-threshold {
                  type uint32 {
                    range 0..4294967295 ;

                  }

                  description 'The alarm threshold of rate drop alarm.' ;
                  status obsolete {
                    ncd:revise-date 2025-01-06 ;
                  }
                }

                leaf check-rate-threshold {
                  description 'The check rate threshold of rate drop alarm.' ;
                  default 500000000 ;
                  units bps ;
                  type uint32 {
                    range 0..4294967295 ;

                  }

                  ncd:revise-date 2025-01-06 ;
                }

                leaf check-utilization-threshold {
                  description 'The check utilization threshold of rate drop alarm.' ;
                  default 20 ;
                  type uint32 {
                    range 1..100 ;

                  }

                  ncd:revise-date 2025-01-06 ;
                }

                leaf change-ratio-threshold {
                  type uint32 {
                    range "0|50..100" ;

                  }

                  description 'The change ratio threshold of rate drop alarm.' ;
                  default 99 ;
                  ncd:revise-date 2025-01-06 ;
                }

              }

              ncd:revise-date 2023-03-03 ;
            }

            container threshold-utilization-change {
              if-feature threshold-utilization-change ;

              description 'Describe the parameters of interface utilization change threshold to be configured.' ;
              list utilization-change {
                description 'Describe the parameters of utilization-type interface threshold to be configured.' ;
                key alarm-type ;
                leaf alarm-type {
                  description 'The type of alarm.' ;
                  type enumeration {
                    enum input {
                      value 1 ;
                    }

                    enum output {
                      value 2 ;
                    }

                  }

                }

                leaf check-threshold {
                  description 'The check threshold of utilization change notice.' ;
                  type uint32 {
                    range 1..100 ;

                  }

                }

                leaf range-threshold {
                  description 'The range threshold of utilization change notice.' ;
                  type uint32 {
                    range 1..100 ;

                  }

                }

              }

              ncd:revise-date 2023-03-03 ;
            }

            container traffic-statistics-change {
              leaf rate-drop-switch {
                type enumeration {
                  enum enable {
                    value 1 ;
                    description 'Enable the interface rate drop alarm function' ;
                  }

                  enum disable {
                    description 'Disable the interface rate drop alarm function' ;
                    value 0 ;
                  }

                }

                description 'Enable or disable the interface rate drop alarm function.' ;
                default enable ;
              }

              leaf utilization-change-switch {
                type enumeration {
                  enum enable {
                    value 1 ;
                    description 'Enable the interface utilization change notice function' ;
                  }

                  enum disable {
                    description 'Enable the interface utilization change notice function' ;
                    value 0 ;
                  }

                }

                description 'Enable or disable the interface utilization change notice function. ' ;
                default enable ;
              }

              description 'Describe the parameters of interface traffic statistics change to be configured' ;
              if-feature traffic-statistics-change ;

              ncd:revise-date 2025-01-06 ;
            }

          }

          container encapsulation {
            description 'Configure the encapsulation for this interface.

Only particular interfaces support encapsulation. For interfaces that do not support encapsulation, the leafs of this container are not present.' ;
            presence "the leaf type of this container should be mandatory, and other leafs are not." ;
            leaf type {
              description 'The encapsulation type for this interface' ;
              type enumeration {
                enum ppp {
                  value 1 ;
                  description 'The encapsulation type is Point-to-Point protocol (PPP).' ;
                }

                enum hdlc {
                  value 2 ;
                  description 'The encapsulation type is High Level Data Link Control (HDLC) protocol.' ;
                }

                enum frame-relay {
                  value 3 ;
                  description 'The encapsulation type is Frame Relay.' ;
                }

                enum eos {
                  value 13 ;
                  description 'The encapsulation type is Ethernet Over Sdh.' ;
                }

                enum ces {
                  value 14 ;
                  description 'The encapsulation type is Circuit Emulation Service.' ;
                }

              }

              mandatory true ;
            }

            leaf single-comm {
              description 'Configure the protocol data packet is a single communication, and choose the protocol data packet is been received only or transported only. If this parameter does not configured, the protocol data packet is been both received and transported.' ;
              type enumeration {
                enum rx {
                  value 1 ;
                  description 'The protocol data packet is been received only.' ;
                }

                enum tx {
                  value 2 ;
                  description 'The protocol data packet is been transported only.' ;
                }

              }

            }

          }

          container switch-attribute {
            description 'Configure the switch attribute of this interface.' ;
            leaf switch-attribute {
              description 'Enable or disable the switch attribute of the interface.' ;
              type enumeration {
                enum disable {
                  value 0 ;
                  description 'Disable the switch attribute of the interface.' ;
                }

                enum enable {
                  value 1 ;
                  description 'Enable the switch attribute of the interface.' ;
                }

              }

            }

          }

          choice phys-address {
            description "The interface's address at its protocol sub-layer.



            For interfaces that do not have such an address, this node is not present." ;
            case mac-address {
              description 'Configure the MAC address of this interface.' ;
              leaf mac-address {
                description 'The MAC address of this interface

For interfaces that do not have the MAC address, this node is not present.' ;
                reference "RFC 2863: The Interfaces Group MIB - ifPhysAddress" ;
                type ncd:mac-address ;

              }

              leaf is-anycast {
                if-feature anycast-mac-address ;

                description 'Configure the MAC address to anycast. Choose true to make it to be anycast,or choose false to make it normal.' ;
                type boolean ;

                default false ;
                ncd:revise-date 2016-11-11 ;
              }

            }

            case mac-address-offset {
              description "Configure the MAC address of this interface offset.



              If the interface is a subinteface, and it's father interface has configured the MAC address, the offset is from the MAC address on it's father interface. Otherwise the offset is from the base MAC on the current device." ;
              leaf mac-address-offset {
                description "Configure the MAC address of this interface offset.



                If the interface is a subinteface, and it's father interface has configured the MAC address, the offset is from the MAC address on it's father interface. Otherwise the offset is from the base MAC on the current device." ;
                type uint32 ;

              }

            }

          }

          leaf mtu {
            description 'The maximum transmission unit with link layer of the interface.

The value of this leaf is the configuration value of MTU, may not equal the effect value.
Only particular interfaces have MTU. For interfaces that do not have this attribute, this node is not present.' ;
            type uint32 {
              range 0..9700 ;

            }

            units bytes ;
          }

          leaf mpls-mtu {
            description 'The maximum transmission unit with MPLS protocol layer of the interface.

The value of this leaf is the configuration value of MPLS MTU, may not equal the effect value.
Only particular interfaces have MPLS MTU. For interfaces that do not have this attribute, this node is not present.' ;
            type uint32 {
              range 68..9600 ;

            }

            units bytes ;
          }

          container gateway {
            description 'Configure gateway for this interface.

Only particular interfaces support gateway. For interfaces that do not support gateway, the leafs of this container are not present.' ;
            leaf is-gateway-interface {
              description 'Configure whether the interface is a gateway interface.

Only particular interfaces can be configured to be a gateway interface. For those one can not be, the leaf of this container are not present or with the value of false.' ;
              type empty ;

            }

          }

          container vrf {
            description 'The parameters of VRF on the interface to be configured.

Only particular interfaces support VRF. For interfaces that do not support VRF, the leafs of this container are not present.' ;
            leaf ip-vrf-forwarding {
              description 'Associates a VRF with the interface

Only particular interfaces support IP VRF forwarding. For interfaces that do not support IP VRF forwarding, the leafs of this container are not present.' ;
              type string {
                length 1..32 ;

              }

            }

          }

          container ip-unnumber {
            description 'The parameters of IP unnumber on the interface to be configured.

Only particular interfaces support IP unnumber. For interfaces that do not support IP unnumber, the leafs of this container are not present.' ;
            leaf ip-unnumber-name {
              description 'the name of the interface which is been ip unnumbered on.

The ip unnumbered configuration command allows you to enable IP processing on a serial interface without assigning it an explicit IP address. The ip unnumbered interface can "borrow" the IP address of another interface already configured, which conserves network and address space. 

Only particular interfaces support IP unnumber. For interfaces that do not support IP unnumber, the node is not present.' ;
              type leafref {
                path "/configuration/interfaces/interface-configuration/interface/name" ;
              }

            }

          }

          container ipv4 {
            description 'The parameters of IPv4 protocol on the interface to be configured.

Only layer 3 interfaces support IPv4 protocol. For interfaces that do not support IPv4 protocol, the leafs of this container are not present.' ;
            container addresses {
              description 'The IPv4 addresses of the interface' ;
              list address {
                description 'The list of IPv4 addresses configured on the interface.' ;
                key 'address mask primary-or-secondly' ;
                leaf address {
                  description "The IPv4 address to which this entry's addressing information pertains." ;
                  type ncd:ipv4-address ;

                }

                leaf mask {
                  description 'The subnet mask associated with the IP address of this entry.  The value of the mask is an IP address with all the network bits set to 1 and all the hosts bits set to 0.' ;
                  type ncd:ipv4-mask ;

                }

                leaf primary-or-secondly {
                  description "Describe whether this entry's address is primary or secondly.



                  Each interface can only configure one primary address, but more secondly addresses. And the secondly addresses can only be configured when the primary address is already exist." ;
                  type enumeration {
                    enum primary {
                      value 1 ;
                      description "this entry's address is primary address." ;
                    }

                    enum secondly {
                      value 2 ;
                      description "this entry's address is escondly address." ;
                    }

                  }

                }

                leaf is-mclag {
                  if-feature mc-lag-address ;

                  description 'Configure the address type. Choose true to make it to be MC-LAG address,or choose false to make it normal.' ;
                  type boolean ;

                  default false ;
                  ncd:revise-date 2021-03-03 ;
                }

                leaf is-extra-mc-lag {
                  if-feature extra-mc-lag-address ;

                  description 'Configure the address type. Choose true to make it to be EXTRA-MC-LAG address,or choose false to make it normal.' ;
                  type boolean ;

                  default false ;
                  ncd:revise-date 2023-07-25 ;
                }

              }

            }

            leaf mtu {
              description 'The maximum transmission unit with IPv4 protocol layer of the interface.

The value of this leaf is the configuration value of IPv4 MTU, may not equal the effect value.
Only particular interfaces have IPv4 MTU. For interfaces that do not have this attribute, this node is not present.' ;
              type uint32 {
                range 0..9600 ;

              }

              units bytes ;
            }

          }

          container ipv6 {
            description 'The parameters of IPv6 protocol on the interface to be configured.

Only particular interfaces support IPv6 protocol. For interfaces that do not support IPv6 protocol, the leafs of this container are not present.' ;
            leaf enable {
              description 'Enable IPv6 protocol on the interface.' ;
              type empty ;

            }

            container addresses {
              description 'The IPv6 addresses of the interface' ;
              list address {
                description 'The list of IPv6 addresses configured on the interface.' ;
                key 'address flag' ;
                leaf address {
                  description "The IPv6 address to which this entry's addressing information pertains." ;
                  type ncd:ipv6-address ;

                }

                leaf flag {
                  description "The IPv6 address type to which this entry's addressing information pertains, which includes linklocal address, anycast address, eui-64 address and unicast address." ;
                  type enumeration {
                    enum link-local {
                      value 1 ;
                      description 'IPv6 linklocal address' ;
                    }

                    enum unicast {
                      value 2 ;
                      description 'IPv6 unicast address' ;
                    }

                    enum anycast {
                      value 3 ;
                      description 'IPv6 anycast address' ;
                    }

                    enum eui-64 {
                      value 4 ;
                      description '64-bit extended unique identifier(EUI-64) address' ;
                    }

                  }

                }

                leaf prefix-len {
                  description "The prefix length to which this entry's addressing information pertains. The value of the mask prefix length is from 1 to 128." ;
                  type ncd:ipv6-mask-length {
                    range 1..128 ;

                  }

                }

                leaf is-mclag {
                  if-feature mc-lag-address ;

                  description 'Configure the address type. Choose true to make it to be MC-LAG address,or choose false to make it normal.' ;
                  type boolean ;

                  default false ;
                  ncd:revise-date 2021-03-03 ;
                }

                leaf is-extra-mc-lag {
                  if-feature extra-mc-lag-address ;

                  description 'Configure the address type. Choose true to make it to be EXTRA-MC-LAG address,or choose false to make it normal.' ;
                  type boolean ;

                  default false ;
                  ncd:revise-date 2023-07-25 ;
                }

              }

            }

            leaf mtu {
              description 'The maximum transmission unit with IPv6 protocol layer of the interface.

The value of this leaf is the configuration value of IPv6 MTU, may not equal the effect value.
Only particular interfaces have IPv6 MTU. For interfaces that do not have this attribute, this node is not present.' ;
              type uint32 {
                range 1280..9600 ;

              }

              units bytes ;
            }

          }

          container load-sharing {
            description 'The parameters of load sharing on the interface to be configured.

Only particular interfaces support load sharing. For interfaces that do not support load sharing, the leafs of this container are not present.' ;
            leaf bandwidth {
              description 'The load sharing bandwidth of the interface

Only particular interfaces support load sharing. For interfaces that do not support load sharing, this node is not present.' ;
              type uint32 {
                range 1..4294967295 ;

              }

              units "kbits / second" ;
            }

            leaf policy {
              description 'The load sharing policy of the interface

Only particular interfaces support load sharing. For interfaces that do not support load sharing, this node is not present.' ;
              type enumeration {
                enum per-destination {
                  value 0 ;
                  description 'The device distributes the packets based on the destination address.' ;
                }

                enum per-packet {
                  value 1 ;
                  description 'The device distributes the packets based on the packets.' ;
                }

              }

            }

            container priority {
              description 'The load sharing priority of the interface for dynamic load sharing.

Only particular interfaces support load sharing. For interfaces that do not support load sharing, the leafs of this container are not present.' ;
              presence "the leaf priority of this container should be mandatory, and other leafs are not." ;
              leaf priority {
                description 'The load sharing priority of the interface for dynamic load sharing. 
The traffic goes through the link with higher priority. When the traffic beyonds the bandwidth of the link, traffic beyonds the limit would go to the link with lower priority.

Only particular interfaces support load sharing. For interfaces that do not support load sharing, this node is not present.' ;
                type uint8 {
                  range 1..7 ;

                }

                mandatory true ;
              }

              leaf level {
                description 'The load sharing priority waterline of the interface for dynamic load sharing. 
When the traffic reaches the waterline*bandwidth of the link, traffic beyonds the limit would go to the link with lower priority.

Only particular interfaces support load sharing. For interfaces that do not support load sharing, this node is not present.' ;
                type uint8 {
                  range 50..95 ;

                }

                default 90 ;
              }

            }

          }

          container if-track {
            description 'The parameters of interface track to be configured.

Only particular interfaces can configure track entries.' ;
            list track {
              description 'The list of interface track entries.

Only particular interfaces can configure track entries.' ;
              key 'name type' ;
              leaf name {
                description 'The name of the track entry' ;
                type string {
                  length 1..31 ;

                }

              }

              leaf type {
                description 'The type of the track entry' ;
                type enumeration {
                  enum l2 {
                    value 1 ;
                    description 'The type of the track entry is layer2.' ;
                  }

                  enum ipv4 {
                    value 2 ;
                    description 'The type of the track entry is IPv4 protocol.' ;
                  }

                  enum ipv6 {
                    value 3 ;
                    description 'The type of the track entry is IPv6 protocol.' ;
                  }

                }

              }

              leaf is-group {
                description 'Describe whether the track entry is group or not.' ;
                type boolean ;

                mandatory true ;
              }

            }

          }

          container multicase-ecmp {
            description 'The parameters of Equal Cost Multipath (ECMP) multicast on the interface to be configured.

Only particular interfaces support ECMP. For interfaces that do not support ECMP, the leafs of this container are not present.' ;
            leaf multicase-ecmp-cost {
              description 'Equal Cost Multipath (ECMP) multicast bandwidth weight of the interface

Only particular interfaces support Equal Cost Multipath (ECMP) multicast bandwidth weight. For interfaces that do not support this attribute, this node is not present.' ;
              type uint8 {
                range 1..8 ;

              }

              default 1 ;
            }

          }

          container port-limit {
            description 'The parameters of qos on the interface to be configured.

Only particular interfaces support qos. For interfaces that do not support qos, the leafs of this container are not present or with the value of 0.' ;
            container high {
              description 'The parameters of high qos on the interface to be configured.

Only particular interfaces support high qos. For interfaces that do not support high qos, the leafs of this container are not present or with the value of 0.' ;
              presence "The parameter cir and cbs should be configured at the same time." ;
              leaf cir {
                description 'The committed information rate of high qos on the interface.

Only particular interfaces have the committed information rate. For interfaces that do not have this rate, this node is not present or with the value of 0.' ;
                type uint32 {
                  range 0..1000000 ;

                }

                units "packets / second" ;
                mandatory true ;
              }

              leaf cbs {
                description 'The committed burst size of high qos on the interface.

Only particular interfaces have the committed burst size. For interfaces that do not have this size, this node is not present or with the value of 0.' ;
                type uint32 {
                  range "0 | 16..100000" {
                    description 'The value of 0 indicates that the effective committed burst size would be adapted by the link layer, which would be different in different devices.' ;
                  }

                }

                units KB ;
                mandatory true ;
              }

            }

            container low {
              description 'The parameters of low qos on the interface to be configured.

Only particular interfaces support low qos. For interfaces that do not support low qos, the leafs of this container are not present or with the value of 0.' ;
              presence "The parameter cir and cbs should be configured at the same time." ;
              leaf cir {
                description 'The committed information rate of low qos on the interface.

Only particular interfaces have the committed information rate. For interfaces that do not have this rate, this node is not present or with the value of 0.' ;
                type uint32 {
                  range 0..1000000 ;

                }

                units "packets / second" ;
                mandatory true ;
              }

              leaf cbs {
                description 'The committed burst size of low qos on the interface.

Only particular interfaces have the committed burst size. For interfaces that do not have this size, this node is not present or with the value of 0.' ;
                type uint32 {
                  range "0 | 16..100000" {
                    description 'The value of 0 indicates that the effective committed burst size would be adapted by the link layer, which would be different in different devices.' ;
                  }

                }

                units KB ;
                mandatory true ;
              }

            }

          }

          container vlan-limit {
            description 'The parameters of VLAN qos on the interface to be configured.

Only particular interfaces support qos. For interfaces that do not support qos, the leafs of this container are not present or with the value of 0.' ;
            container high {
              description 'The parameters of VLAN high qos on the interface to be configured.

Only particular interfaces support high qos. For interfaces that do not support high qos, the leafs of this container are not present or with the value of 0.' ;
              presence "The parameter cir and cbs should be configured at the same time." ;
              leaf cir {
                description 'The committed information rate of VLAN high qos on the interface.

Only particular interfaces have the committed information rate. For interfaces that do not have this rate, this node is not present or with the value of 0.' ;
                type uint32 {
                  range 0..200000 ;

                }

                units "packets / second" ;
                mandatory true ;
              }

              leaf cbs {
                description 'The committed burst size of VLAN high qos on the interface.

Only particular interfaces have the committed burst size. For interfaces that do not have this size, this node is not present or with the value of 0.' ;
                type uint32 {
                  range "0 | 16..20000" {
                    description 'The value of 0 indicates that the effective committed burst size would be adapted by the link layer, which would be different in different devices.' ;
                  }

                }

                units KB ;
                mandatory true ;
              }

            }

            container low {
              description 'The parameters of VLAN low qos on the interface to be configured.

Only particular interfaces support low qos. For interfaces that do not support low qos, the leafs of this container are not present or with the value of 0.' ;
              presence "The parameter cir and cbs should be configured at the same time." ;
              leaf cir {
                description 'The committed information rate of VLAN low qos on the interface.

Only particular interfaces have the committed information rate. For interfaces that do not have this rate, this node is not present or with the value of 0.' ;
                type uint32 {
                  range 0..200000 ;

                }

                units "packets / second" ;
                mandatory true ;
              }

              leaf cbs {
                description 'The committed burst size of VLAN low qos on the interface.

Only particular interfaces have the committed burst size. For interfaces that do not have this size, this node is not present or with the value of 0.' ;
                type uint32 {
                  range "0 | 16..20000" {
                    description 'The value of 0 indicates that the effective committed burst size would be adapted by the link layer, which would be different in different devices.' ;
                  }

                }

                units KB ;
                mandatory true ;
              }

            }

          }

          container track-trigger {
            description 'Set interface track trigger' ;
            presence "the leaf name and track-status of this container should be mandatory, and other leafs are not." ;
            leaf name {
              description 'The name of the track entry' ;
              type string {
                length 1..31 ;

              }

              mandatory true ;
            }

            leaf track-status {
              description 'Block or shutdown the interface' ;
              type enumeration {
                enum block {
                  value 1 ;
                  description 'Block interface' ;
                }

                enum shutdown {
                  value 2 ;
                  description 'Shutdown interface' ;
                }

              }

              mandatory true ;
            }

            leaf is-group {
              description 'Describe whether the track entry is group or not.' ;
              type boolean ;

              mandatory true ;
            }

            leaf period {
              description 'Shutdown time' ;
              type uint16 {
                range 10..600 {
                  description 'shutdown time' ;
                }

              }

              units seconds ;
            }

          }

          leaf type {
            description 'The type of the interface.
When an interface entry is created, a server MAY initialize the type leaf with a valid value, e.g., if it is possible to derive the type from the name of the interface.
the leaf can only be read.' ;
            type uint16 ;

          }

          container off-line {
            description 'Indicates whether the physical state is off-line for the interface.' ;
            leaf off-line {
              description 'Indicates whether the physical state is off-line for the interface.' ;
              type empty ;

            }

          }

          leaf index {
            description 'The index of the interface.
the leaf can only be read.' ;
            type uint32 ;

            ncd:revise-date 2017-04-10 ;
          }

          container mode {
            description 'Configure the mode of interfaces' ;
            leaf type {
              description 'Configure the mode of interface virtual_template' ;
              type enumeration {
                enum ppp {
                  value 1 ;
                  description 'ppp mode' ;
                }

                enum ps-core {
                  value 2 ;
                  description 'ps-core mode' ;
                }

              }

            }

            ncd:revise-date 2017-09-09 ;
          }

          container byname-set {
            description 'The parameters of byname on the interface to be configured.' ;
            leaf byname {
              description 'Associates byname with the interface.
Only particular interfaces support byname. For interfaces that do not support byname, the leafs of this container are not present.' ;
              type string {
                length 1..32 ;

              }

            }

            ncd:revise-date 2018-06-22 ;
          }

          leaf chinese-description {
            if-feature chinese-desc ;

            description 'A textual chinese description of the interface.This string should include the name of the
manufacturer, the product name and the version of the interface hardware/software.' ;
            type ncd:string-with-blank-and-chinese {
              length 1..242 ;

            }

            ncd:revise-date 2019-07-02 ;
          }

          container bandwidth-set {
            description 'The parameters of bandwidth on the interface to be configured.' ;
            leaf bandwidth {
              description 'The bandwidth of the interface

Only particular interfaces support bandwidth. For interfaces that do not support bandwidth, this node is not present.' ;
              type uint32 {
                range 1..1000000 ;

              }

              units "mbits / second" ;
            }

            ncd:revise-date 2019-08-13 ;
          }

          container channel-bandwidth {
            if-feature channel-bandwidth ;

            description 'The parameters of channel bandwidth on the interface to be configured.' ;
            leaf bandwidth {
              description 'The channel bandwidth of the interface.' ;
              type uint32 {
                range 0..1000000 ;

              }

              units "mbits / second" ;
            }

            ncd:revise-date 2021-10-12 ;
          }

          ncd:select name ;
          ncd:select type ;
          ncd:select index ;
        }

      }

      container pw-configuration {
        description 'Describe the parameters of pseudo wires to be configured' ;
        list pw {
          description 'The list of pseudo wires for configuring parameters' ;
          key name ;
          leaf name {
            description 'The name of the pseudo wire' ;
            type ncd:ifname ;

          }

        }

      }

      container ip-address {
        description 'Configure the interface IP/IPv6 address characters.' ;
        leaf primary-secondary {
          if-feature ip-address-primary-sec ;

          description 'Configure the interface IP address primary-secondary mode.' ;
          type enumeration {
            enum enable {
              value 1 ;
              description 'Enable IP address primary-secondary mode.' ;
            }

            enum disable {
              value 0 ;
              description 'Disable IP address primary-secondary mode.' ;
            }

          }

        }

        ncd:revise-date 2019-02-18 ;
      }

      container shutdown-interface {
        description 'Configuration about interfaces which configed shutdown command.' ;
        leaf alarm-shield {
          if-feature shutdown-interface-alarm-shield ;

          description 'Interface alarm shield funciton.' ;
          type enumeration {
            enum enable {
              value 1 ;
              description 'Enable the alarm sheild function.' ;
            }

            enum disable {
              value 0 ;
              description 'Disable alarm sheild function.' ;
            }

          }

        }

        ncd:revise-date 2020-06-29 ;
      }

    }

  }

  container state {
    config false ;
    description 'Data nodes for the operational state of interfaces.' ;
    container interfaces {
      description 'Describe the data nodes for the operational state of interfaces.' ;
      list interface {
        description 'The list of interfaces on the device' ;
        key name ;
        leaf name {
          description 'The name of the interface.

This leaf MAY be mapped to ifName by an implementation. Such an implementation MUST restrict the values for this leaf so that it matches the restrictions of ifName.' ;
          reference "RFC 2863: The Interfaces Group MIB - ifName" ;
          type leafref {
            path "/configuration/interfaces/interface-configuration/interface/name" ;
          }

        }

        leaf admin-status {
          description 'The desired state of the interface.

This leaf has the same semantics as ifAdminStatus.' ;
          reference "RFC 2863: The Interfaces Group MIB - ifAdminStatus" ;
          type enumeration {
            enum down {
              value 0 ;
              description 'The desired state of the interface is down.' ;
            }

            enum up {
              value 1 ;
              description 'The desired state of the interface is up.' ;
            }

          }

        }

        leaf phy-status {
          description 'The physical state of the interface.' ;
          type enumeration {
            enum down {
              value 0 ;
              description 'The physical state of the interface is down.' ;
            }

            enum up {
              value 1 ;
              description 'The physical state of the interface is up.' ;
            }

          }

        }

        leaf oper-status {
          description 'The current operational state of the interface.

This leaf has the same semantics as ifOperStatus.' ;
          reference "RFC 2863: The Interfaces Group MIB - ifOperStatus" ;
          type enumeration {
            enum down {
              value 0 ;
              description 'The current operational state of the interface is down.' ;
            }

            enum up {
              value 1 ;
              description 'The current operational state of the interface is up.' ;
            }

          }

        }

        leaf speed {
          description "An estimate of the interface's current bandwidth in bits per second." ;
          reference "RFC 2863: The Interfaces Group MIB ifSpeed, ifHighSpeed" ;
          type uint64 ;

          units "bits / second" ;
        }

        leaf duplex-mode {
          description 'The duplex mode of the interface.

Only the physical interfaces with ether type have duplex mode. For interfaces that do not have duplex mode, this node is not present or with the value of n/a.' ;
          type enumeration {
            enum "duplex/auto" {
              value 0 ;
              description 'The duplex mode of the interface is auto negotiation.' ;
            }

            enum "duplex/full" {
              value 1 ;
              description 'The duplex mode of the interface is full duplex.' ;
            }

            enum "duplex/half" {
              value 2 ;
              description 'The duplex mode of the interface is half duplex.' ;
            }

            enum "n/a" {
              value 255 ;
              description 'The interface does not have the duplex mode.' ;
            }

          }

        }

        leaf mtu {
          description 'The maximum transmission unit with link layer of the interface.

The value of this leaf is the effective value of MTU, may not equal the configuration value.
Only particular interfaces have MTU. For interfaces that do not have this attribute, this node is not present.
This leaf has the same semantics as ifMtu.' ;
          reference "RFC 2863: The Interfaces Group MIB - ifMtu" ;
          type uint32 {
            range 0..9700 ;

          }

          units bytes ;
        }

        leaf mpls-mtu {
          description 'The maximum transmission unit with MPLS protocol layer of the interface.

The value of this leaf is the effective value of MPLS MTU, may not equal the configuration value.
Only particular interfaces have MPLS MTU. For interfaces that do not have this attribute, this node is not present.' ;
          type uint32 {
            range 68..9600 ;

          }

          units bytes ;
        }

        leaf ip-mtu {
          description 'The maximum transmission unit with IPv4 protocol layer of the interface.

The value of this leaf is the effective value of IPv4 MTU, may not equal the configuration value.
Only particular interfaces have IPv4 MTU. For interfaces that do not have this attribute, this node is not present.' ;
          type uint32 {
            range 0..9600 ;

          }

          units bytes ;
        }

        leaf ipv6-mtu {
          description 'The maximum transmission unit with IPv6 protocol layer of the interface.

The value of this leaf is the effective value of IPv6 MTU, may not equal the configuration value.
Only particular interfaces have IPv6 MTU. For interfaces that do not have this attribute, this node is not present.' ;
          type uint32 {
            range 1280..9600 ;

          }

          units bytes ;
        }

        leaf ipv4-oper-status {
          description 'The current IPv4 protocol operational state of the interface.' ;
          type enumeration {
            enum down {
              value 0 ;
              description 'The current IPv4 protocol operational state of the interface is down.' ;
            }

            enum up {
              value 1 ;
              description 'The current IPv4 protocol operational state of the interface is up.' ;
            }

          }

        }

        leaf ipv6-oper-status {
          description 'The current IPv6 protocol operational state of the interface.' ;
          type enumeration {
            enum down {
              value 0 ;
              description 'The current IPv4 protocol operational state of the interface is down.' ;
            }

            enum up {
              value 1 ;
              description 'The current IPv4 protocol operational state of the interface is up.' ;
            }

          }

        }

        leaf phys-address {
          description 'The MAC address of the interface.

Only the interfaces with ether type have such an address. For interfaces which do not have such an address (e.g., a serial line), this node should not be present or with the value of zero.' ;
          reference "RFC 2863: The Interfaces Group MIB - ifPhysAddress" ;
          type ncd:mac-address ;

        }

        leaf photo-electricity {
          description 'The photoelectric property of the interface.

Only the physical interfaces with ether type have photoelectric property. For interfaces that do not have photoelectric property, this node is not present or with the value of n/a.' ;
          type enumeration {
            enum optical {
              value 0 ;
              description 'The photoelectric property of the interface is optical.' ;
            }

            enum electric {
              value 1 ;
              description 'The photoelectric property of the interface is electric.' ;
            }

            enum "n/a" {
              value 2 ;
              description 'The interface does not have the photoelectric property.' ;
            }

            enum "pho&elec" {
              value 3 ;
              description 'The photoelectric property of the interface is optical and electronic hybrid.' ;
            }

          }

        }

        container interface-statistics {
          description 'Describe the data nodes for the operational state of interface statistics.' ;
          container common-statistics {
            description 'Describe the data nodes for the operational state of common interface statistics.' ;
            leaf last-clear-time {
              description 'The last clear traffic statistics time.' ;
              type ncd:datetime ;

            }

            leaf last-update-time {
              description 'The last time of system update new data.' ;
              type ncd:datetime ;

            }

            leaf input-bytes-rate {
              description 'The average vlaue of receive bytes rate among 120 seconds.' ;
              type uint64 ;

            }

            leaf input-pkts-rate {
              description 'The average vlaue of receive packets rate among 120 seconds.' ;
              type uint64 ;

            }

            leaf output-bytes-rate {
              description 'The average vlaue of sending bytes rate among 120 seconds.' ;
              type uint64 ;

            }

            leaf output-pkts-rate {
              description 'The average vlaue of sending packets rate among 120 seconds.' ;
              type uint64 ;

            }

            leaf input-rate-peak {
              description 'The peak vlaue of receiving bytes rate.' ;
              type uint64 ;

            }

            leaf input-rate-peak-time {
              description 'The time when the peak vlaue of receiving bytes rate appears.' ;
              type ncd:string-with-blank ;

            }

            leaf output-rate-peak {
              description 'The peak vlaue of sending bytes rate.' ;
              type uint64 ;

            }

            leaf output-rate-peak-time {
              description 'The time when the peak vlaue of sending bytes rate appears.' ;
              type ncd:string-with-blank ;

            }

            leaf input-utilization {
              description 'The input utilization of bandwidith.' ;
              type uint32 {
                range 0..100 ;

              }

            }

            leaf output-utilization {
              description 'The output utilization of bandwidith.' ;
              type uint32 {
                range 0..100 ;

              }

            }

            leaf input-crcerrors-ratio {
              description 'The input CRC errors ratio.' ;
              type uint32 {
                range 0..100 ;

              }

            }

            leaf output-crcerrors-ratio {
              description 'The output CRC errors ratio.' ;
              type uint32 {
                range 0..100 ;

              }

            }

            leaf ipv4-input-bytes-rate {
              description 'The average vlaue of receive v4 bytes rate among 120 seconds.' ;
              type uint64 ;

              ncd:revise-date 2020-06-15 ;
            }

            leaf ipv4-input-pkts-rate {
              description 'The average vlaue of receive v4 packets rate among 120 seconds.' ;
              type uint64 ;

              ncd:revise-date 2020-06-15 ;
            }

            leaf ipv4-output-bytes-rate {
              description 'The average vlaue of sending v4 bytes rate among 120 seconds.' ;
              type uint64 ;

              ncd:revise-date 2020-06-15 ;
            }

            leaf ipv4-output-pkts-rate {
              description 'The average vlaue of sending v4 packets rate among 120 seconds.' ;
              type uint64 ;

              ncd:revise-date 2020-06-15 ;
            }

            leaf ipv6-input-bytes-rate {
              description 'The average vlaue of receive v6 bytes rate among 120 seconds.' ;
              type uint64 ;

              ncd:revise-date 2020-06-15 ;
            }

            leaf ipv6-input-pkts-rate {
              description 'The average vlaue of receive v6 packets rate among 120 seconds.' ;
              type uint64 ;

              ncd:revise-date 2020-06-15 ;
            }

            leaf ipv6-output-bytes-rate {
              description 'The average vlaue of sending v6 bytes rate among 120 seconds.' ;
              type uint64 ;

              ncd:revise-date 2020-06-15 ;
            }

            leaf ipv6-output-pkts-rate {
              description 'The average vlaue of sending v6 packets rate among 120 seconds.' ;
              type uint64 ;

              ncd:revise-date 2020-06-15 ;
            }

            leaf ipv4-input-rate-peak {
              description 'The peak vlaue of receiving v4 bytes rate.' ;
              type uint64 ;

              ncd:revise-date 2020-06-15 ;
            }

            leaf ipv4-input-rate-peak-time {
              description 'The time when the peak vlaue of receiving v4 bytes rate appears.' ;
              type ncd:string-with-blank ;

              ncd:revise-date 2020-06-15 ;
            }

            leaf ipv4-output-rate-peak {
              description 'The peak vlaue of sending v4 bytes rate.' ;
              type uint64 ;

              ncd:revise-date 2020-06-15 ;
            }

            leaf ipv4-output-rate-peak-time {
              description 'The time when the peak vlaue of sending v4 bytes rate appears.' ;
              type ncd:string-with-blank ;

              ncd:revise-date 2020-06-15 ;
            }

            leaf ipv6-input-rate-peak {
              description 'The peak vlaue of receiving v6 bytes rate.' ;
              type uint64 ;

              ncd:revise-date 2020-06-15 ;
            }

            leaf ipv6-input-rate-peak-time {
              description 'The time when the peak vlaue of receiving v6 bytes rate appears.' ;
              type ncd:string-with-blank ;

              ncd:revise-date 2020-06-15 ;
            }

            leaf ipv6-output-rate-peak {
              description 'The peak vlaue of sending v6 bytes rate.' ;
              type uint64 ;

              ncd:revise-date 2020-06-15 ;
            }

            leaf ipv6-output-rate-peak-time {
              description 'The time when the peak vlaue of sending v6 bytes rate appears.' ;
              type ncd:string-with-blank ;

              ncd:revise-date 2020-06-15 ;
            }

            leaf ipv4-input-utilization {
              description 'The v4 input utilization of bandwidith.' ;
              type uint32 {
                range 0..100 ;

              }

              ncd:revise-date 2020-06-15 ;
            }

            leaf ipv4-output-utilization {
              description 'The v4 output utilization of bandwidith.' ;
              type uint32 {
                range 0..100 ;

              }

              ncd:revise-date 2020-06-15 ;
            }

            leaf ipv6-input-utilization {
              description 'The v6 input utilization of bandwidith.' ;
              type uint32 {
                range 0..100 ;

              }

              ncd:revise-date 2020-06-15 ;
            }

            leaf ipv6-output-utilization {
              description 'The v6 output utilization of bandwidith.' ;
              type uint32 {
                range 0..100 ;

              }

              ncd:revise-date 2020-06-15 ;
            }

            leaf mpls-input-bytes-rate {
              description 'The average vlaue of receive MPLS bytes rate among 120 seconds.' ;
              type uint64 ;

              ncd:revise-date 2021-02-03 ;
            }

            leaf mpls-input-pkts-rate {
              description 'The average vlaue of receive MPLS packets rate among 120 seconds.' ;
              type uint64 ;

              ncd:revise-date 2021-02-03 ;
            }

            leaf mpls-output-bytes-rate {
              description 'The average vlaue of sending MPLS bytes rate among 120 seconds.' ;
              type uint64 ;

              ncd:revise-date 2021-02-03 ;
            }

            leaf mpls-output-pkts-rate {
              description 'The average vlaue of sending MPLS packets rate among 120 seconds.' ;
              type uint64 ;

              ncd:revise-date 2021-02-03 ;
            }

            leaf mpls-input-rate-peak {
              description 'The peak vlaue of receiving MPLS bytes rate.' ;
              type uint64 ;

              ncd:revise-date 2021-02-03 ;
            }

            leaf mpls-input-rate-peak-time {
              description 'The time when the peak vlaue of receiving MPLS bytes rate appears.' ;
              type ncd:string-with-blank ;

              ncd:revise-date 2021-02-03 ;
            }

            leaf mpls-output-rate-peak {
              description 'The peak vlaue of sending MPLS bytes rate.' ;
              type uint64 ;

              ncd:revise-date 2021-02-03 ;
            }

            leaf mpls-output-rate-peak-time {
              description 'The time when the peak vlaue of sending MPLS bytes rate appears.' ;
              type ncd:string-with-blank ;

              ncd:revise-date 2021-02-03 ;
            }

            leaf mpls-input-utilization {
              description 'The MPLS input utilization of bandwidith.' ;
              type uint32 {
                range 0..100 ;

              }

              ncd:revise-date 2021-02-03 ;
            }

            leaf mpls-output-utilization {
              description 'The MPLS output utilization of bandwidith.' ;
              type uint32 {
                range 0..100 ;

              }

              ncd:revise-date 2021-02-03 ;
            }

            leaf input-bytes {
              description 'Total bytes received' ;
              type uint64 ;

              ncd:revise-date 2021-08-13 ;
            }

            leaf input-pkts {
              description 'Total packets received' ;
              type uint64 ;

              ncd:revise-date 2021-08-13 ;
            }

            leaf output-bytes {
              description 'Total bytes sent' ;
              type uint64 ;

              ncd:revise-date 2021-08-13 ;
            }

            leaf output-pkts {
              description 'Total packets sent' ;
              type uint64 ;

              ncd:revise-date 2021-08-13 ;
            }

          }

          container hw-counters {
            description 'Describe the data nodes for the operational state of interface statistics.These performace items are updated by product managment.' ;
            container eth-statistics {
              description 'Describe the data nodes for the operational state of ether-port statistics.These performace items are updated by product managment.' ;
              leaf in-byte-speed {
                description 'Total bytes received,include packets with space.' ;
                type uint64 ;

              }

              leaf in-bytes {
                description 'Total bytes received' ;
                type uint64 ;

              }

              leaf in-pkts {
                description 'Total packets received' ;
                type uint64 ;

              }

              leaf in-byteok {
                description 'Total normal frame bytes received' ;
                type uint64 ;

              }

              leaf in-pktok {
                description 'Total normal frames received' ;
                type uint64 ;

              }

              leaf in-pause {
                description 'Total pause frames received' ;
                type uint64 ;

              }

              leaf in-singcollision {
                description 'Single conflict packets received' ;
                type uint64 ;

              }

              leaf in-multcollision {
                description 'multiple conflict packets received' ;
                type uint64 ;

              }

              leaf in-Latecollision {
                description 'Total packets received with conflict detected' ;
                type uint64 ;

              }

              leaf in-excecollision {
                description 'Total packets dropped for conflict received' ;
                type uint64 ;

              }

              leaf in-crc-error {
                description 'Total packets received with CRC error received' ;
                type uint64 ;

              }

              leaf in-alignerror {
                description 'Total packets received with alignment error received' ;
                type uint64 ;

              }

              leaf in-symbolerror {
                description 'Total PHY Std Reg 10, Idle error packets received' ;
                type uint64 ;

              }

              leaf in-error {
                description 'Total error packets received' ;
                type uint64 ;

              }

              leaf in-unicasts {
                description 'Total unicast packets received' ;
                type uint64 ;

              }

              leaf in-broadcasts {
                description 'Total broadcast packets received' ;
                type uint64 ;

              }

              leaf in-multicasts {
                description 'Total multicast packets received' ;
                type uint64 ;

              }

              leaf in-byteall {
                description 'Total bytes received,include normal/error packets,mac header and FCS.' ;
                type uint64 ;

              }

              leaf in-packetall {
                description 'Total packets received(include normal/error packets)' ;
                type uint64 ;

              }

              leaf in-undersize {
                description 'Total packets shorter than 64 bytes received' ;
                type uint64 ;

              }

              leaf in-oversize {
                description 'Total packets longer than Max bytes received' ;
                type uint64 ;

              }

              leaf in-fragments {
                description 'Total fragment packets received' ;
                type uint64 ;

              }

              leaf in-jabbers {
                description 'Total Jabber packets received' ;
                type uint64 ;

              }

              leaf in-64b {
                description 'Total packets of 64 bytes received' ;
                type uint64 ;

              }

              leaf in-65-127b {
                description 'Total packets of 65~127 bytes received' ;
                type uint64 ;

              }

              leaf in-128-255b {
                description 'Total packets of 128~255 bytes received' ;
                type uint64 ;

              }

              leaf in-256-511b {
                description 'Total packets of 256~511 bytes received' ;
                type uint64 ;

              }

              leaf in-512-1023b {
                description 'Total packets of 512~1023 bytes received' ;
                type uint64 ;

              }

              leaf in-1024-1518b {
                description 'Total packets of 1024~1518 bytes received' ;
                type uint64 ;

              }

              leaf in-1519-maxb {
                description 'Total packets of 1519~Max bytes received' ;
                type uint64 ;

              }

              leaf in-dropevents {
                description 'Total dropped frames received for FIFO overflow' ;
                type uint64 ;

              }

              leaf e-byte-speed {
                description 'Total bytes sent include packets with space' ;
                type uint64 ;

              }

              leaf e-bytes {
                description 'Total bytes sent' ;
                type uint64 ;

              }

              leaf e-packets {
                description 'Total packets sent' ;
                type uint64 ;

              }

              leaf e-byteok {
                description 'Total normal frame bytes sent' ;
                type uint64 ;

              }

              leaf e-packetok {
                description 'Total normal frames sent' ;
                type uint64 ;

              }

              leaf e-pause {
                description 'Total pause frames sent' ;
                type uint64 ;

              }

              leaf e-singcollision {
                description 'Single conflict packets sent' ;
                type uint64 ;

              }

              leaf e-multcollision {
                description 'Multi-conflict packets sent' ;
                type uint64 ;

              }

              leaf e-Latecollision {
                description 'Total packets sent with conflict detected' ;
                type uint64 ;

              }

              leaf e-excecollision {
                description 'Total packets dropped for conflict' ;
                type uint64 ;

              }

              leaf e-crc-error {
                description 'Total packets sent with CRC error' ;
                type uint64 ;

              }

              leaf e-alignerror {
                description 'Total packets sent with alignment error' ;
                type uint64 ;

              }

              leaf e-symbolerror {
                description 'Total PHY Std Reg 10, Idle error packets sent' ;
                type uint64 ;

              }

              leaf e-error {
                description 'Total error packets sent' ;
                type uint64 ;

              }

              leaf e-unicasts {
                description 'Total unicast packets sent' ;
                type uint64 ;

              }

              leaf e-broadcasts {
                description 'Total broadcast packets sent' ;
                type uint64 ;

              }

              leaf e-multicasts {
                description 'Total multicast packets sent' ;
                type uint64 ;

              }

              leaf e-byteall {
                description 'Total bytes send,include normal/error packets,mac header and FCS.' ;
                type uint64 ;

              }

              leaf e-packetall {
                description 'Total packets send(include normal/error packets)' ;
                type uint64 ;

              }

              leaf e-undersize {
                description 'Total packets shorter than 64 bytes sent' ;
                type uint64 ;

              }

              leaf e-oversize {
                description 'Total packets longer than Max bytes sent' ;
                type uint64 ;

              }

              leaf e-fragments {
                description 'Total fragment packets sent' ;
                type uint64 ;

              }

              leaf e-jabbers {
                description 'Total Jabber packets sent' ;
                type uint64 ;

              }

              leaf e-64b {
                description 'Total packets of 64 bytes sent' ;
                type uint64 ;

              }

              leaf e-65-127b {
                description 'Total packets of 65~127 bytes sent' ;
                type uint64 ;

              }

              leaf e-128-255b {
                description 'Total packets of 128~255 bytes sent' ;
                type uint64 ;

              }

              leaf e-256-511b {
                description 'Total packets of 256~511 bytes sent' ;
                type uint64 ;

              }

              leaf e-512-1023b {
                description 'Total packets of 512~1023 bytes sent' ;
                type uint64 ;

              }

              leaf e-1024-1518b {
                description 'Total packets of 1024~1518 bytes sent' ;
                type uint64 ;

              }

              leaf e-1519-maxb {
                description 'Total packets of 1519~Max bytes sent' ;
                type uint64 ;

              }

              leaf e-dropevents {
                description 'Total dropped frames sent for FIFO overflow' ;
                type uint64 ;

              }

              leaf in-macrxerror {
                description 'Total macrxerror received.' ;
                type uint64 ;

              }

              leaf in-overrun {
                description 'Total overrun received' ;
                type uint64 ;

              }

              leaf in-pktsdrop {
                description 'Total packets of dropped received.' ;
                type uint64 ;

                ncd:revise-date 2015-05-19 ;
              }

              leaf in-pktserror {
                description 'Total error packets received.' ;
                type uint64 ;

                ncd:revise-date 2015-05-19 ;
              }

              leaf e-pktsdrop {
                description 'Total packets of dropped sent.' ;
                type uint64 ;

                ncd:revise-date 2015-05-19 ;
              }

              leaf e-pktserror {
                description 'Total error packets sent.' ;
                type uint64 ;

                ncd:revise-date 2015-05-19 ;
              }

            }

            container pos-statistics {
              description 'Describe the data nodes for the operational state of pos-port statistics.These performace items are updated by product managment.' ;
              leaf in-byte-speed {
                description 'Total bytes received,include packets with space.' ;
                type uint64 ;

              }

              leaf in-bytes {
                description 'Total bytes received,include error packets and FCS.' ;
                type uint64 ;

              }

              leaf in-packets {
                description 'Total packets received' ;
                type uint64 ;

              }

              leaf in-byteok {
                description 'Total bytes received,include packets with space.' ;
                type uint64 ;

              }

              leaf in-packetok {
                description 'Total normal packets received' ;
                type uint64 ;

              }

              leaf in-abort {
                description 'Total packets marked by 0x7D 0x7E  received' ;
                type uint64 ;

              }

              leaf in-overflow {
                description 'Total error packets received for FIFO overflow' ;
                type uint64 ;

              }

              leaf in-runt {
                description 'Too short packets received,shorter than 8 bytes.' ;
                type uint64 ;

              }

              leaf in-giant {
                description 'Too long packets received,longer than 9600 K.' ;
                type uint64 ;

              }

              leaf in-drop {
                description 'Total packets dropped by device' ;
                type uint64 ;

              }

              leaf in-fcserror {
                description 'Total FCS error packets received' ;
                type uint64 ;

              }

              leaf e-byte-speed {
                description 'Total bytes sent,include packets with space.' ;
                type uint64 ;

              }

              leaf e-bytes {
                description 'Total bytes sent,include error packets and FCS.' ;
                type uint64 ;

              }

              leaf e-packets {
                description 'Total packets sent' ;
                type uint64 ;

              }

              leaf e-byteok {
                description 'Total bytes sent,only include normal packets.' ;
                type uint64 ;

              }

              leaf e-packetok {
                description 'Total normal packets received' ;
                type uint64 ;

              }

              leaf e-abort {
                description 'Total packets dropped for sending error' ;
                type uint64 ;

              }

              leaf e-underflow {
                description 'Total packets dropped or marked as error for FIFO overflow' ;
                type uint64 ;

              }

              leaf e-runt {
                description 'Too short packets sent,shorter than 8 bytes.' ;
                type uint64 ;

              }

              leaf e-giant {
                description 'Too long packets sent,longer than 9600 K.' ;
                type uint64 ;

              }

              leaf in-overrun {
                description 'Total overrun received' ;
                type uint64 ;

              }

              leaf in-pktsdrop {
                description 'Total packets of dropped received.' ;
                type uint64 ;

                ncd:revise-date 2015-05-19 ;
              }

              leaf in-pktserror {
                description 'Total error packets received.' ;
                type uint64 ;

                ncd:revise-date 2015-05-19 ;
              }

              leaf e-pktsdrop {
                description 'Total packets of dropped sent.' ;
                type uint64 ;

                ncd:revise-date 2015-05-19 ;
              }

              leaf e-pktserror {
                description 'Total error packets sent.' ;
                type uint64 ;

                ncd:revise-date 2015-05-19 ;
              }

            }

            container l3vlan-statistics {
              description 'Describe the data nodes for the operational state of l3vlan-port statistics.These performace items are updated by product managment.' ;
              leaf in-pkts {
                description 'Total packets received' ;
                type uint64 ;

              }

              leaf in-bytes {
                description 'Total bytes received' ;
                type uint64 ;

              }

              leaf e-pkts {
                description 'Total packets sent' ;
                type uint64 ;

              }

              leaf e-bytes {
                description 'Total bytes sent' ;
                type uint64 ;

              }

              leaf in-pktsdrop {
                description 'Total packets of dropped received' ;
                type uint64 ;

                ncd:revise-date 2015-05-19 ;
              }

              leaf in-bytesdrop {
                description 'Total bytes of dropped received' ;
                type uint64 ;

                ncd:revise-date 2015-05-19 ;
              }

              leaf e-pktsdrop {
                description 'Total packets of dropped sent' ;
                type uint64 ;

                ncd:revise-date 2015-05-19 ;
              }

              leaf e-bytesdrop {
                description 'Total bytes of dropped sent' ;
                type uint64 ;

                ncd:revise-date 2015-05-19 ;
              }

            }

            container smartgroup-statistics {
              description "Describe the data nodes for the operational state of smartgroup-port statistics.These performace items are calculated by platform with the items of smartgroup-port's members." ;
              leaf in-bytes {
                description 'Total bytes received' ;
                type uint64 ;

              }

              leaf in-pkts {
                description 'Total packets received' ;
                type uint64 ;

              }

              leaf e-bytes {
                description 'Total bytes sent' ;
                type uint64 ;

              }

              leaf e-packets {
                description 'Total packets sent' ;
                type uint64 ;

              }

              leaf in-byte-speed {
                description 'Total bytes received' ;
                type uint64 ;

              }

              leaf in-pkt-speed {
                description 'Total packets received' ;
                type uint64 ;

              }

              leaf e-byte-speed {
                description 'Total bytes sent' ;
                type uint64 ;

              }

              leaf e-pkt-speed {
                description 'Total packets sent' ;
                type uint64 ;

              }

              leaf in-discards {
                description 'Total dropped frames received for FIFO overflow' ;
                type uint64 ;

              }

              leaf e-discards {
                description 'Total dropped frames sent for FIFO overflow' ;
                type uint64 ;

              }

              leaf in-crc-error {
                description 'Total packets received with CRC error received' ;
                type uint64 ;

              }

              leaf in-unicasts {
                description 'Total unicast packets received' ;
                type uint64 ;

              }

              leaf in-broadcasts {
                description 'Total broadcast packets received' ;
                type uint64 ;

              }

              leaf in-multicasts {
                description 'Total multicast packets received' ;
                type uint64 ;

              }

              leaf in-undersize {
                description 'Total packets shorter than 64 bytes received' ;
                type uint64 ;

              }

              leaf in-oversize {
                description 'Total packets longer than Max bytes received' ;
                type uint64 ;

              }

              leaf in-64b {
                description 'Total packets of 64 bytes received' ;
                type uint64 ;

              }

              leaf in-65-127b {
                description 'Total packets of 65~127 bytes received' ;
                type uint64 ;

              }

              leaf in-128-255b {
                description 'Total packets of 128~255 bytes received' ;
                type uint64 ;

              }

              leaf in-256-511b {
                description 'Total packets of 256~511 bytes received' ;
                type uint64 ;

              }

              leaf in-512-1023b {
                description 'Total packets of 512~1023 bytes received' ;
                type uint64 ;

              }

              leaf in-1024-1518b {
                description 'Total packets of 1024~1518 bytes received' ;
                type uint64 ;

              }

              leaf in-1519-Maxb {
                description 'Total packets of 1519~Max bytes received' ;
                type uint64 ;

              }

              leaf e-crc-error {
                description 'Total packets sent with CRC error' ;
                type uint64 ;

              }

              leaf e-unicasts {
                description 'Total unicast packets sent' ;
                type uint64 ;

              }

              leaf e-broadcasts {
                description 'Total broadcast packets sent' ;
                type uint64 ;

              }

              leaf e-multicasts {
                description 'Total multicast packets sent' ;
                type uint64 ;

              }

              leaf e-undersize {
                description 'Total packets shorter than 64 bytes sent' ;
                type uint64 ;

              }

              leaf e-oversize {
                description 'Total packets longer than Max bytes sent' ;
                type uint64 ;

              }

              leaf e-64b {
                description 'Total packets of 64 bytes sent' ;
                type uint64 ;

              }

              leaf e-65-127b {
                description 'Total packets of 65~127 bytes sent' ;
                type uint64 ;

              }

              leaf e-128-255b {
                description 'Total packets of 128~255 bytes sent' ;
                type uint64 ;

              }

              leaf e-256-511b {
                description 'Total packets of 256~511 bytes sent' ;
                type uint64 ;

              }

              leaf e-512-1023b {
                description 'Total packets of 512~1023 bytes sent' ;
                type uint64 ;

              }

              leaf e-1024-1518b {
                description 'Total packets of 1024~1518 bytes sent' ;
                type uint64 ;

              }

              leaf e-1519-Maxb {
                description 'Total packets of 1519~Max bytes sent' ;
                type uint64 ;

              }

              leaf in-fragments {
                description 'Total fragment packets received' ;
                type uint64 ;

              }

              leaf in-jabbers {
                description 'Total Jabber packets received' ;
                type uint64 ;

              }

              leaf in-macrxerror {
                description 'Total macrxerror received.' ;
                type uint64 ;

              }

              leaf e-scollpks {
                description 'Single conflict packets sent' ;
                type uint64 ;

              }

              leaf e-latecollpks {
                description 'Total packets sent with conflict detected' ;
                type uint64 ;

              }

              leaf e-multcollision {
                description 'Multi-conflict packets sent' ;
                type uint64 ;

              }

              leaf e-excecollision {
                description 'Total packets dropped for conflict' ;
                type uint64 ;

              }

              leaf in-overrun {
                description 'Total overrun received' ;
                type uint64 ;

              }

              leaf in-pktsdrop {
                description 'Total packets of dropped received.' ;
                type uint64 ;

                ncd:revise-date 2015-05-19 ;
              }

              leaf in-pktserror {
                description 'Total error packets received.' ;
                type uint64 ;

                ncd:revise-date 2015-05-19 ;
              }

              leaf e-pktsdrop {
                description 'Total packets of dropped sent.' ;
                type uint64 ;

                ncd:revise-date 2015-05-19 ;
              }

              leaf e-pktserror {
                description 'Total error packets sent.' ;
                type uint64 ;

                ncd:revise-date 2015-05-19 ;
              }

            }

            container atm-statistics {
              description 'Describe the data nodes for the operational state of atm-port statistics.These performace items are updated by product managment.' ;
              leaf in-cellsall {
                description 'Total cell received' ;
                type uint64 ;

              }

              leaf in-cellsgood {
                description 'Total good cell received' ;
                type uint64 ;

              }

              leaf in-bytesall {
                description 'Total bytes received' ;
                type uint64 ;

              }

              leaf in-bytesgood {
                description 'Total good bytes received' ;
                type uint64 ;

              }

              leaf in-cellsoverflow {
                description 'Overflow cell received' ;
                type uint64 ;

              }

              leaf in-cellsdrop {
                description 'Discarded cell received' ;
                type uint64 ;

              }

              leaf in-sbithec {
                description 'Sbithec count received' ;
                type uint64 ;

              }

              leaf in-mbithec {
                description 'Mbithec count received' ;
                type uint64 ;

              }

              leaf in-cellsidle {
                description 'Spare cell received' ;
                type uint64 ;

              }

              leaf in-pktsgood {
                description 'Total good packets received' ;
                type uint64 ;

              }

              leaf e-cellsall {
                description 'Total cell sent' ;
                type uint64 ;

              }

              leaf e-cellsgood {
                description 'Total good cell sent' ;
                type uint64 ;

              }

              leaf e-bytesall {
                description 'Total bytes sent' ;
                type uint64 ;

              }

              leaf e-bytesgood {
                description 'Total good bytes sent' ;
                type uint64 ;

              }

              leaf e-cellsidle {
                description 'Spare cell sent' ;
                type uint64 ;

              }

              leaf e-pktsgood {
                description 'Total good packets sent' ;
                type uint64 ;

              }

              leaf in-pktsdrop {
                description 'Total packets of dropped received.' ;
                type uint64 ;

                ncd:revise-date 2015-05-19 ;
              }

              leaf in-pktserror {
                description 'Total error packets received.' ;
                type uint64 ;

                ncd:revise-date 2015-05-19 ;
              }

              leaf e-pktsdrop {
                description 'Total packets of dropped sent.' ;
                type uint64 ;

                ncd:revise-date 2015-05-19 ;
              }

              leaf e-pktserror {
                description 'Total error packets sent.' ;
                type uint64 ;

                ncd:revise-date 2015-05-19 ;
              }

            }

            container posgroup-statistics {
              description "Describe the data nodes for the operational state of posgroup-port statistics.These performace items are calculated by platform with the items of posgroup-port's members." ;
              leaf in-bytes {
                description 'Total bytes received' ;
                type uint64 ;

              }

              leaf in-packets {
                description 'Total packets received' ;
                type uint64 ;

              }

              leaf e-bytes {
                description 'Total bytes sent' ;
                type uint64 ;

              }

              leaf e-packets {
                description 'Total packets sent' ;
                type uint64 ;

              }

              leaf in-byte-rate {
                description 'Total bytes received' ;
                type uint64 ;

              }

              leaf in-packet-rate {
                description 'Total packets received' ;
                type uint64 ;

              }

              leaf e-byte-rate {
                description 'Total bytes sent' ;
                type uint64 ;

              }

              leaf e-packet-rate {
                description 'Total packets sent' ;
                type uint64 ;

              }

              leaf in-discards {
                description 'Total dropped frames received for FIFO overflow' ;
                type uint64 ;

              }

              leaf e-discards {
                description 'Total dropped frames sent for FIFO overflow' ;
                type uint64 ;

              }

              leaf in-abort {
                description 'Total packets marked by 0x7D 0x7E  received' ;
                type uint64 ;

              }

              leaf in-overflow {
                description 'Total error packets received for FIFO overflow' ;
                type uint64 ;

              }

              leaf in-runt {
                description 'Too short packets received,shorter than 8 bytes.' ;
                type uint64 ;

              }

              leaf in-giant {
                description 'Too long packets received,longer than 9600 K.' ;
                type uint64 ;

              }

              leaf in-drop {
                description 'Total packets dropped by device' ;
                type uint64 ;

              }

              leaf in-fcserror {
                description 'Total FCS error packets received' ;
                type uint64 ;

              }

              leaf e-abort {
                description 'Total packets dropped for sending error' ;
                type uint64 ;

              }

              leaf e-underflow {
                description 'Total packets dropped or marked as error for FIFO overflow' ;
                type uint64 ;

              }

              leaf e-runt {
                description 'Too short packets sent,shorter than 8 bytes.' ;
                type uint64 ;

              }

              leaf e-giant {
                description 'Too long packets sent,longer than 9600 K.' ;
                type uint64 ;

              }

              leaf in-overrun {
                description 'Total overrun received' ;
                type uint64 ;

              }

              leaf in-pktsdrop {
                description 'Total packets of dropped received.' ;
                type uint64 ;

                ncd:revise-date 2015-05-19 ;
              }

              leaf in-pktserror {
                description 'Total error packets received.' ;
                type uint64 ;

                ncd:revise-date 2015-05-19 ;
              }

              leaf e-pktsdrop {
                description 'Total packets of dropped sent.' ;
                type uint64 ;

                ncd:revise-date 2015-05-19 ;
              }

              leaf e-pktserror {
                description 'Total error packets sent.' ;
                type uint64 ;

                ncd:revise-date 2015-05-19 ;
              }

            }

            container serial-statistics {
              description 'Describe the data nodes for the operational state of serial-port statistics.These performace items are updated by product managment.' ;
              leaf in-bytes {
                description 'Total bytes received' ;
                type uint64 ;

              }

              leaf in-packets {
                description 'Total packets received' ;
                type uint64 ;

              }

              leaf in-fcserrs {
                description 'Total FCS error packets received' ;
                type uint64 ;

              }

              leaf in-pktlengmax {
                description 'PktLenGMax count received' ;
                type uint64 ;

              }

              leaf in-overflow {
                description 'Total error packets received for FIFO overflow' ;
                type uint64 ;

              }

              leaf e-bytes {
                description 'Total bytes sent' ;
                type uint64 ;

              }

              leaf e-packets {
                description 'Total packets sent' ;
                type uint64 ;

              }

            }

            container cpos-statistics {
              description 'Describe the data nodes for the operational state of cpos-port statistics.These performace items are updated by product managment.' ;
              leaf in-bytes {
                description 'Total bytes received' ;
                type uint64 ;

              }

              leaf in-packets {
                description 'Total packets received' ;
                type uint64 ;

              }

              leaf in-frameaborts {
                description 'FrameAbort count received' ;
                type uint64 ;

              }

              leaf in-fcserrs {
                description 'Total FCS error packets received' ;
                type uint64 ;

              }

              leaf in-pktlengmax {
                description 'PktLenGMax count received' ;
                type uint64 ;

              }

              leaf in-nonalignedfrms {
                description 'NonAlignedFrm count received' ;
                type uint64 ;

              }

              leaf in-smalldiscbytes {
                description 'Total dropped frames received for FIFO overflow' ;
                type uint64 ;

              }

              leaf in-smalldiscards {
                description 'Total dropped packets received' ;
                type uint64 ;

              }

              leaf in-chunkexbytes {
                description 'ChunkExByte count received' ;
                type uint64 ;

              }

              leaf in-chunkex {
                description 'ChunkEx count received' ;
                type uint64 ;

              }

              leaf e-bytes {
                description 'Total bytes sent' ;
                type uint64 ;

              }

              leaf e-packets {
                description 'Total packets sent' ;
                type uint64 ;

              }

              leaf e-frameaborts {
                description 'FrameAbort count sent' ;
                type uint64 ;

              }

              leaf in-pktsdrop {
                description 'Total packets of dropped received.' ;
                type uint64 ;

                ncd:revise-date 2015-05-19 ;
              }

              leaf in-pktserror {
                description 'Total error packets received.' ;
                type uint64 ;

                ncd:revise-date 2015-05-19 ;
              }

              leaf e-pktsdrop {
                description 'Total packets of dropped sent.' ;
                type uint64 ;

                ncd:revise-date 2015-05-19 ;
              }

              leaf e-pktserror {
                description 'Total error packets sent.' ;
                type uint64 ;

                ncd:revise-date 2015-05-19 ;
              }

            }

            container cpos-fr-statistics {
              description 'Describe the data nodes for the operational state of cpos-fr port statistics.These performace items are updated by product managment.' ;
              leaf in-packets {
                description 'Total packets received' ;
                type uint64 ;

              }

              leaf in-bytes {
                description 'Total bytes received' ;
                type uint64 ;

              }

              leaf in-fcserrs {
                description 'Total FCS error packets received' ;
                type uint64 ;

              }

              leaf in-nonalignedfrms {
                description 'NonAlignedFrm count received' ;
                type uint64 ;

              }

              leaf in-frameaborts {
                description 'FrameAbort count received' ;
                type uint64 ;

              }

              leaf e-packets {
                description 'Total packets sent' ;
                type uint64 ;

              }

              leaf e-bytes {
                description 'Total bytes sent' ;
                type uint64 ;

              }

              leaf e-frameaborts {
                description 'FrameAbort count sent' ;
                type uint64 ;

              }

            }

            container cpos-tdm-statistics {
              description 'Describe the data nodes for the operational state of cpos-tdm port statistics.These performace items are updated by product managment.' ;
              leaf in-bytes {
                description 'Total bytes received' ;
                type uint64 ;

              }

              leaf in-packets {
                description 'Total packets received' ;
                type uint64 ;

              }

              leaf in-rxfwdpkt {
                description 'RxFwdPkt count received' ;
                type uint64 ;

              }

              leaf in-oosync {
                description 'Oosync count received' ;
                type uint64 ;

              }

              leaf in-drop {
                description 'Total packets dropped by device' ;
                type uint64 ;

              }

              leaf e-packets {
                description 'Total packets sent' ;
                type uint64 ;

              }

              leaf e-bytes {
                description 'Total bytes sent' ;
                type uint64 ;

              }

              leaf e-nearrecvpkt {
                description 'NearRecvPkt count sent' ;
                type uint64 ;

              }

              leaf e-malformpkt {
                description 'MalformPkt count sent' ;
                type uint64 ;

              }

              leaf e-bufovercont {
                description 'BufOverCont count sent' ;
                type uint64 ;

              }

              leaf e-nearlospkt {
                description 'Total dropped frames sent for FIFO overflow' ;
                type uint64 ;

              }

              leaf e-farlospkt {
                description 'FarLosPkt count sent' ;
                type uint64 ;

              }

              leaf e-rdipkt {
                description 'RdiPkt count sent' ;
                type uint64 ;

              }

              leaf e-csfpkt {
                description 'CsfPkt count sent' ;
                type uint64 ;

              }

              leaf e-idlepkt {
                description 'IdlePkt count sent' ;
                type uint64 ;

              }

              leaf e-snerrpkt {
                description 'SNErrPkt count sent' ;
                type uint64 ;

              }

              leaf e-bufundcont {
                description 'Buffer underrun cont' ;
                type uint64 ;

                ncd:revise-date 2017-07-18 ;
              }

              leaf e-farsqdpcont {
                description 'Far sequence drop cont' ;
                type uint64 ;

                ncd:revise-date 2017-07-18 ;
              }

              leaf e-farowincont {
                description 'Far out of window cont' ;
                type uint64 ;

                ncd:revise-date 2017-07-18 ;
              }

            }

            container bep-statistic {
              description 'Describe the data nodes for the operational state of bep-port statistics.These performace items are updated by product managment.' ;
              leaf in-byte-speed {
                description 'Total bytes received,include packets with space.' ;
                type uint64 ;

              }

              leaf in-bytes {
                description 'Total bytes received' ;
                type uint64 ;

              }

              leaf in-pkts {
                description 'Total packets received' ;
                type uint64 ;

              }

              leaf in-byteok {
                description 'Total normal frame bytes received' ;
                type uint64 ;

              }

              leaf in-pktok {
                description 'Total normal frames received' ;
                type uint64 ;

              }

              leaf in-pause {
                description 'Total pause frames received' ;
                type uint64 ;

              }

              leaf in-singcollision {
                description 'Single conflict packets received' ;
                type uint64 ;

              }

              leaf in-multcollision {
                description 'multiple conflict packets received' ;
                type uint64 ;

              }

              leaf in-latecollision {
                description 'Total packets received with conflict detected' ;
                type uint64 ;

              }

              leaf in-excecollision {
                description 'Total packets dropped for conflict received' ;
                type uint64 ;

              }

              leaf in-crc-error {
                description 'Total packets received with CRC error received' ;
                type uint64 ;

              }

              leaf in-alignerror {
                description 'Total packets received with alignment error received' ;
                type uint64 ;

              }

              leaf in-symbolerror {
                description 'Total PHY Std Reg 10, Idle error packets received' ;
                type uint64 ;

              }

              leaf in-error {
                description 'Total error packets received' ;
                type uint64 ;

              }

              leaf in-unicasts {
                description 'Total unicast packets received' ;
                type uint64 ;

              }

              leaf in-broadcasts {
                description 'Total broadcast packets received' ;
                type uint64 ;

              }

              leaf in-multicasts {
                description 'Total multicast packets received' ;
                type uint64 ;

              }

              leaf in-byteall {
                description 'Total bytes received,include normal/error packets,mac header and FCS.' ;
                type uint64 ;

              }

              leaf in-packetall {
                description 'Total packets received(include normal/error packets)' ;
                type uint64 ;

              }

              leaf in-undersize {
                description 'Total packets shorter than 64 bytes received' ;
                type uint64 ;

              }

              leaf in-oversize {
                description 'Total packets longer than Max bytes received' ;
                type uint64 ;

              }

              leaf in-fragments {
                description 'Total fragment packets received' ;
                type uint64 ;

              }

              leaf in-jabbers {
                description 'Total Jabber packets received' ;
                type uint64 ;

              }

              leaf in-64b {
                description 'Total packets of 64 bytes received' ;
                type uint64 ;

              }

              leaf in-65-127b {
                description 'Total packets of 65~127 bytes received' ;
                type uint64 ;

              }

              leaf in-128-255b {
                description 'Total packets of 128~255 bytes received' ;
                type uint64 ;

              }

              leaf in-256-511b {
                description 'Total packets of 256~511 bytes received' ;
                type uint64 ;

              }

              leaf in-512-1023b {
                description 'Total packets of 512~1023 bytes received' ;
                type uint64 ;

              }

              leaf in-1024-1518b {
                description 'Total packets of 1024~1518 bytes received' ;
                type uint64 ;

              }

              leaf in-1519-maxb {
                description 'Total packets of 1519~Max bytes received' ;
                type uint64 ;

              }

              leaf in-dropevents {
                description 'Total dropped frames received for FIFO overflow' ;
                type uint64 ;

              }

              leaf e-byte-speed {
                description 'Total bytes sent include packets with space' ;
                type uint64 ;

              }

              leaf e-bytes {
                description 'Total bytes sent' ;
                type uint64 ;

              }

              leaf e-packets {
                description 'Total packets sent' ;
                type uint64 ;

              }

              leaf e-byteok {
                description 'Total normal frame bytes sent' ;
                type uint64 ;

              }

              leaf e-packetok {
                description 'Total normal frames sent' ;
                type uint64 ;

              }

              leaf e-pause {
                description 'Total pause frames sent' ;
                type uint64 ;

              }

              leaf e-singcollision {
                description 'Single conflict packets sent' ;
                type uint64 ;

              }

              leaf e-multcollision {
                description 'Multi-conflict packets sent' ;
                type uint64 ;

              }

              leaf e-latecollision {
                description 'Total packets sent with conflict detected' ;
                type uint64 ;

              }

              leaf e-excecollision {
                description 'Total packets dropped for conflict' ;
                type uint64 ;

              }

              leaf e-crc-error {
                description 'Total packets sent with CRC error' ;
                type uint64 ;

              }

              leaf e-alignerror {
                description 'Total packets sent with alignment error' ;
                type uint64 ;

              }

              leaf e-symbolerror {
                description 'Total PHY Std Reg 10, Idle error packets sent' ;
                type uint64 ;

              }

              leaf e-error {
                description 'Total error packets sent' ;
                type uint64 ;

              }

              leaf e-unicasts {
                description 'Total unicast packets sent' ;
                type uint64 ;

              }

              leaf e-broadcasts {
                description 'Total broadcast packets sent' ;
                type uint64 ;

              }

              leaf e-multicasts {
                description 'Total multicast packets sent' ;
                type uint64 ;

              }

              leaf e-byteall {
                description 'Total bytes send,include normal/error packets,mac header and FCS.' ;
                type uint64 ;

              }

              leaf e-packetall {
                description 'Total packets send(include normal/error packets)' ;
                type uint64 ;

              }

              leaf e-undersize {
                description 'Total packets shorter than 64 bytes sent' ;
                type uint64 ;

              }

              leaf e-oversize {
                description 'Total packets longer than Max bytes sent' ;
                type uint64 ;

              }

              leaf e-fragments {
                description 'Total fragment packets sent' ;
                type uint64 ;

              }

              leaf e-jabbers {
                description 'Total Jabber packets sent' ;
                type uint64 ;

              }

              leaf e-64b {
                description 'Total packets of 64 bytes sent' ;
                type uint64 ;

              }

              leaf e-65-127b {
                description 'Total packets of 65~127 bytes sent' ;
                type uint64 ;

              }

              leaf e-128-255b {
                description 'Total packets of 128~255 bytes sent' ;
                type uint64 ;

              }

              leaf e-256-511b {
                description 'Total packets of 256~511 bytes sent' ;
                type uint64 ;

              }

              leaf e-512-1023b {
                description 'Total packets of 512~1023 bytes sent' ;
                type uint64 ;

              }

              leaf e-1024-1518b {
                description 'Total packets of 1024~1518 bytes sent' ;
                type uint64 ;

              }

              leaf e-1519-maxb {
                description 'Total packets of 1519~Max bytes sent' ;
                type uint64 ;

              }

              leaf e-dropevents {
                description 'Total dropped frames sent for FIFO overflow' ;
                type uint64 ;

              }

              leaf in-macrxerror {
                description 'Each time a frame is received with size is between 10-63 bytes in length' ;
                type uint64 ;

              }

              ncd:revise-date 2015-11-18 ;
            }

            container vei-statistics {
              description 'Describe the data nodes for the operational state of vei-port statistics.These performace items are updated by product managment.' ;
              leaf in-byte-speed {
                description 'Total bytes received,include packets with space.' ;
                type uint64 ;

              }

              leaf in-bytes {
                description 'Total bytes received' ;
                type uint64 ;

              }

              leaf in-pkts {
                description 'Total packets received' ;
                type uint64 ;

              }

              leaf in-byteok {
                description 'Total normal frame bytes received' ;
                type uint64 ;

              }

              leaf in-pktok {
                description 'Total normal frames received' ;
                type uint64 ;

              }

              leaf in-pause {
                description 'Total pause frames received' ;
                type uint64 ;

              }

              leaf in-singcollision {
                description 'Single conflict packets received' ;
                type uint64 ;

              }

              leaf in-multcollision {
                description 'multiple conflict packets received' ;
                type uint64 ;

              }

              leaf in-Latecollision {
                description 'Total packets received with conflict detected' ;
                type uint64 ;

              }

              leaf in-excecollision {
                description 'Total packets dropped for conflict received' ;
                type uint64 ;

              }

              leaf in-crc-error {
                description 'Total packets received with CRC error received' ;
                type uint64 ;

              }

              leaf in-alignerror {
                description 'Total packets received with alignment error received' ;
                type uint64 ;

              }

              leaf in-symbolerror {
                description 'Total PHY Std Reg 10, Idle error packets received' ;
                type uint64 ;

              }

              leaf in-error {
                description 'Total error packets received' ;
                type uint64 ;

              }

              leaf in-unicasts {
                description 'Total unicast packets received' ;
                type uint64 ;

              }

              leaf in-broadcasts {
                description 'Total broadcast packets received' ;
                type uint64 ;

              }

              leaf in-multicasts {
                description 'Total multicast packets received' ;
                type uint64 ;

              }

              leaf in-byteall {
                description 'Total bytes received,include normal/error packets,mac header and FCS.' ;
                type uint64 ;

              }

              leaf in-packetall {
                description 'Total packets received(include normal/error packets)' ;
                type uint64 ;

              }

              leaf in-undersize {
                description 'Total packets shorter than 64 bytes received' ;
                type uint64 ;

              }

              leaf in-oversize {
                description 'Total packets longer than Max bytes received' ;
                type uint64 ;

              }

              leaf in-fragments {
                description 'Total fragment packets received' ;
                type uint64 ;

              }

              leaf in-jabbers {
                description 'Total Jabber packets received' ;
                type uint64 ;

              }

              leaf in-64b {
                description 'Total packets of 64 bytes received' ;
                type uint64 ;

              }

              leaf in-65-127b {
                description 'Total packets of 65~127 bytes received' ;
                type uint64 ;

              }

              leaf in-128-255b {
                description 'Total packets of 128~255 bytes received' ;
                type uint64 ;

              }

              leaf in-256-511b {
                description 'Total packets of 256~511 bytes received' ;
                type uint64 ;

              }

              leaf in-512-1023b {
                description 'Total packets of 512~1023 bytes received' ;
                type uint64 ;

              }

              leaf in-1024-1518b {
                description 'Total packets of 1024~1518 bytes received' ;
                type uint64 ;

              }

              leaf in-1519-maxb {
                description 'Total packets of 1519~Max bytes received' ;
                type uint64 ;

              }

              leaf in-dropevents {
                description 'Total dropped frames received for FIFO overflow' ;
                type uint64 ;

              }

              leaf e-byte-speed {
                description 'Total bytes sent include packets with space' ;
                type uint64 ;

              }

              leaf e-bytes {
                description 'Total bytes sent' ;
                type uint64 ;

              }

              leaf e-packets {
                description 'Total packets sent' ;
                type uint64 ;

              }

              leaf e-byteok {
                description 'Total normal frame bytes sent' ;
                type uint64 ;

              }

              leaf e-packetok {
                description 'Total normal frames sent' ;
                type uint64 ;

              }

              leaf e-pause {
                description 'Total pause frames sent' ;
                type uint64 ;

              }

              leaf e-singcollision {
                description 'Single conflict packets sent' ;
                type uint64 ;

              }

              leaf e-multcollision {
                description 'Multi-conflict packets sent' ;
                type uint64 ;

              }

              leaf e-Latecollision {
                description 'Total packets sent with conflict detected' ;
                type uint64 ;

              }

              leaf e-excecollision {
                description 'Total packets dropped for conflict' ;
                type uint64 ;

              }

              leaf e-crc-error {
                description 'Total packets sent with CRC error' ;
                type uint64 ;

              }

              leaf e-alignerror {
                description 'Total packets sent with alignment error' ;
                type uint64 ;

              }

              leaf e-symbolerror {
                description 'Total PHY Std Reg 10, Idle error packets sent' ;
                type uint64 ;

              }

              leaf e-error {
                description 'Total error packets sent' ;
                type uint64 ;

              }

              leaf e-unicasts {
                description 'Total unicast packets sent' ;
                type uint64 ;

              }

              leaf e-broadcasts {
                description 'Total broadcast packets sent' ;
                type uint64 ;

              }

              leaf e-multicasts {
                description 'Total multicast packets sent' ;
                type uint64 ;

              }

              leaf e-byteall {
                description 'Total bytes send,include normal/error packets,mac header and FCS.' ;
                type uint64 ;

              }

              leaf e-packetall {
                description 'Total packets send(include normal/error packets)' ;
                type uint64 ;

              }

              leaf e-undersize {
                description 'Total packets shorter than 64 bytes sent' ;
                type uint64 ;

              }

              leaf e-oversize {
                description 'Total packets longer than Max bytes sent' ;
                type uint64 ;

              }

              leaf e-fragments {
                description 'Total fragment packets sent' ;
                type uint64 ;

              }

              leaf e-jabbers {
                description 'Total Jabber packets sent' ;
                type uint64 ;

              }

              leaf e-64b {
                description 'Total packets of 64 bytes sent' ;
                type uint64 ;

              }

              leaf e-65-127b {
                description 'Total packets of 65~127 bytes sent' ;
                type uint64 ;

              }

              leaf e-128-255b {
                description 'Total packets of 128~255 bytes sent' ;
                type uint64 ;

              }

              leaf e-256-511b {
                description 'Total packets of 256~511 bytes sent' ;
                type uint64 ;

              }

              leaf e-512-1023b {
                description 'Total packets of 512~1023 bytes sent' ;
                type uint64 ;

              }

              leaf e-1024-1518b {
                description 'Total packets of 1024~1518 bytes sent' ;
                type uint64 ;

              }

              leaf e-1519-maxb {
                description 'Total packets of 1519~Max bytes sent' ;
                type uint64 ;

              }

              leaf e-dropevents {
                description 'Total dropped frames sent for FIFO overflow' ;
                type uint64 ;

              }

              leaf in-macrxerror {
                description 'Total macrxerror received.' ;
                type uint64 ;

              }

              leaf in-overrun {
                description 'Total overrun received' ;
                type uint64 ;

              }

              leaf in-pktsdrop {
                description 'Total packets of dropped received.' ;
                type uint64 ;

              }

              leaf in-pktserror {
                description 'Total error packets received.' ;
                type uint64 ;

              }

              leaf e-pktsdrop {
                description 'Total packets of dropped sent.' ;
                type uint64 ;

              }

              leaf e-pktserror {
                description 'Total error packets sent.' ;
                type uint64 ;

              }

              ncd:revise-date 2020-02-14 ;
            }

            container sat-statistics {
              description 'Describe the data nodes for the operational state of sat-port statistics.These performace items are updated by product managment.' ;
              leaf in-byte-speed {
                description 'Total bytes received,include packets with space.' ;
                type uint64 ;

              }

              leaf in-bytes {
                description 'Total bytes received' ;
                type uint64 ;

              }

              leaf in-pkts {
                description 'Total packets received' ;
                type uint64 ;

              }

              leaf in-byteok {
                description 'Total normal frame bytes received' ;
                type uint64 ;

              }

              leaf in-pktok {
                description 'Total normal frames received' ;
                type uint64 ;

              }

              leaf in-pause {
                description 'Total pause frames received' ;
                type uint64 ;

              }

              leaf in-singcollision {
                description 'Single conflict packets received' ;
                type uint64 ;

              }

              leaf in-multcollision {
                description 'multiple conflict packets received' ;
                type uint64 ;

              }

              leaf in-Latecollision {
                description 'Total packets received with conflict detected' ;
                type uint64 ;

              }

              leaf in-excecollision {
                description 'Total packets dropped for conflict received' ;
                type uint64 ;

              }

              leaf in-crc-error {
                description 'Total packets received with CRC error received' ;
                type uint64 ;

              }

              leaf in-alignerror {
                description 'Total packets received with alignment error received' ;
                type uint64 ;

              }

              leaf in-symbolerror {
                description 'Total PHY Std Reg 10, Idle error packets received' ;
                type uint64 ;

              }

              leaf in-error {
                description 'Total error packets received' ;
                type uint64 ;

              }

              leaf in-unicasts {
                description 'Total unicast packets received' ;
                type uint64 ;

              }

              leaf in-broadcasts {
                description 'Total broadcast packets received' ;
                type uint64 ;

              }

              leaf in-multicasts {
                description 'Total multicast packets received' ;
                type uint64 ;

              }

              leaf in-byteall {
                description 'Total bytes received,include normal/error packets,mac header and FCS.' ;
                type uint64 ;

              }

              leaf in-packetall {
                description 'Total packets received(include normal/error packets)' ;
                type uint64 ;

              }

              leaf in-undersize {
                description 'Total packets shorter than 64 bytes received' ;
                type uint64 ;

              }

              leaf in-oversize {
                description 'Total packets longer than Max bytes received' ;
                type uint64 ;

              }

              leaf in-fragments {
                description 'Total fragment packets received' ;
                type uint64 ;

              }

              leaf in-jabbers {
                description 'Total Jabber packets received' ;
                type uint64 ;

              }

              leaf in-64b {
                description 'Total packets of 64 bytes received' ;
                type uint64 ;

              }

              leaf in-65-127b {
                description 'Total packets of 65~127 bytes received' ;
                type uint64 ;

              }

              leaf in-128-255b {
                description 'Total packets of 128~255 bytes received' ;
                type uint64 ;

              }

              leaf in-256-511b {
                description 'Total packets of 256~511 bytes received' ;
                type uint64 ;

              }

              leaf in-512-1023b {
                description 'Total packets of 512~1023 bytes received' ;
                type uint64 ;

              }

              leaf in-1024-1518b {
                description 'Total packets of 1024~1518 bytes received' ;
                type uint64 ;

              }

              leaf in-1519-maxb {
                description 'Total packets of 1519~Max bytes received' ;
                type uint64 ;

              }

              leaf in-dropevents {
                description 'Total dropped frames received for FIFO overflow' ;
                type uint64 ;

              }

              leaf e-byte-speed {
                description 'Total bytes sent include packets with space' ;
                type uint64 ;

              }

              leaf e-bytes {
                description 'Total bytes sent' ;
                type uint64 ;

              }

              leaf e-packets {
                description 'Total packets sent' ;
                type uint64 ;

              }

              leaf e-byteok {
                description 'Total normal frame bytes sent' ;
                type uint64 ;

              }

              leaf e-packetok {
                description 'Total normal frames sent' ;
                type uint64 ;

              }

              leaf e-pause {
                description 'Total pause frames sent' ;
                type uint64 ;

              }

              leaf e-singcollision {
                description 'Single conflict packets sent' ;
                type uint64 ;

              }

              leaf e-multcollision {
                description 'Multi-conflict packets sent' ;
                type uint64 ;

              }

              leaf e-Latecollision {
                description 'Total packets sent with conflict detected' ;
                type uint64 ;

              }

              leaf e-excecollision {
                description 'Total packets dropped for conflict' ;
                type uint64 ;

              }

              leaf e-crc-error {
                description 'Total packets sent with CRC error' ;
                type uint64 ;

              }

              leaf e-alignerror {
                description 'Total packets sent with alignment error' ;
                type uint64 ;

              }

              leaf e-symbolerror {
                description 'Total PHY Std Reg 10, Idle error packets sent' ;
                type uint64 ;

              }

              leaf e-error {
                description 'Total error packets sent' ;
                type uint64 ;

              }

              leaf e-unicasts {
                description 'Total unicast packets sent' ;
                type uint64 ;

              }

              leaf e-broadcasts {
                description 'Total broadcast packets sent' ;
                type uint64 ;

              }

              leaf e-multicasts {
                description 'Total multicast packets sent' ;
                type uint64 ;

              }

              leaf e-byteall {
                description 'Total bytes send,include normal/error packets,mac header and FCS.' ;
                type uint64 ;

              }

              leaf e-packetall {
                description 'Total packets send(include normal/error packets)' ;
                type uint64 ;

              }

              leaf e-undersize {
                description 'Total packets shorter than 64 bytes sent' ;
                type uint64 ;

              }

              leaf e-oversize {
                description 'Total packets longer than Max bytes sent' ;
                type uint64 ;

              }

              leaf e-fragments {
                description 'Total fragment packets sent' ;
                type uint64 ;

              }

              leaf e-jabbers {
                description 'Total Jabber packets sent' ;
                type uint64 ;

              }

              leaf e-64b {
                description 'Total packets of 64 bytes sent' ;
                type uint64 ;

              }

              leaf e-65-127b {
                description 'Total packets of 65~127 bytes sent' ;
                type uint64 ;

              }

              leaf e-128-255b {
                description 'Total packets of 128~255 bytes sent' ;
                type uint64 ;

              }

              leaf e-256-511b {
                description 'Total packets of 256~511 bytes sent' ;
                type uint64 ;

              }

              leaf e-512-1023b {
                description 'Total packets of 512~1023 bytes sent' ;
                type uint64 ;

              }

              leaf e-1024-1518b {
                description 'Total packets of 1024~1518 bytes sent' ;
                type uint64 ;

              }

              leaf e-1519-maxb {
                description 'Total packets of 1519~Max bytes sent' ;
                type uint64 ;

              }

              leaf e-dropevents {
                description 'Total dropped frames sent for FIFO overflow' ;
                type uint64 ;

              }

              leaf in-macrxerror {
                description 'Total macrxerror received.' ;
                type uint64 ;

              }

              leaf in-overrun {
                description 'Total overrun received' ;
                type uint64 ;

              }

              leaf in-pktsdrop {
                description 'Total packets of dropped received.' ;
                type uint64 ;

              }

              leaf in-pktserror {
                description 'Total error packets received.' ;
                type uint64 ;

              }

              leaf e-pktsdrop {
                description 'Total packets of dropped sent.' ;
                type uint64 ;

              }

              leaf e-pktserror {
                description 'Total error packets sent.' ;
                type uint64 ;

              }

              ncd:revise-date 2022-09-19 ;
            }

          }

          container stream-counters {
            container mc-statistics {
              description 'Describe the data nodes for the operational state of statistics whose checkpoint is BYMC.These performace items are calculated by platform with the items of subport.' ;
              leaf in-bytes {
                description 'Total bytes received' ;
                type uint64 ;

              }

              leaf in-packets {
                description 'Total packets received' ;
                type uint64 ;

              }

              leaf e-bytes {
                description 'Total bytes sent' ;
                type uint64 ;

              }

              leaf e-packets {
                description 'Total packets sent' ;
                type uint64 ;

              }

              leaf in-byte-rate {
                description 'Total bytes received' ;
                type uint64 ;

              }

              leaf in-packet-rate {
                description 'Total packets received' ;
                type uint64 ;

              }

              leaf e-byte-rate {
                description 'Total bytes sent' ;
                type uint64 ;

              }

              leaf e-packet-rate {
                description 'Total packets sent' ;
                type uint64 ;

              }

              leaf in-discards {
                description 'Total dropped frames received for FIFO overflow' ;
                type uint64 ;

              }

              leaf e-discards {
                description 'Total dropped frames sent for FIFO overflow' ;
                type uint64 ;

              }

              leaf in-upsendcar-drop {
                description 'Upsend-car discard packets received' ;
                type uint64 ;

              }

              leaf in-v4bytes {
                description 'IPv4 bytes received' ;
                type uint64 ;

              }

              leaf in-v4pkts {
                description 'IPv4 packets received' ;
                type uint64 ;

              }

              leaf e-v4bytes {
                description 'IPv4 bytes sent' ;
                type uint64 ;

              }

              leaf e-v4pkts {
                description 'IPv4 packets sent' ;
                type uint64 ;

              }

              leaf in-v6bytes {
                description 'IPv6 bytes received' ;
                type uint64 ;

              }

              leaf in-v6pkts {
                description 'IPv6 packets received' ;
                type uint64 ;

              }

              leaf e-v6bytes {
                description 'IPv6 bytes sent' ;
                type uint64 ;

              }

              leaf e-v6pkts {
                description 'IPv6 packets sent' ;
                type uint64 ;

              }

              leaf in-v4hdrerrors {
                description 'IPv4 HdrError count received' ;
                type uint64 ;

              }

              leaf in-v4addrerrors {
                description 'IPv4 AddrError count received' ;
                type uint64 ;

              }

              leaf in-v4truncateds {
                description 'IPv4 Truncated count received' ;
                type uint64 ;

              }

              leaf in-v4bcasts {
                description 'IPv4 Bcast count received' ;
                type uint64 ;

              }

              leaf in-v4noroutes {
                description 'IPv4 NoRoute count received' ;
                type uint64 ;

              }

              leaf in-v4unknownprotos {
                description 'IPv4 unknown protol count received' ;
                type uint64 ;

              }

              leaf in-v4discards {
                description 'IPv4 dropped frames received' ;
                type uint64 ;

              }

              leaf in-v4forwdatagrams {
                description 'IPv4 ForwDatagram count received' ;
                type uint64 ;

              }

              leaf in-v6hdrerrors {
                description 'IPv6 HdrError count received' ;
                type uint64 ;

              }

              leaf in-v6truncateds {
                description 'IPv6 Truncated count received' ;
                type uint64 ;

              }

              leaf in-v6addrerrors {
                description 'IPv6 AddrError count received' ;
                type uint64 ;

              }

              leaf in-v6bcasts {
                description 'IPv6 Bcast count received' ;
                type uint64 ;

              }

              leaf in-v6noroutes {
                description 'IPv6 NoRoute count received' ;
                type uint64 ;

              }

              leaf in-v6unknownprotos {
                description 'IPv6 unknown protol count received' ;
                type uint64 ;

              }

              leaf in-v6discards {
                description 'IPv6 dropped frames received' ;
                type uint64 ;

              }

              leaf in-v6forwdatagrams {
                description 'IPv6 ForwDatagram count received' ;
                type uint64 ;

              }

              leaf e-v4discards {
                description 'IPv4 dropped frames sent' ;
                type uint64 ;

              }

              leaf e-v4forwdatagrams {
                description 'IPv4 ForwDatagram count sent' ;
                type uint64 ;

              }

              leaf e-v4fragreqds {
                description 'IPv4 FragReqd count sent' ;
                type uint64 ;

              }

              leaf e-v6discards {
                description 'IPv6 dropped frames sent' ;
                type uint64 ;

              }

              leaf e-v6forwdatagrams {
                description 'IPv6 ForwDatagram count sent' ;
                type uint64 ;

              }

              leaf e-v6fragreqds {
                description 'IPv6 FragReqd count sent' ;
                type uint64 ;

              }

              leaf in-multicastpkts {
                description 'Total multicast packets received' ;
                type uint64 ;

              }

              leaf in-broadcastpkts {
                description 'Total broadcast packets received' ;
                type uint64 ;

              }

              leaf e-multicastpkts {
                description 'Total multicast packets sent' ;
                type uint64 ;

              }

              leaf e-broadcastpkts {
                description 'Total broadcast packets sent' ;
                type uint64 ;

              }

              leaf e-upsendcar-drop {
                description 'Upsend-car discard packets sent' ;
                type uint64 ;

              }

              leaf in-urpf-v4drppkts {
                description 'URPF V4 discards packets received' ;
                type uint64 ;

              }

              leaf in-urpf-v6drppkts {
                description 'URPF V6 discards packets received' ;
                type uint64 ;

              }

              leaf in-pktsdrop {
                description 'Total packets of dropped received.' ;
                type uint64 ;

                ncd:revise-date 2015-05-19 ;
              }

              leaf in-pktserror {
                description 'Total error packets received.' ;
                type uint64 ;

                ncd:revise-date 2015-05-19 ;
              }

              leaf e-pktsdrop {
                description 'Total packets of dropped sent.' ;
                type uint64 ;

                ncd:revise-date 2015-05-19 ;
              }

              leaf e-pktserror {
                description 'Total error packets sent.' ;
                type uint64 ;

                ncd:revise-date 2015-05-19 ;
              }

              leaf in-acl-drop {
                description 'Acl discard packets received.' ;
                type uint64 ;

                ncd:revise-date 2020-12-11 ;
              }

              leaf in-car-drop {
                description 'Car discard packets received.' ;
                type uint64 ;

                ncd:revise-date 2020-12-11 ;
              }

              leaf in-l3-rtmiss-drop {
                description 'L3-rtmiss discard packets received.' ;
                type uint64 ;

                ncd:revise-date 2020-12-11 ;
              }

              leaf in-vlanmiss-drop {
                description 'Vlan-miss discard packets received.' ;
                type uint64 ;

                ncd:revise-date 2020-12-11 ;
              }

              leaf in-mplsmiss-drop {
                description 'Mpls-miss discard packets received.' ;
                type uint64 ;

                ncd:revise-date 2020-12-11 ;
              }

              leaf in-notfinde-drop {
                description 'Not found e-port discard packets received.' ;
                type uint64 ;

                ncd:revise-date 2020-12-11 ;
              }

              leaf in-broadcast-drop {
                description 'Broad-cast discard packets received.' ;
                type uint64 ;

                ncd:revise-date 2020-12-11 ;
              }

              leaf in-l2-proto-drop {
                description 'L2-proto discard packets received.' ;
                type uint64 ;

                ncd:revise-date 2020-12-11 ;
              }

              leaf in-remaining-drop {
                description 'Remaining discard packets received.' ;
                type uint64 ;

                ncd:revise-date 2020-12-11 ;
              }

              leaf e-acl-drop {
                description 'Acl discard packets send.' ;
                type uint64 ;

                ncd:revise-date 2020-12-11 ;
              }

              leaf e-notfinde-drop {
                description 'Not found e-port discard packets send.' ;
                type uint64 ;

                ncd:revise-date 2020-12-11 ;
              }

              leaf e-remaining-drop {
                description 'Remaining discard packets send.' ;
                type uint64 ;

                ncd:revise-date 2020-12-11 ;
              }

              leaf in-v4bytes-l1 {
                description 'L1 IPv4 bytes received' ;
                type uint64 ;

                ncd:revise-date 2021-02-03 ;
              }

              leaf e-v4bytes-l1 {
                description 'L1 IPv4 bytes sent' ;
                type uint64 ;

                ncd:revise-date 2021-02-03 ;
              }

              leaf in-v6bytes-l1 {
                description 'L1 IPv6 bytes received' ;
                type uint64 ;

                ncd:revise-date 2021-02-03 ;
              }

              leaf e-v6bytes-l1 {
                description 'L1 IPv6 bytes sent' ;
                type uint64 ;

                ncd:revise-date 2021-02-03 ;
              }

              leaf in-mpls-bytes {
                description 'MPLS bytes received' ;
                type uint64 ;

                ncd:revise-date 2021-02-03 ;
              }

              leaf e-mpls-bytes {
                description 'MPLS bytes sent' ;
                type uint64 ;

                ncd:revise-date 2021-02-03 ;
              }

              leaf in-mpls-pkts {
                description 'MPLS packets received' ;
                type uint64 ;

                ncd:revise-date 2021-02-03 ;
              }

              leaf e-mpls-pkts {
                description 'MPLS packets sent' ;
                type uint64 ;

                ncd:revise-date 2021-02-03 ;
              }

              leaf in-mpls-bytes-l1 {
                description 'L1 MPLS bytes received' ;
                type uint64 ;

                ncd:revise-date 2021-02-03 ;
              }

              leaf e-mpls-bytes-l1 {
                description 'L1 MPLS bytes sent' ;
                type uint64 ;

                ncd:revise-date 2021-02-03 ;
              }

              leaf e-notteuti-bytes {
                description 'Bytes sent by non-Te utilization.' ;
                type uint64 ;

                ncd:revise-date 2021-03-29 ;
              }

              leaf e-notteuti-pkts {
                description 'Packets sent by non-Te utilization.' ;
                type uint64 ;

                ncd:revise-date 2021-03-29 ;
              }

              leaf in-upsendcarpkts {
                description 'Upsend-car packets received' ;
                type uint64 ;

                ncd:revise-date 2022-09-19 ;
              }

              leaf in-urpf-drop-pkts {
                description 'URPF drop packets received' ;
                type uint64 ;

                ncd:revise-date 2022-10-31 ;
              }

              leaf in-bier-bytes {
                description 'Bier bytes received' ;
                type uint64 ;

                ncd:revise-date 2022-11-18 ;
              }

              leaf in-bier-pkts {
                description 'Bier packets received' ;
                type uint64 ;

                ncd:revise-date 2022-11-18 ;
              }

              leaf e-bier-bytes {
                description 'Bier bytes sent' ;
                type uint64 ;

                ncd:revise-date 2022-11-18 ;
              }

              leaf e-bier-pkts {
                description 'Bier packets sent' ;
                type uint64 ;

                ncd:revise-date 2022-11-18 ;
              }

            }

            container dialer-statistics {
              description 'Describe the data nodes for the operational state of dialer-port statistics.These performace items are updated by microcode.' ;
              leaf in-bytes {
                description 'Total bytes received' ;
                type uint64 ;

              }

              leaf in-pkts {
                description 'Total packets received' ;
                type uint64 ;

              }

              leaf e-bytes {
                description 'Total bytes sent' ;
                type uint64 ;

              }

              leaf e-pkts {
                description 'Total packets sent' ;
                type uint64 ;

              }

            }

            container mppp-statistics {
              description 'Describe the data nodes for the operational state of mutilink-port statistics.These performace items are updated by microcode.' ;
              leaf in-bytes {
                description 'Total bytes received' ;
                type uint64 ;

              }

              leaf in-packets {
                description 'Total packets received' ;
                type uint64 ;

              }

              leaf in-discards {
                description 'Total dropped frames received for FIFO overflow' ;
                type uint64 ;

              }

              leaf in-v4bytes {
                description 'IPv4 bytes received' ;
                type uint64 ;

              }

              leaf in-v4pkts {
                description 'IPv4 packets received' ;
                type uint64 ;

              }

              leaf in-v6bytes {
                description 'IPv6 bytes received' ;
                type uint64 ;

              }

              leaf in-v6pkts {
                description 'IPv6 packets received' ;
                type uint64 ;

              }

              leaf e-bytes {
                description 'Total bytes sent' ;
                type uint64 ;

              }

              leaf e-packets {
                description 'Total packets sent' ;
                type uint64 ;

              }

              leaf e-discards {
                description 'Total dropped frames sent for FIFO overflow' ;
                type uint64 ;

              }

              leaf e-v4bytes {
                description 'IPv4 bytes sent' ;
                type uint64 ;

              }

              leaf e-v4pkts {
                description 'IPv4 packets sent' ;
                type uint64 ;

              }

              leaf e-v6bytes {
                description 'IPv6 bytes sent' ;
                type uint64 ;

              }

              leaf e-v6pkts {
                description 'IPv6 packets sent' ;
                type uint64 ;

              }

              leaf in-upsendcar-drop {
                description 'Upsend-car discard packets received' ;
                type uint64 ;

              }

            }

            container subport-statistics {
              description 'Describe the data nodes for the operational state of subport statistics.These performace items are updated by microcode.' ;
              leaf in-bytes {
                description 'Total bytes received' ;
                type uint64 ;

              }

              leaf in-packets {
                description 'Total packets received' ;
                type uint64 ;

              }

              leaf e-bytes {
                description 'Total bytes sent' ;
                type uint64 ;

              }

              leaf e-packets {
                description 'Total packets sent' ;
                type uint64 ;

              }

              leaf in-discards {
                description 'Total dropped frames received for FIFO overflow' ;
                type uint64 ;

              }

              leaf e-discards {
                description 'Total dropped frames sent for FIFO overflow' ;
                type uint64 ;

              }

              leaf in-upsendcar-drop {
                description 'Upsend-car discard packets received' ;
                type uint64 ;

              }

              leaf in-v4bytes {
                description 'IPv4 bytes received' ;
                type uint64 ;

              }

              leaf in-v4pkts {
                description 'IPv4 packets received' ;
                type uint64 ;

              }

              leaf e-v4bytes {
                description 'IPv4 bytes sent' ;
                type uint64 ;

              }

              leaf e-v4pkts {
                description 'IPv4 packets sent' ;
                type uint64 ;

              }

              leaf in-v6bytes {
                description 'IPv6 bytes received' ;
                type uint64 ;

              }

              leaf in-v6pkts {
                description 'IPv6 packets received' ;
                type uint64 ;

              }

              leaf e-v6bytes {
                description 'IPv6 bytes sent' ;
                type uint64 ;

              }

              leaf e-v6pkts {
                description 'IPv6 packets sent' ;
                type uint64 ;

              }

              leaf in-multicastbytes {
                description 'Total multicast bytes received' ;
                type uint64 ;

              }

              leaf in-multicastpkts {
                description 'Total multicast packets received' ;
                type uint64 ;

              }

              leaf in-broadcastbytes {
                description 'Total broadcast bytes received' ;
                type uint64 ;

              }

              leaf in-broadcastpkts {
                description 'Total broadcast packets received' ;
                type uint64 ;

              }

              leaf e-multicastbytes {
                description 'Total multicast bytes sent' ;
                type uint64 ;

              }

              leaf e-multicastpkts {
                description 'Total multicast packets sent' ;
                type uint64 ;

              }

              leaf e-broadcastbytes {
                description 'Total broadcast bytes sent' ;
                type uint64 ;

              }

              leaf e-broadcastpkts {
                description 'Total broadcast packets sent' ;
                type uint64 ;

              }

              leaf in-upsendpkts {
                description 'Upsend packets received' ;
                type uint64 ;

              }

              leaf e-upsendpkts {
                description 'Upsend packets sent' ;
                type uint64 ;

              }

              leaf in-v4hdrerrors {
                description 'IPv4 HdrError count received' ;
                type uint64 ;

              }

              leaf in-v4addrerrors {
                description 'IPv4 AddrError count received' ;
                type uint64 ;

              }

              leaf in-v4truncateds {
                description 'IPv4 Truncated count received' ;
                type uint64 ;

              }

              leaf in-v4bcasts {
                description 'IPv4 Bcast count received' ;
                type uint64 ;

              }

              leaf in-v4noroutes {
                description 'IPv4 NoRoute count received' ;
                type uint64 ;

              }

              leaf in-v4unknownprotos {
                description 'IPv4 unknown protol count received' ;
                type uint64 ;

              }

              leaf in-v4discards {
                description 'IPv4 dropped frames received' ;
                type uint64 ;

              }

              leaf in-v4forwdatagrams {
                description 'IPv4 ForwDatagram count received' ;
                type uint64 ;

              }

              leaf in-v6hdrerrors {
                description 'IPv6 HdrError count received' ;
                type uint64 ;

              }

              leaf in-v6truncateds {
                description 'IPv6 Truncated count received' ;
                type uint64 ;

              }

              leaf in-v6addrerrors {
                description 'IPv6 AddrError count received' ;
                type uint64 ;

              }

              leaf in-v6bcasts {
                description 'IPv6 Bcast count received' ;
                type uint64 ;

              }

              leaf in-v6noroutes {
                description 'IPv6 NoRoute count received' ;
                type uint64 ;

              }

              leaf in-v6unknownprotos {
                description 'IPv6 unknown protol count received' ;
                type uint64 ;

              }

              leaf in-v6discards {
                description 'IPv6 dropped frames received' ;
                type uint64 ;

              }

              leaf in-v6forwdatagrams {
                description 'IPv6 ForwDatagram count received' ;
                type uint64 ;

              }

              leaf e-v4discards {
                description 'IPv4 dropped frames sent' ;
                type uint64 ;

              }

              leaf e-v4forwdatagrams {
                description 'IPv4 ForwDatagram count sent' ;
                type uint64 ;

              }

              leaf e-v4fragreqds {
                description 'IPv4 FragReqd count sent' ;
                type uint64 ;

              }

              leaf e-v6discards {
                description 'IPv6 dropped frames sent' ;
                type uint64 ;

              }

              leaf e-v6forwdatagrams {
                description 'IPv6 ForwDatagram count sent' ;
                type uint64 ;

              }

              leaf e-v6fragreqds {
                description 'IPv6 FragReqd count sent' ;
                type uint64 ;

              }

              leaf in-unicastbytes {
                description 'Total unicast bytes received' ;
                type uint64 ;

              }

              leaf in-unicastpkts {
                description 'Total unicast packets received' ;
                type uint64 ;

              }

              leaf in-unknownunicastbytes {
                description 'Total unknow unicast bytes received' ;
                type uint64 ;

              }

              leaf in-unknownunicastpkts {
                description 'Total unknow unicast packets received' ;
                type uint64 ;

              }

              leaf in-discbytes {
                description 'Discard bytes received' ;
                type uint64 ;

              }

              leaf e-discbytes {
                description 'Discard bytes sent' ;
                type uint64 ;

              }

              leaf e-upsendcar-drop {
                description 'Upsend-car discard packets sent' ;
                type uint64 ;

              }

              leaf in-urpf-v4drppkts {
                description 'URPF V4 discards packets received' ;
                type uint64 ;

              }

              leaf in-urpf-v6drppkts {
                description 'URPF V6 discards packets received' ;
                type uint64 ;

              }

              leaf in-pktsdrop {
                description 'Total packets of dropped received.' ;
                type uint64 ;

                ncd:revise-date 2015-05-19 ;
              }

              leaf in-pktserror {
                description 'Total error packets received.' ;
                type uint64 ;

                ncd:revise-date 2015-05-19 ;
              }

              leaf e-pktsdrop {
                description 'Total packets of dropped sent.' ;
                type uint64 ;

                ncd:revise-date 2015-05-19 ;
              }

              leaf e-pktserror {
                description 'Total error packets sent.' ;
                type uint64 ;

                ncd:revise-date 2015-05-19 ;
              }

              leaf in-acl-drop {
                description 'Acl discard packets received.' ;
                type uint64 ;

                ncd:revise-date 2020-12-11 ;
              }

              leaf in-car-drop {
                description 'Car discard packets received.' ;
                type uint64 ;

                ncd:revise-date 2020-12-11 ;
              }

              leaf in-l3-rtmiss-drop {
                description 'L3-rtmiss discard packets received.' ;
                type uint64 ;

                ncd:revise-date 2020-12-11 ;
              }

              leaf in-vlanmiss-drop {
                description 'Vlan-miss discard packets received.' ;
                type uint64 ;

                ncd:revise-date 2020-12-11 ;
              }

              leaf in-mplsmiss-drop {
                description 'Mpls-miss discard packets received.' ;
                type uint64 ;

                ncd:revise-date 2020-12-11 ;
              }

              leaf in-notfinde-drop {
                description 'Not found e-port discard packets received.' ;
                type uint64 ;

                ncd:revise-date 2020-12-11 ;
              }

              leaf in-broadcast-drop {
                description 'Broad-cast discard packets received.' ;
                type uint64 ;

                ncd:revise-date 2020-12-11 ;
              }

              leaf in-l2-proto-drop {
                description 'L2-proto discard packets received.' ;
                type uint64 ;

                ncd:revise-date 2020-12-11 ;
              }

              leaf in-remaining-drop {
                description 'Remaining discard packets received.' ;
                type uint64 ;

                ncd:revise-date 2020-12-11 ;
              }

              leaf e-acl-drop {
                description 'Acl discard packets send.' ;
                type uint64 ;

                ncd:revise-date 2020-12-11 ;
              }

              leaf e-notfinde-drop {
                description 'Not found e-port discard packets send.' ;
                type uint64 ;

                ncd:revise-date 2020-12-11 ;
              }

              leaf e-remaining-drop {
                description 'Remaining discard packets send.' ;
                type uint64 ;

                ncd:revise-date 2020-12-11 ;
              }

              leaf in-v4bytes-l1 {
                description 'L1 IPv4 bytes received' ;
                type uint64 ;

                ncd:revise-date 2021-02-03 ;
              }

              leaf e-v4bytes-l1 {
                description 'L1 IPv4 bytes sent' ;
                type uint64 ;

                ncd:revise-date 2021-02-03 ;
              }

              leaf in-v6bytes-l1 {
                description 'L1 IPv6 bytes received' ;
                type uint64 ;

                ncd:revise-date 2021-02-03 ;
              }

              leaf e-v6bytes-l1 {
                description 'L1 IPv6 bytes sent' ;
                type uint64 ;

                ncd:revise-date 2021-02-03 ;
              }

              leaf in-mpls-bytes {
                description 'MPLS bytes received' ;
                type uint64 ;

                ncd:revise-date 2021-02-03 ;
              }

              leaf e-mpls-bytes {
                description 'MPLS bytes sent' ;
                type uint64 ;

                ncd:revise-date 2021-02-03 ;
              }

              leaf in-mpls-pkts {
                description 'MPLS packets received' ;
                type uint64 ;

                ncd:revise-date 2021-02-03 ;
              }

              leaf e-mpls-pkts {
                description 'MPLS packets sent' ;
                type uint64 ;

                ncd:revise-date 2021-02-03 ;
              }

              leaf in-mpls-bytes-l1 {
                description 'L1 MPLS bytes received' ;
                type uint64 ;

                ncd:revise-date 2021-02-03 ;
              }

              leaf e-mpls-bytes-l1 {
                description 'L1 MPLS bytes sent' ;
                type uint64 ;

                ncd:revise-date 2021-02-03 ;
              }

              leaf e-notteuti-bytes {
                description 'Bytes sent by non-Te utilization.' ;
                type uint64 ;

                ncd:revise-date 2021-03-29 ;
              }

              leaf e-notteuti-pkts {
                description 'Packets sent by non-Te utilization.' ;
                type uint64 ;

                ncd:revise-date 2021-03-29 ;
              }

              leaf in-upsendcarpkts {
                description 'Upsend-car packets received' ;
                type uint64 ;

                ncd:revise-date 2022-09-19 ;
              }

              leaf in-urpf-drop-pkts {
                description 'URPF drop packets received' ;
                type uint64 ;

                ncd:revise-date 2022-10-31 ;
              }

              leaf in-bier-bytes {
                description 'Bier bytes received' ;
                type uint64 ;

                ncd:revise-date 2022-11-18 ;
              }

              leaf in-bier-pkts {
                description 'Bier packets received' ;
                type uint64 ;

                ncd:revise-date 2022-11-18 ;
              }

              leaf e-bier-bytes {
                description 'Bier bytes sent' ;
                type uint64 ;

                ncd:revise-date 2022-11-18 ;
              }

              leaf e-bier-pkts {
                description 'Bier packets sent' ;
                type uint64 ;

                ncd:revise-date 2022-11-18 ;
              }

            }

            container supervlan-statistics {
              description "Describe the data nodes for the operational state of statistics whose checkpoint is SUPERVLAN.These performace items are calculated by platform with the items of supervlan-port's members." ;
              leaf in-bytes {
                description 'Total bytes received' ;
                type uint64 ;

              }

              leaf in-packets {
                description 'Total packets received' ;
                type uint64 ;

              }

              leaf e-bytes {
                description 'Total bytes sent' ;
                type uint64 ;

              }

              leaf e-packets {
                description 'Total packets sent' ;
                type uint64 ;

              }

              leaf in-byte-rate {
                description 'Total bytes received' ;
                type uint64 ;

              }

              leaf in-packet-rate {
                description 'Total packets received' ;
                type uint64 ;

              }

              leaf e-byte-rate {
                description 'Total bytes sent' ;
                type uint64 ;

              }

              leaf e-packet-rate {
                description 'Total packets sent' ;
                type uint64 ;

              }

              leaf in-discards {
                description 'Total dropped frames received for FIFO overflow' ;
                type uint64 ;

              }

              leaf e-discards {
                description 'Total dropped frames sent for FIFO overflow' ;
                type uint64 ;

              }

              leaf in-v4bytes {
                description 'IPv4 bytes received' ;
                type uint64 ;

              }

              leaf in-v4pkts {
                description 'IPv4 packets received' ;
                type uint64 ;

              }

              leaf in-v6bytes {
                description 'IPv6 bytes received' ;
                type uint64 ;

              }

              leaf in-v6pkts {
                description 'IPv6 packets received' ;
                type uint64 ;

              }

              leaf e-v4bytes {
                description 'IPv4 bytes sent' ;
                type uint64 ;

              }

              leaf e-v4pkts {
                description 'IPv4 packets sent' ;
                type uint64 ;

              }

              leaf e-v6bytes {
                description 'IPv6 bytes sent' ;
                type uint64 ;

              }

              leaf e-v6pkts {
                description 'IPv6 packets sent' ;
                type uint64 ;

              }

              leaf in-upsendcar-drop {
                description 'Upsend-car discard packets received' ;
                type uint64 ;

              }

              leaf in-v4hdrerrors {
                description 'IPv4 HdrError count received' ;
                type uint64 ;

              }

              leaf in-v4addrerrors {
                description 'IPv4 AddrError count received' ;
                type uint64 ;

              }

              leaf in-v4truncateds {
                description 'IPv4 Truncated count received' ;
                type uint64 ;

              }

              leaf in-v4bcasts {
                description 'IPv4 Bcast count received' ;
                type uint64 ;

              }

              leaf in-v4noroutes {
                description 'IPv4 NoRoute count received' ;
                type uint64 ;

              }

              leaf in-v4unknownprotos {
                description 'IPv4 unknown protol count received' ;
                type uint64 ;

              }

              leaf in-v4discards {
                description 'IPv4 dropped frames received' ;
                type uint64 ;

              }

              leaf in-v4forwdatagrams {
                description 'IPv4 ForwDatagram count received' ;
                type uint64 ;

              }

              leaf in-v6hdrerrors {
                description 'IPv6 HdrError count received' ;
                type uint64 ;

              }

              leaf in-v6truncateds {
                description 'IPv6 Truncated count received' ;
                type uint64 ;

              }

              leaf in-v6addrerrors {
                description 'IPv6 AddrError count received' ;
                type uint64 ;

              }

              leaf in-v6bcasts {
                description 'IPv6 Bcast count received' ;
                type uint64 ;

              }

              leaf in-v6noroutes {
                description 'IPv6 NoRoute count received' ;
                type uint64 ;

              }

              leaf in-v6unknownprotos {
                description 'IPv6 unknown protol count received' ;
                type uint64 ;

              }

              leaf in-v6discards {
                description 'IPv6 dropped frames received' ;
                type uint64 ;

              }

              leaf in-v6forwdatagrams {
                description 'IPv6 ForwDatagram count received' ;
                type uint64 ;

              }

              leaf e-v4discards {
                description 'IPv4 dropped frames sent' ;
                type uint64 ;

              }

              leaf e-v4forwdatagrams {
                description 'IPv4 ForwDatagram count sent' ;
                type uint64 ;

              }

              leaf e-v4fragreqds {
                description 'IPv4 FragReqd count sent' ;
                type uint64 ;

              }

              leaf e-v6discards {
                description 'IPv6 dropped frames sent' ;
                type uint64 ;

              }

              leaf e-v6forwdatagrams {
                description 'IPv6 ForwDatagram count sent' ;
                type uint64 ;

              }

              leaf e-v6fragreqds {
                description 'IPv6 FragReqd count sent' ;
                type uint64 ;

              }

              leaf in-multicastpkts {
                description 'Total multicast packets received' ;
                type uint64 ;

              }

              leaf in-broadcastpkts {
                description 'Total broadcast packets received' ;
                type uint64 ;

              }

              leaf e-multicastpkts {
                description 'Total multicast packets sent' ;
                type uint64 ;

              }

              leaf e-broadcastpkts {
                description 'Total broadcast packets sent' ;
                type uint64 ;

              }

              leaf in-broadcastbytes {
                description 'Total broadcast bytes received' ;
                type uint64 ;

              }

              leaf in-unicastbytes {
                description 'Total unicast bytes received' ;
                type uint64 ;

              }

              leaf in-unicastpkts {
                description 'Total unicast packets received' ;
                type uint64 ;

              }

              leaf in-unknownunicastbytes {
                description 'Total unknow unicast bytes received' ;
                type uint64 ;

              }

              leaf in-unknownunicastpkts {
                description 'Total unknow unicast packets received' ;
                type uint64 ;

              }

              leaf in-discbytes {
                description 'Discard bytes received' ;
                type uint64 ;

              }

              leaf e-discbytes {
                description 'Discard bytes sent' ;
                type uint64 ;

              }

              leaf e-upsendcar-drop {
                description 'Upsend-car discard packets sent' ;
                type uint64 ;

              }

              leaf in-multicastbytes {
                description 'Total multicast bytes received' ;
                type uint64 ;

              }

              leaf e-multicastbytes {
                description 'Total multicast bytes sent' ;
                type uint64 ;

              }

              leaf e-broadcastbytes {
                description 'Total broadcast bytes sent' ;
                type uint64 ;

              }

              leaf in-urpf-v4drppkts {
                description 'URPF V4 discards packets received' ;
                type uint64 ;

              }

              leaf in-urpf-v6drppkts {
                description 'URPF V6 discards packets received' ;
                type uint64 ;

              }

              leaf in-pktsdrop {
                description 'Total packets of dropped received.' ;
                type uint64 ;

                ncd:revise-date 2015-05-19 ;
              }

              leaf in-pktserror {
                description 'Total error packets received.' ;
                type uint64 ;

                ncd:revise-date 2015-05-19 ;
              }

              leaf e-pktsdrop {
                description 'Total packets of dropped sent.' ;
                type uint64 ;

                ncd:revise-date 2015-05-19 ;
              }

              leaf e-pktserror {
                description 'Total error packets sent.' ;
                type uint64 ;

                ncd:revise-date 2015-05-19 ;
              }

            }

            container tetunnel-statistics {
              description 'Describe the data nodes for the operational state of te-tunnel statistics.These performace items are updated by microcode.' ;
              leaf e-bytes {
                description 'Total bytes sent' ;
                type uint64 ;

                ncd:revise-date 2015-11-05 ;
              }

              leaf e-packets {
                description 'Total packets sent' ;
                type uint64 ;

                ncd:revise-date 2015-11-05 ;
              }

              leaf e-bytes-pri0 {
                description 'Total bytes with priority 0 sent' ;
                type uint64 ;

                ncd:revise-date 2015-11-05 ;
              }

              leaf e-packets-pri0 {
                description 'Total packets with priority 0 sent' ;
                type uint64 ;

                ncd:revise-date 2015-11-05 ;
              }

              leaf e-bytes-pri1 {
                description 'Total bytes with priority 1 sent' ;
                type uint64 ;

                ncd:revise-date 2015-11-05 ;
              }

              leaf e-packets-pri1 {
                description 'Total packets with priority 1 sent' ;
                type uint64 ;

                ncd:revise-date 2015-11-05 ;
              }

              leaf e-bytes-pri2 {
                description 'Total bytes with priority 2 sent' ;
                type uint64 ;

                ncd:revise-date 2015-11-05 ;
              }

              leaf e-packets-pri2 {
                description 'Total packets with priority 2 sent' ;
                type uint64 ;

                ncd:revise-date 2015-11-05 ;
              }

              leaf e-bytes-pri3 {
                description 'Total bytes with priority 3 sent' ;
                type uint64 ;

                ncd:revise-date 2015-11-05 ;
              }

              leaf e-packets-pri3 {
                description 'Total packets with priority 3 sent' ;
                type uint64 ;

                ncd:revise-date 2015-11-05 ;
              }

              leaf e-bytes-pri4 {
                description 'Total bytes with priority 4 sent' ;
                type uint64 ;

                ncd:revise-date 2015-11-05 ;
              }

              leaf e-packets-pri4 {
                description 'Total packets with priority 4 sent' ;
                type uint64 ;

                ncd:revise-date 2015-11-05 ;
              }

              leaf e-bytes-pri5 {
                description 'Total bytes with priority 5 sent' ;
                type uint64 ;

                ncd:revise-date 2015-11-05 ;
              }

              leaf e-packets-pri5 {
                description 'Total packets with priority 5 sent' ;
                type uint64 ;

                ncd:revise-date 2015-11-05 ;
              }

              leaf e-bytes-pri6 {
                description 'Total bytes with priority 6 sent' ;
                type uint64 ;

                ncd:revise-date 2015-11-05 ;
              }

              leaf e-packets-pri6 {
                description 'Total packets with priority 6 sent' ;
                type uint64 ;

                ncd:revise-date 2015-11-05 ;
              }

              leaf e-bytes-pri7 {
                description 'Total bytes with priority 7 sent' ;
                type uint64 ;

                ncd:revise-date 2015-11-05 ;
              }

              leaf e-packets-pri7 {
                description 'Total packets with priority 7 sent' ;
                type uint64 ;

                ncd:revise-date 2015-11-05 ;
              }

              leaf in-packets {
                description 'Total packets received' ;
                type uint64 ;

                ncd:revise-date 2015-11-05 ;
              }

              leaf in-bytes {
                description 'Total bytes received' ;
                type uint64 ;

                ncd:revise-date 2015-11-05 ;
              }

              leaf in-discbytes {
                description 'Discard bytes received' ;
                type uint64 ;

                ncd:revise-date 2015-11-05 ;
              }

              leaf in-discpkts {
                description 'Discard packets received' ;
                type uint64 ;

                ncd:revise-date 2015-11-05 ;
              }

              leaf e-discbytes {
                description 'Discard bytes sent' ;
                type uint64 ;

                ncd:revise-date 2015-11-05 ;
              }

              leaf e-discpkts {
                description 'Discard packets sent' ;
                type uint64 ;

                ncd:revise-date 2015-11-05 ;
              }

              leaf in-pnodebytes {
                description 'Te tunnel interface reverse receiving bytes of Node-P' ;
                type uint64 ;

                ncd:revise-date 2017-02-15 ;
              }

              leaf in-pnodepkts {
                description 'Te tunnel interface reverse receiving packets of Node-P' ;
                type uint64 ;

                ncd:revise-date 2017-02-15 ;
              }

              leaf e-pnodebytes {
                description 'Te tunnel interface reverse sending bytes of Node-P' ;
                type uint64 ;

                ncd:revise-date 2017-02-15 ;
              }

              leaf e-pnodepkts {
                description 'Te tunnel interface reverse sending packets of Node-P' ;
                type uint64 ;

                ncd:revise-date 2017-02-15 ;
              }

            }

            container ulei-statistics {
              description 'Describe the data nodes for the operational state of ulei-port statistics.These performace items are calculated by platform with the items of subinterface.' ;
              leaf in-bytes {
                description 'Total bytes received' ;
                type uint64 ;

              }

              leaf in-packets {
                description 'Total packets received' ;
                type uint64 ;

              }

              leaf e-bytes {
                description 'Total bytes sent' ;
                type uint64 ;

              }

              leaf e-packets {
                description 'Total packets sent' ;
                type uint64 ;

              }

              leaf in-byte-rate {
                description 'Total bytes received' ;
                type uint64 ;

              }

              leaf in-packet-rate {
                description 'Total packets received' ;
                type uint64 ;

              }

              leaf e-byte-rate {
                description 'Total bytes sent' ;
                type uint64 ;

              }

              leaf e-packet-rate {
                description 'Total packets sent' ;
                type uint64 ;

              }

              leaf in-discards {
                description 'Total dropped frames received for FIFO overflow' ;
                type uint64 ;

              }

              leaf e-discards {
                description 'Total dropped frames sent for FIFO overflow' ;
                type uint64 ;

              }

              leaf in-v4bytes {
                description 'IPv4 bytes received' ;
                type uint64 ;

              }

              leaf in-v4pkts {
                description 'IPv4 packets received' ;
                type uint64 ;

              }

              leaf in-v6bytes {
                description 'IPv6 bytes received' ;
                type uint64 ;

              }

              leaf in-v6pkts {
                description 'IPv6 packets received' ;
                type uint64 ;

              }

              leaf e-v4bytes {
                description 'IPv4 bytes sent' ;
                type uint64 ;

              }

              leaf e-v4pkts {
                description 'IPv4 packets sent' ;
                type uint64 ;

              }

              leaf e-v6bytes {
                description 'IPv6 bytes sent' ;
                type uint64 ;

              }

              leaf e-v6pkts {
                description 'IPv6 packets sent' ;
                type uint64 ;

              }

              leaf in-upsendcar-drop {
                description 'Upsend-car discard packets received' ;
                type uint64 ;

              }

              leaf in-v4hdrerrors {
                description 'IPv4 HdrError count received' ;
                type uint64 ;

              }

              leaf in-v4addrerrors {
                description 'IPv4 AddrError count received' ;
                type uint64 ;

              }

              leaf in-v4truncateds {
                description 'IPv4 Truncated count received' ;
                type uint64 ;

              }

              leaf in-v4bcasts {
                description 'IPv4 Bcast count received' ;
                type uint64 ;

              }

              leaf in-v4noroutes {
                description 'IPv4 NoRoute count received' ;
                type uint64 ;

              }

              leaf in-v4unknownprotos {
                description 'IPv4 unknown protol count received' ;
                type uint64 ;

              }

              leaf in-v4discards {
                description 'IPv4 dropped frames received' ;
                type uint64 ;

              }

              leaf in-v4forwdatagrams {
                description 'IPv4 ForwDatagram count received' ;
                type uint64 ;

              }

              leaf in-v6hdrerrors {
                description 'IPv6 HdrError count received' ;
                type uint64 ;

              }

              leaf in-v6truncateds {
                description 'IPv6 Truncated count received' ;
                type uint64 ;

              }

              leaf in-v6addrerrors {
                description 'IPv6 AddrError count received' ;
                type uint64 ;

              }

              leaf in-v6bcasts {
                description 'IPv6 Bcast count received' ;
                type uint64 ;

              }

              leaf in-v6noroutes {
                description 'IPv6 NoRoute count received' ;
                type uint64 ;

              }

              leaf in-v6unknownprotos {
                description 'IPv6 unknown protol count received' ;
                type uint64 ;

              }

              leaf in-v6discards {
                description 'IPv6 dropped frames received' ;
                type uint64 ;

              }

              leaf in-v6forwdatagrams {
                description 'IPv6 ForwDatagram count received' ;
                type uint64 ;

              }

              leaf e-v4discards {
                description 'IPv4 dropped frames sent' ;
                type uint64 ;

              }

              leaf e-v4forwdatagrams {
                description 'IPv4 ForwDatagram count sent' ;
                type uint64 ;

              }

              leaf e-v4fragreqds {
                description 'IPv4 FragReqd count sent' ;
                type uint64 ;

              }

              leaf e-v6discards {
                description 'IPv6 dropped frames sent' ;
                type uint64 ;

              }

              leaf e-v6forwdatagrams {
                description 'IPv6 ForwDatagram count sent' ;
                type uint64 ;

              }

              leaf e-v6fragreqds {
                description 'IPv6 FragReqd count sent' ;
                type uint64 ;

              }

              leaf in-multicastpkts {
                description 'Total multicast packets received' ;
                type uint64 ;

              }

              leaf in-broadcastpkts {
                description 'Total broadcast packets received' ;
                type uint64 ;

              }

              leaf e-multicastpkts {
                description 'Total multicast packets sent' ;
                type uint64 ;

              }

              leaf e-broadcastpkts {
                description 'Total broadcast packets sent' ;
                type uint64 ;

              }

              leaf e-upsendcar-drop {
                description 'Upsend-car discard packets sent' ;
                type uint64 ;

              }

              leaf in-urpf-v4drppkts {
                description 'URPF V4 discards packets received' ;
                type uint64 ;

              }

              leaf in-urpf-v6drppkts {
                description 'URPF V6 discards packets received' ;
                type uint64 ;

              }

              leaf in-upsendcarpkts {
                description 'Upsend-car packets received' ;
                type uint64 ;

                ncd:revise-date 2022-09-19 ;
              }

            }

            container pvcgroup-statisitc {
              description "Describe the data nodes for the operational state of statistics whose checkpoint is PVCGROUP.These performace items are calculated by platform with the items of pvcgroup-port's members." ;
              leaf in-bytes {
                description 'Total bytes received' ;
                type uint64 ;

              }

              leaf in-packets {
                description 'Total packets received' ;
                type uint64 ;

              }

              leaf e-bytes {
                description 'Total bytes sent' ;
                type uint64 ;

              }

              leaf e-packets {
                description 'Total packets sent' ;
                type uint64 ;

              }

              leaf in-discards {
                description 'Total dropped frames received for FIFO overflow' ;
                type uint64 ;

              }

              leaf e-discards {
                description 'Total dropped frames sent for FIFO overflow' ;
                type uint64 ;

              }

              leaf in-upsendcar-drop {
                description 'Upsend-car discard packets received' ;
                type uint64 ;

              }

              leaf in-v4bytes {
                description 'IPv4 bytes received' ;
                type uint64 ;

              }

              leaf in-v4pkts {
                description 'IPv4 packets received' ;
                type uint64 ;

              }

              leaf e-v4bytes {
                description 'IPv4 bytes sent' ;
                type uint64 ;

              }

              leaf e-v4pkts {
                description 'IPv4 packets sent' ;
                type uint64 ;

              }

              leaf in-v6bytes {
                description 'IPv6 bytes received' ;
                type uint64 ;

              }

              leaf in-v6pkts {
                description 'IPv6 packets received' ;
                type uint64 ;

              }

              leaf e-v6bytes {
                description 'IPv6 bytes sent' ;
                type uint64 ;

              }

              leaf e-v6pkts {
                description 'IPv6 packets sent' ;
                type uint64 ;

              }

              leaf in-multicastbytes {
                description 'Total multicast bytes received' ;
                type uint64 ;

              }

              leaf in-multicastpkts {
                description 'Total multicast packets received' ;
                type uint64 ;

              }

              leaf in-broadcastbytes {
                description 'Total broadcast bytes received' ;
                type uint64 ;

              }

              leaf in-broadcastpkts {
                description 'Total broadcast packets received' ;
                type uint64 ;

              }

              leaf e-multicastbytes {
                description 'Total multicast bytes sent' ;
                type uint64 ;

              }

              leaf e-multicastpkts {
                description 'Total multicast packets sent' ;
                type uint64 ;

              }

              leaf e-broadcastbytes {
                description 'Total broadcast bytes sent' ;
                type uint64 ;

              }

              leaf e-broadcastpkts {
                description 'Total broadcast packets sent' ;
                type uint64 ;

              }

              leaf in-upsendpkts {
                description 'Upsend packets received' ;
                type uint64 ;

              }

              leaf e-upsendpkts {
                description 'Upsend packets sent' ;
                type uint64 ;

              }

              leaf in-v4hdrerrors {
                description 'IPv4 HdrError count received' ;
                type uint64 ;

              }

              leaf in-v4addrerrors {
                description 'IPv4 AddrError count received' ;
                type uint64 ;

              }

              leaf in-v4truncateds {
                description 'IPv4 Truncated count received' ;
                type uint64 ;

              }

              leaf in-v4bcasts {
                description 'IPv4 Bcast count received' ;
                type uint64 ;

              }

              leaf in-v4noroutes {
                description 'IPv4 NoRoute count received' ;
                type uint64 ;

              }

              leaf in-v4unknownprotos {
                description 'IPv4 unknown protol count received' ;
                type uint64 ;

              }

              leaf in-v4discards {
                description 'IPv4 dropped frames received' ;
                type uint64 ;

              }

              leaf in-v4forwdatagrams {
                description 'IPv4 ForwDatagram count received' ;
                type uint64 ;

              }

              leaf in-v6hdrerrors {
                description 'IPv6 HdrError count received' ;
                type uint64 ;

              }

              leaf in-v6truncateds {
                description 'IPv6 Truncated count received' ;
                type uint64 ;

              }

              leaf in-v6addrerrors {
                description 'IPv6 AddrError count received' ;
                type uint64 ;

              }

              leaf in-v6bcasts {
                description 'IPv6 Bcast count received' ;
                type uint64 ;

              }

              leaf in-v6noroutes {
                description 'IPv6 NoRoute count received' ;
                type uint64 ;

              }

              leaf in-v6unknownprotos {
                description 'IPv6 unknown protol count received' ;
                type uint64 ;

              }

              leaf in-v6discards {
                description 'IPv6 dropped frames received' ;
                type uint64 ;

              }

              leaf in-v6forwdatagrams {
                description 'IPv6 ForwDatagram count received' ;
                type uint64 ;

              }

              leaf e-v4discards {
                description 'IPv4 dropped frames sent' ;
                type uint64 ;

              }

              leaf e-v4forwdatagrams {
                description 'IPv4 ForwDatagram count sent' ;
                type uint64 ;

              }

              leaf e-v4fragreqds {
                description 'IPv4 FragReqd count sent' ;
                type uint64 ;

              }

              leaf e-v6discards {
                description 'IPv6 dropped frames sent' ;
                type uint64 ;

              }

              leaf e-v6forwdatagrams {
                description 'IPv6 ForwDatagram count sent' ;
                type uint64 ;

              }

              leaf e-v6fragreqds {
                description 'IPv6 FragReqd count sent' ;
                type uint64 ;

              }

              leaf in-unicastbytes {
                description 'Total unicast bytes received' ;
                type uint64 ;

              }

              leaf in-unicastpkts {
                description 'Total unicast packets received' ;
                type uint64 ;

              }

              leaf in-unknownunicastbytes {
                description 'Total unknown unicast bytes received' ;
                type uint64 ;

              }

              leaf in-unknownunicastpkts {
                description 'Total unknown unicast packets received' ;
                type uint64 ;

              }

              leaf in-discbytes {
                description 'Discard bytes received' ;
                type uint64 ;

              }

              leaf e-discbytes {
                description 'Discard bytes sent' ;
                type uint64 ;

              }

              leaf e-upsendcar-drop {
                description 'Upsend-car discard packets sent' ;
                type uint64 ;

              }

              leaf in-urpf-v4drppkts {
                description 'URPF V4 discards packets received' ;
                type uint64 ;

              }

              leaf in-urpf-v6drppkts {
                description 'URPF V6 discards packets received' ;
                type uint64 ;

              }

              leaf in-byte-rate {
                description 'Total bytes received' ;
                type uint64 ;

              }

              leaf e-byte-rate {
                description 'Total bytes received' ;
                type uint64 ;

              }

              leaf in-pktsdrop {
                description 'Total packets of dropped received.' ;
                type uint64 ;

              }

              leaf in-pktserror {
                description 'Total error packets received.' ;
                type uint64 ;

              }

              leaf e-pktsdrop {
                description 'Total packets of dropped sent.' ;
                type uint64 ;

              }

              leaf e-pktserror {
                description 'Total error packets sent.' ;
                type uint64 ;

              }

              leaf in-pkts-rate {
                description 'Total packets received' ;
                type uint64 ;

              }

              leaf e-pkts-rate {
                description 'Total packets sent' ;
                type uint64 ;

              }

              ncd:revise-date 2015-05-19 ;
            }

            container null-statisitcs {
              description 'Describe the data nodes for the operational state of null-port statistics.These performace items are updated by microcode.' ;
              leaf in-bytes {
                description 'Total bytes received' ;
                type uint64 ;

              }

              leaf in-packets {
                description 'Total packets received' ;
                type uint64 ;

              }

              leaf in-discards {
                description 'Total dropped frames received for FIFO overflow' ;
                type uint64 ;

              }

              leaf in-v4bytes {
                description 'IPv4 bytes received' ;
                type uint64 ;

              }

              leaf in-v4pkts {
                description 'IPv4 packets received' ;
                type uint64 ;

              }

              leaf in-v6bytes {
                description 'IPv6 bytes received' ;
                type uint64 ;

              }

              leaf in-v6pkts {
                description 'IPv6 packets received' ;
                type uint64 ;

              }

              leaf e-bytes {
                description 'Total bytes sent' ;
                type uint64 ;

              }

              leaf e-packets {
                description 'Total packets sent' ;
                type uint64 ;

              }

              leaf e-discards {
                description 'Total dropped frames sent for FIFO overflow' ;
                type uint64 ;

              }

              leaf e-v4bytes {
                description 'IPv4 bytes sent' ;
                type uint64 ;

              }

              leaf e-v4pkts {
                description 'IPv4 packets sent' ;
                type uint64 ;

              }

              leaf e-v6bytes {
                description 'IPv6 bytes sent' ;
                type uint64 ;

              }

              leaf e-v6pkts {
                description 'IPv6 packets sent' ;
                type uint64 ;

              }

              leaf in-upsendcar-drop {
                description 'Upsend-car discard packets received' ;
                type uint64 ;

              }

              ncd:revise-date 2015-07-14 ;
            }

            container loopback-statistics {
              description 'Describe the data nodes for the operational state of loopback-port statistics.These performace items are updated by microcode.' ;
              leaf in-bytes {
                description 'Total bytes received' ;
                type uint64 ;

              }

              leaf in-packets {
                description 'Total packets received' ;
                type uint64 ;

              }

              leaf in-discards {
                description 'Total dropped frames received for FIFO overflow' ;
                type uint64 ;

              }

              leaf in-v4bytes {
                description 'IPv4 bytes received' ;
                type uint64 ;

              }

              leaf in-v4pkts {
                description 'IPv4 packets received' ;
                type uint64 ;

              }

              leaf in-v6bytes {
                description 'IPv6 bytes received' ;
                type uint64 ;

              }

              leaf in-v6pkts {
                description 'IPv6 packets received' ;
                type uint64 ;

              }

              leaf e-bytes {
                description 'Total bytes sent' ;
                type uint64 ;

              }

              leaf e-packets {
                description 'Total packets sent' ;
                type uint64 ;

              }

              leaf e-discards {
                description 'Total dropped frames sent for FIFO overflow' ;
                type uint64 ;

              }

              leaf e-v4bytes {
                description 'IPv4 bytes sent' ;
                type uint64 ;

              }

              leaf e-v4pkts {
                description 'IPv4 packets sent' ;
                type uint64 ;

              }

              leaf e-v6bytes {
                description 'IPv6 bytes sent' ;
                type uint64 ;

              }

              leaf e-v6pkts {
                description 'IPv6 packets sent' ;
                type uint64 ;

              }

              leaf in-upsendcar-drop {
                description 'Upsend-car discard packets received' ;
                type uint64 ;

              }

              ncd:revise-date 2015-07-14 ;
            }

            container vxlantunnel-statistics {
              description 'Describe the data nodes for the operational state of vxlan-tunnel statistics.These performace items are updated by microcode.' ;
              leaf in-bytes {
                description 'Total bytes received' ;
                type uint64 ;

              }

              leaf in-packets {
                description 'Total packets received' ;
                type uint64 ;

              }

              leaf e-bytes {
                description 'Total bytes sent' ;
                type uint64 ;

              }

              leaf e-packets {
                description 'Total packets sent' ;
                type uint64 ;

              }

              leaf in-discbytes {
                description 'Total dropped bytes received for FIFO overflow' ;
                type uint64 ;

              }

              leaf in-discpkts {
                description 'Total dropped packets received for FIFO overflow' ;
                type uint64 ;

              }

              leaf e-discbytes {
                description 'Total dropped bytes sent for FIFO overflow' ;
                type uint64 ;

              }

              leaf e-discpkts {
                description 'Total dropped packets sent for FIFO overflow' ;
                type uint64 ;

              }

              ncd:revise-date 2015-08-27 ;
            }

            container spi-statistics {
              description 'Describe the data nodes for the operational state of spi-port statistics.These performace items are updated by microcode.' ;
              leaf in-bytes {
                description 'Total bytes received' ;
                type uint64 ;

              }

              leaf in-pkts {
                description 'Total packets received' ;
                type uint64 ;

              }

              leaf e-bytes {
                description 'Total bytes sent' ;
                type uint64 ;

              }

              leaf e-pkts {
                description 'Total packets sent' ;
                type uint64 ;

              }

              leaf in-crc-error {
                description 'Total crc-error packets received' ;
                type uint64 ;

              }

              leaf in-droppkts {
                description 'Total packets of dropped received' ;
                type uint64 ;

                ncd:revise-date 2016-09-14 ;
              }

              leaf e-droppkts {
                description 'Total packets of dropped sent' ;
                type uint64 ;

                ncd:revise-date 2016-09-14 ;
              }

              leaf in-upsendcarpkts {
                description 'Upsend-car packets received' ;
                type uint64 ;

                ncd:revise-date 2022-09-19 ;
              }

              leaf in-upsendcar-drop {
                description 'Upsend-car discard packets received' ;
                type uint64 ;

                ncd:revise-date 2022-09-19 ;
              }

              ncd:revise-date 2016-06-22 ;
            }

            container irb-statistics {
              description 'Describe the data nodes for the operational state of irb-port statistics.These performace items are updated by microcode.' ;
              leaf in-bytes {
                description 'Total bytes received' ;
                type uint64 ;

              }

              leaf in-pkts {
                description 'Total packets received' ;
                type uint64 ;

              }

              leaf e-bytes {
                description 'Total bytes sent' ;
                type uint64 ;

              }

              leaf e-pkts {
                description 'Total packets sent' ;
                type uint64 ;

              }

              leaf in-discards {
                description 'Total dropped frames received for FIFO overflow' ;
                type uint64 ;

                ncd:revise-date 2017-12-19 ;
              }

              leaf in-upsendcar-drop {
                description 'Upsend-car discard packets received' ;
                type uint64 ;

                ncd:revise-date 2017-12-19 ;
              }

              leaf in-v4bytes {
                description 'IPv4 bytes received' ;
                type uint64 ;

                ncd:revise-date 2017-12-19 ;
              }

              leaf in-v4pkts {
                description 'IPv4 packets received' ;
                type uint64 ;

                ncd:revise-date 2017-12-19 ;
              }

              leaf in-v6bytes {
                description 'IPv6 bytes received' ;
                type uint64 ;

                ncd:revise-date 2017-12-19 ;
              }

              leaf in-v6pkts {
                description 'IPv6 packets received' ;
                type uint64 ;

                ncd:revise-date 2017-12-19 ;
              }

              leaf in-multicastbytes {
                description 'Total multicast bytes received' ;
                type uint64 ;

                ncd:revise-date 2017-12-19 ;
              }

              leaf in-multicastpkts {
                description 'Total multicast packets received' ;
                type uint64 ;

                ncd:revise-date 2017-12-19 ;
              }

              leaf in-broadcastbytes {
                description 'Total broadcast bytes received' ;
                type uint64 ;

                ncd:revise-date 2017-12-19 ;
              }

              leaf in-broadcastpkts {
                description 'Total broadcast packets received' ;
                type uint64 ;

                ncd:revise-date 2017-12-19 ;
              }

              leaf in-urpf-v4drppkts {
                description 'URPF V4 discards packets received' ;
                type uint64 ;

                ncd:revise-date 2017-12-19 ;
              }

              leaf in-urpf-v6drppkts {
                description 'URPF V6 discards packets received' ;
                type uint64 ;

                ncd:revise-date 2017-12-19 ;
              }

              leaf e-discards {
                description 'Total dropped frames sent for FIFO overflow' ;
                type uint64 ;

                ncd:revise-date 2017-12-19 ;
              }

              leaf e-v4bytes {
                description 'IPv4 bytes sent' ;
                type uint64 ;

                ncd:revise-date 2017-12-19 ;
              }

              leaf e-v4pkts {
                description 'IPv4 packets sent' ;
                type uint64 ;

                ncd:revise-date 2017-12-19 ;
              }

              leaf e-v6bytes {
                description 'IPv6 bytes sent' ;
                type uint64 ;

                ncd:revise-date 2017-12-19 ;
              }

              leaf e-v6pkts {
                description 'IPv6 packets sent' ;
                type uint64 ;

                ncd:revise-date 2017-12-19 ;
              }

              leaf e-multicastbytes {
                description 'Total multicast bytes sent' ;
                type uint64 ;

                ncd:revise-date 2017-12-19 ;
              }

              leaf e-multicastpkts {
                description 'Total multicast packets sent' ;
                type uint64 ;

                ncd:revise-date 2017-12-19 ;
              }

              leaf e-broadcastbytes {
                description 'Total broadcast bytes sent' ;
                type uint64 ;

                ncd:revise-date 2017-12-19 ;
              }

              leaf e-broadcastpkts {
                description 'Total broadcast packets sent' ;
                type uint64 ;

                ncd:revise-date 2017-12-19 ;
              }

              leaf e-upsendcar-drop {
                description 'Upsend-car discard packets sent' ;
                type uint64 ;

                ncd:revise-date 2017-12-19 ;
              }

              leaf in-upsendcarpkts {
                description 'Upsend-car packets received' ;
                type uint64 ;

                ncd:revise-date 2022-09-19 ;
              }

              ncd:revise-date 2016-08-28 ;
            }

            container svi-statistics {
              leaf in-bytes {
                description 'Total bytes received' ;
                type uint64 ;

              }

              leaf in-pkts {
                description 'Total packets received' ;
                type uint64 ;

              }

              leaf e-bytes {
                description 'Total bytes sent' ;
                type uint64 ;

              }

              leaf e-pkts {
                description 'Total packets sent' ;
                type uint64 ;

              }

              ncd:revise-date 2016-11-23 ;
            }

            container tegtunnel-statistics {
              description 'Describe the data nodes for the operational state of te_gtunnel statistics.These performace items are updated by microcode.' ;
              leaf in-bytes {
                description 'Total bytes received' ;
                type uint64 ;

              }

              leaf in-packets {
                description 'Total packets received' ;
                type uint64 ;

              }

              leaf e-bytes {
                description 'Total bytes sent' ;
                type uint64 ;

              }

              leaf e-packets {
                description 'Total packets sent' ;
                type uint64 ;

              }

              leaf in-discards {
                description 'Total dropped frames received for FIFO overflow' ;
                type uint64 ;

              }

              leaf e-discards {
                description 'Total dropped frames sent for FIFO overflow' ;
                type uint64 ;

              }

              leaf in-upsendcar-drop {
                description 'Upsend-car discard packets received' ;
                type uint64 ;

              }

              leaf in-v4bytes {
                description 'IPv4 bytes received' ;
                type uint64 ;

              }

              leaf in-v4pkts {
                description 'IPv4 packets received' ;
                type uint64 ;

              }

              leaf e-v4bytes {
                description 'IPv4 bytes sent' ;
                type uint64 ;

              }

              leaf e-v4pkts {
                description 'IPv4 packets sent' ;
                type uint64 ;

              }

              leaf in-v6bytes {
                description 'IPv6 bytes received' ;
                type uint64 ;

              }

              leaf in-v6pkts {
                description 'IPv6 packets received' ;
                type uint64 ;

              }

              leaf e-v6bytes {
                description 'IPv6 bytes sent' ;
                type uint64 ;

              }

              leaf e-v6pkts {
                description 'IPv6 packets sent' ;
                type uint64 ;

              }

              leaf in-multicastbytes {
                description 'Total multicast bytes received' ;
                type uint64 ;

              }

              leaf in-multicastpkts {
                description 'Total multicast packets received' ;
                type uint64 ;

              }

              leaf in-broadcastbytes {
                description 'Total broadcast bytes received' ;
                type uint64 ;

              }

              leaf in-broadcastpkts {
                description 'Total broadcast packets received' ;
                type uint64 ;

              }

              leaf e-multicastbytes {
                description 'Total multicast bytes sent' ;
                type uint64 ;

              }

              leaf e-multicastpkts {
                description 'Total multicast packets sent' ;
                type uint64 ;

              }

              leaf e-broadcastbytes {
                description 'Total broadcast bytes sent' ;
                type uint64 ;

              }

              leaf e-broadcastpkts {
                description 'Total broadcast packets sent' ;
                type uint64 ;

              }

              leaf in-upsendpkts {
                description 'Upsend packets received' ;
                type uint64 ;

              }

              leaf e-upsendpkts {
                description 'Upsend packets sent' ;
                type uint64 ;

              }

              leaf in-v4hdrerrors {
                description 'IPv4 HdrError count received' ;
                type uint64 ;

              }

              leaf in-v4addrerrors {
                description 'IPv4 AddrError count received' ;
                type uint64 ;

              }

              leaf in-v4truncateds {
                description 'IPv4 Truncated count received' ;
                type uint64 ;

              }

              leaf in-v4bcasts {
                description 'IPv4 Bcast count received' ;
                type uint64 ;

              }

              leaf in-v4noroutes {
                description 'IPv4 NoRoute count received' ;
                type uint64 ;

              }

              leaf in-v4unknownprotos {
                description 'IPv4 Unknown protol count received' ;
                type uint64 ;

              }

              leaf in-v4discards {
                description 'IPv4 dropped frames received' ;
                type uint64 ;

              }

              leaf in-v4forwdatagrams {
                description 'IPv4 ForwDatagram count received' ;
                type uint64 ;

              }

              leaf in-v6hdrerrors {
                description 'IPv6 HdrError count received' ;
                type uint64 ;

              }

              leaf in-v6truncateds {
                description 'IPv6 Truncated count received' ;
                type uint64 ;

              }

              leaf in-v6addrerrors {
                description 'IPv6 AddrError count received' ;
                type uint64 ;

              }

              leaf in-v6bcasts {
                description 'IPv6 Bcast count received' ;
                type uint64 ;

              }

              leaf in-v6noroutes {
                description 'IPv6 NoRoute count received' ;
                type uint64 ;

              }

              leaf in-v6unknownprotos {
                description 'IPv6 Unknown protol count received' ;
                type uint64 ;

              }

              leaf in-v6discards {
                description 'IPv6 dropped frames received' ;
                type uint64 ;

              }

              leaf in-v6forwdatagrams {
                description 'IPv6 ForwDatagram count received' ;
                type uint64 ;

              }

              leaf e-v4discards {
                description 'IPv4 dropped frames sent' ;
                type uint64 ;

              }

              leaf e-v4forwdatagrams {
                description 'IPv4 ForwDatagram count sent' ;
                type uint64 ;

              }

              leaf e-v4fragreqds {
                description 'IPv4 FragReqd count sent' ;
                type uint64 ;

              }

              leaf e-v6discards {
                description 'IPv6 dropped frames sent' ;
                type uint64 ;

              }

              leaf e-v6forwdatagrams {
                description 'IPv6 ForwDatagram count sent' ;
                type uint64 ;

              }

              leaf e-v6fragreqds {
                description 'IPv6 FragReqd count sent' ;
                type uint64 ;

              }

              leaf in-unicastbytes {
                description 'Total unicast bytes received' ;
                type uint64 ;

              }

              leaf in-unicastpkts {
                description 'Total unicast packets received' ;
                type uint64 ;

              }

              leaf in-unknownunicastbytes {
                description 'Total unknow unicast bytes received' ;
                type uint64 ;

              }

              leaf in-unknownunicastpkts {
                description 'Total unknow unicast packets received' ;
                type uint64 ;

              }

              leaf in-discbytes {
                description 'Discard bytes received' ;
                type uint64 ;

              }

              leaf e-discbytes {
                description 'Discard bytes sent' ;
                type uint64 ;

              }

              leaf e-upsendcar-drop {
                description 'Upsend-car discard packets sent' ;
                type uint64 ;

              }

              leaf in-urpf-v4drppkts {
                description 'URPF V4 discards packets received' ;
                type uint64 ;

              }

              leaf in-urpf-v6drppkts {
                description 'URPF V6 discards packets received' ;
                type uint64 ;

              }

              leaf in-pktsdrop {
                description 'Total packets of dropped received.' ;
                type uint64 ;

              }

              leaf in-pktserror {
                description 'Total error packets received.' ;
                type uint64 ;

              }

              leaf e-pktsdrop {
                description 'Total packets of dropped sent.' ;
                type uint64 ;

              }

              leaf e-pktserror {
                description 'Total error packets sent.' ;
                type uint64 ;

              }

              ncd:revise-date 2016-12-13 ;
            }

            container gtunnelgroup-statistics {
              description 'Describe the data nodes for the operational state of gtunnelgroup statistics.' ;
              leaf in-bytes {
                description 'Total bytes received' ;
                type uint64 ;

              }

              leaf in-packets {
                description 'Total packets received' ;
                type uint64 ;

              }

              leaf e-bytes {
                description 'Total bytes sent' ;
                type uint64 ;

              }

              leaf e-packets {
                description 'Total packets sent' ;
                type uint64 ;

              }

              leaf in-discards {
                description 'Total dropped frames received for FIFO overflow' ;
                type uint64 ;

              }

              leaf e-discards {
                description 'Total dropped frames sent for FIFO overflow' ;
                type uint64 ;

              }

              leaf in-upsendcar-drop {
                description 'Upsend-car discard packets received' ;
                type uint64 ;

              }

              leaf in-v4bytes {
                description 'IPv4 bytes received' ;
                type uint64 ;

              }

              leaf in-v4pkts {
                description 'IPv4 packets received' ;
                type uint64 ;

              }

              leaf e-v4bytes {
                description 'IPv4 bytes sent' ;
                type uint64 ;

              }

              leaf e-v4pkts {
                description 'IPv4 packets sent' ;
                type uint64 ;

              }

              leaf in-v6bytes {
                description 'IPv6 bytes received' ;
                type uint64 ;

              }

              leaf in-v6pkts {
                description 'IPv6 packets received' ;
                type uint64 ;

              }

              leaf e-v6bytes {
                description 'IPv6 bytes sent' ;
                type uint64 ;

              }

              leaf e-v6pkts {
                description 'IPv6 packets sent' ;
                type uint64 ;

              }

              leaf in-multicastbytes {
                description 'Total multicast bytes received' ;
                type uint64 ;

              }

              leaf in-multicastpkts {
                description 'Total multicast packets received' ;
                type uint64 ;

              }

              leaf in-broadcastbytes {
                description 'Total broadcast bytes received' ;
                type uint64 ;

              }

              leaf in-broadcastpkts {
                description 'Total broadcast packets received' ;
                type uint64 ;

              }

              leaf e-multicastbytes {
                description 'Total multicast bytes sent' ;
                type uint64 ;

              }

              leaf e-multicastpkts {
                description 'Total multicast packets sent' ;
                type uint64 ;

              }

              leaf e-broadcastbytes {
                description 'Total broadcast bytes sent' ;
                type uint64 ;

              }

              leaf e-broadcastpkts {
                description 'Total broadcast packets sent' ;
                type uint64 ;

              }

              leaf in-upsendpkts {
                description 'Upsend packets received' ;
                type uint64 ;

              }

              leaf e-upsendpkts {
                description 'Upsend packets sent' ;
                type uint64 ;

              }

              leaf in-v4hdrerrors {
                description 'IPv4 HdrError count received' ;
                type uint64 ;

              }

              leaf in-v4addrerrors {
                description 'IPv4 AddrError count received' ;
                type uint64 ;

              }

              leaf in-v4truncateds {
                description 'IPv4 Truncated count received' ;
                type uint64 ;

              }

              leaf in-v4bcasts {
                description 'IPv4 Bcast count received' ;
                type uint64 ;

              }

              leaf in-v4noroutes {
                description 'IPv4 NoRoute count received' ;
                type uint64 ;

              }

              leaf in-v4unknownprotos {
                description 'IPv4 Unknown protol count received' ;
                type uint64 ;

              }

              leaf in-v4discards {
                description 'IPv4 dropped frames received' ;
                type uint64 ;

              }

              leaf in-v4forwdatagrams {
                description 'IPv4 ForwDatagram count received' ;
                type uint64 ;

              }

              leaf in-v6hdrerrors {
                description 'IPv6 HdrError count received' ;
                type uint64 ;

              }

              leaf in-v6truncateds {
                description 'IPv6 Truncated count received' ;
                type uint64 ;

              }

              leaf in-v6addrerrors {
                description 'IPv6 AddrError count received' ;
                type uint64 ;

              }

              leaf in-v6bcasts {
                description 'IPv6 Bcast count received' ;
                type uint64 ;

              }

              leaf in-v6noroutes {
                description 'IPv6 NoRoute count received' ;
                type uint64 ;

              }

              leaf in-v6unknownprotos {
                description 'IPv6 Unknown protol count received' ;
                type uint64 ;

              }

              leaf in-v6discards {
                description 'IPv6 dropped frames received' ;
                type uint64 ;

              }

              leaf in-v6forwdatagrams {
                description 'IPv6 ForwDatagram count received' ;
                type uint64 ;

              }

              leaf e-v4discards {
                description 'IPv4 dropped frames sent' ;
                type uint64 ;

              }

              leaf e-v4forwdatagrams {
                description 'IPv4 ForwDatagram count sent' ;
                type uint64 ;

              }

              leaf e-v4fragreqds {
                description 'IPv4 FragReqd count sent' ;
                type uint64 ;

              }

              leaf e-v6discards {
                description 'IPv6 dropped frames sent' ;
                type uint64 ;

              }

              leaf e-v6forwdatagrams {
                description 'IPv6 ForwDatagram count sent' ;
                type uint64 ;

              }

              leaf e-v6fragreqds {
                description 'IPv6 FragReqd count sent' ;
                type uint64 ;

              }

              leaf in-unicastbytes {
                description 'Total unicast bytes received' ;
                type uint64 ;

              }

              leaf in-unicastpkts {
                description 'Total unicast packets received' ;
                type uint64 ;

              }

              leaf in-unknownunicastbytes {
                description 'Total unknow unicast bytes received' ;
                type uint64 ;

              }

              leaf in-unknownunicastpkts {
                description 'Total unknow unicast packets received' ;
                type uint64 ;

              }

              leaf in-discbytes {
                description 'Discard bytes received' ;
                type uint64 ;

              }

              leaf e-discbytes {
                description 'Discard bytes sent' ;
                type uint64 ;

              }

              leaf e-upsendcar-drop {
                description 'Upsend-car discard packets sent' ;
                type uint64 ;

              }

              leaf in-urpf-v4drppkts {
                description 'URPF V4 discards packets received' ;
                type uint64 ;

              }

              leaf in-urpf-v6drppkts {
                description 'URPF V6 discards packets received' ;
                type uint64 ;

              }

              leaf in-pktsdrop {
                description 'Total packets of dropped received.' ;
                type uint64 ;

              }

              leaf in-pktserror {
                description 'Total error packets received.' ;
                type uint64 ;

              }

              leaf e-pktsdrop {
                description 'Total packets of dropped sent.' ;
                type uint64 ;

              }

              leaf e-pktserror {
                description 'Total error packets sent.' ;
                type uint64 ;

              }

              ncd:revise-date 2016-12-13 ;
            }

            container ipsectunnel-statistics {
              description 'Describe the data nodes for the operational state of ipsec-tunnel statistics.These performace items are updated by microcode.' ;
              leaf in-bytes {
                description 'Total bytes received' ;
                type uint64 ;

              }

              leaf in-packets {
                description 'Total packets received' ;
                type uint64 ;

              }

              leaf e-bytes {
                description 'Total bytes sent' ;
                type uint64 ;

              }

              leaf e-packets {
                description 'Total packets sent' ;
                type uint64 ;

              }

              leaf in-discbytes {
                description 'Discard bytes received' ;
                type uint64 ;

              }

              leaf in-discpkts {
                description 'Discard packets received' ;
                type uint64 ;

              }

              leaf e-discbytes {
                description 'Discard bytes sent' ;
                type uint64 ;

              }

              leaf e-discpkts {
                description 'Discard packets sent' ;
                type uint64 ;

              }

              ncd:revise-date 2018-09-13 ;
            }

          }

          container defque-counters {
            description 'Describe the data nodes for the default queue detection point.' ;
            container ethdefque-statistics {
              description 'Describe the data nodes for the default queue detection point of ether interface.' ;
              leaf in-bytes-tm {
                description 'Total bytes received' ;
                type uint64 ;

              }

              leaf in-pkts-tm {
                description 'Total packets received' ;
                type uint64 ;

              }

              leaf in-dropbytes-tm {
                description 'Total bytes of dropped received' ;
                type uint64 ;

              }

              leaf in-droppkts-tm {
                description 'Total packets of dropped received' ;
                type uint64 ;

              }

              leaf e-bytes-tm {
                description 'Total bytes sent' ;
                type uint64 ;

              }

              leaf e-pkts-tm {
                description 'Total packets sent' ;
                type uint64 ;

              }

              leaf e-dropbytes-tm {
                description 'Total bytes of dropped sent' ;
                type uint64 ;

              }

              leaf e-droppkts-tm {
                description 'Total packets of dropped sent' ;
                type uint64 ;

              }

            }

            ncd:revise-date 2021-01-14 ;
          }

        }

        leaf type {
          description 'The type of the interface.' ;
          type uint16 ;

          ncd:revise-date 2020-10-16 ;
        }

      }

      list logic-interface-summary {
        description 'Show logic interface information' ;
        key name ;
        leaf name {
          description 'The name of the logic interface.

This leaf MAY be mapped to ifName by an implementation. Such an implementation MUST restrict the values for this leaf so that it matches the restrictions of ifName.' ;
          type ncd:string-all {
            length 1..31 ;

          }

        }

        leaf number {
          description 'The number of logic interface' ;
          type uint32 {
            range 0..99999999 ;

          }

        }

        leaf config-limited-number {
          if-feature config-limited-number ;

          description 'The configuration limited number of logic interface.' ;
          type uint32 ;

          ncd:revise-date 2019-04-30 ;
        }

      }

    }

    container vrfs {
      list vrf {
        leaf vrf-name {
          type leafref {
            path "/configuration/interfaces/interface-configuration/interface/vrf/ip-vrf-forwarding" ;
          }

          description 'The name of the VRF' ;
        }

        container interfaces {
          list interface {
            leaf name {
              type leafref {
                path "/configuration/interfaces/interface-configuration/interface/name" ;
              }

              description 'The name of the interface.

This leaf MAY be mapped to ifName by an implementation. Such an implementation MUST restrict the values for this leaf so that it matches the restrictions of ifName.' ;
            }

            key name ;
            description 'The list of interfaces under this VRF' ;
          }

          description 'Describe the data nodes for the state of interfaces under this VRF.' ;
        }

        key vrf-name ;
        description 'The list of VRFs with interfaces' ;
      }

      description 'Describe the data nodes for the operational state of VRFs with interfaces.' ;
      ncd:revise-date 2023-08-16 ;
    }

  }

  container operation {
    config false ;
    description 'Describe the operation nodes of interfaces.' ;
    container interfaces {
      description 'Describe the operation nodes of interfaces.' ;
      container interface-statistics {
        description 'Describe the operation nodes of interface statistics.' ;
        leaf clear-one-minute-peak-all {
          if-feature one-minute-peak ;

          description 'The operation nodes for clear the one-minute-peak-value of all eth-port.' ;
          type enumeration {
            enum all {
              value 255 ;
            }

          }

        }

        leaf clear-interface-statistics-all {
          description 'The operation nodes for clear the performace items value of all interfaces.' ;
          type enumeration {
            enum all {
              value 255 ;
            }

          }

        }

        container clear {
          description 'Describe the operation nodes for clear statistcs.' ;
          list one-minute-peak {
            if-feature one-minute-peak ;

            description 'The operation nodes for clear the one-minute-peak-value of single eth-port.' ;
            key name ;
            leaf name {
              description 'The name of ether interfaces.' ;
              type leafref {
                path "/configuration/interfaces/interface-configuration/interface/name" ;
              }

            }

          }

          list interface-statistics {
            description 'The operation nodes for clear the performace items value of single interfaces.' ;
            key name ;
            leaf name {
              description 'The name of interface which supports traffic statistics.' ;
              type leafref {
                path "/configuration/interfaces/interface-configuration/interface/name" ;
              }

            }

          }

        }

      }

    }

  }

}
