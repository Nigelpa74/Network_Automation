module zxr10-dhcp {
  namespace "http://www.zte.com.cn/zxr10/netconf/schema/rosng/dhcp" ;
  prefix dhcp ;
  yang-version 1 ;
  import zxr10-netconf-defs {
    prefix ncd ;
  }

  organization "ZTE Corporation" ;
  contact "ZTE Corporation
  Nanjing Institute of ZTE Corporation
  No.68 Zijinghua Rd. Yuhuatai District, Nanjing, China
  Tel: +86-25-52870000" ;
  description 'The netconf module to describe DHCP.' ;
  revision 2025-02-26 {
    description 'Add leaf node "inter-chassis-enable" under path path "configuration/dhcp/server/global-config".' ;
  }

  revision 2024-11-18 {
    description '1.Modified some comments.
2.Add length of leaf node under path "operation/dhcp/clear-dead-server/special/ip-vrf".' ;
  }

  revision 2023-04-13 {
    description '1.Modify range of leaf node from 1~64000 to 1~12800 under path "configuration/dhcp/interfaces/interface/user-quota".
2.Modify range of leaf node from 1~8 to 1~128 under path "configuration/dhcp/relay/server-groups/server-group/servers/server/index".
3.Modify range of leaf node from 1~64000 to 1~128000 under path "configuration/dhcp/relay/global-config/max-user".
4.Modify range of leaf node from 1~64000 to 1~128000 under path "configuration/dhcp/server/global-config/max-user".' ;
  }

  revision 2022-09-21 {
    description '1.Modify the leaf node named "server-group" under path "configuration/dhcp/relay/interfaces/interface".
2.Modify the leaf node named "group-no" under path "configuration/dhcp/relay/server-groups/server-group".
3.Modify the leaf node named "server-group-no" under path "configuration/dhcp/relay/policy-groups/policy-group".
4.Modify the leaf node named "server-group" under path "configuration/dhcp/relay/instances/instance".
5.Modify the leaf node named "server-group" under path "configuration/dhcp/interfaces/interface/relay-if".' ;
  }

  revision 2022-08-29 {
    description '1.Modify leaf node "format" under path "configuration/dhcp/relay/opt82-config".' ;
  }

  revision 2022-05-27 {
    description '1.Add container node "option93" under path "configuration/dhcp/server/policys/policy".' ;
  }

  revision 2022-05-17 {
    description '1.Add container node "option82-vendor-specifics" under path "configuration/dhcp/relay/interface-based-instances/instance".' ;
  }

  revision 2022-05-05 {
    description '1.Modify the leaf node named "server-group" under path "configuration/dhcp/relay/interfaces/interface".
2.Modify the leaf node named "group-no" under path "configuration/dhcp/relay/server-groups/server-group".
3.Modify the leaf node named "policy-no" under path "configuration/dhcp/relay/policy-groups/policy-group".
4.Modify the leaf node named "server-group-no" under path "configuration/dhcp/relay/policy-groups/policy-group".
5.Modify the leaf node named "server-group" under path "configuration/dhcp/relay/instances/instance".
6.Modify the leaf node named "server-group" under path "configuration/dhcp/interfaces/interface/relay-if".' ;
  }

  revision 2022-04-23 {
    description '1.Add leaf node "file-auto-save" under path path "configuration/dhcp/relay/global-config".' ;
  }

  revision 2022-04-01 {
    description 'Modify the leaf node named "option-code" under path "configuration/dhcp/relay/instances/relay-agent-index"' ;
  }

  revision 2022-03-10 {
    description '1.Add leaf node "packet-rate-limit" under path "configuration/dhcp/global".' ;
  }

  revision 2022-01-17 {
    description '1.Add leaf node "server-id-override" under path "configuration/dhcp/relay/interface-based-instances/instance".
2.Add container node "vss-option" under path "configuration/dhcp/relay/interface-based-instances/instance".' ;
  }

  revision 2021-10-21 {
    description '1.Add leaf node "forward-unrestrict" under path path "configuration/dhcp/interfaces/relay-if/".
2.Add leaf node "inter-chassis-enable" under path path "configuration/dhcp/relay/global-config".' ;
  }

  revision 2021-10-13 {
    description '1.Add container "bootp-cfg" under path "configuration/dhcp/server/pools/pool/".
2.Add container "file" under path "configuration/dhcp/server/pools/pool/bootp-cfg".
3.Add choice "file-data-type" under path "configuration/dhcp/server/pools/pool/bootp-cfg/file".
4.Add case "ascii" under path "configuration/dhcp/server/pools/pool/bootp-cfg/file/file-data-type".
5.Add leaf "ascii-str" under path "configuration/dhcp/server/pools/pool/bootp-cfg/file/file-data-type/ascii".
6.Add case "hex" under path "configuration/dhcp/server/pools/pool/bootp-cfg/file/file-data-type".
7.Add leaf "hex-str" under path "configuration/dhcp/server/pools/pool/bootp-cfg/file/file-data-type/hex".
8.Add container "bootp-hops-configs" under path "configuration/dhcp/relay/bootp-hops-configs".
9.Add container "bootp-flags-configs" under path "configuration/dhcp/relay/bootp-flags-configs".
10.Add container "bootp-next-server-ip-configs" under path "configuration/dhcp/relay/bootp-next-server-ip-configs".
11.Add container "bootp-sname-configs" under path "configuration/dhcp/relay/bootp-sname-configs".
12.Add container "bootp-file-configs" under path "configuration/dhcp/relay/bootp-file-configs".' ;
  }

  revision 2021-10-09 {
    description '1.del leaf "remove" under path path "configuration/dhcp/relay/pkt-end-padding-configs/pkt-end-padding-config/oper-type/remove".
2.del case "remove" under path path "configuration/dhcp/relay/pkt-end-padding-configs/pkt-end-padding-config/oper-type".' ;
  }

  revision 2021-09-06 {
    description '1.Add container "pkt-end-padding-configs" under path path "configuration/dhcp/relay/".' ;
  }

  revision 2021-07-01 {
    description '1.Modify the leaf named ascii-str under this path: configuration/dhcp/relay/policy-groups/policy-group/options/option/type/ascii/ascii-str.
2.Add leaf node "next-server-ip" under path path "configuration/dhcp/server/pools/pool/".' ;
  }

  revision 2021-05-15 {
    description '1.Add container "bootp-cfg" under path "configuration/dhcp/server/pools/pool/".
2.Add container "sname" under path "configuration/dhcp/server/pools/pool/bootp-cfg".
3.Add choice "sname-data-type" under path "configuration/dhcp/server/pools/pool/bootp-cfg/sname".
4.Add case "ascii" under path "configuration/dhcp/server/pools/pool/bootp-cfg/sname/sname-data-type".
5.Add leaf "ascii-str" under path "configuration/dhcp/server/pools/pool/bootp-cfg/sname/sname-data-type/ascii".
6.Add case "hex" under path "configuration/dhcp/server/pools/pool/bootp-cfg/sname/sname-data-type".
7.Add leaf "hex-str" under path "configuration/dhcp/server/pools/pool/bootp-cfg/sname/sname-data-type/hex".' ;
  }

  revision 2021-04-26 {
    description 'Add leaf node "broadband-user-access" under path :/configuration/dhcp/interfaces/interface' ;
  }

  revision 2021-03-31 {
    description '1.Add leaf "pkt-from-sib-check-master" under path "configuration/dhcp/relay/global-config/pkt-from-sib-check-master".' ;
  }

  revision 2020-12-01 {
    description '1.Add container "option-templates" under path "configuration/dhcp/global/option-templates".
2.Add leaf "option-template" under path "configuration/dhcp/server/pools/poo/static-pool-conf/static-pool-vrfs/static-pool-vrf/option-template".
3.Add leaf "option-template" under path "configuration/dhcp/server/pools/poo/static-pool-conf/static-pools/static-pool/option-template".' ;
  }

  revision 2020-11-26 {
    description '1.Add container "authen-templates" under path:/configuration/dhcp/global.
2.Add leaf named "authen-template-name" under path:/configuration/dhcp/relay/interface-based-instances/instance.
3.Add leaf named "authen-template-name" under path:/configuration/dhcp/server/interface-based-instances/instance.' ;
  }

  revision 2020-08-20 {
    description 'Add leaf node named "user-interact" under path:configuration/dhcp/global.' ;
  }

  revision 2020-07-20 {
    description 'Add leaf node named "non-online-user-mismatched-option54-delete" under path:configuration/dhcp/global' ;
  }

  revision 2020-07-06 {
    description 'Add leaf node "reserved-vrf-name" under path "configuration/dhcp/server/policys/policy/reserved-vrf-name".' ;
  }

  revision 2020-07-02 {
    description 'Add leaf node "forward-release-unrestrict" under path "configuration/dhcp/relay/global-config".' ;
  }

  revision 2020-07-01 {
    description 'Modify the leaf named operate-policy under this path: configuration/dhcp/relay/opt82-config.' ;
  }

  revision 2020-06-09 {
    description '1)Add container node "interface-based-instances" under this path:/configuration/dhcp/relay/interface-based-instances;
2)Add container node "interface-based-instances" under this path:/configuration/dhcp/server/interface-based-instances;
3)Add leaf node "bind-relay-instance" under this path:/configuration/dhcp/interfaces/interface/relay-if;
4)Add leaf node "bind-server-instance" under this path:/configuration/dhcp/interfaces/interface/server-if;' ;
  }

  revision 2020-06-08 {
    description '1.Extend the range of leaf "pool-name" under this path:/configuration/dhcp/server/policys/policy/pool-name.
2.Extend the range of leaf "name" under this path:/configuration/dhcp/server/pools/pool/name.
3.Extend the range of leaf "ippool-name" under this path:/configuration/dhcp/server/pools/pool/ippool-name.
4.Extend the range of leaf "pool-name" under this path:/configuration/dhcp/server/instances/instance/pool-name.' ;
  }

  revision 2020-01-19 {
    description 'Add container named "suppress-packet" under path:/configuration/dhcp/global.' ;
  }

  revision 2019-12-24 {
    description 'Add leaf named "online-user-reonline-suppression-time" under path:/configuration/dhcp/global.' ;
  }

  revision 2019-11-19 {
    description 'Add container named "option-configs" and leafs under path:/configuration/dhcp/relay.
Add container named "leasetime-configs" and leafs under path:/configuration/dhcp/relay.' ;
  }

  revision 2019-05-23 {
    description 'Add container named "user-connect-statistics" and leafs under path:/state/dhcp/relay.' ;
  }

  revision 2019-04-18 {
    description '1.Add leaf named "user-identifier-format" under path:/configuration/dhcp/global/user-identifier-format.' ;
  }

  revision 2019-04-03 {
    description 'Add leaf named "cos" under path:/configuration/dhcp/relay/server-groups/server-group.' ;
  }

  revision 2019-03-05 {
    description 'Add container named "packet" and leafs under path:/configuration/dhcp/relay/instances/instance.
Add container named "packet" and leafs under path:/configuration/dhcp/interfaces/interface/relay-if/packet.' ;
  }

  revision 2019-01-18 {
    description 'Add container named "online-user-forward-algorithm" and leafs under path:/configuration/dhcp/relay/server-groups/server-group.' ;
  }

  revision 2019-01-17 {
    description '1.Add lead named "relay-agent-mask" under this path: /configuration/dhcp/relay/instances/instance/relay-agent-mask.' ;
  }

  revision 2018-12-25 {
    description '1.Add case named "from-request-packet" under path:/configuration/dhcp/server/pools/pool/options-conf/options/option/type.' ;
  }

  revision 2018-10-08 {
    description '1.Obsolete container named "arp-detect" and leafs under this path: /configuration/dhcp/interfaces/interface/server-if/.
2.Obsolete feature "arp-detect".
3.Add container named "detect-client-IP" and leafs under this path: /configuration/dhcp/interfaces/interface/server-if/.
4.Add feature "detect-client-ip".' ;
  }

  revision 2018-06-30 {
    description '1.Extend the range of leaf "retry" under this path:/configuration/dhcp/relay/server-groups/server-group/retry.
2.Modify the description of leaf "retry" under this path:/configuration/dhcp/relay/server-groups/server-group/retry.' ;
  }

  revision 2018-04-11 {
    description '1.Add container named "arp-detect" and leafs under this path: /configuration/dhcp/interfaces/interface/server-if/.
2.Modify the description of leafs "lease-time" under the path:/state/dhcp/relay/relay-user/detail/lease-time,and /state/dhcp/server/server-user/detail/lease-time.' ;
  }

  revision 2018-03-23 {
    description "1.Add leaf named 'nak-client-offline' under this path:/configuration/dhcp/interfaces/interface/server-if/.
    2.Add leaf named 'nak-client-offline' under this path:/configuration/dhcp/server/instances/instance/." ;
  }

  revision 2018-01-22 {
    description '1.Add leaf node named "lease-seconds" under the path :/configuration/dhcp/server/pools/pool/leasetime/type/finite/lease-item' ;
  }

  revision 2017-12-26 {
    description '1.Modify the leaf node dead-time under this path:/configuration/dhcp/relay/server-groups/server-group/dead-time, modify the range from 0 to 3600.
2.Modify the leaf node max-timeout under this path:/configuration/dhcp/relay/server-groups/server-group/max-timeout, modify the range from 0 to 255 and add default value 
10.' ;
  }

  revision 2017-10-09 {
    description '1.Remove mandary of leaf node option-code,under path /configuration/dhcp/interfaces/interface/relay-if/relay-agent-indexs/relay-agent-index/option-code.' ;
  }

  revision 2017-08-14 {
    description '1.Add enum value vendor-specific under path /configuration/dhcp/client/policys/policy/request-lists/request-list/req-opt-code' ;
  }

  revision 2017-01-12 {
    description "1.Remove leaf node named 'instance-no',and add a leaf node named 'instance-name' under the path:/configuration/dhcp/relay/instances/instance.
    2.Remove leaf node named 'instance-no',and add a leaf node named 'instance-name' under the path:/configuration/dhcp/server/instances/instance.
    3.Modify the description of some leaf nodes." ;
  }

  revision 2016-12-20 {
    description '1.Add leaf node named "check-option82" under path:/configuration/dhcp/global.
2.Add leaf node named "log" under path:/configuration/dhcp/global.
3.Add leaf node named "force-reply-broadcast" under path:/configuration/dhcp/global.
4.Add container named "vxlan-config" and leafs under this container,under path:/configuration/dhcp/global.
5.Add container named "options" and leafs under this container,under path:/configuration/dhcp/relay/policy-groups/policy-group.
6.Add leaf node named "max-timeout" under path:/configuration/dhcp/relay/server-groups/server-group.
7.Add leaf node named "check-server-packet" under path:/configuration/dhcp/relay/global-config.
8.Add leaf node named "client-write" under path:/configuration/dhcp/client/global-config.
9.Add container and leafs named "dead-server" under path:/state/dhcp/relay.' ;
  }

  revision 2016-12-06 {
    description '1.Add choice node named "vpn" under path:/configuration/dhcp/relay/server-groups/server-group/servers/server.
2.Add case node named "public" under path:/configuration/dhcp/relay/server-groups/server-group/servers/server/vpn.
3.Add case node named "vrf" under path:/configuration/dhcp/relay/server-groups/server-group/servers/server/vpn.
4.Move leaf node named "public" from path:/configuration/dhcp/relay/server-groups/server-group/servers/server to path:/configuration/dhcp/relay/server-groups/server-group/servers/server/vpn/public.
5.Add leaf node named "vrf-name" under path:/configuration/dhcp/relay/server-groups/server-group/servers/server/vpn/vrf.' ;
  }

  revision 2016-11-17 {
    description '1.Add leaf named "public" under  path:/configuration/dhcp/relay/server-groups/server-group/servers/server.' ;
  }

  revision 2016-09-20 {
    description '1.Add container named instances and leafs under  path:/configuration/dhcp/relay.
2.Add container named instances and leafs under  path:/configuration/dhcp/server.' ;
  }

  revision 2016-08-22 {
    description '1)Add option125-conf container: \configuration\dhcp\server\pools\pool.' ;
  }

  revision 2016-07-04 {
    description '1.Add notification named relay-user-report.
2.Add leaf node "report-user-info" under this path:/configuration/dhcp/relay/global-config/report-user-info.' ;
  }

  revision 2016-03-14 {
    description '1.Add container named upgrade-leastime under this path:/configuration/dhcp/global/upgrade-leasetime.' ;
  }

  revision 2016-01-28 {
    description '1.Add server list container "server-list"under this path ://configuration/dhcp/interfaces/interface/relay-if/.
2.Modify description of leaf node "dscp",path is ://configuration/dhcp/interfaces/interface/server-if/dscp,and path ://configuration:/dhcp/server/interfaces/interface/dscp,and path://configuration:/dhcp/relay/server-groups/server-group/servers/server/dscp.
3.Modify description of leaf node "rule-no",the path is ://configuration/dhcp/access-lists/access-list/rules/rule/rule-no.' ;
  }

  revision 2016-01-05 {
    description '1.Add leaf node named "ignore-request-list" under this path:/configuration/dhcp/server/pools/pool/ignore-request-list.' ;
  }

  revision 2015-12-22 {
    description "1.Add a leaf node named 'host-name' under this path:/configuration/dhcp/client/policys/policy,the string length of this leaf is 1 to 64." ;
  }

  revision 2015-10-21 {
    description '1.Modify the leaf node mask-len under this path:/configuration/dhcp/server/pools/pool/opt212-6rd/mask-len, add the range from 0 to 32.
2.Modify the leaf node dns under this path:/configuration/dhcp/server/pools/pool/import/dns, modify the enum description.
3.Modify the leaf node keep-opt82 under this path:/configuration/dhcp/server/global-config/keep-opt82, modify the enum description.' ;
  }

  revision 2015-08-11 {
    description 'Modify the config from true to false under the state and operation containers.' ;
  }

  revision 2015-06-18 {
    description '1.Modify the sequence of leaf nodes in-vlan-range and ex-vlan-range, under this path :/configuration/relay/policy-groups/policy-group/policy-vlans/policy-vlan,after adjustment,ex-vlan-range before in-vlan-range.' ;
  }

  revision 2015-02-12 {
    description '1.Add container named option-content under this path:/configuration/dhcp/interfaces/interface/relay-if/relay-agent-indexs/relay-agent-index,and move two leaf node option-type and option-text under this new container.Change the mandatory of two leaf node option-type and option-text from false to true.
2.Modify the leaf node reply-all under this path:/state/dhcp/global/packet-statistics/packet-statistic/reply-all,change the type from string to uint32.
3.Modify the leaf node dscp under this path:/configuration/dhcp/interfaces/interface/server-if/dscp, remove the default value 0 and add reset value 63. The same operation is to the leaf node dscp under the path:/configuration/dhcp/relay/server-groups/server-group/servers/server/dscp.
4.Modify the leaf node forward-mode under this path:/configuration/dhcp/relay/server-groups/server-group/servers/server,change the mandatory from true to false.
5.Create container named options-conf under this path:/configuration/dhcp/server/pools/pool/,change the name of options to sub-options, and move it under containor options-conf,and create a new container named options under options-conf.Modify the sub-options container,change the mandatory of two leaf node ascii-str and hex-str from false to true.
6.Modify the leaf node under this path:/configuration/dhcp/client/policys/policy/name, add the string length is 1..16,and add description.
7.Modify the leaf node under this path:/configuration/dhcp/client/global-config/client-policy, add the string length is 1..16,and add description.
8.Add leaf node named default-router-priority under this path:/configuration/dhcp/interfaces/interface/client-if/.
9.Add two leaf nodes named local-server and verify-server-id under this path:path:/configuration/dhcp/relay/server-groups/server-group.' ;
  }

  revision 2015-01-20 {
    description '1.Add forward-mode leaf under relay-if container.
2.Modify the choice node of this path:\configuration\dhcp\client\policys\policy\options\option\type, and two leaf nodes ascii-string and hex-string under this node, change the mandatory of these nodes from false to true.' ;
  }

  revision 2014-12-02 {
    description '1.Add relay-if container: \configuration\dhcp\interfaces\interface\relay-if.
2.Add server-if container: \configuration\dhcp\interfaces\interface\server-if.
3.Add client-if container: \configuration\dhcp\interfaces\interface\client-if.' ;
  }

  revision 2014-07-30 {
    description '1.Create a container named relay-agent-indexs under relay interfaces, which contains DHCP relay agent index configuration.' ;
  }

  revision 2014-03-20 {
    description '1.Add perf-para for some nodes which need.
2.Add hidden-para for some nodes which need.
3.Create a leasetime container which contains DHCP pool leasetime configuration.
4.Create a import container which contains DHCP pool import configuration.
5.Create a static-pool-vrf list which contains DHCP static pool with vrf configuration.
6.Add leaf node total-user of relay-user.
7.Add selects "interface" for detail of relay-user.
8.Add leaf node total-user of server-user.
9.Add selects "interface" for detail of server-user.
10.Create a type choice under option list of server instead of old leaf nodes.
11.Create a type choice under option list of client instead of old leaf nodes.
12.Change type of node expiration under client-user from ncd:datetime to ncd:string-with-  blank.
13.Change type of node ifname under client-user from ncd:ifname to string.
14.Delete mandatory true for some nodes of operation.
15.Change range of some leaf nodes.' ;
  }

  revision 2014-01-16 {
    description '1.Create a server container which contains DHCP server configuration under configuration container.
2.Create a client container which contains DHCP client configuration under configuration container.
3.create a server container which contains DHCP server state information under state container.
4.create a client container which contains DHCP client state information under state container.
5.create a global container which contains DHCP global state information under state container.
6.create a server-kick-user container under operation container.
7.create a clear-pkt-stat container under operation container.
8.create a clear-dead-server container under operation container.
9.Modify some description.' ;
  }

  revision 2014-01-14 {
    description '1.Set derivedType of string string-with-blank for nodes which support string with blank.
2.Add if-filterid for nodes related with interface.' ;
  }

  revision 2013-12-25 {
    description '1.Create a relay container and move containers relay-if-config,relay-server-groups,
relay-policy-groups,relay-global-config and relay-opt82-config to relay container.
2.Change name of containers relay-if-config to interfaces,add a leaf name and set it the key.
3.Change name of containers relay-server-groups to server-groups.
4.Change name of containers relay-policy-groups to policy-groups.
5.Change name of containers relay-global-config to global-config.
6.Change name of containers relay-opt82-config to opt82-config.
7.Set reset value or default value for some nodes which were not set.' ;
  }

  revision 2013-12-06 {
    description '1.Add leaf node fwd-unrstrctd-opt82-plcy.
2.Add leaf node board-name.
3.Delete leaf node total of relay-user.
4.Add leaf node total of detail.
5.Change type of node state from string to enumeration.
6.Delete config true for some nodes of detail.
7.Change type of node ex-vlan-range from ipv4-address to range.
8.Change length of node if-user from 1~32 to 1~31.
9.Delete mandatory true for key nodes.' ;
  }

  revision 2013-08-05 {
    description 'Initial version.' ;
  }

  feature intf-server-list {
    description 'Configure server list under DHCP interface.' ;
  }

  feature ignore-request-list {
    description 'When server send response packet,fill in option,ignore request list or not.' ;
  }

  feature vxlan-config ;

  feature check-server-packet ;

  feature arp-detect {
    status obsolete ;

  }

  feature detect-client-ip ;

  feature user-identifier-format ;

  container configuration {
    description 'Configuration.' ;
    container dhcp {
      description 'DHCP config.' ;
      container global {
        description 'DHCP global common config.' ;
        leaf enable {
          description 'Enable DHCP process.' ;
          type enumeration {
            enum disable {
              value 0 ;
              description 'DHCP disable.' ;
            }

            enum enable {
              value 1 ;
              description 'DHCP enable.' ;
            }

          }

          default disable ;
        }

        leaf ramble {
          description 'Enable DHCP user ramble.' ;
          type enumeration {
            enum ramble-off {
              value 0 ;
              description 'Turn off DHCP ramble.' ;
            }

            enum ramble-on {
              value 1 ;
              description 'Turn on DHCP ramble.' ;
            }

          }

          default ramble-off ;
        }

        leaf check-option82 {
          description 'Enable or disable check option82 in request packet.' ;
          type enumeration {
            enum off {
              value 0 ;
              description 'Turn off DHCP check option82.' ;
            }

            enum on {
              value 1 ;
              description 'Turn on DHCP check option82.' ;
            }

          }

          default off ;
          ncd:revise-date 2016-12-20 ;
        }

        leaf max-hops {
          description 'Max hops of DHCP message.[1,16].' ;
          type uint32 {
            range 1..16 ;

          }

          default 4 ;
        }

        leaf suppress-nak {
          description 'Suppress DHCPNAK message.' ;
          type enumeration {
            enum suppress-nak-off {
              value 0 ;
              description 'Turn off suppress-nak.' ;
            }

            enum suppress-nak-on {
              value 1 ;
              description 'Turn on suppress-nak.' ;
            }

          }

          default suppress-nak-off ;
        }

        leaf log {
          description 'Log on or off.' ;
          type enumeration {
            enum off {
              value 0 ;
              description 'Turn off log.' ;
            }

            enum on {
              value 1 ;
              description 'Turn on log.' ;
            }

          }

          default off ;
          ncd:revise-date 2016-12-20 ;
        }

        leaf force-reply-broadcast {
          description 'Suppress force reply broadcast packet.' ;
          type enumeration {
            enum off {
              value 0 ;
              description 'Turn off force reply broadcast.' ;
            }

            enum on {
              value 1 ;
              description 'Turn on force reply broadcast.' ;
            }

          }

          default off ;
          ncd:revise-date 2016-12-20 ;
        }

        container upgrade-leasetime {
          description 'DHCP upgrade leasetime.' ;
          presence upgrade-leasetime ;
          leaf lease-days {
            description 'DHCP upgrade leasetime days.' ;
            type uint16 {
              range 0..365 ;

            }

            mandatory true ;
          }

          leaf lease-hours {
            description 'DHCP upgrade leasetime hours.' ;
            type uint8 {
              range 0..23 ;

            }

            mandatory true ;
          }

          leaf lease-minutes {
            description 'DHCP upgrade leasetime minutes.' ;
            type uint8 {
              range 0..59 ;

            }

            mandatory true ;
          }

          ncd:revise-date 2016-03-14 ;
        }

        container vxlan-config {
          if-feature vxlan-config ;

          description 'DHCP vxlan configuration.' ;
          list vxlan {
            description 'DHCP vxlan configuration.' ;
            key vxlan-id ;
            leaf vxlan-id {
              description 'Vxlan id.' ;
              type uint32 {
                range 1..16777215 {
                  description 'Vxlan id' ;
                }

              }

            }

            leaf interface-name {
              description 'Interface name.' ;
              type ncd:ifname {
                length 1..31 {
                  description 'The interface name length.' ;
                }

              }

              mandatory true ;
            }

          }

          ncd:revise-date 2016-12-20 ;
        }

        leaf user-identifier-format {
          if-feature user-identifier-format ;

          description 'DHCP user identifier format: [1,2], mac(1), pvlan-cvlan-port-mac(2).' ;
          type enumeration {
            enum mac {
              value 1 ;
              description 'DHCP user identifier format is mac.' ;
            }

            enum pvlan-cvlan-port-mac {
              value 2 ;
              description 'DHCP user identifier format is pvlan-cvlan-port-mac.' ;
            }

          }

          default mac ;
          ncd:revise-date 2019-04-18 ;
        }

        leaf online-user-reonline-suppression-time {
          description "Suppression time for online user re-online. Unit is seconds. It's toplimit depends on ability of the device. The default value is generally 20." ;
          type uint32 {
            range 0..20 {
              description "It's toplimit depends on ability of the device." ;
            }

          }

          units second ;
          ncd:revise-date 2019-12-24 ;
        }

        container suppress-packet {
          description 'DHCP suppress packet.' ;
          presence suppress-packet ;
          leaf packet-type {
            description 'DHCP suppress packet type.' ;
            type enumeration {
              enum request-packet {
                value 1 ;
                description 'All request packet.' ;
              }

            }

            mandatory true ;
          }

          leaf packet-count {
            description 'The received packet count before packet suppression.' ;
            type uint32 {
              range 1..10000 {
                description 'Packet count.[1,10000].' ;
              }

            }

            mandatory true ;
          }

          leaf check-period {
            description 'Check period.' ;
            type uint32 {
              range 1..3600 {
                description 'Check period.[1,3600].' ;
              }

            }

            mandatory true ;
          }

          leaf suppress-period {
            description 'Suppress period.' ;
            type uint32 {
              range 1..3600 {
                description 'Suppress period.[1,3600].' ;
              }

            }

            mandatory true ;
          }

          ncd:revise-date 2020-01-19 ;
        }

        leaf non-online-user-mismatched-option54-delete {
          description 'Receive DHCP non-online-user mismatched option54 request packet,delete or not delete user.' ;
          type enumeration {
            enum not-delete-user {
              value 0 ;
              description "Receive DHCP non-online-user mismatched option54 request packet,don't delete user." ;
            }

            enum delete-user {
              value 1 ;
              description 'Receive DHCP non-online-user mismatched option54 request packet,delete user.' ;
            }

          }

          default not-delete-user ;
          ncd:revise-date 2020-07-20 ;
        }

        leaf user-interact {
          description 'Recording interaction logs.' ;
          type enumeration {
            enum record-off {
              value 0 ;
              description 'Recording interaction log off.' ;
            }

            enum record-on {
              value 1 ;
              description 'Recording interaction log on.' ;
            }

          }

          default record-off ;
          ncd:revise-date 2020-08-20 ;
        }

        container authen-templates {
          description 'DHCP authentication templates configuration.' ;
          list authen-template {
            description 'DHCP authentication template configuration.' ;
            key template-name ;
            leaf template-name {
              description 'DHCP authentication template name.' ;
              type string {
                length 1..64 {
                  description 'The length of DHCP authentication template name.' ;
                }

              }

            }

            leaf radius-group-name {
              description 'RADIUS group name configured in the DHCP authen template.' ;
              type string {
                length 1..31 {
                  description 'The length of RADIUS group name.' ;
                }

              }

            }

            container authen-radius-attributes {
              description 'RADIUS authentication attributes configuration.' ;
              list authen-radius-attribute {
                description 'RADIUS authentication attribute configuration.' ;
                key attribute-type ;
                leaf attribute-type {
                  description 'RADIUS authentication attribute type.' ;
                  type enumeration {
                    enum user-name {
                      value 1 ;
                      description 'RADIUS authentication attribute type is user-name.' ;
                    }

                    enum user-password {
                      value 2 ;
                      description 'RADIUS authentication attribute type is user-password.' ;
                    }

                    enum nas-port-id {
                      value 3 ;
                      description 'RADIUS authentication attribute type is nas-port-id.' ;
                    }

                  }

                }

                leaf attribute-source {
                  description 'RADIUS authentication attribute source.' ;
                  type enumeration {
                    enum chaddr {
                      value 1 ;
                      description 'Get RADIUS authentication attribute from packet chaddr.' ;
                    }

                    enum china-tel-opt82 {
                      value 2 ;
                      description 'Get RADIUS authentication attribute from local china-tel-opt82.' ;
                    }

                  }

                }

              }

            }

          }

          ncd:revise-date 2020-11-26 ;
        }

        container option-templates {
          description 'DHCP option template configuration.' ;
          list option-template {
            description 'DHCP option template configuration.' ;
            key template-name ;
            leaf template-name {
              description 'DHCP option template name.' ;
              type string {
                length 1..64 {
                  description 'The length of DHCP option template name.' ;
                }

              }

            }

            container options-conf {
              description 'DHCP option template options configure.' ;
              container options {
                description 'DHCP option template options configure.' ;
                list option {
                  description 'DHCP option template options configure.' ;
                  key code ;
                  leaf code {
                    description 'DHCP option template option code.' ;
                    type uint8 {
                      range 1..254 {
                        description 'The value of DHCP option template option code.' ;
                      }

                    }

                  }

                  choice type {
                    description 'DHCP option template option type.' ;
                    case ascii {
                      description 'DHCP option type is ASCII string.' ;
                      leaf ascii-str {
                        description 'DHCP option ASCII string configured.' ;
                        type string {
                          length 1..200 {
                            description 'The length of ASCII string.' ;
                          }

                        }

                      }

                    }

                    case hex {
                      description 'DHCP option type is HEX string.' ;
                      leaf hex-str {
                        description 'DHCP option HEX string configured.' ;
                        type string {
                          length 1..200 {
                            description 'The length of HEX string.' ;
                          }

                        }

                      }

                    }

                    case ip {
                      description 'DHCP option type is IP string.' ;
                      leaf ip-addr1 {
                        description 'DHCP option IP address configured.' ;
                        type ncd:ipv4-address-none-zero ;

                      }

                      leaf ip-addr2 {
                        description 'DHCP option IP address configured.' ;
                        type ncd:ipv4-address-none-zero ;

                      }

                      leaf ip-addr3 {
                        description 'DHCP option IP address configured.' ;
                        type ncd:ipv4-address-none-zero ;

                      }

                      leaf ip-addr4 {
                        description 'DHCP option IP address configured.' ;
                        type ncd:ipv4-address-none-zero ;

                      }

                      leaf ip-addr5 {
                        description 'DHCP option IP address configured.' ;
                        type ncd:ipv4-address-none-zero ;

                      }

                      leaf ip-addr6 {
                        description 'DHCP option IP address configured.' ;
                        type ncd:ipv4-address-none-zero ;

                      }

                      leaf ip-addr7 {
                        description 'DHCP option IP address configured.' ;
                        type ncd:ipv4-address-none-zero ;

                      }

                      leaf ip-addr8 {
                        description 'DHCP option IP address configured.' ;
                        type ncd:ipv4-address-none-zero ;

                      }

                    }

                  }

                }

              }

            }

          }

          ncd:revise-date 2020-12-01 ;
        }

        leaf packet-rate-limit {
          description 'DHCP online packet rate limit.' ;
          type uint16 {
            range 0..65535 ;

          }

          default 65535 ;
          ncd:revise-date 2022-03-10 ;
        }

      }

      container interfaces {
        description 'Interface-related configurations.' ;
        list interface {
          description 'DHCP interface common configuration.Dependent on the interface.' ;
          key name ;
          leaf name {
            description 'DHCP interface name.' ;
            type ncd:ifname {
              length 1..31 {
                description 'The interface name length.' ;
              }

            }

          }

          leaf mode {
            description 'DHCP interface work mode: [1,4], server(1), relay(2), proxy(3), client(4).' ;
            type enumeration {
              enum server {
                value 1 ;
                description 'DHCP interface work mode is server.' ;
              }

              enum relay {
                value 2 ;
                description 'DHCP interface work mode is relay.' ;
              }

              enum proxy {
                value 3 ;
                description 'DHCP interface work mode is proxy.' ;
              }

              enum client {
                value 4 ;
                description 'DHCP interface work mode is client.' ;
              }

            }

          }

          leaf user-quota {
            description "Specify quota of DHCP users on this interface. It's toplimit depends on ability of the device." ;
            type uint32 {
              range 1..128000 {
                description "It's toplimit depends on ability of the device." ;
              }

            }

          }

          leaf access-list {
            description 'DHCP interface bound access list.' ;
            type string {
              length 1..16 {
                description 'The length of dhcp access list name.' ;
              }

            }

          }

          leaf broadband-user-access {
            description 'Configure DHCP broadband user access under this interface.' ;
            type enumeration {
              enum enable {
                value 1 ;
                description 'This interface is broadband user access interface.' ;
              }

              enum disable {
                value 0 ;
                description 'This interface is not broadband user access interface.' ;
              }

            }

            default disable ;
            ncd:revise-date 2021-04-26 ;
          }

          container relay-if {
            description 'Interface-related configurations.' ;
            presence relay-if ;
            leaf relay-agent {
              description 'DHCP interface relay agent IP address.' ;
              type ncd:ipv4-address ;

            }

            leaf server-group {
              description "DHCP relay server group index of the interface.It's toplimit depends on ability of the device." ;
              type uint32 {
                range 1..4000 {
                  description "DHCP relay server group index of the interface.It's toplimit depends on ability of the device." ;
                }

              }

            }

            leaf source-ip {
              description 'DHCP relay source IP.' ;
              type ncd:ipv4-address ;

            }

            leaf relay-policy {
              description 'The DHCP relay helper-address policy of the interface.' ;
              type enumeration {
                enum vclassId {
                  value 1 ;
                  description 'The DHCP relay helper-address policy of the interface is vclassId.' ;
                }

                enum vlanId {
                  value 2 ;
                  description 'The DHCP relay helper-address policy of the interface is vlanId.' ;
                }

              }

            }

            leaf link-ip {
              description 'DHCP relay link-selection IP.' ;
              type ncd:ipv4-address ;

            }

            leaf remote-id {
              description 'The option82 remote-id of the interface.' ;
              type ncd:string-with-blank {
                length 1..64 {
                  description 'The option82 remote-id of the interface.' ;
                }

              }

            }

            leaf circuit-id {
              description 'The option82 circuit-id of the interface.' ;
              type ncd:string-with-blank {
                length 1..64 {
                  description 'The option82 circuit-id of the interface.' ;
                }

              }

            }

            leaf forward-mode {
              description 'The DHCP relay forward mode: standard(1), security(2).' ;
              type enumeration {
                enum standard {
                  value 1 ;
                  description 'The DHCP relay forward mode is standard.' ;
                }

                enum security {
                  value 2 ;
                  description 'The DHCP relay forward mode is security.' ;
                }

              }

              default standard ;
            }

            container relay-agent-indexs {
              description 'Set DHCP relay agent indexs.' ;
              list relay-agent-index {
                description 'Set DHCP relay agent index.' ;
                max-elements 32 ;
                key index ;
                leaf index {
                  description 'DHCP relay agent index No.[1,32].' ;
                  type uint8 {
                    range 1..32 {
                      description 'DHCP relay agent index.' ;
                    }

                  }

                }

                leaf relay-agent-IP {
                  description 'DHCP relay agent IP.' ;
                  type ncd:ipv4-address ;

                  mandatory true ;
                }

                leaf option-code {
                  description 'DHCP option code. [1,254].' ;
                  type uint8 {
                    range 1..254 {
                      description 'option code. [1,254].' ;
                    }

                  }

                }

                container option-content {
                  description 'Config DHCP option content.' ;
                  presence option-content ;
                  leaf option-type {
                    description 'DHCP option type.[1,2].
1:ASCII string type.
2:HEX string type.' ;
                    type uint8 {
                      range 1..2 {
                        description '1:ASCII string type.
2:HEX string type.' ;
                      }

                    }

                    mandatory true ;
                  }

                  leaf option-text {
                    description 'DHCP option text.' ;
                    type ncd:string-with-blank {
                      length 1..64 {
                        description 'DHCP option text.' ;
                      }

                    }

                    mandatory true ;
                  }

                }

              }

            }

            container server-list {
              if-feature intf-server-list ;

              description 'DHCP server list configuration under DHCP interface.' ;
              list server {
                description 'DHCP server list configuration under DHCP interface.' ;
                key server-index ;
                leaf server-index {
                  description 'DHCP relay server group server index.' ;
                  type uint32 {
                    range 1..128 ;

                  }

                }

                leaf server-ip {
                  description 'The server IP address.' ;
                  type ncd:ipv4-address ;

                  mandatory true ;
                }

                leaf dscp {
                  description 'The DSCP value of DHCP relay when it sends packet to the server.[0,63].' ;
                  type uint8 {
                    range 0..63 {
                      description 'dscp is from 0 to 63.' ;
                    }

                  }

                }

              }

              ncd:revise-date 2016-01-28 ;
            }

            container packet {
              list packet-list {
                max-elements 128 ;
                description 'Configures the policy for processing the request packets of the DHCP relay online users.' ;
                key packet-type ;
                leaf packet-type {
                  type enumeration {
                    enum init-reboot {
                      value 1 ;
                      description 'Init-reboot packets.' ;
                    }

                    enum discover {
                      value 2 ;
                      description 'Discover packets.' ;
                    }

                  }

                  description 'Request packet type. Currently, only discover and init-reboot are supported.' ;
                }

                leaf action {
                  type enumeration {
                    enum drop {
                      value 1 ;
                      description 'Drop packets.' ;
                    }

                    enum reply {
                      value 2 ;
                      description 'Reply packets.' ;
                    }

                  }

                  description 'The policy for processing the request packets. Currently, only drop and reply are supported.' ;
                }

              }

              description 'Configures the policy for processing the request packets of the DHCP relay online users.' ;
              ncd:revise-date 2019-03-05 ;
            }

            leaf bind-relay-instance {
              description 'The relay instance of the interface.' ;
              type string {
                length 1..16 {
                  description 'The instance name length.' ;
                }

              }

              ncd:revise-date 2020-06-09 ;
            }

            leaf forward-unrestrict {
              description 'Set forwarding DHCP reply packet without limit or not.' ;
              type enumeration {
                enum forward-off {
                  value 0 ;
                  description 'Turn off forward-unrestrict.' ;
                }

                enum forward-on {
                  value 1 ;
                  description 'Turn on forward-unrestrict.' ;
                }

              }

              default forward-off ;
              ncd:revise-date 2021-10-21 ;
            }

          }

          container server-if {
            description 'Interface-related configurations.' ;
            presence server-if ;
            leaf server-policy {
              description 'DHCP policy of the interface for DHCP server.' ;
              type string {
                length 1..16 {
                  description 'The length of DHCP policy name.' ;
                }

              }

            }

            leaf dest-port {
              description 'Destination UDP port of sending packet to DHCP relay by DHCP server.' ;
              type enumeration {
                enum dest-port-server {
                  value 67 ;
                  description 'Destination UDP port is 67.' ;
                }

                enum dest-port-client {
                  value 68 ;
                  description 'Destination UDP port is 68.' ;
                }

              }

            }

            leaf dscp {
              description 'DHCP server DSCP value.' ;
              type uint8 {
                range 0..63 {
                  description 'dscp is from 0 to 63.' ;
                }

              }

            }

            leaf nak-client-offline {
              description 'Turn on or off nak-client-offline.When turn on this switch,after server reply nak,client offline.' ;
              type enumeration {
                enum nak-client-offline-off {
                  value 0 ;
                  description 'Turn off nak-client-offline.' ;
                }

                enum nak-client-offline-on {
                  value 1 ;
                  description 'Turn on nak-client-offline.' ;
                }

              }

              default nak-client-offline-off ;
              ncd:revise-date 2018-03-23 ;
            }

            container detect-client-IP {
              if-feature detect-client-ip ;

              description "Server ARP or PING detect client's IP configuration." ;
              presence detect-client-IP ;
              leaf detect-type {
                description 'Server detect client IP switch.' ;
                type enumeration {
                  enum detect-off {
                    value 0 ;
                    description 'Server detect switch is off.' ;
                  }

                  enum arp-detect {
                    value 1 ;
                    description 'Server ARP detect switch is on.' ;
                  }

                  enum ping-detect {
                    value 2 ;
                    description 'Server ping detect switch is on.' ;
                  }

                }

                mandatory true ;
              }

              leaf detect-time {
                description 'Server ARP or PING detect timeout seconds.' ;
                type uint8 {
                  range 1..10 {
                    description 'Server ARP or ping detect timeout seconds.' ;
                  }

                }

                default 1 ;
              }

              ncd:revise-date 2018-10-08 ;
            }

            container arp-detect {
              if-feature arp-detect ;

              status obsolete {
                ncd:revise-date 2018-10-08 ;
              }

              description 'Server ARP detect configuration.' ;
              presence arp-detect ;
              leaf arp-detect-switch {
                status obsolete {
                  ncd:revise-date 2018-10-08 ;
                }

                description 'Server ARP detect switch.' ;
                type enumeration {
                  enum arp-detect-off {
                    value 0 ;
                    description 'Server ARP detect switch is off.' ;
                  }

                  enum arp-detect-on {
                    value 1 ;
                    description 'Server ARP detect switch is on.' ;
                  }

                }

                mandatory true ;
              }

              leaf arp-detect-time {
                status obsolete {
                  ncd:revise-date 2018-10-08 ;
                }

                description 'Server ARP detect timeout seconds.' ;
                type uint8 {
                  range 1..10 {
                    description 'Server ARP detect timeout seconds.' ;
                  }

                }

                default 1 ;
              }

              ncd:revise-date 2018-04-11 ;
            }

            leaf bind-server-instance {
              description 'The server instance of the interface.' ;
              type string {
                length 1..16 {
                  description 'The instance name length.' ;
                }

              }

              ncd:revise-date 2020-06-09 ;
            }

          }

          container client-if {
            description 'Interface-related configurations.' ;
            presence client-if ;
            container client-switch {
              description 'DHCP client interface switch configuration.' ;
              leaf switch {
                description 'DHCP interface client switch.' ;
                type enumeration {
                  enum stop {
                    value 0 ;
                    description 'DHCP client stop.' ;
                  }

                  enum start {
                    value 1 ;
                    description 'DHCP client start.' ;
                  }

                }

                default stop ;
              }

            }

            leaf client-policy {
              description 'DHCP policy of the interface for DHCP client.' ;
              type string {
                length 1..16 {
                  description 'The length of DHCP policy name.' ;
                }

              }

            }

            leaf default-router-priority {
              description 'Configure priority of default route generated by DHCP client.' ;
              type uint32 {
                range 1..254 {
                  description '<1-254>  Default route priority.' ;
                }

              }

              default 200 ;
            }

          }

        }

      }

      container access-lists {
        description 'DHCP access control list.' ;
        list access-list {
          description 'DHCP access control list.' ;
          max-elements 20 ;
          key name ;
          leaf name {
            description 'DHCP access list name.' ;
            type string {
              length 1..16 {
                description 'DHCP access list name.' ;
              }

            }

          }

          container default-rule {
            description 'The default action for access control filter table.' ;
            leaf action {
              description 'The default rule operation type of the DHCP access list.' ;
              type enumeration {
                enum permit {
                  value 1 ;
                  description 'The default rule operation type of the dhcp access list is permit.' ;
                }

                enum deny {
                  value 2 ;
                  description 'The default rule operation type of the dhcp access list is deny.' ;
                }

              }

              default permit ;
            }

          }

          container rules {
            description 'DHCP access list rule.' ;
            list rule {
              description 'DHCP access list rule.' ;
              key rule-no ;
              leaf rule-no {
                description 'The DHCP access list rule No.' ;
                type uint8 {
                  range 1..20 {
                    description 'RuleNo is from 1 to 20.' ;
                  }

                }

              }

              choice rule-oper {
                description 'DHCP access list rule operate type.' ;
                mandatory true ;
                case rule-deny {
                  description 'The DHCP access list rule operate type is deny or not.' ;
                  leaf deny {
                    description 'The DHCP access list rule operate type is deny or not.' ;
                    type enumeration {
                      enum deny {
                        value 2 ;
                        description 'The DHCP access list rule operate type is deny.' ;
                      }

                    }

                  }

                }

                case rule-permit {
                  description 'The DHCP access list rule operate type is deny or not.' ;
                  leaf permit {
                    description 'The DHCP access list rule operate type is permit or not.' ;
                    type enumeration {
                      enum permit {
                        value 1 ;
                        description 'The DHCP access list rule operate type is permit.' ;
                      }

                    }

                  }

                }

              }

              choice rule-content {
                description 'DHCP access list rule content.' ;
                mandatory true ;
                case rule-opt60 {
                  description 'DHCP access list rule option60.' ;
                  leaf partial {
                    description 'The DHCP access rule matching option60 type is partial or whole.' ;
                    type enumeration {
                      enum whole {
                        value 0 ;
                        description 'The DHCP access rule matching option60 type is whole.' ;
                      }

                      enum partial {
                        value 4 ;
                        description 'The DHCP access rule matching option60 type is partial.' ;
                      }

                    }

                    default whole ;
                  }

                  leaf opt60 {
                    description 'Option60 matching string.' ;
                    type ncd:string-with-blank {
                      length 1..64 {
                        description 'DHCP option60 string.' ;
                      }

                    }

                  }

                }

                case rule-any {
                  description 'DHCP access list rule any.' ;
                  leaf any {
                    description 'The rule content type is any.' ;
                    type enumeration {
                      enum none {
                        value 0 ;
                        description 'The rule content is not any.' ;
                      }

                      enum any {
                        value 6 ;
                        description 'The rule content type is any.' ;
                      }

                    }

                    default none ;
                  }

                }

              }

            }

          }

        }

      }

      container relay {
        description 'DHCP relay config.' ;
        container interfaces {
          description 'DHCP relay interface configuration.' ;
          list interface {
            description 'DHCP relay interface configuration on the interface.' ;
            key name ;
            leaf name {
              description 'DHCP interface name.' ;
              type ncd:ifname {
                length 1..31 {
                  description 'The interface name length.' ;
                }

              }

            }

            leaf relay-agent {
              description 'DHCP interface relay agent IP address.' ;
              type ncd:ipv4-address ;

            }

            leaf server-group {
              description "DHCP relay server group index of the interface.It's toplimit depends on ability of the device." ;
              type uint32 {
                range 1..4000 {
                  description "DHCP relay server group index of the interface.It's toplimit depends on ability of the device." ;
                }

              }

            }

            leaf source-ip {
              description 'DHCP relay source IP.' ;
              type ncd:ipv4-address ;

            }

            leaf relay-policy {
              description 'The DHCP relay helper-address policy of the interface.' ;
              type enumeration {
                enum vclassId {
                  value 1 ;
                  description 'The DHCP relay helper-address policy of the interface is vclassId.' ;
                }

                enum vlanId {
                  value 2 ;
                  description 'The DHCP relay helper-address policy of the interface is vlanId.' ;
                }

              }

            }

            leaf link-ip {
              description 'DHCP relay link-selection IP.' ;
              type ncd:ipv4-address ;

            }

            leaf circuit-id {
              description 'The option82 circuit-id of the interface.' ;
              type ncd:string-with-blank {
                length 1..64 {
                  description 'The option82 circuit-id of the interface.' ;
                }

              }

            }

            leaf remote-id {
              description 'The option82 remote-id of the interface.' ;
              type ncd:string-with-blank {
                length 1..64 {
                  description 'The option82 remote-id of the interface.' ;
                }

              }

            }

            container relay-agent-indexs {
              description 'Set DHCP relay agent indexs.' ;
              list relay-agent-index {
                description 'Set DHCP relay agent index.' ;
                max-elements 32 ;
                key index ;
                leaf index {
                  description 'DHCP relay agent index No.[1,32].' ;
                  type uint8 {
                    range 1..32 {
                      description 'DHCP relay agent index.' ;
                    }

                  }

                }

                leaf relay-agent-IP {
                  description 'DHCP relay agent IP.' ;
                  type ncd:ipv4-address ;

                  mandatory true ;
                }

                leaf option-code {
                  description 'DHCP option code. [1,254].' ;
                  type uint8 {
                    range 1..254 {
                      description 'option code. [1,254].' ;
                    }

                  }

                  mandatory true ;
                }

                leaf option-type {
                  description 'DHCP option type.[1,2].
1:ASCII string type.
2:HEX string type.' ;
                  type uint8 {
                    range 1..2 {
                      description '1:ASCII string type.
2:HEX string type.' ;
                    }

                  }

                }

                leaf option-text {
                  description 'DHCP option text.' ;
                  type ncd:string-with-blank {
                    length 1..64 {
                      description 'DHCP option text.' ;
                    }

                  }

                }

              }

            }

          }

        }

        container server-groups {
          description 'DHCP relay server group configuration.' ;
          list server-group {
            description 'DHCP relay server group configuration.' ;
            key group-no ;
            leaf group-no {
              description "DHCP relay server group No.It's toplimit depends on ability of the device." ;
              type uint32 {
                range 1..4000 {
                  description "DHCP relay server group No.It's toplimit depends on ability of the device." ;
                }

              }

            }

            leaf algorithm {
              description 'DHCP relay server group algorithm.' ;
              type enumeration {
                enum first {
                  value 0 ;
                  description 'The DHCP relay server group algorithm is first.' ;
                }

                enum round-robin {
                  value 1 ;
                  description 'The DHCP relay server group algorithm is round-robin.' ;
                }

                enum forward-all {
                  value 2 ;
                  description 'DHCP relay server group algorithm is forward-all.' ;
                }

              }

              default first ;
            }

            leaf dead-time {
              description 'Deadtime of DHCP relay server.[0,3600]. unit is seconds.' ;
              type uint32 {
                range 0..3600 {
                  description 'Deadtime of DHCP relay server.[0,3600]. unit is seconds.' ;
                }

              }

              units second ;
              default 60 ;
            }

            leaf retry {
              description 'Max retry times of DHCP relay server group server.[0,20],except 1,2,3,4.' ;
              type uint32 {
                range 0..20 {
                  description 'Max retry times of DHCP relay server group server.[0,20],except 1,2,3,4.' ;
                }

              }

              default 10 ;
            }

            leaf max-timeout {
              description 'Set max timeout seconds of request for DHCP relay server group.[0-255]' ;
              type uint8 {
                range 0..255 {
                  description 'Max timeout of relay forward server(seconds).' ;
                }

              }

              units second ;
              default 10 ;
              ncd:revise-date 2016-12-20 ;
            }

            leaf description {
              description 'Description of DHCP relay server group.' ;
              type string {
                length 1..32 {
                  description 'Description of DHCP relay server group.' ;
                }

              }

            }

            leaf local-server {
              description 'Local server switch.' ;
              type enumeration {
                enum off {
                  value 0 ;
                  description 'local-server off.' ;
                }

                enum on {
                  value 1 ;
                  description 'local-server on.' ;
                }

              }

              default off ;
            }

            leaf verify-server-id {
              description 'Verify server-id.' ;
              type enumeration {
                enum off {
                  value 0 ;
                  description 'verify server-id off.' ;
                }

                enum on {
                  value 1 ;
                  description 'verify server-id on.' ;
                }

              }

              default off ;
            }

            container servers {
              description 'DHCP relay server group server.' ;
              list server {
                description 'DHCP relay server group server.' ;
                key index ;
                leaf index {
                  description 'DHCP relay server group server No.' ;
                  type uint32 {
                    range 1..128 {
                      description 'server No.[1,128].' ;
                    }

                  }

                }

                leaf ip {
                  description 'The IP address of the relay server group server.' ;
                  type ncd:ipv4-address ;

                  mandatory true ;
                }

                leaf forward-mode {
                  description 'The DHCP relay server group server forward mode: standard(1),security(2).' ;
                  type enumeration {
                    enum standard {
                      value 1 ;
                      description 'The Dhcp relay server group server forward mode is standard.' ;
                    }

                    enum security {
                      value 2 ;
                      description 'The Dhcp relay server group server forward mode is security.' ;
                    }

                  }

                }

                leaf master {
                  description 'The DHCP relay server group server is slave or master. Only one master server exists in the DHCP server group.slave(0),master(1).' ;
                  type enumeration {
                    enum slave {
                      value 0 ;
                      description 'The DHCP relay server group server is slave.' ;
                    }

                    enum master {
                      value 1 ;
                      description 'The DHCP relay server group server is master.' ;
                    }

                  }

                  default slave ;
                }

                leaf dscp {
                  description 'The DSCP value of DHCP relay when it sends packet to the server.[0,63].' ;
                  type uint8 {
                    range 0..63 {
                      description 'dscp is from 0 to 63.' ;
                    }

                  }

                }

                choice vpn {
                  description 'The DHCP server in DHCP relay server group is private or public.' ;
                  case public {
                    description 'The DHCP relay server group server is private or public' ;
                    leaf public {
                      description 'The DHCP relay server group server is private or public. not-public(0),public(1).' ;
                      type boolean ;

                      default false ;
                    }

                  }

                  case vrf {
                    description 'The DHCP server in DHCP relay server group is private.' ;
                    leaf vrf-name {
                      description 'The VRF instance name configured for DHCP server in DHCP relay server group.' ;
                      type string ;

                    }

                  }

                  ncd:revise-date 2016-12-06 ;
                }

              }

            }

            container online-user-forward-algorithm {
              description 'DHCP relay server group online-user forward algorithm.' ;
              presence online-user-forward-algorithm ;
              leaf forward-algorithm {
                description 'DHCP relay server group online-user forward algorithm.' ;
                type enumeration {
                  enum forward-all {
                    value 1 ;
                    description 'DHCP relay server group online-user forward algorithm is forward-all.' ;
                  }

                  enum NULL {
                    value 0 ;
                  }

                }

                mandatory true ;
              }

              container packet-type {
                description 'DHCP relay server group online-user forward packet type.' ;
                leaf renew-request {
                  description 'DHCP relay server group online-user forward renew-request.' ;
                  type uint8 ;

                  default 0 ;
                }

                leaf rebinding-request {
                  description 'DHCP relay server group online-user forward rebinding-request.' ;
                  type uint8 ;

                  default 0 ;
                }

                leaf release {
                  description 'DHCP relay server group online-user forward release.' ;
                  type uint8 ;

                  default 0 ;
                }

                leaf decline {
                  description 'DHCP relay server group online-user forward decline.' ;
                  type uint8 ;

                  default 0 ;
                }

              }

              ncd:revise-date 2019-01-18 ;
            }

            leaf cos {
              description '802.1P value of DHCP relay server group.[0,7].' ;
              type uint8 {
                range 0..7 {
                  description 'The range of 802.1P value.[0,7]' ;
                }

              }

              ncd:revise-date 2019-04-03 ;
            }

          }

        }

        container policy-groups {
          description 'DHCP relay server policy group.' ;
          list policy-group {
            description 'DHCP relay server policy group.' ;
            max-elements 64 ;
            key policy-no ;
            leaf policy-no {
              description 'Relay server policy group No.' ;
              type uint32 {
                range 1..64 {
                  description 'Relay server policy group NO.' ;
                }

              }

            }

            leaf server-group-no {
              description 'DHCP relay server group No.' ;
              type uint32 {
                range 1..4000 {
                  description 'DHCP relay server group-no.' ;
                }

              }

            }

            leaf vclass-id {
              description 'Vclass id of this relay server policy group.' ;
              type ncd:string-with-blank {
                length 1..32 {
                  description 'The length of vclass-id.' ;
                }

              }

            }

            container policy-vlans {
              description 'DHCP relay server policy group vlan info.' ;
              list policy-vlan {
                description 'DHCP relay server policy group vlan info.' ;
                max-elements 8 ;
                key index ;
                leaf index {
                  description 'Relay server policy group vlan index.' ;
                  type uint32 {
                    range 1..8 ;

                  }

                }

                leaf ex-vlan-range {
                  description 'The range of external vlan,[1,4094].' ;
                  type ncd:range ;

                  mandatory true ;
                }

                leaf in-vlan-range {
                  description 'The range of internal vlan,[1,4094].' ;
                  type ncd:range ;

                }

              }

            }

            container options {
              description 'Configurate options under DHCP relay policy group.' ;
              presence options ;
              list option {
                description 'Configurate option under DHCP relay policy group.' ;
                max-elements 16256 ;
                key code ;
                leaf code {
                  description 'Option code under DHCP relay policy group.' ;
                  type uint32 {
                    range 1..254 ;

                  }

                }

                choice type {
                  description 'Option type under DHCP relay policy group.' ;
                  mandatory true ;
                  case ascii {
                    description 'Option type under DHCP relay policy group is ASCII string.' ;
                    leaf ascii-str {
                      description 'Option ASCII string under DHCP relay policy group is configured.' ;
                      type ncd:string-with-blank {
                        length 1..64 {
                          description 'The length of ASCII string.' ;
                        }

                      }

                      mandatory true ;
                    }

                  }

                  case hex {
                    description 'Option type under DHCP relay policy group is HEX string.' ;
                    leaf hex-str {
                      description 'Option HEX string under DHCP relay policy group is configured.' ;
                      type string {
                        length 1..64 {
                          description 'The length of HEX string.' ;
                        }

                      }

                      mandatory true ;
                    }

                  }

                }

              }

              ncd:revise-date 2016-12-20 ;
            }

          }

        }

        container global-config {
          description 'DHCP relay global configuration.' ;
          leaf max-user {
            description "Max user numbers of DHCP relay. It's toplimit depends on ability of the device.The default value is generally 64000." ;
            type uint32 {
              range 1..128000 {
                description "It's toplimit depends on ability of the device." ;
              }

            }

            default 64000 ;
          }

          leaf forbid-send-release {
            description 'Forbid DHCP relay to send DHCPRELEASE to server or not.' ;
            type enumeration {
              enum allow {
                value 0 ;
                description 'Allow DHCP relay to send DHCPRELEASE to server.' ;
              }

              enum forbid {
                value 1 ;
                description 'Forbid DHCP relay to send DHCPRELEASE to server.' ;
              }

            }

            default allow ;
          }

          leaf proxy-lease-time {
            description 'Set client lease time of proxy.[30,3600]. unit is seconds.' ;
            type uint32 {
              range 30..3600 {
                description 'lease time of proxy.[30,3600]. unit is seconds.' ;
              }

            }

            units second ;
            default 60 ;
          }

          leaf update-arp {
            description 'Set the ARP deadtime to DHCP lease or not.' ;
            type enumeration {
              enum update-off {
                value 0 ;
                description 'Turn off update-arp.' ;
              }

              enum update-on {
                value 1 ;
                description 'Turn on update-arp.' ;
              }

            }

            default update-off ;
          }

          leaf forward-unrestrict {
            description 'Set forwarding DHCP reply packet without limit or not.' ;
            type enumeration {
              enum forward-off {
                value 0 ;
                description 'Turn off forward-unrestrict.' ;
              }

              enum forward-on {
                value 1 ;
                description 'Turn on forward-unrestrict.' ;
              }

            }

            default forward-off ;
          }

          leaf fwd-unrstrctd-opt82-plcy {
            description 'Set forwarding DHCP reply packet without limit by option82 or not.' ;
            type enumeration {
              enum opt82-plcy-off {
                value 0 ;
                description 'Set forwarding DHCP reply packet without limit not by option82.' ;
              }

              enum opt82-plcy-on {
                value 1 ;
                description 'Set forwarding DHCP reply packet without limit by option82.' ;
              }

            }

            default opt82-plcy-off ;
          }

          leaf check-server-packet {
            description 'Check server packet or not.' ;
            type enumeration {
              enum off {
                value 0 ;
                description 'Turn off check server packet.' ;
              }

              enum on {
                value 1 ;
                description 'Turn on check server packet.' ;
              }

            }

            default off ;
            ncd:revise-date 2016-12-20 ;
          }

          leaf report-user-info {
            description 'Turn on or off the function of reporting DHCP relay user information to netconf.' ;
            type enumeration {
              enum report-user-off {
                value 0 ;
                description 'Turn off report-user-info.' ;
              }

              enum report-user-on {
                value 1 ;
                description 'Turn on report-user-info.' ;
              }

            }

            default report-user-off ;
            ncd:revise-date 2016-07-04 ;
          }

          leaf forward-release-unrestrict {
            description 'Set forwarding DHCP unexist user release to server without limit or not.' ;
            type enumeration {
              enum forward-off {
                value 0 ;
                description 'Turn off forward-release-unrestrict.' ;
              }

              enum forward-on {
                value 1 ;
                description 'Turn on forward-release-unrestrict.' ;
              }

            }

            default forward-off ;
            ncd:revise-date 2020-07-02 ;
          }

          leaf pkt-from-sib-check-master {
            description 'Set checking local is master or not when receive packet from sib.' ;
            type enumeration {
              enum off {
                value 0 ;
                description 'Not check local is hotback master or not when receive packet from sib.' ;
              }

              enum on {
                value 1 ;
                description "Check local is hotback master or not when receive packet from sib. Drop packet when local isn't hotback master." ;
              }

            }

            default off ;
            ncd:revise-date 2021-03-31 ;
          }

          leaf inter-chassis-enable {
            description 'Enable DHCP relay inter-chassis.' ;
            type enumeration {
              enum true {
                value 1 ;
                description 'Enable DHCP relay inter-chassis.' ;
              }

              enum false {
                value 0 ;
                description 'Disable DHCP relay inter-chassis.' ;
              }

            }

            default false ;
            ncd:revise-date 2021-10-21 ;
          }

          leaf file-auto-save {
            description 'DHCP relay file auto-save.' ;
            type enumeration {
              enum on {
                value 1 ;
                description 'Enable DHCP relay file auto-save.' ;
              }

              enum off {
                value 0 ;
                description 'Disable DHCP relay file auto-save.' ;
              }

            }

            default off ;
            ncd:revise-date 2022-04-23 ;
          }

        }

        container opt82-config {
          description 'DHCP relay option82 global configuration.' ;
          leaf option {
            description 'Insert relay option82 or not in BOOTREQUEST.' ;
            type enumeration {
              enum insert-off {
                value 0 ;
                description 'Not insert relay option82 in BOOTREQUEST.' ;
              }

              enum insert-on {
                value 1 ;
                description 'Insert relay option82 in BOOTREQUEST.' ;
              }

            }

            default insert-off ;
          }

          leaf format {
            description 'DHCP relay option82 format: [1,5], china-tel(1), dsl-forum(2), telenor(3), user-configuration(4), china-tel-with-shelf(5) .' ;
            type enumeration {
              enum china-tel {
                value 1 ;
                description 'DHCP relay option82 format is china-tel.' ;
              }

              enum dsl-forum {
                value 2 ;
                description 'DHCP relay option82 format is dsl-forum.' ;
              }

              enum telenor {
                value 3 ;
                description 'DHCP relay option82 format is telenor.' ;
              }

              enum user-configuration {
                value 4 ;
                description 'DHCP relay option82 format is user-configuration.' ;
              }

              enum china-tel-with-shelf {
                value 5 ;
                description 'DHCP relay option82 format is china-tel-with-shelf.' ;
              }

            }

            default china-tel ;
          }

          leaf operate-policy {
            description 'The option82 policy of DHCP relay: [2,5], keep(2), replace(3), add(4), add-no-check(5).' ;
            type enumeration {
              enum keep {
                value 2 ;
                description 'The option82 policy of DHCP relay is keep.' ;
              }

              enum replace {
                value 3 ;
                description 'The option82 policy of DHCP relay is replace.' ;
              }

              enum add {
                value 4 ;
                description 'The option82 policy of DHCP relay is add.' ;
              }

              enum add-no-check {
                value 5 ;
                description 'The option82 policy of DHCP relay is add without checking existing information.' ;
              }

            }

            default replace ;
          }

          leaf user-policy {
            description 'DHCP option82 policy of user configuration: [1,2], interface(1), uniform(2).' ;
            type enumeration {
              enum interface {
                value 1 ;
                description 'DHCP option82 policy of user configuration is interface.' ;
              }

              enum uniform {
                value 2 ;
                description 'DHCP option82 policy of user configuration is uniform.' ;
              }

            }

            default interface ;
          }

          leaf circuit-id {
            description 'The circuit-id subitem of uniform option82.' ;
            type ncd:string-with-blank {
              length 1..64 {
                description 'The length of the circuit-id subitem.' ;
              }

            }

          }

          leaf remote-id {
            description 'The remote-id subitem of uniform option82.' ;
            type ncd:string-with-blank {
              length 1..64 {
                description 'The length of the remote-id subitem.' ;
              }

            }

          }

        }

        container instances {
          description 'DHCP relay instance configuration.' ;
          list instance {
            description 'DHCP relay instance configuration.' ;
            key instance-name ;
            leaf instance-name {
              description 'DHCP relay instance name.' ;
              type string {
                length 1..16 {
                  description 'DHCP relay instance name.' ;
                }

              }

              ncd:revise-date 2017-01-12 ;
            }

            leaf link-ip {
              description 'DHCP relay instance link-selection IP.' ;
              type ncd:ipv4-address {
                pattern '([1-9][0-9]*\.[1-9][0-9]*\.[1-9][0-9]*\.[1-9][0-9]*)|([1-9][0-9]*\.0\.0\.0)|(0\.[1-9][0-9]*\.0\.0)|(0\.0\.[1-9][0-9]*\.0)|(0\.0\.0\.[1-9][0-9]*)|([1-9][0-9]*\.[1-9][0-9]*\.0\.0)|(0\.[1-9][0-9]*\.[1-9][0-9]*\.0)|(0\.0\.[1-9][0-9]*\.[1-9][0-9]*)|([1-9][0-9]*\.0\.0\.[1-9][0-9]*)|(0\.[1-9][0-9]*\.0\.[1-9][0-9]*)|([1-9][0-9]*\.0\.[1-9][0-9]*\.0)|([1-9][0-9]*\.[1-9][0-9]*\.[1-9][0-9]*\.0)|([1-9][0-9]*\.[1-9][0-9]*\.0\.[1-9][0-9]*)|([1-9][0-9]*\.0\.[1-9][0-9]*\.[1-9][0-9]*)|(0\.[1-9][0-9]*\.[1-9][0-9]*\.[1-9][0-9]*)' ;

              }

            }

            leaf circuit-id {
              description 'The option82 circuit-id of DHCP relay instance.' ;
              type ncd:string-with-blank {
                length 1..64 {
                  description 'The option82 circuit-id of DHCP relay instance.' ;
                }

              }

            }

            leaf remote-id {
              description 'The option82 remote-id of DHCP relay instance.' ;
              type ncd:string-with-blank {
                length 1..64 {
                  description 'The option82 remote-id of DHCP relay instance.' ;
                }

              }

            }

            leaf server-group {
              description "DHCP relay server group index of relay instance.It's toplimit depends on ability of the device." ;
              type uint32 {
                range 1..4000 {
                  description "DHCP relay server group index of relay instance.It's toplimit depends on ability of the device." ;
                }

              }

            }

            leaf short-leasetime {
              description 'Short lease time for DHCP relay.' ;
              type uint32 {
                range 60..4294967295 {
                  description 'The range of short leasetime.' ;
                }

              }

            }

            container relay-agent-indexs {
              description 'Set DHCP relay agent indexs.' ;
              list relay-agent-index {
                description 'Set DHCP relay agent index.' ;
                max-elements 32 ;
                key index ;
                leaf index {
                  description 'DHCP relay agent index No.[1,32].' ;
                  type uint32 {
                    range 1..32 {
                      description 'DHCP relay agent index range.' ;
                    }

                  }

                }

                leaf relay-agent-IP {
                  description 'DHCP relay agent IP.' ;
                  type ncd:ipv4-address ;

                  mandatory true ;
                }

                leaf option-code {
                  description 'DHCP option code.[1,254].' ;
                  type uint32 {
                    range 1..254 {
                      description 'DHCP option code.[1,254].' ;
                    }

                  }

                }

                container option-content {
                  description 'Config DHCP option content.' ;
                  presence option-content ;
                  leaf option-type {
                    description 'DHCP option type.' ;
                    type enumeration {
                      enum ASCII {
                        value 1 ;
                        description 'ASCII string type.' ;
                      }

                      enum HEX {
                        value 2 ;
                        description 'HEX string type.' ;
                      }

                    }

                    mandatory true ;
                  }

                  leaf option-text {
                    description 'DHCP option text.' ;
                    type ncd:string-with-blank {
                      length 1..64 {
                        description 'DHCP option text.' ;
                      }

                    }

                    mandatory true ;
                  }

                }

              }

            }

            leaf relay-agent {
              description 'DHCP interface relay agent ip address.' ;
              type ncd:ipv4-address {
                pattern '([1-9][0-9]*\.[1-9][0-9]*\.[1-9][0-9]*\.[1-9][0-9]*)|([1-9][0-9]*\.0\.0\.0)|(0\.[1-9][0-9]*\.0\.0)|(0\.0\.[1-9][0-9]*\.0)|(0\.0\.0\.[1-9][0-9]*)|([1-9][0-9]*\.[1-9][0-9]*\.0\.0)|(0\.[1-9][0-9]*\.[1-9][0-9]*\.0)|(0\.0\.[1-9][0-9]*\.[1-9][0-9]*)|([1-9][0-9]*\.0\.0\.[1-9][0-9]*)|(0\.[1-9][0-9]*\.0\.[1-9][0-9]*)|([1-9][0-9]*\.0\.[1-9][0-9]*\.0)|([1-9][0-9]*\.[1-9][0-9]*\.[1-9][0-9]*\.0)|([1-9][0-9]*\.[1-9][0-9]*\.0\.[1-9][0-9]*)|([1-9][0-9]*\.0\.[1-9][0-9]*\.[1-9][0-9]*)|(0\.[1-9][0-9]*\.[1-9][0-9]*\.[1-9][0-9]*)' ;

              }

            }

            container source-ip-config {
              description 'DHCP relay source IP.' ;
              presence source-ip-config ;
              choice source-ip {
                description 'DHCP relay source IP.' ;
                case ip {
                  description 'Source IP address of DHCP relay instance.' ;
                  leaf ip-addr {
                    description 'Source IP address of DHCP relay instance.' ;
                    type ncd:ipv4-address ;

                    mandatory true ;
                  }

                }

                case interface {
                  description 'Get the IP address of this interface.' ;
                  leaf interface-name {
                    description 'Interface name.' ;
                    type ncd:ifname {
                      length 1..31 {
                        description 'Interface name.' ;
                      }

                    }

                    mandatory true ;
                  }

                }

              }

            }

            container relay-policy {
              description 'DHCP relay help-address policy of relay instance.' ;
              presence relay-policy ;
              choice policy-type {
                description 'DHCP relay help-address policy of relay instance.' ;
                case vclass {
                  description 'DHCP relay help-address policy of relay instance is vclass-id.' ;
                  leaf vclass-id {
                    description 'DHCP relay help-address policy of relay instance is vclass-id.' ;
                    type empty ;

                    mandatory true ;
                  }

                }

                case vlan {
                  description 'DHCP relay help-address policy of relay instance is vlan-id.' ;
                  leaf vlan-id {
                    description 'DHCP relay help-address policy of relay instance is vlan-id.' ;
                    type empty ;

                    mandatory true ;
                  }

                }

                case option {
                  description 'DHCP relay help-address policy of relay instance is option-code.' ;
                  leaf option-code {
                    description 'DHCP relay help-address policy of relay instance is option-code.' ;
                    type empty ;

                    mandatory true ;
                  }

                  leaf option-code-number {
                    description 'DHCP option code.' ;
                    type uint32 {
                      range 1..254 {
                        description 'The range of DHCP option code.' ;
                      }

                    }

                    mandatory true ;
                  }

                }

              }

            }

            leaf relay-agent-mask {
              description 'DHCP relay agent IP mask. When config relay agent IP mask, the relay agent IP must not be 0.0.0.0.' ;
              type ncd:ipv4-mask {
                pattern '([1-9][0-9]*\.[1-9][0-9]*\.[1-9][0-9]*\.[1-9][0-9]*)|([1-9][0-9]*\.0\.0\.0)|(0\.[1-9][0-9]*\.0\.0)|(0\.0\.[1-9][0-9]*\.0)|(0\.0\.0\.[1-9][0-9]*)|([1-9][0-9]*\.[1-9][0-9]*\.0\.0)|(0\.[1-9][0-9]*\.[1-9][0-9]*\.0)|(0\.0\.[1-9][0-9]*\.[1-9][0-9]*)|([1-9][0-9]*\.0\.0\.[1-9][0-9]*)|(0\.[1-9][0-9]*\.0\.[1-9][0-9]*)|([1-9][0-9]*\.0\.[1-9][0-9]*\.0)|([1-9][0-9]*\.[1-9][0-9]*\.[1-9][0-9]*\.0)|([1-9][0-9]*\.[1-9][0-9]*\.0\.[1-9][0-9]*)|([1-9][0-9]*\.0\.[1-9][0-9]*\.[1-9][0-9]*)|(0\.[1-9][0-9]*\.[1-9][0-9]*\.[1-9][0-9]*)' ;

              }

              ncd:revise-date 2019-01-17 ;
            }

            container packet {
              list packet-list {
                description 'Configures the policy for processing the request packets of online users in DHCP relay instance mode.' ;
                key packet-type ;
                leaf packet-type {
                  type enumeration {
                    enum init-reboot {
                      value 1 ;
                      description 'Init-reboot packets.' ;
                    }

                    enum discover {
                      value 2 ;
                      description 'Discoverpackets.' ;
                    }

                  }

                  description 'Request packet type. Currently, only discover and init-reboot are supported.' ;
                }

                leaf action {
                  type enumeration {
                    enum drop {
                      value 1 ;
                      description 'Drop packets.' ;
                    }

                    enum reply {
                      value 2 ;
                      description 'Reply packets.' ;
                    }

                  }

                  description 'The policy for processing the request packets of online users. Currently, only drop and reply are supported.' ;
                }

              }

              description 'Configures the policy for processing the request packets of online users in DHCP relay instance mode.' ;
              ncd:revise-date 2019-03-05 ;
            }

          }

          ncd:revise-date 2016-09-20 ;
        }

        container interface-based-instances {
          description 'DHCP relay interface based instance configuration.' ;
          list instance {
            description 'DHCP relay interface based instance configuration.' ;
            key instance-name ;
            leaf instance-name {
              description 'DHCP relay instance name.' ;
              type string {
                length 1..16 {
                  description 'DHCP relay instance name.' ;
                }

              }

            }

            leaf description {
              description 'DHCP relay instance description.' ;
              type string {
                length 1..31 {
                  description 'DHCP relay instance description.' ;
                }

              }

            }

            leaf authen-template-name {
              description 'Binding authentication template name.' ;
              type string {
                length 1..64 {
                  description 'The length of authentication template name.' ;
                }

              }

              ncd:revise-date 2020-11-26 ;
            }

            leaf server-id-override {
              description 'DHCP relay option82 suboption11 configuration.' ;
              type ncd:ipv4-address {
                pattern '([1-9][0-9]*\.[1-9][0-9]*\.[1-9][0-9]*\.[1-9][0-9]*)|([1-9][0-9]*\.0\.0\.0)|(0\.[1-9][0-9]*\.0\.0)|(0\.0\.[1-9][0-9]*\.0)|(0\.0\.0\.[1-9][0-9]*)|([1-9][0-9]*\.[1-9][0-9]*\.0\.0)|(0\.[1-9][0-9]*\.[1-9][0-9]*\.0)|(0\.0\.[1-9][0-9]*\.[1-9][0-9]*)|([1-9][0-9]*\.0\.0\.[1-9][0-9]*)|(0\.[1-9][0-9]*\.0\.[1-9][0-9]*)|([1-9][0-9]*\.0\.[1-9][0-9]*\.0)|([1-9][0-9]*\.[1-9][0-9]*\.[1-9][0-9]*\.0)|([1-9][0-9]*\.[1-9][0-9]*\.0\.[1-9][0-9]*)|([1-9][0-9]*\.0\.[1-9][0-9]*\.[1-9][0-9]*)|(0\.[1-9][0-9]*\.[1-9][0-9]*\.[1-9][0-9]*)' ;

              }

              ncd:revise-date 2022-01-17 ;
            }

            container vss-option {
              description 'VSS option in DHCP relay.' ;
              presence vss-option ;
              choice vss-type {
                description 'DHCP relay VSS option type.' ;
                case vrf-name {
                  description 'DHCP relay VSS option type is VRF name.' ;
                  leaf vrf-name {
                    description 'VRF name in VSS option.' ;
                    type string {
                      length 1..32 {
                        description 'VRF name' ;
                      }

                    }

                    mandatory true ;
                  }

                }

                case vpnid-from-name {
                  description 'DHCP relay VSS option type is VPN ID.' ;
                  leaf vpnid-from-vrf-name {
                    description 'VPN ID from VRF name in VSS option.' ;
                    type string {
                      length 1..32 {
                        description 'VRF name' ;
                      }

                    }

                    mandatory true ;
                  }

                }

                case public {
                  description 'DHCP relay VSS option type is public.' ;
                  leaf public {
                    description 'Public VRF in VSS option.' ;
                    type empty ;

                    mandatory true ;
                  }

                }

              }

              ncd:revise-date 2022-01-17 ;
            }

            container option82-vendor-specifics {
              description 'DHCP relay option82 suboption9 configuration.' ;
              list option82-vendor-specific {
                description 'Configure suboption9 of option82.' ;
                max-elements 255 ;
                key suboption-code ;
                leaf suboption-code {
                  description 'Configuration suboption code of suboption9.' ;
                  type uint8 {
                    range 1..255 {
                      description 'Configure suboption of suboption9.' ;
                    }

                  }

                }

                choice data-type {
                  description 'DHCP suboption date type of suboption9 of option82.' ;
                  mandatory true ;
                  case ip {
                    description 'Data type is IP.' ;
                    leaf ip-addr {
                      description 'DHCP suboption of suboption9 IP address configured.' ;
                      type ncd:ipv4-address {
                        pattern '([1-9][0-9]*\.[1-9][0-9]*\.[1-9][0-9]*\.[1-9][0-9]*)|([1-9][0-9]*\.0\.0\.0)|(0\.[1-9][0-9]*\.0\.0)|(0\.0\.[1-9][0-9]*\.0)|(0\.0\.0\.[1-9][0-9]*)|([1-9][0-9]*\.[1-9][0-9]*\.0\.0)|(0\.[1-9][0-9]*\.[1-9][0-9]*\.0)|(0\.0\.[1-9][0-9]*\.[1-9][0-9]*)|([1-9][0-9]*\.0\.0\.[1-9][0-9]*)|(0\.[1-9][0-9]*\.0\.[1-9][0-9]*)|([1-9][0-9]*\.0\.[1-9][0-9]*\.0)|([1-9][0-9]*\.[1-9][0-9]*\.[1-9][0-9]*\.0)|([1-9][0-9]*\.[1-9][0-9]*\.0\.[1-9][0-9]*)|([1-9][0-9]*\.0\.[1-9][0-9]*\.[1-9][0-9]*)|(0\.[1-9][0-9]*\.[1-9][0-9]*\.[1-9][0-9]*)' ;

                      }

                      mandatory true ;
                    }

                  }

                }

              }

              ncd:revise-date 2022-05-17 ;
            }

          }

          ncd:revise-date 2020-06-09 ;
        }

        container option-configs {
          description 'DHCP relay packet option configurations.' ;
          list option-config {
            description 'DHCP relay packet option configuration.' ;
            key 'packet-direction packet-type option-code' ;
            leaf packet-direction {
              description 'DHCP relay packet direction.' ;
              type enumeration {
                enum receive {
                  value 1 ;
                }

                enum send {
                  value 2 ;
                }

              }

            }

            leaf packet-type {
              description 'DHCP relay packet type.' ;
              type enumeration {
                enum request {
                  value 1 ;
                }

                enum reply {
                  value 2 ;
                }

              }

            }

            leaf option-code {
              description 'DHCP relay packet option code.' ;
              type uint8 {
                range "1..50 | 52..254" ;

              }

            }

            choice oper-type {
              description 'DHCP relay packet oper type.' ;
              case set {
                description 'DHCP relay packet oper type is set.' ;
                leaf set {
                  description 'DHCP relay packet oper type is set.' ;
                  type enumeration {
                    enum on {
                      value 1 ;
                    }

                  }

                  mandatory true ;
                }

                leaf set-hex-str {
                  description 'DHCP relay packet option value is HEX string.' ;
                  type string {
                    length 1..200 {
                      description 'The length of HEX string.' ;
                    }

                  }

                  mandatory true ;
                }

              }

              case add {
                description 'DHCP relay packet oper type is add.' ;
                leaf add {
                  description 'DHCP relay packet oper type is add.' ;
                  type enumeration {
                    enum on {
                      value 3 ;
                    }

                  }

                  mandatory true ;
                }

                leaf add-hex-str {
                  description 'DHCP relay packet option value is HEX string.' ;
                  type string {
                    length 1..200 {
                      description 'The length of HEX string.' ;
                    }

                  }

                  mandatory true ;
                }

              }

              case remove {
                description 'DHCP relay packet oper type is remove.' ;
                leaf remove {
                  description 'DHCP relay packet oper type is remove.' ;
                  type enumeration {
                    enum on {
                      value 2 ;
                    }

                  }

                  mandatory true ;
                }

              }

              case keep {
                description 'DHCP relay packet oper type is keep.' ;
                leaf keep {
                  description 'DHCP relay packet oper type is keep.' ;
                  type enumeration {
                    enum on {
                      value 4 ;
                    }

                  }

                  mandatory true ;
                }

              }

            }

          }

          ncd:revise-date 2019-11-19 ;
        }

        container leasetime-configs {
          description 'DHCP relay packet leasetime option configurations.' ;
          list leasetime-config {
            description 'DHCP relay packet leasetime option configuration.' ;
            key 'packet-direction packet-type leasetime' ;
            leaf packet-direction {
              description 'DHCP relay packet direction.' ;
              type enumeration {
                enum receive {
                  value 1 ;
                }

                enum send {
                  value 2 ;
                }

              }

            }

            leaf packet-type {
              description 'DHCP relay packet type.' ;
              type enumeration {
                enum request {
                  value 1 ;
                }

                enum reply {
                  value 2 ;
                }

              }

            }

            leaf leasetime {
              description 'Leasetime option.' ;
              type enumeration {
                enum leasetime {
                  value 51 ;
                }

              }

            }

            choice oper-type {
              description 'DHCP relay packet oper type.' ;
              case set {
                description 'DHCP relay packet oper type is set.' ;
                leaf set {
                  description 'DHCP relay packet oper type is set.' ;
                  type enumeration {
                    enum on {
                      value 1 ;
                    }

                  }

                  mandatory true ;
                }

                leaf set-value {
                  description 'DHCP relay packet option value.' ;
                  type uint32 {
                    range 60..4294967295 ;

                  }

                  mandatory true ;
                }

              }

              case add {
                description 'DHCP relay packet oper type is add.' ;
                leaf add {
                  description 'DHCP relay packet oper type is add.' ;
                  type enumeration {
                    enum on {
                      value 3 ;
                    }

                  }

                  mandatory true ;
                }

                leaf add-value {
                  description 'DHCP relay packet option value.' ;
                  type uint32 {
                    range 60..4294967295 ;

                  }

                  mandatory true ;
                }

              }

              case remove {
                description 'DHCP relay packet oper type is remove.' ;
                leaf remove {
                  description 'DHCP relay packet oper type is remove.' ;
                  type enumeration {
                    enum on {
                      value 2 ;
                    }

                  }

                  mandatory true ;
                }

              }

              case keep {
                description 'DHCP relay packet oper type is keep.' ;
                leaf keep {
                  description 'DHCP relay packet oper type is keep.' ;
                  type enumeration {
                    enum on {
                      value 4 ;
                    }

                  }

                  mandatory true ;
                }

              }

            }

          }

          ncd:revise-date 2019-11-19 ;
        }

        container pkt-end-padding-configs {
          description 'DHCP relay packet end padding configurations.' ;
          list pkt-end-padding-config {
            description 'DHCP relay packet end padding configuration.' ;
            key packet-type ;
            leaf packet-type {
              description 'DHCP relay packet type.' ;
              type enumeration {
                enum request {
                  value 1 ;
                }

                enum reply {
                  value 2 ;
                }

              }

            }

            choice oper-type {
              description 'DHCP relay packet end padding oper type.' ;
              mandatory true ;
              case set {
                description 'DHCP relay packet end padding oper type is set.' ;
                leaf set {
                  description 'DHCP relay packet end padding oper type is set.' ;
                  type enumeration {
                    enum on {
                      value 1 ;
                    }

                  }

                  mandatory true ;
                }

                leaf set-hex-str {
                  description 'DHCP relay packet end padding value is HEX string.' ;
                  type string {
                    length 1..200 {
                      description 'The length of HEX string.' ;
                    }

                  }

                  mandatory true ;
                }

              }

              case keep {
                description 'DHCP relay packet end padding oper type is keep.' ;
                leaf keep {
                  description 'DHCP relay packet end padding oper type is keep.' ;
                  type enumeration {
                    enum on {
                      value 3 ;
                    }

                  }

                  mandatory true ;
                }

              }

            }

          }

          ncd:revise-date 2021-09-06 ;
        }

        container bootp-hops-configs {
          description 'DHCP relay packet BOOTP hops configurations.' ;
          list bootp-hops-config {
            description 'DHCP relay packet BOOTP hops configuration.' ;
            key 'packet-direction packet-type hops' ;
            leaf packet-direction {
              description 'DHCP relay packet direction.' ;
              type enumeration {
                enum receive {
                  value 1 ;
                }

                enum send {
                  value 2 ;
                }

              }

            }

            leaf packet-type {
              description 'DHCP relay packet type.' ;
              type enumeration {
                enum request {
                  value 1 ;
                }

                enum reply {
                  value 2 ;
                }

              }

            }

            leaf hops {
              description 'DHCP relay packet hops field.' ;
              type enumeration {
                enum hops {
                  value 1 ;
                }

              }

            }

            leaf hops-value {
              description 'DHCP relay packet hops valde.' ;
              type uint8 {
                range 0..254 ;

              }

              mandatory true ;
            }

          }

          ncd:revise-date 2021-10-13 ;
        }

        container bootp-flags-configs {
          description 'DHCP relay packet BOOTP flags configurations.' ;
          list bootp-flags-config {
            description 'DHCP relay packet BOOTP flags configuration.' ;
            key 'packet-direction packet-type flags' ;
            leaf packet-direction {
              description 'DHCP relay packet direction.' ;
              type enumeration {
                enum receive {
                  value 1 ;
                }

                enum send {
                  value 2 ;
                }

              }

            }

            leaf packet-type {
              description 'DHCP relay packet type.' ;
              type enumeration {
                enum request {
                  value 1 ;
                }

                enum reply {
                  value 2 ;
                }

              }

            }

            leaf flags {
              description 'DHCP relay packet flags field.' ;
              type enumeration {
                enum flags {
                  value 2 ;
                }

              }

            }

            leaf flags-str {
              description 'DHCP relay packet flags string.' ;
              type string {
                length 4 {
                  description 'The length of flags string.' ;
                }

              }

              mandatory true ;
            }

          }

          ncd:revise-date 2021-10-13 ;
        }

        container bootp-next-server-ip-configs {
          description 'DHCP relay packet BOOTP next server IP configurations.' ;
          list bootp-next-server-ip-config {
            description 'DHCP relay packet BOOTP next server IP configuration.' ;
            key 'packet-direction packet-type next-server-ip' ;
            leaf packet-direction {
              description 'DHCP relay packet direction.' ;
              type enumeration {
                enum receive {
                  value 1 ;
                }

                enum send {
                  value 2 ;
                }

              }

            }

            leaf packet-type {
              description 'DHCP relay packet type.' ;
              type enumeration {
                enum request {
                  value 1 ;
                }

                enum reply {
                  value 2 ;
                }

              }

            }

            leaf next-server-ip {
              description 'DHCP relay packet next server IP field.' ;
              type enumeration {
                enum next-server-ip {
                  value 3 ;
                }

              }

            }

            leaf next-server-ip-str {
              description 'DHCP relay packet next server IP string.' ;
              type ncd:ipv4-address-none-zero ;

              mandatory true ;
            }

          }

          ncd:revise-date 2021-10-13 ;
        }

        container bootp-sname-configs {
          description 'DHCP relay packet BOOTP sname configurations.' ;
          list bootp-sname-config {
            description 'DHCP relay packet BOOTP sname configuration.' ;
            key 'packet-direction packet-type sname' ;
            leaf packet-direction {
              description 'DHCP relay packet direction.' ;
              type enumeration {
                enum receive {
                  value 1 ;
                }

                enum send {
                  value 2 ;
                }

              }

            }

            leaf packet-type {
              description 'DHCP relay packet type.' ;
              type enumeration {
                enum request {
                  value 1 ;
                }

                enum reply {
                  value 2 ;
                }

              }

            }

            leaf sname {
              description 'DHCP relay packet sname field.' ;
              type enumeration {
                enum sname {
                  value 4 ;
                }

              }

            }

            choice sname-data-type {
              description 'DHCP relay packet sname data type.' ;
              mandatory true ;
              case ascii {
                description 'DHCP relay packet sname data type is ASCII string.' ;
                leaf ascii-str {
                  description 'BOOTP sname ASCII string configured.' ;
                  type string {
                    length 1..63 {
                      description 'The length of ASCII string.' ;
                    }

                  }

                  mandatory true ;
                }

              }

              case hex {
                description 'DHCP relay packet sname data type is HEX string.' ;
                leaf hex-str {
                  description 'BOOTP sname HEX string configured.' ;
                  type string {
                    length 1..128 {
                      description 'The length of HEX string.' ;
                    }

                  }

                  mandatory true ;
                }

              }

            }

          }

          ncd:revise-date 2021-10-13 ;
        }

        container bootp-file-configs {
          description 'DHCP relay packet BOOTP file configurations.' ;
          list bootp-file-config {
            description 'DHCP relay packet BOOTP file configuration.' ;
            key 'packet-direction packet-type file' ;
            leaf packet-direction {
              description 'DHCP relay packet direction.' ;
              type enumeration {
                enum receive {
                  value 1 ;
                }

                enum send {
                  value 2 ;
                }

              }

            }

            leaf packet-type {
              description 'DHCP relay packet type.' ;
              type enumeration {
                enum request {
                  value 1 ;
                }

                enum reply {
                  value 2 ;
                }

              }

            }

            leaf file {
              description 'DHCP relay packet file field.' ;
              type enumeration {
                enum file {
                  value 5 ;
                }

              }

            }

            choice file-data-type {
              description 'DHCP relay packet file data type.' ;
              mandatory true ;
              case ascii {
                description 'DHCP relay packet file data type is ASCII string.' ;
                leaf ascii-str {
                  description 'BOOTP file ASCII string configured.' ;
                  type string {
                    length 1..127 {
                      description 'The length of ASCII string.' ;
                    }

                  }

                  mandatory true ;
                }

              }

              case hex {
                description 'DHCP relay packet file data type is HEX string.' ;
                leaf hex-str {
                  description 'BOOTP file HEX string configured.' ;
                  type string {
                    length 1..254 {
                      description 'The length of HEX string.' ;
                    }

                  }

                  mandatory true ;
                }

              }

            }

          }

          ncd:revise-date 2021-10-13 ;
        }

      }

      container server {
        description 'DHCP server config.' ;
        container interfaces {
          description 'Interface-related configurations.' ;
          list interface {
            description 'DHCP server interface configuration on the interface.' ;
            key name ;
            leaf name {
              description 'DHCP interface name.' ;
              type ncd:ifname {
                length 1..31 {
                  description 'The interface name length.' ;
                }

              }

            }

            leaf server-policy {
              description 'DHCP policy of the interface for DHCP server.' ;
              type string {
                length 1..16 {
                  description 'The length of DHCP policy name.' ;
                }

              }

            }

            leaf dest-port {
              description 'Destination UDP port of sending packet to DHCP relay by DHCP server.' ;
              type enumeration {
                enum dest-port-server {
                  value 67 ;
                  description 'Destination UDP port is 67.' ;
                }

                enum dest-port-client {
                  value 68 ;
                  description 'Destination UDP port is 68.' ;
                }

              }

            }

            leaf dscp {
              description 'DHCP server DSCP value.' ;
              type uint8 {
                range 0..63 {
                  description 'dscp is from 0 to 63.' ;
                }

              }

              default 0 ;
            }

          }

        }

        container policys {
          description 'DHCP policy configuration.' ;
          list policy {
            description 'DHCP policy configuration.' ;
            key 'name priority' ;
            leaf name {
              description 'DHCP policy name.' ;
              type string {
                length 1..16 {
                  description 'The length of DHCP policy name.' ;
                }

              }

            }

            leaf priority {
              description 'DHCP policy priority.' ;
              type uint32 {
                range 1..64 ;

              }

            }

            leaf pool-name {
              description 'DHCP pool name configured in the policy.' ;
              type string {
                length 1..64 {
                  description 'The length of DHCP pool name.' ;
                }

              }

            }

            leaf vrf-name {
              description 'The VRF instance name configured in the policy.' ;
              type string {
                length 1..32 {
                  description 'The length of VRF name.' ;
                }

              }

            }

            leaf reserved-vrf-name {
              description 'The reserved VRF instance name configured in the policy.' ;
              type enumeration {
                enum null-value {
                  value 0 ;
                  description 'Not config reserved VRF name.' ;
                }

                enum mng {
                  value 1 ;
                  description 'The reserved VRF name is mng.' ;
                }

              }

              default null-value ;
              ncd:revise-date 2020-07-06 ;
            }

            leaf relay-agent {
              description 'DHCP relay agent IP address configured in the policy.' ;
              type ncd:ipv4-address ;

            }

            container option60 {
              description 'DHCP policy option60 configuration.' ;
              choice match-type {
                description 'The match type of option60.' ;
                case opt60-str {
                  description 'Match the option60 only when the option60 string configured is (or partialy) same as in the packet.' ;
                  leaf partial {
                    description 'Match the option60 only when the option60 string configured is (or partialy) same as in the packet.' ;
                    type enumeration {
                      enum whole {
                        value 0 ;
                        description 'Match the option60 only when the option60 string configured is same as in the packet.' ;
                      }

                      enum partial {
                        value 1 ;
                        description 'Match the option60 only when the option60 string configured is partialy same as in the packet.' ;
                      }

                    }

                    default whole ;
                  }

                  leaf string {
                    description 'Option60 string.' ;
                    type ncd:string-with-blank {
                      length 1..64 {
                        description 'The length of option60 string.' ;
                      }

                    }

                    mandatory true ;
                  }

                }

                case opt60-any {
                  description 'Match the option60 if the packet carries option60.' ;
                  leaf any {
                    description 'The option60 string is any.' ;
                    type enumeration {
                      enum none {
                        value 0 ;
                        description 'The option60 string is not any.' ;
                      }

                      enum any {
                        value 1 ;
                        description 'The option60 string is any.' ;
                      }

                    }

                    default none ;
                  }

                }

              }

            }

            container option93 {
              description 'DHCP policy option93 configuration.' ;
              choice match-type {
                description 'The match type of option93.' ;
                case hex {
                  description 'Match the option93 only when the option93 HEX string configured is same as in the packet.' ;
                  leaf hex-string {
                    description 'Option93 HEX string.' ;
                    type string {
                      length 1..64 {
                        description 'The length of option93 hex string.' ;
                      }

                    }

                    mandatory true ;
                  }

                }

                case other {
                  description 'Match the option93 if the packet carries option93.' ;
                  leaf other {
                    description 'The option93 string is other.' ;
                    type enumeration {
                      enum off {
                        value 0 ;
                        description 'The option93 string is not other.' ;
                      }

                      enum on {
                        value 2 ;
                        description 'The option93 string is other.' ;
                      }

                    }

                    default off ;
                  }

                }

              }

              ncd:revise-date 2022-05-27 ;
            }

          }

        }

        container global-config {
          description 'DHCP server global configuration.' ;
          leaf max-user {
            description "Max user numbers of DHCP server. It's toplimit depends on ability of the device. The default value is generally 64000." ;
            type uint32 {
              range 1..128000 {
                description "It's toplimit depends on ability of the device." ;
              }

            }

            default 64000 ;
          }

          leaf update-arp {
            description 'Updating the ARP or not.' ;
            type enumeration {
              enum update-off {
                value 0 ;
                description 'Turn off update-arp.' ;
              }

              enum update-on {
                value 1 ;
                description 'Turn on update-arp.' ;
              }

            }

            default update-off ;
          }

          leaf keep-opt82 {
            description 'Keeping option82 info of the request packet or not.' ;
            type enumeration {
              enum keep-opt82-off {
                value 0 ;
                description 'Turn off keep-opt82.' ;
              }

              enum keep-opt82-on {
                value 1 ;
                description 'Turn on keep-opt82.' ;
              }

            }

            default keep-opt82-off ;
          }

          leaf inter-chassis-enable {
            type enumeration {
              enum true {
                value 1 ;
                description 'Enable DHCP server inter-chassis.' ;
              }

              enum false {
                value 0 ;
                description 'Disable DHCP server inter-chassis.' ;
              }

            }

            description 'Enable DHCP server inter-chassis.' ;
            default false ;
            ncd:revise-date 2025-02-26 ;
          }

        }

        container pools {
          description 'DHCP pool configuration.' ;
          list pool {
            description 'DHCP pool cofiguration.' ;
            key name ;
            leaf name {
              description 'DHCP pool name.' ;
              type string {
                length 1..64 {
                  description 'The length of DHCP pool name.' ;
                }

              }

            }

            leaf ippool-name {
              description 'IP pool name configured in the DHCP pool.' ;
              type string {
                length 1..64 {
                  description 'The length of ip pool name.' ;
                }

              }

            }

            leaf ignore-request-list {
              if-feature ignore-request-list ;

              description 'When server send response packet,fill in option,ignore request list or not.' ;
              type enumeration {
                enum ignore {
                  value 1 ;
                  description 'When fill in option, ignore request list.' ;
                }

                enum not-ignore {
                  value 0 ;
                  description 'When fill in option,by request list.' ;
                }

              }

              default not-ignore ;
              ncd:revise-date 2016-01-05 ;
            }

            container static-pool-conf {
              description 'DHCP static pool configuration.' ;
              container static-pool-vrfs {
                description 'DHCP static pool with VRF configuration.' ;
                list static-pool-vrf {
                  description 'DHCP static pool with VRF configuration.' ;
                  key 'vrf-name mac-addr' ;
                  leaf vrf-name {
                    description 'The VRF instance name.' ;
                    type string {
                      length 1..32 {
                        description 'The length of VRF name.' ;
                      }

                    }

                  }

                  leaf mac-addr {
                    description 'The static user MAC address.' ;
                    type ncd:mac-address ;

                  }

                  leaf client-ip {
                    description 'DHCP static user IP address.' ;
                    type ncd:ipv4-address ;

                    mandatory true ;
                  }

                  leaf client-mask {
                    description 'DHCP static user mask address.' ;
                    type ncd:ipv4-mask ;

                    mandatory true ;
                  }

                  leaf option-template {
                    description 'DHCP static user option template.' ;
                    type string {
                      length 1..64 {
                        description 'The length of DHCP option template name.' ;
                      }

                    }

                    ncd:revise-date 2020-12-01 ;
                  }

                }

              }

              container static-pools {
                description 'DHCP static pool configuration.' ;
                list static-pool {
                  description 'DHCP static pool configuration.' ;
                  key mac-addr ;
                  leaf mac-addr {
                    description 'The static user MAC address.' ;
                    type ncd:mac-address ;

                  }

                  leaf client-ip {
                    description 'DHCP static user IP address.' ;
                    type ncd:ipv4-address ;

                    mandatory true ;
                  }

                  leaf client-mask {
                    description 'DHCP static user mask address.' ;
                    type ncd:ipv4-mask ;

                    mandatory true ;
                  }

                  leaf option-template {
                    description 'DHCP static user option template.' ;
                    type string {
                      length 1..64 {
                        description 'The length of DHCP option template name.' ;
                      }

                    }

                    ncd:revise-date 2020-12-01 ;
                  }

                }

              }

            }

            container default-routers {
              description 'DHCP pool default router configuration.' ;
              list default-router {
                description 'DHCP pool default router configuration.' ;
                key router-ip ;
                leaf router-ip {
                  description 'DHCP pool default router IP address.' ;
                  type ncd:ipv4-address ;

                }

              }

            }

            container dns-servers {
              description 'DHCP pool DNS server configuration.' ;
              list dns-server {
                description 'DHCP pool DNS server configuration.' ;
                key server-ip ;
                leaf server-ip {
                  description 'DHCP pool DNS server IP address.' ;
                  type ncd:ipv4-address ;

                }

              }

            }

            container options-conf {
              container sub-options {
                description 'DHCP pool option sub options configuration.' ;
                presence sub-options ;
                list sub-option {
                  description 'DHCP pool sub option configuration.' ;
                  key 'code sub-code' ;
                  leaf code {
                    description 'DHCP pool option code.' ;
                    type uint32 {
                      range 1..254 ;

                    }

                  }

                  leaf sub-code {
                    description 'DHCP pool option sub-option code.' ;
                    type uint32 {
                      range 1..254 ;

                    }

                  }

                  choice type {
                    description 'DHCP pool option type.' ;
                    mandatory true ;
                    case ascii {
                      description 'DHCP pool option type is ASCII string.' ;
                      leaf ascii-str {
                        description 'DHCP pool option ASCII string configured.' ;
                        type string {
                          length 1..200 {
                            description 'The length of ASCII string.' ;
                          }

                        }

                        mandatory true ;
                      }

                    }

                    case hex {
                      description 'DHCP pool option type is HEX string.' ;
                      leaf hex-str {
                        description 'DHCP pool option HEX string configured.' ;
                        type string {
                          length 1..200 {
                            description 'The length of HEX string.' ;
                          }

                        }

                        mandatory true ;
                      }

                    }

                    case ip {
                      description 'DHCP pool option type is IP.' ;
                      leaf ip-addr1 {
                        description 'DHCP pool option IP address configured.' ;
                        type ncd:ipv4-address {
                          pattern '([1-9][0-9]*\.[1-9][0-9]*\.[1-9][0-9]*\.[1-9][0-9]*)|([1-9][0-9]*\.0\.0\.0)|(0\.[1-9][0-9]*\.0\.0)|(0\.0\.[1-9][0-9]*\.0)|(0\.0\.0\.[1-9][0-9]*)|([1-9][0-9]*\.[1-9][0-9]*\.0\.0)|(0\.[1-9][0-9]*\.[1-9][0-9]*\.0)|(0\.0\.[1-9][0-9]*\.[1-9][0-9]*)|([1-9][0-9]*\.0\.0\.[1-9][0-9]*)|(0\.[1-9][0-9]*\.0\.[1-9][0-9]*)|([1-9][0-9]*\.0\.[1-9][0-9]*\.0)|([1-9][0-9]*\.[1-9][0-9]*\.[1-9][0-9]*\.0)|([1-9][0-9]*\.[1-9][0-9]*\.0\.[1-9][0-9]*)|([1-9][0-9]*\.0\.[1-9][0-9]*\.[1-9][0-9]*)|(0\.[1-9][0-9]*\.[1-9][0-9]*\.[1-9][0-9]*)' ;

                        }

                        mandatory true ;
                      }

                      leaf ip-addr2 {
                        description 'DHCP pool option IP address configured.' ;
                        type ncd:ipv4-address {
                          pattern '([1-9][0-9]*\.[1-9][0-9]*\.[1-9][0-9]*\.[1-9][0-9]*)|([1-9][0-9]*\.0\.0\.0)|(0\.[1-9][0-9]*\.0\.0)|(0\.0\.[1-9][0-9]*\.0)|(0\.0\.0\.[1-9][0-9]*)|([1-9][0-9]*\.[1-9][0-9]*\.0\.0)|(0\.[1-9][0-9]*\.[1-9][0-9]*\.0)|(0\.0\.[1-9][0-9]*\.[1-9][0-9]*)|([1-9][0-9]*\.0\.0\.[1-9][0-9]*)|(0\.[1-9][0-9]*\.0\.[1-9][0-9]*)|([1-9][0-9]*\.0\.[1-9][0-9]*\.0)|([1-9][0-9]*\.[1-9][0-9]*\.[1-9][0-9]*\.0)|([1-9][0-9]*\.[1-9][0-9]*\.0\.[1-9][0-9]*)|([1-9][0-9]*\.0\.[1-9][0-9]*\.[1-9][0-9]*)|(0\.[1-9][0-9]*\.[1-9][0-9]*\.[1-9][0-9]*)' ;

                        }

                      }

                      leaf ip-addr3 {
                        description 'DHCP pool option IP address configured.' ;
                        type ncd:ipv4-address {
                          pattern '([1-9][0-9]*\.[1-9][0-9]*\.[1-9][0-9]*\.[1-9][0-9]*)|([1-9][0-9]*\.0\.0\.0)|(0\.[1-9][0-9]*\.0\.0)|(0\.0\.[1-9][0-9]*\.0)|(0\.0\.0\.[1-9][0-9]*)|([1-9][0-9]*\.[1-9][0-9]*\.0\.0)|(0\.[1-9][0-9]*\.[1-9][0-9]*\.0)|(0\.0\.[1-9][0-9]*\.[1-9][0-9]*)|([1-9][0-9]*\.0\.0\.[1-9][0-9]*)|(0\.[1-9][0-9]*\.0\.[1-9][0-9]*)|([1-9][0-9]*\.0\.[1-9][0-9]*\.0)|([1-9][0-9]*\.[1-9][0-9]*\.[1-9][0-9]*\.0)|([1-9][0-9]*\.[1-9][0-9]*\.0\.[1-9][0-9]*)|([1-9][0-9]*\.0\.[1-9][0-9]*\.[1-9][0-9]*)|(0\.[1-9][0-9]*\.[1-9][0-9]*\.[1-9][0-9]*)' ;

                        }

                      }

                      leaf ip-addr4 {
                        description 'DHCP pool option IP address configured.' ;
                        type ncd:ipv4-address {
                          pattern '([1-9][0-9]*\.[1-9][0-9]*\.[1-9][0-9]*\.[1-9][0-9]*)|([1-9][0-9]*\.0\.0\.0)|(0\.[1-9][0-9]*\.0\.0)|(0\.0\.[1-9][0-9]*\.0)|(0\.0\.0\.[1-9][0-9]*)|([1-9][0-9]*\.[1-9][0-9]*\.0\.0)|(0\.[1-9][0-9]*\.[1-9][0-9]*\.0)|(0\.0\.[1-9][0-9]*\.[1-9][0-9]*)|([1-9][0-9]*\.0\.0\.[1-9][0-9]*)|(0\.[1-9][0-9]*\.0\.[1-9][0-9]*)|([1-9][0-9]*\.0\.[1-9][0-9]*\.0)|([1-9][0-9]*\.[1-9][0-9]*\.[1-9][0-9]*\.0)|([1-9][0-9]*\.[1-9][0-9]*\.0\.[1-9][0-9]*)|([1-9][0-9]*\.0\.[1-9][0-9]*\.[1-9][0-9]*)|(0\.[1-9][0-9]*\.[1-9][0-9]*\.[1-9][0-9]*)' ;

                        }

                      }

                      leaf ip-addr5 {
                        description 'DHCP pool option IP address configured.' ;
                        type ncd:ipv4-address {
                          pattern '([1-9][0-9]*\.[1-9][0-9]*\.[1-9][0-9]*\.[1-9][0-9]*)|([1-9][0-9]*\.0\.0\.0)|(0\.[1-9][0-9]*\.0\.0)|(0\.0\.[1-9][0-9]*\.0)|(0\.0\.0\.[1-9][0-9]*)|([1-9][0-9]*\.[1-9][0-9]*\.0\.0)|(0\.[1-9][0-9]*\.[1-9][0-9]*\.0)|(0\.0\.[1-9][0-9]*\.[1-9][0-9]*)|([1-9][0-9]*\.0\.0\.[1-9][0-9]*)|(0\.[1-9][0-9]*\.0\.[1-9][0-9]*)|([1-9][0-9]*\.0\.[1-9][0-9]*\.0)|([1-9][0-9]*\.[1-9][0-9]*\.[1-9][0-9]*\.0)|([1-9][0-9]*\.[1-9][0-9]*\.0\.[1-9][0-9]*)|([1-9][0-9]*\.0\.[1-9][0-9]*\.[1-9][0-9]*)|(0\.[1-9][0-9]*\.[1-9][0-9]*\.[1-9][0-9]*)' ;

                        }

                      }

                      leaf ip-addr6 {
                        description 'DHCP pool option IP address configured.' ;
                        type ncd:ipv4-address {
                          pattern '([1-9][0-9]*\.[1-9][0-9]*\.[1-9][0-9]*\.[1-9][0-9]*)|([1-9][0-9]*\.0\.0\.0)|(0\.[1-9][0-9]*\.0\.0)|(0\.0\.[1-9][0-9]*\.0)|(0\.0\.0\.[1-9][0-9]*)|([1-9][0-9]*\.[1-9][0-9]*\.0\.0)|(0\.[1-9][0-9]*\.[1-9][0-9]*\.0)|(0\.0\.[1-9][0-9]*\.[1-9][0-9]*)|([1-9][0-9]*\.0\.0\.[1-9][0-9]*)|(0\.[1-9][0-9]*\.0\.[1-9][0-9]*)|([1-9][0-9]*\.0\.[1-9][0-9]*\.0)|([1-9][0-9]*\.[1-9][0-9]*\.[1-9][0-9]*\.0)|([1-9][0-9]*\.[1-9][0-9]*\.0\.[1-9][0-9]*)|([1-9][0-9]*\.0\.[1-9][0-9]*\.[1-9][0-9]*)|(0\.[1-9][0-9]*\.[1-9][0-9]*\.[1-9][0-9]*)' ;

                        }

                      }

                      leaf ip-addr7 {
                        description 'DHCP pool option IP address configured.' ;
                        type ncd:ipv4-address {
                          pattern '([1-9][0-9]*\.[1-9][0-9]*\.[1-9][0-9]*\.[1-9][0-9]*)|([1-9][0-9]*\.0\.0\.0)|(0\.[1-9][0-9]*\.0\.0)|(0\.0\.[1-9][0-9]*\.0)|(0\.0\.0\.[1-9][0-9]*)|([1-9][0-9]*\.[1-9][0-9]*\.0\.0)|(0\.[1-9][0-9]*\.[1-9][0-9]*\.0)|(0\.0\.[1-9][0-9]*\.[1-9][0-9]*)|([1-9][0-9]*\.0\.0\.[1-9][0-9]*)|(0\.[1-9][0-9]*\.0\.[1-9][0-9]*)|([1-9][0-9]*\.0\.[1-9][0-9]*\.0)|([1-9][0-9]*\.[1-9][0-9]*\.[1-9][0-9]*\.0)|([1-9][0-9]*\.[1-9][0-9]*\.0\.[1-9][0-9]*)|([1-9][0-9]*\.0\.[1-9][0-9]*\.[1-9][0-9]*)|(0\.[1-9][0-9]*\.[1-9][0-9]*\.[1-9][0-9]*)' ;

                        }

                      }

                      leaf ip-addr8 {
                        description 'DHCP pool option IP address configured.' ;
                        type ncd:ipv4-address {
                          pattern '([1-9][0-9]*\.[1-9][0-9]*\.[1-9][0-9]*\.[1-9][0-9]*)|([1-9][0-9]*\.0\.0\.0)|(0\.[1-9][0-9]*\.0\.0)|(0\.0\.[1-9][0-9]*\.0)|(0\.0\.0\.[1-9][0-9]*)|([1-9][0-9]*\.[1-9][0-9]*\.0\.0)|(0\.[1-9][0-9]*\.[1-9][0-9]*\.0)|(0\.0\.[1-9][0-9]*\.[1-9][0-9]*)|([1-9][0-9]*\.0\.0\.[1-9][0-9]*)|(0\.[1-9][0-9]*\.0\.[1-9][0-9]*)|([1-9][0-9]*\.0\.[1-9][0-9]*\.0)|([1-9][0-9]*\.[1-9][0-9]*\.[1-9][0-9]*\.0)|([1-9][0-9]*\.[1-9][0-9]*\.0\.[1-9][0-9]*)|([1-9][0-9]*\.0\.[1-9][0-9]*\.[1-9][0-9]*)|(0\.[1-9][0-9]*\.[1-9][0-9]*\.[1-9][0-9]*)' ;

                        }

                      }

                    }

                  }

                }

              }

              container options {
                description 'DHCP pool options configuration.' ;
                presence options ;
                list option {
                  description 'DHCP pool option configuration.' ;
                  key code ;
                  leaf code {
                    description 'DHCP pool option code.' ;
                    type uint32 {
                      range 1..254 ;

                    }

                  }

                  choice type {
                    description 'DHCP pool option type.' ;
                    mandatory true ;
                    case ascii {
                      description 'DHCP pool option type is ASCII string.' ;
                      leaf ascii-str {
                        description 'DHCP pool option ASCII string configured.' ;
                        type string {
                          length 1..200 {
                            description 'The length of ASCII string.' ;
                          }

                        }

                        mandatory true ;
                      }

                    }

                    case hex {
                      description 'DHCP pool option type is HEX string.' ;
                      leaf hex-str {
                        description 'DHCP pool option HEX string configured.' ;
                        type string {
                          length 1..200 {
                            description 'The length of HEX string.' ;
                          }

                        }

                        mandatory true ;
                      }

                    }

                    case ip {
                      description 'DHCP pool option type is IP.' ;
                      leaf ip-addr1 {
                        description 'DHCP pool option IP address configured.' ;
                        type ncd:ipv4-address {
                          pattern '([1-9][0-9]*\.[1-9][0-9]*\.[1-9][0-9]*\.[1-9][0-9]*)|([1-9][0-9]*\.0\.0\.0)|(0\.[1-9][0-9]*\.0\.0)|(0\.0\.[1-9][0-9]*\.0)|(0\.0\.0\.[1-9][0-9]*)|([1-9][0-9]*\.[1-9][0-9]*\.0\.0)|(0\.[1-9][0-9]*\.[1-9][0-9]*\.0)|(0\.0\.[1-9][0-9]*\.[1-9][0-9]*)|([1-9][0-9]*\.0\.0\.[1-9][0-9]*)|(0\.[1-9][0-9]*\.0\.[1-9][0-9]*)|([1-9][0-9]*\.0\.[1-9][0-9]*\.0)|([1-9][0-9]*\.[1-9][0-9]*\.[1-9][0-9]*\.0)|([1-9][0-9]*\.[1-9][0-9]*\.0\.[1-9][0-9]*)|([1-9][0-9]*\.0\.[1-9][0-9]*\.[1-9][0-9]*)|(0\.[1-9][0-9]*\.[1-9][0-9]*\.[1-9][0-9]*)' ;

                        }

                        mandatory true ;
                      }

                      leaf ip-addr2 {
                        description 'DHCP pool option IP address configured.' ;
                        type ncd:ipv4-address {
                          pattern '([1-9][0-9]*\.[1-9][0-9]*\.[1-9][0-9]*\.[1-9][0-9]*)|([1-9][0-9]*\.0\.0\.0)|(0\.[1-9][0-9]*\.0\.0)|(0\.0\.[1-9][0-9]*\.0)|(0\.0\.0\.[1-9][0-9]*)|([1-9][0-9]*\.[1-9][0-9]*\.0\.0)|(0\.[1-9][0-9]*\.[1-9][0-9]*\.0)|(0\.0\.[1-9][0-9]*\.[1-9][0-9]*)|([1-9][0-9]*\.0\.0\.[1-9][0-9]*)|(0\.[1-9][0-9]*\.0\.[1-9][0-9]*)|([1-9][0-9]*\.0\.[1-9][0-9]*\.0)|([1-9][0-9]*\.[1-9][0-9]*\.[1-9][0-9]*\.0)|([1-9][0-9]*\.[1-9][0-9]*\.0\.[1-9][0-9]*)|([1-9][0-9]*\.0\.[1-9][0-9]*\.[1-9][0-9]*)|(0\.[1-9][0-9]*\.[1-9][0-9]*\.[1-9][0-9]*)' ;

                        }

                      }

                      leaf ip-addr3 {
                        description 'DHCP pool option IP address configured.' ;
                        type ncd:ipv4-address {
                          pattern '([1-9][0-9]*\.[1-9][0-9]*\.[1-9][0-9]*\.[1-9][0-9]*)|([1-9][0-9]*\.0\.0\.0)|(0\.[1-9][0-9]*\.0\.0)|(0\.0\.[1-9][0-9]*\.0)|(0\.0\.0\.[1-9][0-9]*)|([1-9][0-9]*\.[1-9][0-9]*\.0\.0)|(0\.[1-9][0-9]*\.[1-9][0-9]*\.0)|(0\.0\.[1-9][0-9]*\.[1-9][0-9]*)|([1-9][0-9]*\.0\.0\.[1-9][0-9]*)|(0\.[1-9][0-9]*\.0\.[1-9][0-9]*)|([1-9][0-9]*\.0\.[1-9][0-9]*\.0)|([1-9][0-9]*\.[1-9][0-9]*\.[1-9][0-9]*\.0)|([1-9][0-9]*\.[1-9][0-9]*\.0\.[1-9][0-9]*)|([1-9][0-9]*\.0\.[1-9][0-9]*\.[1-9][0-9]*)|(0\.[1-9][0-9]*\.[1-9][0-9]*\.[1-9][0-9]*)' ;

                        }

                      }

                      leaf ip-addr4 {
                        description 'DHCP pool option IP address configured.' ;
                        type ncd:ipv4-address {
                          pattern '([1-9][0-9]*\.[1-9][0-9]*\.[1-9][0-9]*\.[1-9][0-9]*)|([1-9][0-9]*\.0\.0\.0)|(0\.[1-9][0-9]*\.0\.0)|(0\.0\.[1-9][0-9]*\.0)|(0\.0\.0\.[1-9][0-9]*)|([1-9][0-9]*\.[1-9][0-9]*\.0\.0)|(0\.[1-9][0-9]*\.[1-9][0-9]*\.0)|(0\.0\.[1-9][0-9]*\.[1-9][0-9]*)|([1-9][0-9]*\.0\.0\.[1-9][0-9]*)|(0\.[1-9][0-9]*\.0\.[1-9][0-9]*)|([1-9][0-9]*\.0\.[1-9][0-9]*\.0)|([1-9][0-9]*\.[1-9][0-9]*\.[1-9][0-9]*\.0)|([1-9][0-9]*\.[1-9][0-9]*\.0\.[1-9][0-9]*)|([1-9][0-9]*\.0\.[1-9][0-9]*\.[1-9][0-9]*)|(0\.[1-9][0-9]*\.[1-9][0-9]*\.[1-9][0-9]*)' ;

                        }

                      }

                      leaf ip-addr5 {
                        description 'DHCP pool option IP address configured.' ;
                        type ncd:ipv4-address {
                          pattern '([1-9][0-9]*\.[1-9][0-9]*\.[1-9][0-9]*\.[1-9][0-9]*)|([1-9][0-9]*\.0\.0\.0)|(0\.[1-9][0-9]*\.0\.0)|(0\.0\.[1-9][0-9]*\.0)|(0\.0\.0\.[1-9][0-9]*)|([1-9][0-9]*\.[1-9][0-9]*\.0\.0)|(0\.[1-9][0-9]*\.[1-9][0-9]*\.0)|(0\.0\.[1-9][0-9]*\.[1-9][0-9]*)|([1-9][0-9]*\.0\.0\.[1-9][0-9]*)|(0\.[1-9][0-9]*\.0\.[1-9][0-9]*)|([1-9][0-9]*\.0\.[1-9][0-9]*\.0)|([1-9][0-9]*\.[1-9][0-9]*\.[1-9][0-9]*\.0)|([1-9][0-9]*\.[1-9][0-9]*\.0\.[1-9][0-9]*)|([1-9][0-9]*\.0\.[1-9][0-9]*\.[1-9][0-9]*)|(0\.[1-9][0-9]*\.[1-9][0-9]*\.[1-9][0-9]*)' ;

                        }

                      }

                      leaf ip-addr6 {
                        description 'DHCP pool option IP address configured.' ;
                        type ncd:ipv4-address {
                          pattern '([1-9][0-9]*\.[1-9][0-9]*\.[1-9][0-9]*\.[1-9][0-9]*)|([1-9][0-9]*\.0\.0\.0)|(0\.[1-9][0-9]*\.0\.0)|(0\.0\.[1-9][0-9]*\.0)|(0\.0\.0\.[1-9][0-9]*)|([1-9][0-9]*\.[1-9][0-9]*\.0\.0)|(0\.[1-9][0-9]*\.[1-9][0-9]*\.0)|(0\.0\.[1-9][0-9]*\.[1-9][0-9]*)|([1-9][0-9]*\.0\.0\.[1-9][0-9]*)|(0\.[1-9][0-9]*\.0\.[1-9][0-9]*)|([1-9][0-9]*\.0\.[1-9][0-9]*\.0)|([1-9][0-9]*\.[1-9][0-9]*\.[1-9][0-9]*\.0)|([1-9][0-9]*\.[1-9][0-9]*\.0\.[1-9][0-9]*)|([1-9][0-9]*\.0\.[1-9][0-9]*\.[1-9][0-9]*)|(0\.[1-9][0-9]*\.[1-9][0-9]*\.[1-9][0-9]*)' ;

                        }

                      }

                      leaf ip-addr7 {
                        description 'DHCP pool option IP address configured.' ;
                        type ncd:ipv4-address {
                          pattern '([1-9][0-9]*\.[1-9][0-9]*\.[1-9][0-9]*\.[1-9][0-9]*)|([1-9][0-9]*\.0\.0\.0)|(0\.[1-9][0-9]*\.0\.0)|(0\.0\.[1-9][0-9]*\.0)|(0\.0\.0\.[1-9][0-9]*)|([1-9][0-9]*\.[1-9][0-9]*\.0\.0)|(0\.[1-9][0-9]*\.[1-9][0-9]*\.0)|(0\.0\.[1-9][0-9]*\.[1-9][0-9]*)|([1-9][0-9]*\.0\.0\.[1-9][0-9]*)|(0\.[1-9][0-9]*\.0\.[1-9][0-9]*)|([1-9][0-9]*\.0\.[1-9][0-9]*\.0)|([1-9][0-9]*\.[1-9][0-9]*\.[1-9][0-9]*\.0)|([1-9][0-9]*\.[1-9][0-9]*\.0\.[1-9][0-9]*)|([1-9][0-9]*\.0\.[1-9][0-9]*\.[1-9][0-9]*)|(0\.[1-9][0-9]*\.[1-9][0-9]*\.[1-9][0-9]*)' ;

                        }

                      }

                      leaf ip-addr8 {
                        description 'DHCP pool option IP address configured.' ;
                        type ncd:ipv4-address {
                          pattern '([1-9][0-9]*\.[1-9][0-9]*\.[1-9][0-9]*\.[1-9][0-9]*)|([1-9][0-9]*\.0\.0\.0)|(0\.[1-9][0-9]*\.0\.0)|(0\.0\.[1-9][0-9]*\.0)|(0\.0\.0\.[1-9][0-9]*)|([1-9][0-9]*\.[1-9][0-9]*\.0\.0)|(0\.[1-9][0-9]*\.[1-9][0-9]*\.0)|(0\.0\.[1-9][0-9]*\.[1-9][0-9]*)|([1-9][0-9]*\.0\.0\.[1-9][0-9]*)|(0\.[1-9][0-9]*\.0\.[1-9][0-9]*)|([1-9][0-9]*\.0\.[1-9][0-9]*\.0)|([1-9][0-9]*\.[1-9][0-9]*\.[1-9][0-9]*\.0)|([1-9][0-9]*\.[1-9][0-9]*\.0\.[1-9][0-9]*)|([1-9][0-9]*\.0\.[1-9][0-9]*\.[1-9][0-9]*)|(0\.[1-9][0-9]*\.[1-9][0-9]*\.[1-9][0-9]*)' ;

                        }

                      }

                    }

                    case from-request-packet {
                      description 'Get DHCP pool option value from request packet.' ;
                      leaf from-request-packet {
                        description 'Get DHCP pool option value from request packet or not.' ;
                        type enumeration {
                          enum on {
                            value 1 ;
                            description 'Get DHCP pool option value from request packet.' ;
                          }

                        }

                      }

                      ncd:revise-date 2018-12-25 ;
                    }

                  }

                }

              }

              description 'DHCP pool options configuration.' ;
            }

            container opt212-6rd {
              description 'DHCP pool option212 configuration.' ;
              presence opt212-6rd ;
              leaf ipv6-prefix {
                description 'DHCP pool option212 IPv6 prefix.' ;
                type ncd:ipv6-address ;

                mandatory true ;
              }

              leaf prefix-len {
                description 'DHCP pool option212 IPv6 prefix length.' ;
                type uint32 {
                  range 1..128 ;

                }

                mandatory true ;
              }

              leaf mask-len {
                description 'DHCP pool option212 mask length.' ;
                type uint32 {
                  range 0..32 ;

                }

                mandatory true ;
              }

              leaf br-addr1 {
                description 'DHCP pool option212 BR address 1.' ;
                type ncd:ipv4-address ;

                mandatory true ;
              }

              leaf br-addr2 {
                description 'DHCP pool option212 BR address 2.' ;
                type ncd:ipv4-address ;

              }

              leaf br-addr3 {
                description 'DHCP pool option212 BR address 3.' ;
                type ncd:ipv4-address ;

              }

              leaf br-addr4 {
                description 'DHCP pool option212 BR address 4.' ;
                type ncd:ipv4-address ;

              }

              leaf br-addr5 {
                description 'DHCP pool option212 BR address 5.' ;
                type ncd:ipv4-address ;

              }

            }

            container leasetime {
              description 'DHCP pool leasetime.' ;
              choice type {
                description 'Leasetime type.' ;
                default finite ;
                case finite {
                  description 'DHCP pool leasetime is finite.' ;
                  container lease-item {
                    description 'Finite leasetime item.' ;
                    presence lease-item ;
                    leaf lease-days {
                      description 'DHCP pool leasetime days.' ;
                      type uint32 {
                        range 0..365 ;

                      }

                      mandatory true ;
                    }

                    leaf lease-hours {
                      description 'DHCP pool leasetime hours.' ;
                      type uint8 {
                        range 0..23 ;

                      }

                      default 1 ;
                    }

                    leaf lease-minutes {
                      description 'DHCP pool leasetime minutes.' ;
                      type uint8 {
                        range 0..59 ;

                      }

                      mandatory true ;
                    }

                    leaf lease-seconds {
                      description 'DHCP pool leasetime seconds.' ;
                      type uint8 {
                        range 0..59 ;

                      }

                      ncd:revise-date 2018-01-22 ;
                    }

                  }

                }

                case infinite {
                  description 'DHCP pool leasetime is infinite.' ;
                  leaf lease-infinite {
                    description 'DHCP pool leasetime is infinite or not.' ;
                    type enumeration {
                      enum infinite-off {
                        value 0 ;
                        description 'Set DHCP pool leasetime finite.' ;
                      }

                      enum infinite-on {
                        value 1 ;
                        description 'Set DHCP pool leasetime infinite.' ;
                      }

                    }

                    default infinite-off ;
                  }

                }

              }

            }

            container import {
              description 'Importing DHCP option parameters.' ;
              presence import ;
              leaf ifname {
                description 'Interface name.' ;
                type ncd:ifname {
                  length 1..31 {
                    description 'The length of interface name.' ;
                  }

                }

                mandatory true ;
              }

              leaf dns {
                description 'Import DNS.' ;
                type enumeration {
                  enum import-dns-off {
                    value 0 ;
                    description 'Not import DNS.' ;
                  }

                  enum import-dns-on {
                    value 1 ;
                    description 'Import DNS.' ;
                  }

                }

                mandatory true ;
              }

            }

            container option125-conf {
              description 'Option125 configuration.' ;
              list option125 {
                description 'Option125 configuration.' ;
                key 'enterprise sub-code' ;
                leaf enterprise {
                  description 'DHCP pool option125 enterprise code.' ;
                  type uint32 {
                    range 1..50000 ;

                  }

                }

                leaf sub-code {
                  description 'DHCP pool option125 sub-option code.' ;
                  type uint32 {
                    range 1..254 ;

                  }

                }

                choice type {
                  description 'DHCP pool option125 type.' ;
                  mandatory true ;
                  case ascii {
                    description 'DHCP pool option125 type is ASCII string.' ;
                    leaf ascii-str {
                      description 'DHCP pool option125 ASCII string configured.' ;
                      type string {
                        length 1..200 {
                          description 'The length of ASCII string.' ;
                        }

                      }

                      mandatory true ;
                    }

                  }

                  case hex {
                    description 'DHCP pool option125 type is HEX string.' ;
                    leaf hex-str {
                      description 'DHCP pool option125 HEX string configured.' ;
                      type string {
                        length 1..200 {
                          description 'The length of HEX string.' ;
                        }

                      }

                      mandatory true ;
                    }

                  }

                  case ip {
                    description 'DHCP pool option125 type is IP.' ;
                    leaf ip-addr1 {
                      description 'DHCP pool option125 IP address configured.' ;
                      type ncd:ipv4-address {
                        pattern '([1-9][0-9]*\.[1-9][0-9]*\.[1-9][0-9]*\.[1-9][0-9]*)|([1-9][0-9]*\.0\.0\.0)|(0\.[1-9][0-9]*\.0\.0)|(0\.0\.[1-9][0-9]*\.0)|(0\.0\.0\.[1-9][0-9]*)|([1-9][0-9]*\.[1-9][0-9]*\.0\.0)|(0\.[1-9][0-9]*\.[1-9][0-9]*\.0)|(0\.0\.[1-9][0-9]*\.[1-9][0-9]*)|([1-9][0-9]*\.0\.0\.[1-9][0-9]*)|(0\.[1-9][0-9]*\.0\.[1-9][0-9]*)|([1-9][0-9]*\.0\.[1-9][0-9]*\.0)|([1-9][0-9]*\.[1-9][0-9]*\.[1-9][0-9]*\.0)|([1-9][0-9]*\.[1-9][0-9]*\.0\.[1-9][0-9]*)|([1-9][0-9]*\.0\.[1-9][0-9]*\.[1-9][0-9]*)|(0\.[1-9][0-9]*\.[1-9][0-9]*\.[1-9][0-9]*)' ;

                      }

                      mandatory true ;
                    }

                    leaf ip-addr2 {
                      description 'DHCP pool option125 IP address configured.' ;
                      type ncd:ipv4-address {
                        pattern '([1-9][0-9]*\.[1-9][0-9]*\.[1-9][0-9]*\.[1-9][0-9]*)|([1-9][0-9]*\.0\.0\.0)|(0\.[1-9][0-9]*\.0\.0)|(0\.0\.[1-9][0-9]*\.0)|(0\.0\.0\.[1-9][0-9]*)|([1-9][0-9]*\.[1-9][0-9]*\.0\.0)|(0\.[1-9][0-9]*\.[1-9][0-9]*\.0)|(0\.0\.[1-9][0-9]*\.[1-9][0-9]*)|([1-9][0-9]*\.0\.0\.[1-9][0-9]*)|(0\.[1-9][0-9]*\.0\.[1-9][0-9]*)|([1-9][0-9]*\.0\.[1-9][0-9]*\.0)|([1-9][0-9]*\.[1-9][0-9]*\.[1-9][0-9]*\.0)|([1-9][0-9]*\.[1-9][0-9]*\.0\.[1-9][0-9]*)|([1-9][0-9]*\.0\.[1-9][0-9]*\.[1-9][0-9]*)|(0\.[1-9][0-9]*\.[1-9][0-9]*\.[1-9][0-9]*)' ;

                      }

                    }

                    leaf ip-addr3 {
                      description 'DHCP pool option125 IP address configured.' ;
                      type ncd:ipv4-address {
                        pattern '([1-9][0-9]*\.[1-9][0-9]*\.[1-9][0-9]*\.[1-9][0-9]*)|([1-9][0-9]*\.0\.0\.0)|(0\.[1-9][0-9]*\.0\.0)|(0\.0\.[1-9][0-9]*\.0)|(0\.0\.0\.[1-9][0-9]*)|([1-9][0-9]*\.[1-9][0-9]*\.0\.0)|(0\.[1-9][0-9]*\.[1-9][0-9]*\.0)|(0\.0\.[1-9][0-9]*\.[1-9][0-9]*)|([1-9][0-9]*\.0\.0\.[1-9][0-9]*)|(0\.[1-9][0-9]*\.0\.[1-9][0-9]*)|([1-9][0-9]*\.0\.[1-9][0-9]*\.0)|([1-9][0-9]*\.[1-9][0-9]*\.[1-9][0-9]*\.0)|([1-9][0-9]*\.[1-9][0-9]*\.0\.[1-9][0-9]*)|([1-9][0-9]*\.0\.[1-9][0-9]*\.[1-9][0-9]*)|(0\.[1-9][0-9]*\.[1-9][0-9]*\.[1-9][0-9]*)' ;

                      }

                    }

                    leaf ip-addr4 {
                      description 'DHCP pool option125 IP address configured.' ;
                      type ncd:ipv4-address {
                        pattern '([1-9][0-9]*\.[1-9][0-9]*\.[1-9][0-9]*\.[1-9][0-9]*)|([1-9][0-9]*\.0\.0\.0)|(0\.[1-9][0-9]*\.0\.0)|(0\.0\.[1-9][0-9]*\.0)|(0\.0\.0\.[1-9][0-9]*)|([1-9][0-9]*\.[1-9][0-9]*\.0\.0)|(0\.[1-9][0-9]*\.[1-9][0-9]*\.0)|(0\.0\.[1-9][0-9]*\.[1-9][0-9]*)|([1-9][0-9]*\.0\.0\.[1-9][0-9]*)|(0\.[1-9][0-9]*\.0\.[1-9][0-9]*)|([1-9][0-9]*\.0\.[1-9][0-9]*\.0)|([1-9][0-9]*\.[1-9][0-9]*\.[1-9][0-9]*\.0)|([1-9][0-9]*\.[1-9][0-9]*\.0\.[1-9][0-9]*)|([1-9][0-9]*\.0\.[1-9][0-9]*\.[1-9][0-9]*)|(0\.[1-9][0-9]*\.[1-9][0-9]*\.[1-9][0-9]*)' ;

                      }

                    }

                    leaf ip-addr5 {
                      description 'DHCP pool option125 IP address configured.' ;
                      type ncd:ipv4-address {
                        pattern '([1-9][0-9]*\.[1-9][0-9]*\.[1-9][0-9]*\.[1-9][0-9]*)|([1-9][0-9]*\.0\.0\.0)|(0\.[1-9][0-9]*\.0\.0)|(0\.0\.[1-9][0-9]*\.0)|(0\.0\.0\.[1-9][0-9]*)|([1-9][0-9]*\.[1-9][0-9]*\.0\.0)|(0\.[1-9][0-9]*\.[1-9][0-9]*\.0)|(0\.0\.[1-9][0-9]*\.[1-9][0-9]*)|([1-9][0-9]*\.0\.0\.[1-9][0-9]*)|(0\.[1-9][0-9]*\.0\.[1-9][0-9]*)|([1-9][0-9]*\.0\.[1-9][0-9]*\.0)|([1-9][0-9]*\.[1-9][0-9]*\.[1-9][0-9]*\.0)|([1-9][0-9]*\.[1-9][0-9]*\.0\.[1-9][0-9]*)|([1-9][0-9]*\.0\.[1-9][0-9]*\.[1-9][0-9]*)|(0\.[1-9][0-9]*\.[1-9][0-9]*\.[1-9][0-9]*)' ;

                      }

                    }

                    leaf ip-addr6 {
                      description 'DHCP pool option125 IP address configured.' ;
                      type ncd:ipv4-address {
                        pattern '([1-9][0-9]*\.[1-9][0-9]*\.[1-9][0-9]*\.[1-9][0-9]*)|([1-9][0-9]*\.0\.0\.0)|(0\.[1-9][0-9]*\.0\.0)|(0\.0\.[1-9][0-9]*\.0)|(0\.0\.0\.[1-9][0-9]*)|([1-9][0-9]*\.[1-9][0-9]*\.0\.0)|(0\.[1-9][0-9]*\.[1-9][0-9]*\.0)|(0\.0\.[1-9][0-9]*\.[1-9][0-9]*)|([1-9][0-9]*\.0\.0\.[1-9][0-9]*)|(0\.[1-9][0-9]*\.0\.[1-9][0-9]*)|([1-9][0-9]*\.0\.[1-9][0-9]*\.0)|([1-9][0-9]*\.[1-9][0-9]*\.[1-9][0-9]*\.0)|([1-9][0-9]*\.[1-9][0-9]*\.0\.[1-9][0-9]*)|([1-9][0-9]*\.0\.[1-9][0-9]*\.[1-9][0-9]*)|(0\.[1-9][0-9]*\.[1-9][0-9]*\.[1-9][0-9]*)' ;

                      }

                    }

                    leaf ip-addr7 {
                      description 'DHCP pool option125 IP address configured.' ;
                      type ncd:ipv4-address {
                        pattern '([1-9][0-9]*\.[1-9][0-9]*\.[1-9][0-9]*\.[1-9][0-9]*)|([1-9][0-9]*\.0\.0\.0)|(0\.[1-9][0-9]*\.0\.0)|(0\.0\.[1-9][0-9]*\.0)|(0\.0\.0\.[1-9][0-9]*)|([1-9][0-9]*\.[1-9][0-9]*\.0\.0)|(0\.[1-9][0-9]*\.[1-9][0-9]*\.0)|(0\.0\.[1-9][0-9]*\.[1-9][0-9]*)|([1-9][0-9]*\.0\.0\.[1-9][0-9]*)|(0\.[1-9][0-9]*\.0\.[1-9][0-9]*)|([1-9][0-9]*\.0\.[1-9][0-9]*\.0)|([1-9][0-9]*\.[1-9][0-9]*\.[1-9][0-9]*\.0)|([1-9][0-9]*\.[1-9][0-9]*\.0\.[1-9][0-9]*)|([1-9][0-9]*\.0\.[1-9][0-9]*\.[1-9][0-9]*)|(0\.[1-9][0-9]*\.[1-9][0-9]*\.[1-9][0-9]*)' ;

                      }

                    }

                    leaf ip-addr8 {
                      description 'DHCP pool option125 IP address configured.' ;
                      type ncd:ipv4-address {
                        pattern '([1-9][0-9]*\.[1-9][0-9]*\.[1-9][0-9]*\.[1-9][0-9]*)|([1-9][0-9]*\.0\.0\.0)|(0\.[1-9][0-9]*\.0\.0)|(0\.0\.[1-9][0-9]*\.0)|(0\.0\.0\.[1-9][0-9]*)|([1-9][0-9]*\.[1-9][0-9]*\.0\.0)|(0\.[1-9][0-9]*\.[1-9][0-9]*\.0)|(0\.0\.[1-9][0-9]*\.[1-9][0-9]*)|([1-9][0-9]*\.0\.0\.[1-9][0-9]*)|(0\.[1-9][0-9]*\.0\.[1-9][0-9]*)|([1-9][0-9]*\.0\.[1-9][0-9]*\.0)|([1-9][0-9]*\.[1-9][0-9]*\.[1-9][0-9]*\.0)|([1-9][0-9]*\.[1-9][0-9]*\.0\.[1-9][0-9]*)|([1-9][0-9]*\.0\.[1-9][0-9]*\.[1-9][0-9]*)|(0\.[1-9][0-9]*\.[1-9][0-9]*\.[1-9][0-9]*)' ;

                      }

                    }

                  }

                }

              }

              ncd:revise-date 2016-08-22 ;
            }

            container bootp-cfg {
              description 'BOOTP configuration.' ;
              container file {
                description 'BOOTP file configuration.' ;
                choice file-data-type {
                  description 'DHCP pool BOOTP file data type.' ;
                  case ascii {
                    description 'DHCP pool BOOTP file data type is ASCII string.' ;
                    leaf ascii-str {
                      description 'BOOTP file ASCII string configured.' ;
                      type string {
                        length 1..127 {
                          description 'The length of ASCII string.' ;
                        }

                      }

                      mandatory true ;
                    }

                  }

                  case hex {
                    description 'DHCP pool BOOTP file data type is HEX string.' ;
                    leaf hex-str {
                      description 'BOOTP file HEX string configured.' ;
                      type string {
                        length 1..254 {
                          description 'The length of HEX string.' ;
                        }

                      }

                      mandatory true ;
                    }

                  }

                }

                ncd:revise-date 2021-10-13 ;
              }

              leaf next-server-ip {
                description 'DHCP pool next server IP address.' ;
                type ncd:ipv4-address-none-zero ;

                ncd:revise-date 2021-10-13 ;
              }

              container sname {
                description 'BOOTP sname configuration.' ;
                choice sname-data-type {
                  description 'DHCP pool BOOTP sname data type.' ;
                  case ascii {
                    description 'DHCP pool BOOTP sname data type is ASCII string.' ;
                    leaf ascii-str {
                      description 'BOOTP sname ASCII string configured.' ;
                      type string {
                        length 1..63 {
                          description 'The length of ASCII string.' ;
                        }

                      }

                      mandatory true ;
                    }

                  }

                  case hex {
                    description 'DHCP pool BOOTP sname data type is HEX string.' ;
                    leaf hex-str {
                      description 'BOOTP sname HEX string configured.' ;
                      type string {
                        length 1..128 {
                          description 'The length of HEX string.' ;
                        }

                      }

                      mandatory true ;
                    }

                  }

                }

              }

              ncd:revise-date 2021-05-15 ;
            }

          }

        }

        container instances {
          description 'DHCP server instance configuration.' ;
          list instance {
            description 'DHCP server instance configuration.' ;
            key instance-name ;
            leaf instance-name {
              description 'DHCP server instance name.' ;
              type string {
                length 1..16 {
                  description 'DHCP server instance name.' ;
                }

              }

              ncd:revise-date 2017-01-12 ;
            }

            leaf pool-name {
              description 'Bind DHCP pool.' ;
              type string {
                length 1..64 {
                  description 'The length of pool name.' ;
                }

              }

            }

            leaf relay-destination-port {
              description 'DHCP server relay destination UDP port.' ;
              type enumeration {
                enum 67 {
                  value 67 ;
                  description 'DHCP server relay destination UDP port is 67.' ;
                }

                enum 68 {
                  value 68 ;
                  description 'DHCP server relay destination UDP port is 68.' ;
                }

              }

            }

            leaf nak-client-offline {
              description 'Turn on or off nak-client-offline.When turn on this switch,after server reply nak,client offline.' ;
              type enumeration {
                enum nak-client-offline-off {
                  value 0 ;
                  description 'Turn off nak-client-offline.' ;
                }

                enum nak-client-offline-on {
                  value 1 ;
                  description 'Turn on nak-client-offline.' ;
                }

              }

              default nak-client-offline-off ;
              ncd:revise-date 2018-03-23 ;
            }

          }

          ncd:revise-date 2016-09-20 ;
        }

        container interface-based-instances {
          description 'DHCP server interface based instance configuration.' ;
          list instance {
            description 'DHCP server instance configuration.' ;
            key instance-name ;
            leaf instance-name {
              description 'DHCP server instance name.' ;
              type string {
                length 1..16 {
                  description 'DHCP server instance name.' ;
                }

              }

            }

            leaf description {
              description 'DHCP server instance description.' ;
              type string {
                length 1..31 {
                  description 'DHCP server instance description.' ;
                }

              }

            }

            leaf authen-template-name {
              description 'Binding authentication template name.' ;
              type string {
                length 1..64 {
                  description 'The length of authentication template name.' ;
                }

              }

              ncd:revise-date 2020-11-26 ;
            }

          }

          ncd:revise-date 2020-06-09 ;
        }

      }

      container client {
        description 'DHCP client config.' ;
        container interfaces {
          description 'DHCP client interface configuration.' ;
          list interface {
            description 'DHCP client interface configuration on the interface.' ;
            key name ;
            leaf name {
              description 'DHCP interface name.' ;
              type ncd:ifname {
                length 1..31 {
                  description 'The interface name length.' ;
                }

              }

            }

            leaf client-policy {
              description 'DHCP policy of the interface for DHCP client.' ;
              type string {
                length 1..16 {
                  description 'The length of DHCP policy name.' ;
                }

              }

            }

            container client-switch {
              description 'DHCP client interface switch configuration.' ;
              leaf switch {
                description 'DHCP interface client switch.' ;
                type enumeration {
                  enum stop {
                    value 0 ;
                    description 'DHCP client stop.' ;
                  }

                  enum start {
                    value 1 ;
                    description 'DHCP client start.' ;
                  }

                }

                default stop ;
              }

            }

          }

        }

        container policys {
          description 'DHCP client policy configuration.' ;
          list policy {
            description 'DHCP client policy configuration.' ;
            key name ;
            leaf name {
              description 'DHCP client policy name.' ;
              type string {
                length 1..16 {
                  description 'DHCP client policy name.' ;
                }

              }

            }

            leaf broadcast-flag {
              description 'Broadcast flag.' ;
              type enumeration {
                enum broadcast-off {
                  value 0 ;
                  description 'DHCP client broadcast flag off.' ;
                }

                enum broadcast-on {
                  value 1 ;
                  description 'DHCP client broadcast flag on.' ;
                }

              }

              default broadcast-on ;
            }

            leaf opt60-format {
              description 'The format of option60.' ;
              type enumeration {
                enum china-tel-a8 {
                  value 1 ;
                  description 'The format is china tel format.' ;
                }

                enum user-configuration {
                  value 2 ;
                  description 'The format is user configuration.' ;
                }

              }

            }

            leaf opt61-format {
              description 'The format of option61.' ;
              type enumeration {
                enum standard {
                  value 1 ;
                  description 'The format of standard.' ;
                }

                enum pnp {
                  value 2 ;
                  description 'The format of pnp.' ;
                }

                enum user-configuration {
                  value 3 ;
                  description 'The format of user-configuration.' ;
                }

              }

              default standard ;
            }

            leaf host-name {
              description 'DHCP client host name.' ;
              type string {
                length 1..64 {
                  description 'DHCP client host name.' ;
                }

              }

              ncd:revise-date 2015-12-22 ;
            }

            container request-lists {
              description 'DHCP client request list configuraton.' ;
              list request-list {
                description 'DHCP client request list configuraton.' ;
                key req-opt-code ;
                leaf req-opt-code {
                  description 'The request option code in DHCP client request list.' ;
                  type enumeration {
                    enum domain-name-server {
                      value 6 ;
                      description 'Request domain name server(option 6).' ;
                    }

                    enum log-server-address {
                      value 7 ;
                      description 'Request log server address(option 7).' ;
                    }

                    enum impress-server-address {
                      value 10 ;
                      description 'Request impress server address(option 10).' ;
                    }

                    enum domain-name {
                      value 15 ;
                      description 'Request domain name(option 15).' ;
                    }

                    enum max-dg-reassembly {
                      value 22 ;
                      description 'Request max datagram reassembly size(option 22).' ;
                    }

                    enum tftp-server-name {
                      value 66 ;
                      description 'Request tftp server name(option 66).' ;
                    }

                    enum bootfile-name {
                      value 67 ;
                      description 'Request bootfile name(option 67).' ;
                    }

                    enum classless-static-route {
                      value 121 ;
                      description 'Request classless static route(option 121).' ;
                    }

                    enum tftp-server-address {
                      value 150 ;
                      description 'Request tftp server address(option 150).' ;
                    }

                    enum vendor-specific {
                      value 43 ;
                      description 'Request vendor specific information(option 43).' ;
                    }

                  }

                }

              }

            }

            container options {
              description 'DHCP client options.' ;
              list option {
                description 'DHCP client option.' ;
                key opt-code ;
                leaf opt-code {
                  description 'DHCP client option code.' ;
                  type enumeration {
                    enum 60 {
                      value 60 ;
                      description 'Option 60.' ;
                    }

                    enum 61 {
                      value 61 ;
                      description 'Option 61.' ;
                    }

                  }

                }

                choice type {
                  description 'DHCP client option type.' ;
                  mandatory true ;
                  case ascii {
                    description 'DHCP client option type is ASCII string.' ;
                    leaf ascii-string {
                      description 'Option ASCII string.' ;
                      type string {
                        length 1..64 {
                          description 'The length of ASCII string.' ;
                        }

                      }

                      mandatory true ;
                    }

                  }

                  case hex {
                    leaf hex-string {
                      description 'Option HEX string.' ;
                      type string {
                        length 1..64 {
                          description 'The length of HEX string.' ;
                        }

                      }

                      mandatory true ;
                    }

                    description 'DHCP client option type is HEX string.' ;
                  }

                }

              }

            }

          }

        }

        container global-config {
          description 'DHCP client global configuration.' ;
          leaf client-switch {
            description 'DHCP global interface client switch.' ;
            type enumeration {
              enum stop {
                value 0 ;
                description 'DHCP client stop.' ;
              }

              enum start {
                value 1 ;
                description 'DHCP client start.' ;
              }

            }

            default stop ;
          }

          leaf client-policy {
            description 'Global DHCP policy for DHCP client.' ;
            type string {
              length 1..16 {
                description 'Global DHCP policy for DHCP client.' ;
              }

            }

          }

          leaf client-write {
            description 'DHCP client write file named "dhcpclientinfo.xml" or not.This file is used for client to send release packet after reboot.' ;
            type enumeration {
              enum disable {
                value 0 ;
                description 'DHCP client write disable.' ;
              }

              enum enable {
                value 1 ;
                description 'DHCP client write enable.' ;
              }

            }

            default disable ;
            ncd:revise-date 2016-12-20 ;
          }

        }

      }

    }

  }

  container state {
    config false ;
    description 'State.' ;
    container dhcp {
      description 'DHCP state.' ;
      container relay {
        description 'DHCP relay state.' ;
        container user-connect-statistics {
          description 'DHCP relay user connect statistics on the board.' ;
          list detail {
            description 'Show DHCP relay all user info detail.' ;
            key 'board-name start-time' ;
            leaf board-name {
              description 'Board name of the slot on which DHCP relay user be.' ;
              type string {
                length 1..31 {
                  description 'The length of board name.' ;
                }

              }

            }

            leaf start-time {
              description 'Starting time of each piece of Statistics.' ;
              type ncd:string-with-blank ;

            }

            leaf end-time {
              description 'The end time of each piece of Statistics' ;
              type ncd:string-with-blank ;

            }

            leaf user-capacity {
              description 'DHCP relay user capacity on the board.' ;
              type uint32 ;

            }

            leaf current-online {
              description 'DHCP relay current-online bound-user from board start up to now .' ;
              type uint32 ;

              default 0 ;
            }

            leaf failed-times {
              description 'The failed-times of DHCP relay users generated per 15 minutes on the board.' ;
              type uint32 ;

            }

            ncd:select board-name ;
          }

          ncd:revise-date 2019-05-23 ;
        }

        container relay-user {
          description 'DHCP relay user state.' ;
          list detail {
            description 'Show DHCP relay all user info detail.' ;
            key 'board-name mac' ;
            leaf board-name {
              description 'Board name of the slot on which DHCP relay user be.' ;
              type string {
                length 1..31 {
                  description 'The length of board name.' ;
                }

              }

            }

            leaf mac {
              description 'DHCP relay user MAC.' ;
              type ncd:mac-address ;

            }

            leaf interface {
              description 'DHCP relay user interface name.' ;
              type string {
                length 1..31 {
                  description 'DHCP relay user interface name.' ;
                }

              }

            }

            leaf ip {
              description 'DHCP relay user IP.' ;
              type ncd:ipv4-address ;

            }

            leaf mask {
              description 'DHCP relay user mask.' ;
              type ncd:ipv4-mask ;

            }

            leaf state {
              description 'DHCP relay user state.' ;
              type enumeration {
                enum offering {
                  value 0 ;
                  description 'The user is offering state.' ;
                }

                enum bound {
                  value 1 ;
                  description 'The user is bound state.' ;
                }

              }

            }

            leaf lease-time {
              description 'DHCP relay user remain lease time. Unit is seconds.' ;
              type uint32 ;

              units second ;
            }

            leaf vrf {
              description 'DHCP relay user VRF name.' ;
              type string ;

            }

            leaf slot {
              description 'DHCP relay user slot No.' ;
              type uint32 ;

            }

            leaf total {
              description 'DHCP relay user total count on the whole machine.' ;
              type uint32 ;

            }

            ncd:select "board-name mac" ;
            ncd:select board-name ;
            ncd:select interface ;
          }

          leaf total-user {
            description 'DHCP relay user total count on the whole device.' ;
            type uint32 ;

          }

        }

        container dead-server {
          description 'DHCP relay dead server state.' ;
          list detail {
            description 'Show DHCP relay all dead server info detail.' ;
            key 'board-name server-ip' ;
            leaf board-name {
              description 'Board name of the slot on which DHCP relay dead server be.' ;
              type string {
                length 1..31 {
                  description 'The length of board name.' ;
                }

              }

            }

            leaf server-ip {
              description 'DHCP relay dead server IP.' ;
              type ncd:ipv4-address ;

            }

            leaf vrf {
              description 'DHCP relay dead server VRF name.' ;
              type string ;

            }

            leaf expiration-time {
              description 'The expiration time of DHCP relay dead server state is dead. Unit is seconds.' ;
              type uint32 ;

              units second ;
            }

            ncd:select board-name ;
          }

          ncd:revise-date 2016-12-20 ;
        }

      }

      container server {
        description 'DHCP server state.' ;
        container server-user {
          description 'DHCP server user state.' ;
          list detail {
            description 'Show DHCP server all user info detail.' ;
            key 'board-name mac' ;
            leaf board-name {
              description 'Board name of the slot on which DHCP server user be.' ;
              type string {
                length 1..31 {
                  description 'The length of board name.' ;
                }

              }

            }

            leaf mac {
              description 'DHCP server user MAC.' ;
              type ncd:mac-address ;

            }

            leaf ip {
              description 'DHCP server user IP.' ;
              type ncd:ipv4-address ;

            }

            leaf mask {
              description 'DHCP server user mask.' ;
              type ncd:ipv4-mask ;

            }

            leaf state {
              description 'DHCP server user state.' ;
              type enumeration {
                enum offering {
                  value 0 ;
                  description 'The user is offering state.' ;
                }

                enum bound {
                  value 1 ;
                  description 'The user is bound state.' ;
                }

              }

            }

            leaf lease-time {
              description 'DHCP server user remain lease time. Unit is seconds.' ;
              type uint32 ;

              units second ;
            }

            leaf interface {
              description 'DHCP server user interface name.' ;
              type string {
                length 1..31 {
                  description 'DHCP server user interface name.' ;
                }

              }

            }

            leaf vrf {
              description 'DHCP server user VRF name.' ;
              type string ;

            }

            leaf slot {
              description 'DHCP server user slot No.' ;
              type uint32 ;

            }

            leaf total {
              description 'DHCP server user total count on this board.' ;
              type uint32 ;

            }

            ncd:select "board-name mac" ;
            ncd:select board-name ;
            ncd:select interface ;
          }

          leaf total-user {
            description 'DHCP server user total count on the whole device.' ;
            type uint32 ;

          }

        }

      }

      container client {
        description 'DHCP client state.' ;
        container client-user {
          description 'DHCP client user state.' ;
          list detail {
            description 'Show DHCP client all user info detail.' ;
            key ifname ;
            leaf ifname {
              description 'The name of the interface on which DHCP client runs.' ;
              type string {
                length 1..31 {
                  description 'DHCP client user interface name.' ;
                }

              }

            }

            leaf mac {
              description 'DHCP client user MAC.' ;
              type ncd:mac-address ;

            }

            leaf ip {
              description 'DHCP client user IP.' ;
              type ncd:ipv4-address ;

            }

            leaf lease-server {
              description 'DHCP server from which client get IP.' ;
              type ncd:ipv4-address ;

            }

            leaf mask {
              description 'DHCP client user mask.' ;
              type ncd:ipv4-mask ;

            }

            leaf default-gateway {
              description 'Default gateway of the DHCP client.' ;
              type ncd:ipv4-address ;

            }

            leaf state {
              description 'DHCP client user state.' ;
              type enumeration {
                enum INIT {
                  value 0 ;
                  description 'INIT state.' ;
                }

                enum PURGING {
                  value 1 ;
                  description 'PURGING state.' ;
                }

                enum SELECTING {
                  value 2 ;
                  description 'SELECTING state.' ;
                }

                enum REQUESTING {
                  value 3 ;
                  description 'REQUESTING state.' ;
                }

                enum BOUND {
                  value 4 ;
                  description 'BOUND state.' ;
                }

                enum RENEWING {
                  value 5 ;
                  description 'RENEWING state.' ;
                }

                enum REBINDING {
                  value 6 ;
                  description 'REBINDING state.' ;
                }

                enum INIT_REBOOT {
                  value 7 ;
                  description 'INIT_REBOOT state.' ;
                }

                enum REBOOTING {
                  value 8 ;
                  description 'REBOOTING state.' ;
                }

                enum INVALID {
                  value 9 ;
                  description 'INVALID state.' ;
                }

              }

            }

            leaf lease {
              description 'DHCP client user lease time. Unit is seconds.' ;
              type uint32 ;

              units second ;
            }

            leaf renewal {
              description 'DHCP client user renewal time. Unit is seconds.' ;
              type uint32 ;

              units second ;
            }

            leaf rebind {
              description 'DHCP client user rebind time. Unit is seconds.' ;
              type uint32 ;

              units second ;
            }

            leaf expiration {
              description 'DHCP client user expiration time.' ;
              type ncd:string-with-blank ;

            }

            ncd:select ifname ;
          }

        }

      }

      container global {
        description 'DHCP global state.' ;
        container packet-statistics {
          description 'DHCP packet statistics.' ;
          list packet-statistic {
            description 'DHCP packet statistic.' ;
            key board-name ;
            leaf board-name {
              description 'Board name of the slot on which DHCP packet statistic.' ;
              type string {
                length 1..31 {
                  description 'The length of board name.' ;
                }

              }

            }

            leaf if-name {
              description 'Name of the DHCP interface on which DHCP packet statistic.' ;
              type string {
                length 1..31 {
                  description 'Interface name length.' ;
                }

              }

            }

            leaf discover {
              description 'Count of DHCPDISCOVER send or received.' ;
              type uint32 ;

            }

            leaf offer {
              description 'Count of DHCPOFFER send or received.' ;
              type uint32 ;

            }

            leaf request {
              description 'Count of DHCPREQUEST send or received.' ;
              type uint32 ;

            }

            leaf ack {
              description 'Count of DHCPACK send or received.' ;
              type uint32 ;

            }

            leaf nak {
              description 'Count of DHCPNAK send or received.' ;
              type uint32 ;

            }

            leaf decline {
              description 'Count of DHCPDECLINE send or received.' ;
              type uint32 ;

            }

            leaf release {
              description 'Count of DHCPRELEASE send or received.' ;
              type uint32 ;

            }

            leaf inform {
              description 'Count of DHCPINFORM send or received.' ;
              type uint32 ;

            }

            leaf request-all {
              description 'Count of all DHCP request packet send or received.' ;
              type uint32 ;

            }

            leaf reply-all {
              description 'Count of all DHCP rreply packet send or received.' ;
              type uint32 ;

            }

            ncd:select board-name ;
            ncd:select "board-name if-name" ;
          }

        }

      }

    }

  }

  container operation {
    description 'Operation.' ;
    config false ;
    container dhcp {
      description 'DHCP operation.' ;
      container relay-kick-user {
        description 'DHCP relay kick off user' ;
        choice type {
          description 'DHCP relay kick off user.' ;
          case all {
            description 'DHCP relay kick off all user.' ;
            leaf all-user {
              description 'DHCP relay kick off all user.' ;
              type enumeration {
                enum none {
                  value 0 ;
                  description 'The relay-kick-user type is not all.' ;
                }

                enum all {
                  value 1 ;
                  description 'The relay-kick-user type is all.' ;
                }

              }

              default none ;
            }

          }

          case interface {
            description 'DHCP relay kick off user by interface.' ;
            leaf if-user {
              description 'DHCP relay kick off user by interface.' ;
              type ncd:ifname {
                length 1..31 {
                  description 'The interface name length.' ;
                }

              }

            }

          }

          case mac {
            description 'DHCP relay kick off user by MAC.' ;
            leaf mac-user {
              description 'DHCP relay kick off user by MAC.' ;
              type ncd:mac-address ;

            }

          }

          case ip {
            description 'DHCP relay kick off user by IP.' ;
            leaf ip-user {
              description 'DHCP relay kick off user by IP.' ;
              type ncd:ipv4-address ;

              mandatory true ;
            }

            leaf vrf {
              description 'DHCP relay kick off user by IP and VRF.' ;
              type string {
                length 1..32 {
                  description 'Vrf name.' ;
                }

              }

            }

          }

        }

      }

      container server-kick-user {
        description 'DHCP server kick off user.' ;
        choice type {
          description 'DHCP server kick off user.' ;
          case all {
            description 'DHCP server kick off all user.' ;
            leaf all-user {
              description 'DHCP server kick off all user.' ;
              type enumeration {
                enum none {
                  value 0 ;
                  description 'The relay-kick-user type is not all.' ;
                }

                enum all {
                  value 1 ;
                  description 'The relay-kick-user type is all.' ;
                }

              }

              default none ;
            }

          }

          case interface {
            description 'DHCP server kick off user by interface.' ;
            leaf if-user {
              description 'DHCP server kick off user by interface.' ;
              type ncd:ifname {
                length 1..31 {
                  description 'The interface name length.' ;
                }

              }

            }

          }

          case mac {
            description 'DHCP server kick off user by MAC.' ;
            leaf mac-user {
              description 'DHCP server kick off user by MAC.' ;
              type ncd:mac-address ;

            }

          }

          case ip {
            description 'DHCP server kick off user by IP.' ;
            leaf ip-user {
              description 'DHCP server kick off user by IP.' ;
              type ncd:ipv4-address ;

              mandatory true ;
            }

            leaf vrf {
              description 'DHCP server kick off user by IP and VRF.' ;
              type string {
                length 1..32 {
                  description 'Vrf name.' ;
                }

              }

            }

          }

        }

      }

      container clear-pkt-stat {
        description 'DHCP clear packet statistics.' ;
        leaf board-name {
          description 'Board name of the slot.' ;
          type string {
            length 1..31 {
              description 'The length of board name.' ;
            }

          }

        }

        choice type {
          description 'Type of clearing DHCP packet statistics.' ;
          case global {
            description 'Clear global packet statistics.' ;
            leaf glb-stat {
              description 'DHCP clear global packet statistics.' ;
              type enumeration {
                enum global {
                  value 1 ;
                  description 'The type of clear-pkt-stat is global.' ;
                }

              }

              default global ;
            }

          }

          case interface {
            description 'Clear special interface packet statistics.' ;
            leaf if-stat {
              description 'DHCP clear interface packet statistics.' ;
              type ncd:ifname {
                length 1..31 {
                  description 'The interface name length.' ;
                }

              }

            }

          }

        }

      }

      container clear-dead-server {
        description 'Clear DHCP relay dead server.' ;
        choice type {
          description 'Type of clearing DHCP relay dead server.' ;
          case all {
            description 'Clear all DHCP relay dead server.' ;
            leaf all-dead-svr {
              description 'Clear all DHCP relay dead server.' ;
              type enumeration {
                enum none {
                  value 0 ;
                  description 'The type of clearing DHCP relay dead server is not all.' ;
                }

                enum all {
                  value 1 ;
                  description 'The type of clearing DHCP relay dead server is all.' ;
                }

              }

              default none ;
            }

          }

          case special {
            description 'Clear special DHCP relay dead server,such as specail slot,specail slot and IP and so on.' ;
            leaf board-name {
              description 'Clear dead server by board name of the slot.' ;
              type string {
                length 1..31 {
                  description 'The length of board name.' ;
                }

              }

            }

            leaf ip-addr {
              description 'Clear dead server by IP address.' ;
              type ncd:ipv4-address ;

            }

            leaf ip-vrf {
              description 'Clear dead server by IP address and VRF.' ;
              type string {
                length 1..32 ;

              }

            }

          }

        }

      }

    }

  }

  notification relay-user-report {
    description 'Report DHCP relay user information to network manager.' ;
    list detail {
      config false ;
      description 'Report DHCP relay user information to network manager.' ;
      key 'board-name mac' ;
      leaf board-name {
        description 'Board name of the slot on which DHCP relay user be.' ;
        type string {
          length 1..31 {
            description 'The length of board name.' ;
          }

        }

      }

      leaf mac {
        description 'DHCP relay user mac.' ;
        type ncd:mac-address ;

      }

      leaf pkt-if {
        description 'DHCP relay user L3 interface name.' ;
        type string {
          length 1..31 {
            description 'DHCP relay user interface name.' ;
          }

        }

      }

      leaf phy-if {
        description 'DHCP relay user L2 interface name.' ;
        type string {
          length 1..31 {
            description 'DHCP relay user interface name.' ;
          }

        }

      }

      leaf internal-vlan {
        description 'The internal vlan of DHCP relay interface.' ;
        type uint16 ;

      }

      leaf external-vlan {
        description 'The external vlan of DHCP relay interface.' ;
        type uint16 ;

      }

      leaf ip {
        description 'DHCP relay user IP.' ;
        type ncd:ipv4-address ;

      }

      leaf mask {
        description 'DHCP relay user mask.' ;
        type ncd:ipv4-mask ;

      }

    }

    ncd:revise-date 2016-07-04 ;
  }

}
