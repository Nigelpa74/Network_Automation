module zxr10-ipv6-source-prefix {
  namespace 'http://www.zte.com.cn/zxr10/netconf/schema/rosng/ipv6-source-prefix'
            ;
  prefix ipv6-source-prefix ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  revision 2024-04-20 {
    description '1.Add the container /configuration/ipv6-source-prefix/blocks.' ;
  }
  revision 2023-11-04 {
    description '1.Add the container /configuration/ipv6-source-prefix/prefix-match-ignore-bits.' ;
  }
  revision 2023-02-09 {
    description 'Initial version.'
                ;
  }
  feature ipv6-source-prefix-feature ;
  container configuration {
    description 'ipv6-source-prefix configuration'
                ;
    container ipv6-source-prefix {
      if-feature ipv6-source-prefix-feature ;
      description 'ipv6 source address prefix configuration class information c'
                + 'ontainer.'
                  ;
      container ipv6-src-prefix-names {
        description 'The name container of the upper-layer network slice contai'
                  + 'ns the attributes under prefix-name.'
                    ;
        list ipv6-src-prefix-name {
          description 'The name list of the network slice indicates that multip'
                    + 'le prefix-names can be configured under the ipv6-source-'
                    + 'prefix command.'
                      ;
          key prefix-name ;
          leaf prefix-name {
            description 'Source address Slice name.'
                        ;
            type string {
              length 1..63 ;
            }
          }
          container prefixs {
            description 'Source address slice prefix container.'
                        ;
            presence prefix-slice-range ;
            leaf prefix {
              description 'Source address slice prefix.'
                          ;
              type ncd:ipv6-address-none-zero ;
              mandatory true ;
            }
            leaf prefix-len {
              description 'Source address slice prefix length.'
                          ;
              type uint8 {
                range 8..96 ;
              }
              mandatory true ;
            }
            leaf block-length-value {
              description 'block length.'
                          ;
              type uint8 {
                range 48..64 ;
              }
              mandatory true ;
            }
          }
        }
      }
      container prefix-match-ignore-bits {
        presence bitmap ;
        description 'Configure the matching ignore bits of source prefix.' ;
        leaf value {
          mandatory true ;
          description 'Configure the matching ignore bits of source prefix in range mode, support single bit value or range(max num:32;spacing mark:,) in <1-64>. For example,"1,3-5,10,20-30",etc.' ;
          type ncd:range {
            pattern "((([1-9]|[1-5][0-9]|6[0-4])-([1-9]|[1-5][0-9]|6[0-4]))|([1-9]|[1-5][0-9]|6[0-4]))(,((([1-9]|[1-5][0-9]|6[0-4])-([1-9]|[1-5][0-9]|6[0-4]))|([1-9]|[1-5][0-9]|6[0-4]))){0,31}" ;
          }

        }

        ncd:revise-date 2023-11-04 ;
      }

      container blocks {
        list block {
          leaf block-address {
            type ncd:ipv6-address-none-zero ;

            description 'Block address.' ;
          }

          leaf block-length {
            type uint8 {
              range 48..64 ;

            }

            description 'Block length.' ;
            mandatory true ;
          }

          description 'The block configuration list.' ;
          key block-address ;
        }

        description 'Block configuration.' ;
        ncd:revise-date 2024-04-20 ;
      }
    }
  }
}
