module zxr10-ipsec-dev-15k {
  namespace "http://www.zte.com.cn/zxr10/netconf/schema/rosng/ipsec-dev-15k" ;
  prefix ipsec-dev-15k ;
  import zxr10-ipsec {
    prefix ipsec ;
    revision-date 2016-07-13 ;
  }

  organization "ZTE Corporation" ;
  contact "ZTE Corporation
  Nanjing Institute of ZTE Corporation
  No.68 Zijinghua Rd. Yuhuatai District, Nanjing, China
  Tel: +86-25-52870000" ;
  revision 2024-08-29 {
    description 'Add COMMON and remove mpu node' ;
  }

  revision 2022-11-29 {
    description 'Remove deviation@ipsec:commit-type.
Remove deviation@ipsec:acl-type.
Remove deviation@ipsec:ipv6.
Remove deviation@ipsec:tunnel-mode.' ;
  }

  revision 2017-06-20 {
    description 'Add ah-sha256-hmac,ah-sha384-hmac,ah-sha512-hmac for deviation@ipsec:trans-ah.
Add esp-sha256-hmac,esp-sha384-hmac,esp-sha512-hmac for deviation@ipsec:trans-esp-hmac.' ;
  }

  revision 2016-12-06 ;

  deviation "/ipsec:configuration/ipsec:ipsec/ipsec:ipsec-tunnels/ipsec:ipsec-tunnel/ipsec:crypto-pki-profile" {
    description 'Unsupported encryption PKI profile' ;
    deviate not-supported ;

  }

  deviation "/ipsec:configuration/ipsec:ipsec/ipsec:transform-sets/ipsec:transform-set/ipsec:transforms/ipsec:trans-ah" {
    deviate replace {
      type enumeration {
        enum ah-md5-hmac {
          value 2 ;
          description 'AH-HMAC-MD5 transform' ;
        }

        enum ah-sha-hmac {
          value 3 ;
          description 'AH-HMAC-SHA transform' ;
        }

        enum ah-sha256-hmac {
          value 5 ;
          description 'AH-HMAC-SHA256 transform' ;
        }

        enum ah-sha384-hmac {
          value 6 ;
          description 'AH-HMAC-SHA384 transform' ;
        }

        enum ah-sha512-hmac {
          value 7 ;
          description 'AH-HMAC-SHA512 transform' ;
        }

      }

    }

  }

  deviation "/ipsec:configuration/ipsec:ipsec/ipsec:transform-sets/ipsec:transform-set/ipsec:transforms/ipsec:trans-esp-hmac" {
    deviate replace {
      type enumeration {
        enum esp-md5-hmac {
          value 1 ;
          description 'ESP transform using HMAC-MD5 auth' ;
        }

        enum esp-sha-hmac {
          value 2 ;
          description 'ESP transform using HMAC-SHA auth' ;
        }

        enum esp-sha256-hmac {
          value 5 ;
          description 'ESP transform using HMAC-SHA256 auth' ;
        }

        enum esp-sha384-hmac {
          value 6 ;
          description 'ESP transform using HMAC-SHA384 auth' ;
        }

        enum esp-sha512-hmac {
          value 7 ;
          description 'ESP transform using HMAC-SHA512 auth' ;
        }

      }

    }

  }

  deviation "/ipsec:configuration/ipsec:ipsec/ipsec:transform-sets/ipsec:transform-set/ipsec:transforms/ipsec:trans-esp-cipher" {
    deviate replace {
      type enumeration {
        enum esp-des {
          value 2 ;
          description 'ESP transform using DES cipher (56 bits)' ;
        }

        enum esp-3des {
          value 3 ;
          description 'ESP transform using 3DES(EDE) cipher (168 bits)' ;
        }

        enum esp-null {
          value 11 ;
          description 'ESP transform w/o cipher' ;
        }

        enum esp-aes-128 {
          value 12 ;
          description 'ESP transform using AES cipher(128 bits)' ;
        }

        enum esp-aes-192 {
          value 1012 ;
          description 'ESP transform using AES cipher(192 bits)' ;
        }

        enum esp-aes-256 {
          value 2012 ;
          description 'ESP transform using AES cipher(256 bits)' ;
        }

      }

    }

  }

}
