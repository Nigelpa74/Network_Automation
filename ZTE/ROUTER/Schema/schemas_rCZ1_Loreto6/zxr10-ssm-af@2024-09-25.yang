module zxr10-ssm-af {
  namespace "http://www.zte.com.cn/zxr10/netconf/schema/rosng/ssm-af" ;
  prefix ssm-af ;
  import zxr10-netconf-defs {
    prefix ncd ;
  }

  organization "ZTE Corporation" ;
  contact "ZTE Corporation  
     Nanjing Institute of ZTE Corporation 
     No.68 Zijinghua Rd. Yuhuatai District, Nanjing, China 
     Tel: +86-25-52870000" ;
  description 'The netconf module to describe SSM.' ;
  revision 2024-09-25 {
    description 'Initial version.' ;
  }

  container state {
    description 'The state of SSM.' ;
    config false ;
    container ssm {
      description 'The SSM state.' ;
      container current-clock {
        description 'SSM current system clock information.' ;
        list af-node {
          description 'AF node list of SSM.' ;
          key name ;
          leaf name {
            description 'AF node name.' ;
            type ncd:af-name {
              length 1..32 ;

            }

            config false ;
            mandatory false ;
          }

          leaf if-name {
            description 'SSM current interface name of clock,inner-clk,hold-off or PTP1588-clk is NULL.' ;
            type string {
              length 0..31 ;

            }

            config false ;
            mandatory false ;
          }

          leaf clock-type {
            description 'SSM current clock type.' ;
            type enumeration {
              enum external-clk {
                value 1 ;
                description 'External clock.' ;
                status current ;

              }

              enum line-clk {
                value 2 ;
                description 'Line clock.' ;
                status current ;

              }

              enum inner-clk {
                value 3 ;
                description 'Internal clock.' ;
                status current ;

              }

              enum holdover {
                value 4 ;
                description 'Hold over.' ;
                status current ;

              }

              enum tributeline-clk {
                value 5 ;
                description 'Tribute line clock.' ;
                status current ;

              }

              enum PTP1588-clk {
                value 6 ;
                description 'PTP clock.' ;
                status current ;

              }

              enum gps-clk {
                value 7 ;
                description 'GPS clock.' ;
                status current ;

              }

              enum stm-clk {
                value 8 ;
                description 'Stm-n clock.' ;
                status current ;

              }

            }

            config false ;
            mandatory false ;
          }

          leaf pll-state {
            description 'SSM current clock PLL status.' ;
            type enumeration {
              enum autorun {
                value 0 ;
                description 'PLL status is auto-run.' ;
                status current ;

              }

              enum capture {
                value 1 ;
                description 'PLL status is captured.' ;
                status current ;

              }

              enum track {
                value 2 ;
                description 'PLL status is track.' ;
                status current ;

              }

              enum lock {
                value 3 ;
                description 'PLL status is locked.' ;
                status current ;

              }

              enum unlock {
                value 4 ;
                description 'PLL status is unlocked.' ;
                status current ;

              }

              enum NULL {
                value 254 ;
                description 'PLL status is invalid.' ;
                status current ;

              }

            }

            config false ;
            mandatory false ;
          }

          leaf usessm {
            description 'SSM current clock SSM enable state.' ;
            type enumeration {
              enum enable {
                value 1 ;
                description 'Enable the SSM algorithm.' ;
                status current ;

              }

              enum disable {
                value 2 ;
                description 'Disable the SSM algorithm.' ;
                status current ;

              }

            }

            config false ;
            mandatory false ;
          }

          leaf switch-option {
            description 'SSM current switch status.' ;
            type enumeration {
              enum normal {
                value 1 ;
                description 'Normal mode.' ;
                status current ;

              }

              enum force {
                value 2 ;
                description 'Force mode.' ;
                status current ;

              }

              enum manual {
                value 3 ;
                description 'Manual mode.' ;
                status current ;

              }

            }

            config false ;
            mandatory false ;
          }

          leaf current-quality {
            description 'SSM current clock QL.' ;
            type enumeration {
              enum QL-UNK {
                value 0 ;
                description 'The QL is unknown.' ;
                status current ;

              }

              enum QL-PRC {
                value 2 ;
                description 'The QL is PRC.' ;
                status current ;

              }

              enum QL-SSU-A {
                value 4 ;
                description 'The QL is SSU-A.' ;
                status current ;

              }

              enum QL-SSU-B {
                value 8 ;
                description 'The QL is SSU-B.' ;
                status current ;

              }

              enum QL-SEC {
                value 11 ;
                description 'The QL is SEC.' ;
                status current ;

              }

              enum QL-DNU {
                value 15 ;
                description 'The QL is DNU.' ;
                status current ;

              }

              enum QL-PRTC {
                value 5 ;
                description 'The QL is PRTC.' ;
                status current ;

              }

              enum QL-ePRTC {
                value 1 ;
                description 'The QL is ePRTC.' ;
                status current ;

              }

              enum QL-ePRC {
                value 7 ;
                description 'The QL is ePRC.' ;
                status current ;

              }

              enum QL-eSEC {
                value 10 ;
                description 'The QL is eSEC.' ;
                status current ;

              }

              enum invalid {
                value 254 ;
                status current ;

              }

            }

            config false ;
            mandatory false ;
          }

          leaf current-clock-id {
            description 'SSM current clock ID.' ;
            type string {
              length 0..24 ;

            }

            config false ;
            mandatory false ;
          }

          leaf internal-clock-id {
            description 'SSM internal clock ID.' ;
            type string {
              length 0..24 ;

            }

            config false ;
            mandatory false ;
          }

          leaf station-id {
            description 'ID of NE station.' ;
            type uint8 {
              range 0..255 ;

            }

            config false ;
            mandatory false ;
          }

          leaf node {
            description 'Node of NE station' ;
            type uint8 {
              range 0..255 ;

            }

            config false ;
            mandatory false ;
          }

          leaf mixed-flag {
            description 'Mixed flag,true means at least one of the clocks is not an eEEC,false means all clocks are eEEC.' ;
            type enumeration {
              enum true {
                value 1 ;
                description 'True means at least one of the clocks is not an eEEC.' ;
                status current ;

              }

              enum false {
                value 0 ;
                description 'False means all clocks are eEEC.' ;
                status current ;

              }

            }

            config false ;
            mandatory false ;
          }

          leaf partial-flag {
            description 'Partial flag,1 means partial chain(if the TLV has been generated in the middle of the chain and the count of the EEC/eEEC is incomplete).' ;
            type enumeration {
              enum true {
                value 1 ;
                description 'True means partial chain(if the TLV has been generated in the middle of the chain and the count of the EEC/eEEC is incomplete).' ;
                status current ;

              }

              enum false {
                value 0 ;
                description 'False means the chain is all EEC/eEEC type completely.' ;
                status current ;

              }

            }

            config false ;
            mandatory false ;
          }

          leaf sec-number {
            description 'Number of SEC clocks of the chain.' ;
            type uint8 {
              range 0..255 ;

            }

            config false ;
            mandatory false ;
          }

          leaf esec-number {
            description 'Number of eSEC clocks of the chain.' ;
            type uint8 {
              range 0..255 ;

            }

            config false ;
            mandatory false ;
          }

          leaf output-degrade {
            description 'Output degrade flag.' ;
            type enumeration {
              enum no {
                value 0 ;
                description 'Not in output degrade status.' ;
                status current ;

              }

              enum yes {
                value 1 ;
                description 'In output degrade status.' ;
                status current ;

              }

            }

            config false ;
            mandatory false ;
          }

          config false ;
          ncd:select name ;
        }

        config false ;
      }

      config false ;
    }

    ncd:revise-date 2024-04-20 ;
  }

}
