module zxr10-aaa {
  namespace "http://www.zte.com.cn/zxr10/netconf/schema/rosng/aaa" ;
  prefix aaa ;
  import zxr10-netconf-defs {
    prefix ncd ;
  }
  
  organization "ZTE Corporation" ;
  contact "ZTE Corporation

     Nanjing Institute of ZTE Corporation

     No.68 Zijinghua Rd. Yuhuatai District, Nanjing, China

     Tel: +86-25-52870000" ;
  description 'This module describes the netconf model about AAA.' ;
  revision 2025-04-22 {
    description '1.add leaf node aaa/aaa-accounting-templates/aaa-accounting-template/tacacs-mode' ;
  }

  revision 2015-03-06 {
    description '1. Modefied the zxr10-aaa/configuration/aaa/aaa-authentication-templates/aaa-authentication-template models.

    (1) changed the authen_name leaf node length from 1 to 32 into length from 1 to 31.

 2. Modefied the zxr10-aaa/configuration/aaa/aaa-authorization-templates/aaa-authorization-template models.

    (1) changed the author_name leaf node length from 1 to 32 into length from 1 to 31.

 3. Modefied the zxr10-aaa/configuration/aaa/aaa-accounting-templates/aaa-accounting-template models.

    (1) changed the acct_name leaf node length from 1 to 32 into length from 1 to 31.' ;
  }

  revision 2015-02-10 {
    description '1)Modefied zxr10-aaa/configuration/aaa/aaa-authentication-templates/authen_type model.Add values tacacs-radius(12)and radius-tacacs(13).

2)Modefied zxr10-aaa/configuration/aaa/aaa-authorization-templates/author_type model. Add values tacacs-radius(9)and radius-tacacs(10).

3)Modefied zxr10-aaa/configuration/aaa/aaa-accounting-templates/acct_type model.Add values tacacs-radius(4)and radius-tacacs(5).

4)Modefied zxr10-aaa/configuration/aaa/aaa-authentication-templates/diameter_group leaf,change type from uint16 to string.' ;
  }

  revision 2014-02-11 {
    description 'Initial version.' ;
  }

  container configuration {
    description 'AAA configuration model.' ;
    container aaa {
      description 'AAA configuration model.' ;
      container aaa-authentication-templates {
        description 'AAA authentication template model.' ;
        list aaa-authentication-template {
          description 'AAA authentication template configuration list.' ;
          key temp_num ;
          max-elements 2128 ;
          leaf temp_num {
            description 'AAA authentication template number.' ;
            type uint32 {
              range 1..2128 {
                description 'AAA authentication template number <1-2128>.' ;
              }

            }

          }

          leaf authen_type {
            description 'AAA authentication type.' ;
            type enumeration {
              enum none {
                value 1 ;
                description 'No authentication.' ;
              }

              enum local {
                value 2 ;
                description 'Local authentication.' ;
              }

              enum radius {
                value 3 ;
                description 'RADIUS authentication.' ;
              }

              enum local-radius {
                value 4 ;
                description 'Local RADIUS authentication.' ;
              }

              enum radius-local {
                value 5 ;
                description 'RADIUS local authentication.' ;
              }

              enum radius-none {
                value 6 ;
                description 'RADIUS none authentication.' ;
              }

              enum tacacs {
                value 7 ;
                description 'TACACS authentication.' ;
              }

              enum local-tacacs {
                value 8 ;
                description 'Local TACACS authentication.' ;
              }

              enum tacacs-local {
                value 9 ;
                description 'TACACS local authentication.' ;
              }

              enum tacacs-none {
                value 10 ;
                description 'TACACS none authentication.' ;
              }

              enum diameter {
                value 11 ;
                description 'DIAMETER authentication.' ;
              }

              enum tacacs-radius {
                value 12 ;
                description 'TACACS authentication first and RADIUS second' ;
              }

              enum radius-tacacs {
                value 13 ;
                description 'RADIUS authentication first and TACACS second' ;
              }

            }

          }

          leaf authen_name {
            description 'AAA authentication template description.' ;
            type string {
              length 1..31 {
                description 'Description word (1-31 characters).' ;
              }

            }

          }

          leaf radius_group {
            description 'RADIUS group name.' ;
            type string {
              length 1..31 {
                description 'RADIUS group name (1-31 characters).' ;
              }

            }

          }

          leaf tacacs_group {
            description 'TACACS server group name.' ;
            type string {
              length 1..31 {
                description 'TACACS server group name (1-31 characters).' ;
              }

            }

          }

          leaf diameter_group {
            description 'DIAMETER group name.' ;
            type string {
              length 1..32 {
                description 'DIAMETER group name (1-32 characters).' ;
              }

            }

          }

        }

      }

      container aaa-authorization-templates {
        description 'AAA authorization template model.' ;
        list aaa-authorization-template {
          description 'AAA authorization template configuration list.' ;
          key temp_num ;
          max-elements 2128 ;
          leaf temp_num {
            description 'AAA authorization template number.' ;
            type uint32 {
              range 1..2128 {
                description 'AAA authorization template number <1-2128>.' ;
              }

            }

          }

          leaf author_type {
            description 'AAA authorization type.' ;
            type enumeration {
              enum local {
                value 1 ;
                description 'Local authorization.' ;
              }

              enum radius {
                value 2 ;
                description 'RADIUS authorization.' ;
              }

              enum tacacs {
                value 3 ;
                description 'TACACS authorization.' ;
              }

              enum radius-local {
                value 4 ;
                description 'RADIUS-local authorization.' ;
              }

              enum local-tacacs {
                value 5 ;
                description 'Local-TACACS authorization.' ;
              }

              enum none {
                value 6 ;
                description 'No authorization.' ;
              }

              enum local-radius {
                value 7 ;
                description 'Local-RADIUS authorization.' ;
              }

              enum tacacs-local {
                value 8 ;
                description 'TACACS-local authorization.' ;
              }

              enum tacacs-radius {
                value 9 ;
                description 'TACACS authorization first and RADIUS second' ;
              }

              enum radius-tacacs {
                value 10 ;
                description 'RADIUS authorization first and TACACS second' ;
              }

            }

          }

          leaf author_name {
            description 'AAA authorization template description.' ;
            type string {
              length 1..31 {
                description 'Description word (1-31 characters).' ;
              }

            }

          }

          leaf tacacs_group {
            description 'TACACS server group name.' ;
            type string {
              length 1..31 {
                description 'TACACS server-group name (1-31 characters).' ;
              }

            }

          }

          leaf radius_group {
            description 'RADIUS group name.' ;
            type string {
              length 1..31 {
                description 'RADIUS group name (1-31 characters).' ;
              }

            }

          }

        }

      }

      container aaa-accounting-templates {
        description 'AAA accounting template model.' ;
        list aaa-accounting-template {
          description 'AAA accounting template configuration list.' ;
          key temp_num ;
          max-elements 2128 ;
          leaf temp_num {
            description 'AAA accounting template number.' ;
            type uint32 {
              range 1..2128 {
                description 'AAA accounting template number <1-2128>.' ;
              }

            }

          }

          leaf acct_type {
            description 'AAA accounting type.' ;
            type enumeration {
              enum none {
                value 1 ;
                description 'No accounting.' ;
              }

              enum radius {
                value 2 ;
                description 'RADIUS accounting.' ;
              }

              enum tacacs {
                value 3 ;
                description 'TACACS accounting.' ;
              }

              enum tacacs-radius {
                value 4 ;
                description 'TACACS accounting first and RADIUS second' ;
              }

              enum radius-tacacs {
                value 5 ;
                description 'RADIUS accounting first and TACACS second' ;
              }

            }

          }

          leaf acct_name {
            description 'AAA accounting template description.' ;
            type string {
              length 1..31 {
                description 'Description word (1-31 characters).' ;
              }

            }

          }

          leaf tacacs_group {
            description 'TACACS server group name.' ;
            type string {
              length 1..31 {
                description 'TACACS server group name (1-31 characters).' ;
              }

            }

          }

          leaf tacacs-mode {
            description 'TACACS accounting packet mode.' ;
            type enumeration {
              enum none {
                value 0 ;
                description 'The mode of TACACS accounting is not configured.' ;
              }

              enum cmd {
                value 1 ;
                description 'The mode of TACACS accounting is command.' ;
              }

            }
            default none ;

            ncd:revise-date 2025-04-22 ;
          }

          container radius {
            description 'RADIUS group used by AAA accounting template.' ;
            presence accounting-radius-group ;
            leaf radius_group {
              description 'RADIUS group name.' ;
              type string {
                length 1..31 {
                  description 'RADIUS group name (1-31 characters).' ;
                }

              }

              mandatory true ;
            }

            leaf second_radius_group {
              description 'Second RADIUS group name.' ;
              type string {
                length 1..31 {
                  description 'RADIUS group name (1-31 characters).' ;
                }

              }

            }

          }

        }

      }

    }

  }

}
