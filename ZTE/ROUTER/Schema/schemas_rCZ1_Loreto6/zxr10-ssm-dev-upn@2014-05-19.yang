module zxr10-ssm-dev-upn {
  namespace 'http://www.zte.com.cn/zxr10/netconf/schema/rosng/ssm-dev-upn'
            ;
  prefix ssm-dev-upn ;
  import zxr10-ssm {
    prefix ssm ;
    revision-date 2014-05-19 ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  revision 2014-05-19 {
    description 'Import the new zxr10-ssm.xml'
                ;
  }
  revision 2014-01-21 {
    description 'Initial version.'
                ;
  }
  container configuration ;
  deviation /ssm:configuration/ssm:ssm/ssm:global/ssm:lock-bits-send-dnu {
    deviate not-supported ;
  }
  deviation '/ssm:configuration/ssm:ssm/ssm:extimer-clocks/ssm:out-clock/ssm:if'
          + '-attribute'
            {
    deviate not-supported ;
  }
  deviation '/ssm:configuration/ssm:ssm/ssm:extimer-clocks/ssm:out-clock/ssm:ou'
          + 't-clock-unif-list/ssm:clock-type'
            {
    deviate replace {
      type enumeration {
        enum current-clock {
          value 19 ;
        }
      }
    }
  }
  deviation '/ssm:configuration/ssm:ssm/ssm:extimer-clocks/ssm:out-clock/ssm:ou'
          + 't-clock-list/ssm:clock-type'
            {
    deviate replace {
      type enumeration {
        enum line-clk {
          value 2 ;
        }
        enum tributeline-clk {
          value 5 ;
        }
        enum stm-clk {
          value 8 ;
        }
      }
    }
  }
}
