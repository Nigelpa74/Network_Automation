module zxr10-mld-dev-upn {
  namespace "http://www.zte.com.cn/zxr10/netconf/schema/rosng/mld-dev-upn" ;
  prefix router-mld ;
  import zxr10-mld {
    prefix mld ;
  }

  organization "ZTE Corporation" ;
  contact "ZTE Corporation  
     Nanjing Institute of ZTE Corporation 
     No.68 Zijinghua Rd. Yuhuatai District, Nanjing, China 
     Tel: +86-25-52870000" ;
  description 'MLD in router.' ;
  revision 2023-06-08 {
    description 'Because the project label is released, the command restrictions are released.' ;
  }

  revision 2015-04-02 {
    description 'Delete the revision date of the import.' ;
  }

  revision 2014-03-11 {
    description 'Initial version.' ;
  }

}
