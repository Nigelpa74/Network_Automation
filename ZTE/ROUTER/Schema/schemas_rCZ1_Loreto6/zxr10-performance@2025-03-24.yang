module zxr10-performance {
  namespace "http://www.zte.com.cn/zxr10/netconf/schema/rosng/performance" ;
  prefix pm ;
  yang-version 1 ;
  import zxr10-netconf-defs {
    prefix ncd ;
  }

  organization "ZTE Corporation" ;
  contact "ZTE Corporation
  Nanjing Institute of ZTE Corporation
  No.68 Zijinghua Rd. Yuhuatai District, Nanjing, China
  Tel: +86-25-52870000" ;
  description 'The netconf module to describe performance' ;
  revision 2025-03-24 {
    description '(1) Correct the display of /pm:state/pm:performance/pm:statistics queries for BVI interface (checkpoint-type 402), BVI sub-interface (checkpoint-type 393), and tunnel (checkpoint-type 577). Cap the bandwidth utilization display at 100% once it exceeds 100%.' ;
  }
  revision 2024-12-09 {
    description '(1)Add state/performance/threshold/satellite-current-thresholds' ;
  }

  revision 2024-09-03 {
    description '(1) Modify the description information of the performance module.' ;
  }

  revision 2024-05-23 {
    description '(1) Add leaf state/performance/statistics/currentdata/fifteen-mins/digitaldata/zxr10digitaldatum/tpid-desc;
(2) Add leaf state/performance/statistics/currentdata/fifteen-mins/analogdata/zxr10analogdatum/tpid-desc;
(3) Add leaf state/performance/statistics/currentdata/twenty-four-hours/digitaldata/zxr10digitaldatum/tpid-desc;
(4) Add leaf state/performance/statistics/currentdata/twenty-four-hours/analogdata/zxr10analogdatum/tpid-desc;
(5) Add leaf state/performance/statistics/currentdata/self-defined-minutes/digitaldata/zxr10digitaldatum/tpid-desc;
(6) Add leaf state/performance/statistics/currentdata/self-defined-minutes/analogdata/zxr10analogdatum/tpid-desc;
(7) Add leaf state/performance/statistics/historydata/fifteen-mins/digitaldata/zxr10digitaldatum/tpid-desc;
(8) Add leaf state/performance/statistics/historydata/fifteen-mins/analogdata/zxr10analogdatum/tpid-desc;
(9) Add leaf state/performance/statistics/historydata/twenty-four-hours/digitaldata/zxr10digitaldatum/tpid-desc;
(10) Add leaf state/performance/statistics/historydata/twenty-four-hours/analogdata/zxr10analogdatum/tpid-desc;
(11) Add leaf state/performance/statistics/historydata/self-defined-minutes/digitaldata/zxr10digitaldatum/tpid-desc;
(12) Add leaf state/performance/statistics/historydata/self-defined-minutes/analogdata/zxr10analogdatum/tpid-desc;' ;
  }

  revision 2024-03-28 {
    description "(1)Modify 'configuration/performance/statistics/alarm-hysteretic-characteristics/percent-value' default from 0 to perfpara." ;
  }

  revision 2024-02-20 {
    description '(1)Add configuration\performance\statistics\self-defined-five-minutes;
(2)Add state\performance\statistics\currentdata\self-defined-minutes;
(3)Add state\performance\statistics\historydata\self-defined-minutes;' ;
  }

  revision 2023-08-31 {
    description 'Feature flow-statistics add project labels:HighEndRouter and OTN.' ;
  }

  revision 2023-06-11 {
    description '(1)Modify configuration\performance\threshold with immediate effect.
(2)Set operation\performance\clear with immediate effect.' ;
  }

  revision 2022-03-18 {
    description '(1)Add configuration\performance\statistics\bandwidth-utilization' ;
  }

  revision 2022-01-18 {
    description '(1)Add configuration\performance\statistics\alarm-hysteretic-characteristics' ;
  }

  revision 2020-08-18 {
    description '(1)Add configuration\performance\statistics\flow' ;
  }

  revision 2018-12-12 {
    description '(1)Add configuration\performance\statistics\minute-cycle' ;
  }

  revision 2016-11-16 {
    description '(1)Add leaf state\performance\threshold\default-thresholds\zxr10analog-default-threshold\tpid-mask' ;
  }

  revision 2016-05-05 {
    description '(1)Modify description of leaf operation\performance\monitor\stop\task\taskid;' ;
  }

  revision 2015-12-28 {
    description "(1)Obsolete list state\performance\statistics\currentdata\fifteen-mins\digitaldata\digitaldatum;

    (2)Add list state\performance\statistics\currentdata\fifteen-mins\digitaldata\zxr10digitaldatum;

    (3)Obsolete list state\performance\statistics\currentdata\fifteen-mins\analogdata\analogdatum;

    (4)Add list state\performance\statistics\currentdata\fifteen-mins\analogdata\zxr10analogdatum;

    (5)Obsolete list state\performance\statistics\currentdata        wenty-four-hours\digitaldata\digitaldatum;

    (6)Add list state\performance\statistics\currentdata        wenty-four-hours\digitaldata\zxr10digitaldatum;

    (7)Obsolete list state\performance\statistics\currentdata        wenty-four-hours\analogdata\analogdatum;

    (8)Add list state\performance\statistics\currentdata        wenty-four-hours\analogdata\zxr10analogdatum;

    (9)Obsolete list state\performance\statistics\historydata\fifteen-mins\digitaldata\digitaldatum;

    (10)Add list state\performance\statistics\historydata\fifteen-mins\digitaldata\zxr10digitaldatum;

    (11)Obsolete list state\performance\statistics\historydata\fifteen-mins\analogdata\analogdatum;

    (12)Add list state\performance\statistics\historydata\fifteen-mins\analogdata\zxr10analogdatum;

    (13)Obsolete list state\performance\statistics\historydata        wenty-four-hours\digitaldata\digitaldatum;

    (14)Add list state\performance\statistics\historydata        wenty-four-hours\digitaldata\zxr10digitaldatum;

    (15)Obsolete list state\performance\statistics\historydata        wenty-four-hours\analogdata\analogdatum;

    (16)Add list state\performance\statistics\historydata        wenty-four-hours\analogdata\zxr10analogdatum;

    (17)Obsolete list state\performance\monitor\perfdata\perfdatum;

    (18)Add list state\performance\monitor\perfdata\zxr10perfdatum;

    (19)Obsolete list state\performance        hreshold\default-thresholds\analog-default-threshold;

    (20)Add list state\performance        hreshold\default-thresholds\zxr10analog-default-threshold;

    (21)Modify length of leaf operation\performance\clear\currentdata\currentdatum        pid-matcher to 'from 62 to 128';

    (22)Modify length of leaf operation\performance\clear\currentdata\currentdatum        pid-mask to 'from 8 to 16';

    (23)Modify range of leaf operation\performance\clear\currentdata\currentdatum        pid-length to 'from 62 to 128';

    (24)Modify length of leaf operation\performance\monitor\start-up        ask\checkpoints\checkpoint        pid to 'from 62 to 128';

    (25)Modify range of leaf operation\performance\monitor\start-up        ask\checkpoints\checkpoint        pid-length to 'from 62 to 128';" ;
  }

  revision 2015-12-09 {
    description '(1)Modify description of leaf configuration\performance\statistics\perf-masks\perf-mask\perfcode;
(2)Modify description of leaf configuration\performance\statistics\perf-masks\perf-mask\cycle;
(3)Modify description of leaf configuration\performance\statistics\perf-masks\perf-mask\tpid-class;
(4)Modify description of leaf configuration\performance\statistics\perf-suppresses\perf-suppress\tpid-length;
(5)Add description of leaf configuration\performance\statistics\perf-suppresses\perf-suppress\state;
(6)Add description of container configuration\performance\threshold\perf-thresholds\fifteen-mins;
(7)Add description of container configuration\performance\threshold\perf-thresholds\fifteen-mins\digital;
(8)Add description of leaf configuration\performance\threshold\perf-thresholds\fifteen-mins\digital\tpid-length;
(9)Add description of container configuration\performance\threshold\perf-thresholds\fifteen-mins\analog;
(10)Add description of leaf configuration\performance\threshold\perf-thresholds\fifteen-mins\analog\tpid-length;
(11)Add description of container configuration\performance\threshold\perf-thresholds\twenty-four-hours;
(12)Add description of container configuration\performance\threshold\perf-thresholds\twenty-four-hours\digital;
(13)Add description of leaf configuration\performance\threshold\perf-thresholds\twenty-four-hours\digital\tpid-length;
(14)Modify description of container state\performance\statistics;
(15)Modify description of leaf state\performance\statistics\currentdata\fifteen-mins\digitaldata\digitaldatum\tpid-class;
(16)Modify description of leaf state\performance\statistics\currentdata\fifteen-mins\digitaldata\digitaldatum\tpid-length;
(17)Modify description of leaf state\performance\statistics\currentdata\fifteen-mins\analogdata\analogdatum\tpid-class;
(18)Modify description of leaf state\performance\statistics\currentdata\fifteen-mins\analogdata\analogdatum\tpid-length;
(19)Modify description of leaf state\performance\statistics\currentdata\twenty-four-hours\digitaldata\digitaldatum\tpid-class;
(20)Modify description of leaf state\performance\statistics\currentdata\twenty-four-hours\digitaldata\digitaldatum\tpid-length;
(21)Modify description of leaf state\performance\statistics\currentdata\twenty-four-hours\analogdata\analogdatum\tpid-class;
(22)Modify description of leaf state\performance\statistics\currentdata\twenty-four-hours\analogdata\analogdatum\tpid-length;
(23)Modify description of leaf state\performance\statistics\historydata\fifteen-mins\digitaldata\digitaldatum\tpid-class;
(24)Modify description of leaf state\performance\statistics\historydata\fifteen-mins\digitaldata\digitaldatum\tpid-length;
(25)Modify description of leaf state\performance\statistics\historydata\fifteen-mins\digitaldata\digitaldatum\inner-index;
(26)Modify description of container state\performance\statistics\historydata\fifteen-mins\analogdata;
(27)Modify description of leaf state\performance\statistics\historydata\fifteen-mins\analogdata\analogdatum\tpid-class;
(28)Modify description of leaf state\performance\statistics\historydata\fifteen-mins\analogdata\analogdatum\tpid-length;
(29)Modify description of leaf state\performance\statistics\historydata\fifteen-mins\analogdata\analogdatum\inner-index;
(30)Modify description of container state\performance\statistics\historydata\twenty-four-hours\digitaldata;
(31)Modify description of leaf state\performance\statistics\historydata\twenty-four-hours\digitaldata\digitaldatum\tpid-class;
(32)Modify description of leaf state\performance\statistics\historydata\twenty-four-hours\digitaldata\digitaldatum\tpid-length;
(33)Modify description of leaf state\performance\statistics\historydata\twenty-four-hours\digitaldata\digitaldatum\inner-index;
(34)Modify description of container state\performance\statistics\historydata\twenty-four-hours\analogdata;
(35)Modify description of leaf state\performance\statistics\historydata\twenty-four-hours\analogdata\analogdatum\tpid-class;
(36)Modify description of leaf state\performance\statistics\historydata\twenty-four-hours\analogdata\analogdatum\tpid-length;
(37)Modify description of leaf state\performance\statistics\historydata\twenty-four-hours\analogdata\analogdatum\inner-index;
(38)Modify description of leaf state\performance\threshold\default-thresholds\analog-default-threshold\tpid-length;
(39)Modify description of leaf operation\performance\clear\currentdata\currentdatum\tpid-class;
(40)Modify description of leaf operation\performance\clear\currentdata\currentdatum\tpid-length;' ;
  }

  revision 2015-08-12 {
    description '(1)Add leaf state\performance\statistics\historydata\fifteen-mins\analogdata\analogdatum\max-value-time' ;
  }

  revision 2014-11-05 {
    description '(1) In order to support the replace configuration, the list node "configuration\performance\threshold\perf-thresholds\perf-threshold" is split into three lists: "configuration\performance\threshold\perf-thresholds\fifteen-mins\digital\perf-threshold","configuration\performance\threshold\perf-thresholds\fifteen-mins\analog\perf-threshold","configuration\performance\threshold\perf-thresholds\twenty-four-hours\digital\perf-threshold".
(2) Modify node "configuration\performance\threshold\default-threholds\default-threshold\low","configuration\performance\threshold\default-threholds\default-threshold\warn-low","configuration\performance\threshold\default-threholds\default-threshold\high","configuration\performance\threshold\default-threholds\default-threshold\warn-high" to non-mandatory.' ;
  }

  revision 2014-09-09 {
    description "(1) Modify leaf configuration\performance\statistics\perf-masks\perf-mask\cycle enumeration 'all' to 3" ;
  }

  revision 2014-06-16 {
    description '(1)Add key leaf state\performance\statistics\historydata\fifteen-mins\digitaldata\digitaldatum\inner-index
(2)Add key leaf state\performance\statistics\historydata\fifteen-mins\analogdata\analogdatum\inner-index
(3)Add key leaf state\performance\statistics\historydata\twenty-four-hours\digitaldata\digitaldatum\inner-index
(4)Add key leaf state\performance\statistics\historydata\twenty-four-hours\analogdata\analogdatum\inner-index' ;
  }

  revision 2014-05-30 {
    description "(1) Add 'tpid-length' to 'Selects' in 'list' node of state\performance\statistics\currentdata\fifteen-mins\digitaldata\digitaldatum

    (2) Add 'tpid-length' to 'Selects' in 'list' node of state\performance\statistics\currentdata\fifteen-mins\analogdata\analogdatum

    (3) Add 'tpid-length' to 'Selects' in 'list' node of state\performance\statistics\currentdata        wenty-four-hours\digitaldata\digitaldatum

    (4) Add 'tpid-length' to 'Selects' in 'list' node of state\performance\statistics\currentdata        wenty-four-hours\analogdata\analogdatum

    (5) Add 'tpid-length' to 'Selects' in 'list' node of state\performance\statistics\historydata\fifteen-mins\digitaldata\digitaldatum

    (6) Add 'tpid-length' to 'Selects' in 'list' node of state\performance\statistics\historydata\fifteen-mins\analogdata\analogdatum

    (7) Add 'tpid-length' to 'Selects' in 'list' node of state\performance\statistics\historydata        wenty-four-hours\digitaldata\digitaldatum

    (8) Add 'tpid-length' to 'Selects' in 'list' node of state\performance\statistics\historydata        wenty-four-hours\analogdata\analogdatum

    (9) Add 'Selects' in 'list' node of state\performance        hreshold\default-thresholds\analog-default-threshold

    (10) Add leaf state\performance        hreshold\default-thresholds\analog-default-threshold        pid-length

    (11) Modify range of 'length' of leaf state\performance        hreshold\default-thresholds\analog-default-threshold        pid to 'from 1 to 128'

    (12) Modify range of 'length' of leaf operation\performance\monitor\start-up        ask\checkpoints\checkpoint        pid to 'from 1 to 128'

    (13) Modify leaf operation\performance\monitor\start-up        ask\checkpoints\checkpoint        pid-length to 'from 1 to 128'

    (14)Modify leaf configuration\performance        hreshold\perf-thresholds\perf-threshold        pid-lengh to tpid-length

    (15)Modify leaf state\performance\statistics\currentdata\fifteen-mins\digitaldata\digitaldatum        pid-lengh to tpid-length

    (16)Modify leaf state\performance\statistics\currentdata\fifteen-mins\analogdata\analogdatum        pid-lengh to tpid-length

    (17)Modify leaf state\performance\statistics\currentdata        wenty-four-hours\digitaldata\digitaldatum        pid-lengh to tpid-length

    (18)Modify leaf state\performance\statistics\currentdata        wenty-four-hours\analogdata\analogdatum        pid-lengh to tpid-length

    (19)Modify leaf state\performance\statistics\historydata\fifteen-mins\digitaldata\digitaldatum        pid-lengh to tpid-length

    (20)Modify leaf state\performance\statistics\historydata\fifteen-mins\analogdata\analogdatum        pid-lengh to tpid-length

    (21)Modify leaf state\performance\statistics\historydata        wenty-four-hours\digitaldata\digitaldatum        pid-lengh to tpid-length

    (22)Modify leaf state\performance\statistics\historydata        wenty-four-hours\analogdata\analogdatum        pid-lengh to tpid-length

    (23) Delete operation\performance\clear\currentdata\currentdatum\cycle type 'all'" ;
  }

  revision 2014-05-20 {
    description "(1)Add 'tpid-length' to all 'Selects' in 'list' node of state\performance\monitor\perfdata\perfdatum" ;
  }

  revision 2014-04-29 {
    description "(1) Modify range of 'length' of leaf operation\performance\clear\currentdata\currentdatum        pid-matcher to 'from 1 to 128'

    (2)Modify range of 'length' of leaf operation\performance\clear\currentdata\currentdatum        pid-mask to 'from 1 to 16'

    (3)Add leaf operation\performance\clear\currentdata\currentdatum        pid-length" ;
  }

  revision 2014-01-20 {
    description "(1)Add key leaf configuration\performance\statistics\perf-masks\perf-mask        pid-class

    (2)Modify range of 'length' of leaf configuration\performance\statistics\perf-suppresses\perf-suppress        pid to 'from 62 to 128'

    (3)Add leaf configuration\performance\statistics\perf-suppresses\perf-suppress        pid-length

    (4)Add leaf configuration\performance\statistics\perf-suppresses\perf-suppress\state

    (5)Add key leaf state\performance\statistics\currentdata\fifteen-mins\digitaldata\digitaldatum        pid-class

    (6)Modify range of 'length' of leaf state\performance\statistics\currentdata\fifteen-mins\digitaldata\digitaldatum        pid to 'from 1 to 128'

    (7)Modify range of 'length' of leaf state\performance\statistics\currentdata\fifteen-mins\digitaldata\digitaldatum        pid-matcher to 'from 1 to 128'

    (8)Modify range of 'length' of leaf state\performance\statistics\currentdata\fifteen-mins\digitaldata\digitaldatum        pid-mask to 'from 1 to 16'

    (9)Add leaf state\performance\statistics\currentdata\fifteen-mins\digitaldata\digitaldatum        pid-length

    (10)Add key leaf state\performance\statistics\currentdata\fifteen-mins\analogdata\analogdatum        pid-class

    (11)Modify range of 'length' of leaf state\performance\statistics\currentdata\fifteen-mins\analogdata\analogdatum        pid to 'from 1 to 128'

    (12)Modify range of 'length' of leaf state\performance\statistics\currentdata\fifteen-mins\analogdata\analogdatum        pid-matcher to 'from 1 to 128'

    (13)Modify range of 'length' of leaf state\performance\statistics\currentdata\fifteen-mins\analogdata\analogdatum        pid-mask to 'from 1 to 16'

    (14)Add leaf state\performance\statistics\currentdata\fifteen-mins\analogdata\analogdatum        pid-length

    (15)Add key leaf state\performance\statistics\currentdata        wenty-four-hours\digitaldata\digitaldatum        pid-class

    (16)Modify range of 'length' of leaf state\performance\statistics\currentdata        wenty-four-hours\digitaldata\digitaldatum        pid to 'from 1 to 128'

    (17)Modify range of 'length' of leaf state\performance\statistics\currentdata        wenty-four-hours\digitaldata\digitaldatum        pid-matcher to 'from 1 to 128'

    (18)Modify range of 'length' of leaf state\performance\statistics\currentdata        wenty-four-hours\digitaldata\digitaldatum        pid-mask to 'from 1 to 16'

    (19)Add leaf state\performance\statistics\currentdata        wenty-four-hours\digitaldata\digitaldatum        pid-length

    (20)Add key leaf state\performance\statistics\currentdata        wenty-four-hours\analogdata\analogdatum        pid-class

    (21)Modify range of 'length' of leaf state\performance\statistics\currentdata        wenty-four-hours\analogdata\analogdatum        pid to 'from 1 to 128'

    (22)Modify range of 'length' of leaf state\performance\statistics\currentdata        wenty-four-hours\analogdata\analogdatum        pid-matcher to 'from 1 to 128'

    (23)Modify range of 'length' of leaf state\performance\statistics\currentdata        wenty-four-hours\analogdata\analogdatum        pid-mask to 'from 1 to 16'

    (24)Add leaf state\performance\statistics\currentdata        wenty-four-hours\analogdata\analogdatum        pid-length

    (25)Add key leaf state\performance\statistics\historydata\fifteen-mins\digitaldata\digitaldatum        pid-class

    (26)Modify range of 'length' of leaf state\performance\statistics\historydata\fifteen-mins\digitaldata\digitaldatum        pid to 'from 1 to 128'

    (27)Modify range of 'length' of leaf state\performance\statistics\historydata\fifteen-mins\digitaldata\digitaldatum        pid-matcher to 'from 1 to 128'

    (28)Modify range of 'length' of leaf state\performance\statistics\historydata\fifteen-mins\digitaldata\digitaldatum        pid-mask to 'from 1 to 16'

    (29)Add leaf state\performance\statistics\historydata\fifteen-mins\digitaldata\digitaldatum        pid-length

    (30)Add key leaf state\performance\statistics\historydata\fifteen-mins\analogdata\analogdatum        pid-class

    (31)Modify range of 'length' of leaf state\performance\statistics\historydata\fifteen-mins\analogdata\analogdatum        pid to 'from 1 to 128'

    (32)Modify range of 'length' of leaf state\performance\statistics\historydata\fifteen-mins\analogdata\analogdatum        pid-matcher to 'from 1 to 128'

    (33)Modify range of 'length' of leaf state\performance\statistics\historydata\fifteen-mins\analogdata\analogdatum        pid-mask to 'from 1 to 16'

    (34)Add leaf state\performance\statistics\historydata\fifteen-mins\analogdata\analogdatum        pid-length

    (35)Add key leaf state\performance\statistics\historydata        wenty-four-hours\digitaldata\digitaldatum        pid-class

    (36)Modify range of 'length' of leaf state\performance\statistics\historydata        wenty-four-hours\digitaldata\digitaldatum        pid to 'from 1 to 128'

    (37)Modify range of 'length' of leaf state\performance\statistics\historydata        wenty-four-hours\digitaldata\digitaldatum        pid-matcher to 'from 1 to 128'

    (38)Modify range of 'length' of leaf state\performance\statistics\historydata        wenty-four-hours\digitaldata\digitaldatum        pid-mask to 'from 1 to 16'

    (39)Add leaf state\performance\statistics\historydata        wenty-four-hours\digitaldata\digitaldatum        pid-length

    (40)Add key leaf state\performance\statistics\historydata        wenty-four-hours\analogdata\analogdatum        pid-class

    (41)Modify range of 'length' of leaf state\performance\statistics\historydata        wenty-four-hours\analogdata\analogdatum        pid to 'from 1 to 128'

    (42)Modify range of 'length' of leaf state\performance\statistics\historydata        wenty-four-hours\analogdata\analogdatum        pid-matcher to 'from 1 to 128'

    (43)Modify range of 'length' of leaf state\performance\statistics\historydata        wenty-four-hours\analogdata\analogdatum        pid-mask to 'from 1 to 16'

    (44)Add leaf state\performance\statistics\historydata        wenty-four-hours\analogdata\analogdatum        pid-length

    (45)Modify range of 'length' of leaf state\performance\monitor\perfdata\perfdatum        pid to 'from 1 to 128'

    (46)Add leaf state\performance\monitor\perfdata\perfdatum        pid-length

    (47)Add key leaf operation\performance\clear\currentdata\currentdatum        pid-class

    (48)Modify range of 'length' of leaf state\performance\monitor\perfdata\perfdatum        pid to 'from 62 to 128'

    (49)Add leaf operation\performance\monitor\start-up        ask\checkpoints\checkpoint        pid-length" ;
  }

  revision 2013-12-31 {
    description "(1) Add 'configuration \ performance \ perf-masks \ perf-mask' leaf 'tpid-length'

    (2) Modify Type Range of 'configuration \ performance \ perf-masks \ perf-mask ' leaf 'tpid-matcher' to 'from 62 to 128'

    (3) Delete 'configuration \ performance \ perf-suppresses \ perf-suppress'  leaf 'cycle' type 'all'

    (4) Modify Type Range of 'configuration \ performance \ perf-thresholds \ perf-threshold' leaf 'tpid' to 'from 62 to 128'

    (5) Add 'configuration \ performance \ perf-thresholds \ perf-threshold' leaf 'tpid-length'" ;
  }

  revision 2013-10-15 {
    description "(1) Leaf node checkpoint-type, perfcode is limited to: 1-65535. (2) Real-time performance monitoring of the adoption cycle is limited to: 5-900. (3) Revise 'state\performance\monitor\perfdata\perfdatum\perf-type' definition as enumeration. (4) Add default value for 'operation\performance\monitor\start-up        ask\auto-report' as false." ;
  }

  revision 2013-09-30 {
    description "Current and historical performance modeling of an explicit distinction between 15 minutes and 24 hours queries. Involving state node structural changes. 'configuration \ performance \ default-threholds \ templateId' name changed to template-id." ;
  }

  revision 2013-09-24 {
    description 'Add perf-type for realtime query operation.' ;
  }

  revision 2013-08-22 {
    description 'The real-time performance monitoring tasks from the configuration command to action command.' ;
  }

  revision 2013-08-16 {
    description 'Real-time performance statistics add a query that indicates whether the value of the first sample query. Namely: state \ performance \ statistics \ monitor \ perfdata \ perfdatum \ selet \ first \ first-cycle.' ;
  }

  revision 2013-08-13 {
    description "(1) Remove the leaf node:

    'stateperformance hresholddefault-thresholdsanalog-default-threshold pid-matcher'.

    (2) The node ' state  performance  monitor  perfdata  perfdatum  cycle-end-time' type is changed to ncd: datatime.

    (3) In the following 'list' node, add a layer of 'container' node:

    - configurationperformancestatisticsperf-mask

    - configurationperformancestatisticsperf-suppress

    - configurationperformance hresholdperf-threshold

    - configurationperformance hresholddefault-threshold" ;
  }

  revision 2013-04-22 {
    description 'Initial version.' ;
  }

  feature flow-statistics ;

  feature self-defined-minutes {
    ncd:revise-date 2024-02-20 ;
  }

  container configuration {
    description 'Configuration model info.' ;
    container performance {
      description 'The configuration info about performance.' ;
      container statistics {
        description 'The configuration info about statistics.' ;
        container perf-masks {
          description 'The rules for performance mask.' ;
          list perf-mask {
            description 'The rules for performance mask.' ;
            key 'checkpoint-type tpid-matcher perfcode cycle tpid-mask tpid-class' ;
            leaf checkpoint-type {
              description 'The type of TPID. 0xFFFF for any type.' ;
              type uint16 {
                range 1..65535 ;

              }

            }

            leaf tpid-matcher {
              description "The matcher about TPID, the format is the same to TPID. It always to be used with 'tpid-mask', they can be indicated a group of TPID." ;
              type binary {
                length 62..128 ;

              }

            }

            leaf perfcode {
              description 'Performance code, one TPID may have serval performance codes. 0xFFFF for any code.' ;
              type uint16 {
                range 1..65535 ;

              }

            }

            leaf cycle {
              description 'The performance cycle. 15(5) minutes, 24 hours or all.' ;
              type enumeration {
                enum fifteen-minutes {
                  value 1 ;
                  description 'Minute cycle. The actual cycle value depends on the minute-cycle configuration.' ;
                }

                enum twenty-four-hours {
                  value 2 ;
                }

                enum all {
                  value 3 ;
                }

              }

            }

            leaf tpid-mask {
              description "The mask about tpid-matcher, it indicates which position of 'tpid-matcher' is available." ;
              type binary {
                length 8..16 ;

              }

            }

            leaf tpid-length {
              description 'The length of TPID.' ;
              type uint8 {
                range 62..128 ;

              }

            }

            leaf tpid-class {
              description 'The class of TPID.' ;
              type enumeration {
                enum board {
                  value 1 ;
                }

                enum CPU {
                  value 2 ;
                }

                enum system {
                  value 3 ;
                }

                enum all {
                  value 255 ;
                }

              }

            }

          }

        }

        container perf-suppresses {
          description 'The function about performance suppress.' ;
          list perf-suppress {
            description 'The function about performance suppress.' ;
            key 'checkpoint-type tpid cycle' ;
            leaf checkpoint-type {
              description 'The type of TPID. Only for any TPID type. The value is always 0xFFFF.' ;
              type uint16 {
                range 1..65535 ;

              }

            }

            leaf tpid {
              description "Check point id, only every positon's value is 0xFF can be accepted." ;
              type binary {
                length 62..128 ;

              }

            }

            leaf cycle {
              description 'Statistics cycle.' ;
              type enumeration {
                enum cur15minutes {
                  value 1 ;
                  description 'Current minute cycle. The actual cycle value depends on the minute-cycle configuration.' ;
                }

                enum his15minutes {
                  value 2 ;
                  description 'History minute cycle. The actual cycle value depends on the minute-cycle configuration.' ;
                }

                enum cur24hours {
                  value 3 ;
                }

                enum his24hours {
                  value 4 ;
                }

              }

            }

            leaf tpid-length {
              description 'The length of TPID.' ;
              type uint8 {
                range 62..128 ;

              }

            }

            leaf state {
              description 'Performance suppress state.' ;
              type enumeration {
                enum suppress {
                  value 1 ;
                }

                enum unsuppress {
                  value 2 ;
                }

              }

            }

          }

        }

        container minute-cycle {
          description 'The performance cycle at minute level.' ;
          presence minute-cycle ;
          leaf minute-cycle {
            description 'The performance cycle at minute level. 15 minutes or 5 minutes.' ;
            type enumeration {
              enum fifteen-minutes {
                value 1 ;
              }

              enum five-minutes {
                value 2 ;
              }

            }

            default fifteen-minutes ;
          }

          ncd:revise-date 2018-12-12 ;
        }

        container flow {
          if-feature flow-statistics ;

          description 'Flow statistics.' ;
          presence flow ;
          leaf phy-frame-octs {
            description 'Preamble octets and gap octets between ethernet frames.' ;
            type enumeration {
              enum include {
                value 1 ;
                description 'Include preamble octets and gap octets between ethernet frames.' ;
              }

              enum exclude {
                value 2 ;
                description 'Exclude preamble octets and gap octets between ethernet frames.' ;
              }

            }

          }

          ncd:revise-date 2020-08-18 ;
        }

        container alarm-hysteretic-characteristics {
          description 'The performance alarm hysteretic characteristics.' ;
          presence alarm-hysteretic-characteristics ;
          leaf percent-value {
            description 'The performance alarm hysteretic characteristics percentage.There is default value, which is different in different environments.' ;
            type uint8 {
              range 0..50 ;

            }

          }

          ncd:revise-date 2022-01-18 ;
        }

        container bandwidth-utilization {
          description 'The performance bandwidth utilization.' ;
          leaf statistics-cycle {
            description 'The performance bandwidth utilization statistics cycle.' ;
            type enumeration {
              enum sec30 {
                value 30 ;
              }

              enum sec60 {
                value 60 ;
              }

              enum sec180 {
                value 180 ;
              }

            }

            default sec60 ;
          }

          ncd:revise-date 2022-03-18 ;
        }

        container self-defined-five-minutes {
          list perf-item {
            leaf checkpoint-type {
              type uint16 {
                range 1..65534 ;

              }

              description 'TPID type. Must explicitly specify.' ;
            }

            leaf perfcode {
              type uint16 {
                range 1..65534 ;

              }

              description 'The performance item code of TPID. Must be configured with a valid value (not 0xFFFF).' ;
            }

            description 'The self defined five minutes performance item.' ;
            key 'checkpoint-type perfcode' ;
          }

          description 'The self defined five minutes performance items.' ;
          if-feature self-defined-minutes {
            ncd:revise-date 2024-02-20 ;
          }

          ncd:revise-date 2024-02-20 ;
        }

      }

      container threshold {
        description 'The configuration info about performance threshold. The threshold will immediately take effect, that is, if the alarm disappears conditions are met, the alarm will immediately disappear.' ;
        container perf-thresholds {
          description 'Set the threshold info about performance.' ;
          container fifteen-mins {
            description 'Set the threshold info about minute cycle performance. The actual cycle value depends on the minute-cycle configuration.' ;
            container digital {
              description 'Set the threshold info about digital performance.' ;
              list perf-threshold {
                description "Set the threshold info about performance. 'checkpoint-type' and 'perfcode' must be specified." ;
                key 'checkpoint-type tpid perfcode' ;
                leaf checkpoint-type {
                  description 'TPID type. Must explicitly specify.' ;
                  type uint16 {
                    range 1..65535 ;

                  }

                }

                leaf tpid {
                  description 'The TPID of performance item code belong. May be a full 0xFF.' ;
                  type binary {
                    length 62..128 ;

                  }

                }

                leaf perfcode {
                  description 'The performance item code of TPID. Must be configured with a valid value (not 0xFFFF).' ;
                  type uint16 {
                    range 1..65535 ;

                  }

                }

                leaf low {
                  description 'Value for low threshold.' ;
                  type binary {
                    length 10 ;

                  }

                }

                leaf warn-low {
                  description 'Value for warn-low threshold.' ;
                  type binary {
                    length 10 ;

                  }

                }

                leaf high {
                  description 'Value for high threshold.' ;
                  type binary {
                    length 10 ;

                  }

                }

                leaf warn-high {
                  description 'Value for warn-high threshold.' ;
                  type binary {
                    length 10 ;

                  }

                }

                leaf tpid-length {
                  description 'The length of TPID.' ;
                  type uint8 {
                    range 62..128 ;

                  }

                }

              }

            }

            container analog {
              description 'Set the threshold info about analog performance.' ;
              list perf-threshold {
                description "Set the threshold info about performance. 'checkpoint-type' and 'perfcode' must be specified." ;
                key 'checkpoint-type tpid perfcode' ;
                leaf checkpoint-type {
                  description 'TPID type. Must explicitly specify.' ;
                  type uint16 {
                    range 1..65535 ;

                  }

                }

                leaf tpid {
                  description 'The TPID of performance item code belong. May be a full 0xFF.' ;
                  type binary {
                    length 62..128 ;

                  }

                }

                leaf perfcode {
                  description 'The performance item code of TPID. Must be configured with a valid value (not 0xFFFF).' ;
                  type uint16 {
                    range 1..65535 ;

                  }

                }

                leaf low {
                  description 'Value for low threshold.' ;
                  type binary {
                    length 10 ;

                  }

                }

                leaf warn-low {
                  description 'Value for warn-low threshold.' ;
                  type binary {
                    length 10 ;

                  }

                }

                leaf high {
                  description 'Value for high threshold.' ;
                  type binary {
                    length 10 ;

                  }

                }

                leaf warn-high {
                  description 'Value for warn-high threshold.' ;
                  type binary {
                    length 10 ;

                  }

                }

                leaf tpid-length {
                  description 'The length of TPID.' ;
                  type uint8 {
                    range 62..128 ;

                  }

                }

              }

            }

          }

          container twenty-four-hours {
            description "Set the threshold info about twenty four hours performance. 'checkpoint-type' and 'perfcode' must be specified." ;
            container digital {
              description 'Set the threshold info about digital performance.' ;
              list perf-threshold {
                description "Set the threshold info about performance. 'checkpoint-type' and 'perfcode' must be specified." ;
                key 'checkpoint-type tpid perfcode' ;
                leaf checkpoint-type {
                  description 'TPID type. Must explicitly specify.' ;
                  type uint16 {
                    range 1..65535 ;

                  }

                }

                leaf tpid {
                  description 'The TPID of performance item code belong. May be a full 0xFF.' ;
                  type binary {
                    length 62..128 ;

                  }

                }

                leaf perfcode {
                  description 'The performance item code of TPID. Must be configured with a valid value (not 0xFFFF).' ;
                  type uint16 {
                    range 1..65535 ;

                  }

                }

                leaf low {
                  description 'Value for low threshold.' ;
                  type binary {
                    length 10 ;

                  }

                }

                leaf warn-low {
                  description 'Value for warn-low threshold.' ;
                  type binary {
                    length 10 ;

                  }

                }

                leaf high {
                  description 'Value for high threshold.' ;
                  type binary {
                    length 10 ;

                  }

                }

                leaf warn-high {
                  description 'Value for warn-high threshold.' ;
                  type binary {
                    length 10 ;

                  }

                }

                leaf tpid-length {
                  description 'The length of TPID.' ;
                  type uint8 {
                    range 62..128 ;

                  }

                }

              }

            }

          }

        }

        container default-threholds {
          description 'Set template of default threshold performance item.' ;
          list default-threshold {
            description 'Set template of default threshold for analog performance item.' ;
            key 'template-id perfcode' ;
            leaf template-id {
              description 'The template ID. Now is the optical module certification ID.' ;
              type uint32 ;

            }

            leaf perfcode {
              description 'The code of analog performance item. Must be configured with a valid value (not 0xFFFF).' ;
              type uint16 {
                range 1..65535 ;

              }

            }

            leaf low {
              description 'Value for low threshold. All 0xFF is invalid.' ;
              type binary {
                length 10 ;

              }

            }

            leaf warn-low {
              description 'Value for warn-low threshold. All 0xFF is invalid.' ;
              type binary {
                length 10 ;

              }

            }

            leaf high {
              description 'Value for high threshold. All 0xFF is invalid.' ;
              type binary {
                length 10 ;

              }

            }

            leaf warn-high {
              description 'Value for warn-high threshold. All 0xFF is invalid.' ;
              type binary {
                length 10 ;

              }

            }

            leaf minvalue {
              description 'The minimum detectable value. Not use.' ;
              type binary {
                length 10 ;

              }

            }

            leaf maxvalue {
              description 'The maximum detectable value. Not use.' ;
              type binary {
                length 10 ;

              }

            }

          }

        }

      }

    }

  }

  container state {
    config false ;
    description 'State info.' ;
    container performance {
      description 'State info about performance.' ;
      container statistics {
        description 'Statistics info about performance.' ;
        container currentdata {
          description 'Statistics info about current data.' ;
          container fifteen-mins {
            description 'Current data for minute cycle. The actual cycle value depends on the minute-cycle configuration.' ;
            container digitaldata {
              description 'Used to query the current digital performance.' ;
              list zxr10digitaldatum {
                description 'Used to query the current digital performance.' ;
                key 'inner-index checkpoint-type tpid perfcode tpid-class tpid-length' ;
                leaf inner-index {
                  description 'JID Inner Index.' ;
                  type uint16 ;

                }

                leaf checkpoint-type {
                  description 'TPID type. 0xFFFF indicates that the query all type of check-point.' ;
                  type uint16 {
                    range 1..65535 ;

                  }

                }

                leaf tpid {
                  description 'The TPID of detection point.' ;
                  type binary {
                    length 62..128 ;

                  }

                }

                leaf perfcode {
                  description 'The performance code of this TPID. 0xFFFF indicates any performance items.' ;
                  type uint16 {
                    range 1..65535 ;

                  }

                }

                leaf tpid-class {
                  description 'The class of TPID.' ;
                  type enumeration {
                    enum board {
                      value 1 ;
                    }

                    enum CPU {
                      value 2 ;
                    }

                    enum system {
                      value 3 ;
                    }

                    enum all {
                      value 255 ;
                    }

                  }

                }

                leaf tpid-length {
                  description 'The length of TPID.' ;
                  type uint8 {
                    range 62..128 ;

                  }

                }

                leaf tpid-matcher {
                  description "As a conditions tpid, used with 'tpid-mask'." ;
                  type binary {
                    length 62..128 ;

                  }

                }

                leaf tpid-mask {
                  description "Mask bit of attribute 'tpid-matcher'. Length is always 8 bytes." ;
                  type binary {
                    length 8..16 ;

                  }

                }

                leaf value {
                  description 'The performance value.' ;
                  type binary {
                    length 10 ;

                  }

                }

                leaf isdoubt {
                  description 'Indicates whether the suspect, if the performance test cycle affect the calculation of the events occurred, they sign into doubt.' ;
                  type boolean ;

                }

                leaf elapsetime {
                  description 'Elapsed time. From the query performance calculation cycle until the time of the current performance elapsed time.' ;
                  type uint32 ;

                  units second ;
                }

                leaf tpid-desc {
                  description 'The description of TPID.' ;
                  type ncd:string-all {
                    length 0..127 ;

                  }

                  ncd:revise-date 2024-05-23 ;
                }

                ncd:revise-date 2015-12-28 ;
                ncd:select "checkpoint-type perfcode tpid-class tpid-length tpid-matcher tpid-mask" ;
              }

              list digitaldatum {
                status obsolete {
                  ncd:revise-date 2015-12-28 ;
                }

                description 'Used to query the current digital performance.' ;
                key 'inner-index checkpoint-type tpid perfcode tpid-class' ;
                leaf inner-index {
                  description 'JID Inner Index.' ;
                  type uint16 ;

                }

                leaf checkpoint-type {
                  description 'TPID type. 0xFFFF indicates that the query all type of check-point.' ;
                  type uint16 {
                    range 1..65535 ;

                  }

                }

                leaf tpid {
                  description 'The tpid of detection point.' ;
                  type binary {
                    length 1..128 ;

                  }

                }

                leaf tpid-matcher {
                  description 'As a conditions tpid, used with tpid-mask.' ;
                  type binary {
                    length 1..128 ;

                  }

                }

                leaf tpid-mask {
                  description "Mask bit of attribute 'tpid-matcher'. Length is always 8 bytes." ;
                  type binary {
                    length 1..16 ;

                  }

                }

                leaf perfcode {
                  description 'The performance code of this tpid. 0xFFFF indicates any performance items.' ;
                  type uint16 {
                    range 1..65535 ;

                  }

                }

                leaf value {
                  description 'The performance value.' ;
                  type binary {
                    length 10 ;

                  }

                }

                leaf isdoubt {
                  description 'Indicates whether the suspect, if the performance test cycle affect the calculation of the events occurred, they sign into doubt.' ;
                  type boolean ;

                }

                leaf elapsetime {
                  description 'Elapsed time. From the query performance calculation cycle until the time of the current performance elapsed time.' ;
                  type uint32 ;

                  units second ;
                }

                leaf tpid-class {
                  description 'The class of TPID.' ;
                  type enumeration {
                    enum board {
                      value 1 ;
                    }

                    enum CPU {
                      value 2 ;
                    }

                    enum system {
                      value 3 ;
                    }

                    enum all {
                      value 255 ;
                    }

                  }

                }

                leaf tpid-length {
                  description 'The length of TPID.' ;
                  type uint8 {
                    range 1..128 ;

                  }

                }

                ncd:select "checkpoint-type tpid-matcher tpid-mask perfcode tpid-class tpid-length" ;
              }

            }

            container analogdata {
              description 'Current data about analog check points.' ;
              list zxr10analogdatum {
                description 'Current data about analog check points.' ;
                key 'inner-index checkpoint-type tpid perfcode tpid-class tpid-length' ;
                leaf inner-index {
                  description 'JID Inner Index.' ;
                  type uint16 ;

                }

                leaf checkpoint-type {
                  description 'TPID type. 0xFFFF indicates that the query all type of check-point.' ;
                  type uint16 {
                    range 1..65535 ;

                  }

                }

                leaf tpid {
                  description 'The TPID of detection point.' ;
                  type binary {
                    length 62..128 ;

                  }

                }

                leaf perfcode {
                  description 'The performance code of this TPID. 0xFFFF indicates any performance items.' ;
                  type uint16 {
                    range 1..65535 ;

                  }

                }

                leaf tpid-class {
                  description 'The class of TPID.' ;
                  type enumeration {
                    enum board {
                      value 1 ;
                    }

                    enum CPU {
                      value 2 ;
                    }

                    enum system {
                      value 3 ;
                    }

                    enum all {
                      value 255 ;
                    }

                  }

                }

                leaf tpid-length {
                  description 'The length of TPID.' ;
                  type uint8 {
                    range 62..128 ;

                  }

                }

                leaf tpid-matcher {
                  description "As a conditions tpid, used with 'tpid-mask'." ;
                  type binary {
                    length 62..128 ;

                  }

                }

                leaf tpid-mask {
                  description "Mask bit of attribute 'tpid-matcher'. Length is always 8 bytes." ;
                  type binary {
                    length 8..16 ;

                  }

                }

                leaf value {
                  description 'The performance value.' ;
                  type binary {
                    length 10 ;

                  }

                }

                leaf max-value {
                  description 'So far the maximum.' ;
                  type binary {
                    length 10 ;

                  }

                }

                leaf min-value {
                  description 'So far the minimum value.' ;
                  type binary {
                    length 10 ;

                  }

                }

                leaf avg-value {
                  description 'So far the average value.' ;
                  type binary {
                    length 10 ;

                  }

                }

                leaf isdoubt {
                  description 'Indicates whether the suspect, if the performance test cycle affect the calculation of the events occurred, they sign into doubt.' ;
                  type boolean ;

                }

                leaf elapsetime {
                  description 'Elapsed time. From the query performance calculation cycle until the time of the current performance elapsed time.' ;
                  type uint32 ;

                  units second ;
                }

                leaf tpid-desc {
                  type ncd:string-all {
                    length 0..127 ;

                  }

                  description 'The description of TPID.' ;
                  ncd:revise-date 2024-05-23 ;
                }

                ncd:revise-date 2015-12-28 ;
                ncd:select "checkpoint-type perfcode tpid-class tpid-length tpid-matcher tpid-mask" ;
              }

              list analogdatum {
                status obsolete {
                  ncd:revise-date 2015-12-28 ;
                }

                description 'Current data about analog check points.' ;
                key 'inner-index checkpoint-type tpid perfcode tpid-class' ;
                leaf inner-index {
                  description 'JID Inner Index.' ;
                  type uint16 ;

                }

                leaf checkpoint-type {
                  description 'TPID type. 0xFFFF indicates that the query all type of check-point.' ;
                  type uint16 {
                    range 1..65535 ;

                  }

                }

                leaf tpid {
                  description 'The tpid of detection point.' ;
                  type binary {
                    length 1..128 ;

                  }

                }

                leaf tpid-matcher {
                  description 'As a conditions tpid, used with tpid-mask.' ;
                  type binary {
                    length 1..128 ;

                  }

                }

                leaf tpid-mask {
                  description "Mask bit of attribute 'tpid-matcher'. Length is always 8 bytes." ;
                  type binary {
                    length 1..16 ;

                  }

                }

                leaf perfcode {
                  description 'The performance code of this tpid. 0xFFFF indicates any performance items.' ;
                  type uint16 {
                    range 1..65535 ;

                  }

                }

                leaf value {
                  description 'The performance value.' ;
                  type binary {
                    length 10 ;

                  }

                }

                leaf max-value {
                  description 'So far the maximum.' ;
                  type binary {
                    length 10 ;

                  }

                }

                leaf min-value {
                  description 'So far the minimum value.' ;
                  type binary {
                    length 10 ;

                  }

                }

                leaf avg-value {
                  description 'So far the average value.' ;
                  type binary {
                    length 10 ;

                  }

                }

                leaf isdoubt {
                  description 'Indicates whether the suspect, if the performance test cycle affect the calculation of the events occurred, they sign into doubt.' ;
                  type boolean ;

                }

                leaf elapsetime {
                  description 'Elapsed time. From the query performance calculation cycle until the time of the current performance elapsed time.' ;
                  type uint32 ;

                  units second ;
                }

                leaf tpid-class {
                  description 'The class of TPID.' ;
                  type enumeration {
                    enum board {
                      value 1 ;
                    }

                    enum CPU {
                      value 2 ;
                    }

                    enum system {
                      value 3 ;
                    }

                    enum all {
                      value 255 ;
                    }

                  }

                }

                leaf tpid-length {
                  description 'The length of TPID.' ;
                  type uint8 {
                    range 1..128 ;

                  }

                }

                ncd:select "checkpoint-type tpid-matcher tpid-mask perfcode tpid-class tpid-length" ;
              }

            }

          }

          container twenty-four-hours {
            description 'Current data for twenty four hours.' ;
            container digitaldata {
              description 'Used to query the current digital performance.' ;
              list zxr10digitaldatum {
                description 'Used to query the current digital performance.' ;
                key 'inner-index checkpoint-type tpid perfcode tpid-class tpid-length' ;
                leaf inner-index {
                  description 'JID Inner Index.' ;
                  type uint16 ;

                }

                leaf checkpoint-type {
                  description 'TPID type. 0xFFFF indicates that the query all type of check-point.' ;
                  type uint16 {
                    range 1..65535 ;

                  }

                }

                leaf tpid {
                  description 'The tpid of detection point.' ;
                  type binary {
                    length 62..128 ;

                  }

                }

                leaf perfcode {
                  description 'The performance code of this tpid. 0xFFFF indicates any performance items.' ;
                  type uint16 {
                    range 1..65535 ;

                  }

                }

                leaf tpid-class {
                  description 'The class of TPID.' ;
                  type enumeration {
                    enum board {
                      value 1 ;
                    }

                    enum CPU {
                      value 2 ;
                    }

                    enum system {
                      value 3 ;
                    }

                    enum all {
                      value 255 ;
                    }

                  }

                }

                leaf tpid-length {
                  description 'The length of TPID.' ;
                  type uint8 {
                    range 62..128 ;

                  }

                }

                leaf tpid-matcher {
                  description 'As a conditions tpid, used with tpid-mask.' ;
                  type binary {
                    length 62..128 ;

                  }

                }

                leaf tpid-mask {
                  description "Mask bit of attribute 'tpid-matcher'. Length is always 8 bytes." ;
                  type binary {
                    length 8..16 ;

                  }

                }

                leaf value {
                  description 'The performance value.' ;
                  type binary {
                    length 10 ;

                  }

                }

                leaf isdoubt {
                  description 'Indicates whether the suspect, if the performance test cycle affect the calculation of the events occurred, they sign into doubt.' ;
                  type boolean ;

                }

                leaf elapsetime {
                  description 'Elapsed time. From the query performance calculation cycle until the time of the current performance elapsed time.' ;
                  type uint32 ;

                  units second ;
                }

                leaf tpid-desc {
                  description 'The description of TPID.' ;
                  type ncd:string-all {
                    length 0..127 ;

                  }

                  ncd:revise-date 2024-05-23 ;
                }

                ncd:revise-date 2015-12-28 ;
                ncd:select "checkpoint-type perfcode tpid-class tpid-length tpid-matcher tpid-mask" ;
              }

              list digitaldatum {
                status obsolete {
                  ncd:revise-date 2015-12-28 ;
                }

                description 'Used to query the current digital performance.' ;
                key 'inner-index checkpoint-type tpid perfcode tpid-class' ;
                leaf inner-index {
                  description 'JID Inner Index.' ;
                  type uint16 ;

                }

                leaf checkpoint-type {
                  description 'TPID type. 0xFFFF indicates that the query all type of check-point.' ;
                  type uint16 {
                    range 1..65535 ;

                  }

                }

                leaf tpid {
                  description 'The tpid of detection point.' ;
                  type binary {
                    length 1..128 ;

                  }

                }

                leaf tpid-matcher {
                  description 'As a conditions tpid, used with tpid-mask.' ;
                  type binary {
                    length 1..128 ;

                  }

                }

                leaf tpid-mask {
                  description "Mask bit of attribute 'tpid-matcher'. Length is always 8 bytes." ;
                  type binary {
                    length 1..16 ;

                  }

                }

                leaf perfcode {
                  description 'The performance code of this tpid. 0xFFFF indicates any performance items.' ;
                  type uint16 {
                    range 1..65535 ;

                  }

                }

                leaf value {
                  description 'The performance value.' ;
                  type binary {
                    length 10 ;

                  }

                }

                leaf isdoubt {
                  description 'Indicates whether the suspect, if the performance test cycle affect the calculation of the events occurred, they sign into doubt.' ;
                  type boolean ;

                }

                leaf elapsetime {
                  description 'Elapsed time. From the query performance calculation cycle until the time of the current performance elapsed time.' ;
                  type uint32 ;

                  units second ;
                }

                leaf tpid-class {
                  description 'The class of TPID.' ;
                  type enumeration {
                    enum board {
                      value 1 ;
                    }

                    enum CPU {
                      value 2 ;
                    }

                    enum system {
                      value 3 ;
                    }

                    enum all {
                      value 255 ;
                    }

                  }

                }

                leaf tpid-length {
                  description 'The length of TPID.' ;
                  type uint8 {
                    range 1..128 ;

                  }

                }

                ncd:select "checkpoint-type tpid-matcher tpid-mask perfcode tpid-class tpid-length" ;
              }

            }

            container analogdata {
              description 'Current data about analog check points.' ;
              list zxr10analogdatum {
                description 'Current data about analog check points.' ;
                key 'inner-index checkpoint-type tpid perfcode tpid-class tpid-length' ;
                leaf inner-index {
                  description 'JID Inner Index.' ;
                  type uint16 ;

                }

                leaf checkpoint-type {
                  description 'TPID type. 0xFFFF indicates that the query all type of check-point.' ;
                  type uint16 {
                    range 1..65535 ;

                  }

                }

                leaf tpid {
                  description 'The tpid of detection point.' ;
                  type binary {
                    length 62..128 ;

                  }

                }

                leaf perfcode {
                  description 'The performance code of this tpid. 0xFFFF indicates any performance items.' ;
                  type uint16 {
                    range 1..65535 ;

                  }

                }

                leaf tpid-class {
                  description 'The class of TPID.' ;
                  type enumeration {
                    enum board {
                      value 1 ;
                    }

                    enum CPU {
                      value 2 ;
                    }

                    enum system {
                      value 3 ;
                    }

                    enum all {
                      value 255 ;
                    }

                  }

                }

                leaf tpid-length {
                  description 'The length of TPID.' ;
                  type uint8 {
                    range 62..128 ;

                  }

                }

                leaf tpid-matcher {
                  description 'As a conditions tpid, used with tpid-mask.' ;
                  type binary {
                    length 62..128 ;

                  }

                }

                leaf tpid-mask {
                  description "Mask bit of attribute 'tpid-matcher'. Length is always 8 bytes." ;
                  type binary {
                    length 8..16 ;

                  }

                }

                leaf value {
                  description 'The performance value.' ;
                  type binary {
                    length 10 ;

                  }

                }

                leaf max-value {
                  description 'So far the maximum.' ;
                  type binary {
                    length 10 ;

                  }

                }

                leaf min-value {
                  description 'So far the minimum value.' ;
                  type binary {
                    length 10 ;

                  }

                }

                leaf avg-value {
                  description 'So far the average value.' ;
                  type binary {
                    length 10 ;

                  }

                }

                leaf isdoubt {
                  description 'Indicates whether the suspect, if the performance test cycle affect the calculation of the events occurred, they sign into doubt.' ;
                  type boolean ;

                }

                leaf elapsetime {
                  description 'Elapsed time. From the query performance calculation cycle until the time of the current performance elapsed time.' ;
                  type uint32 ;

                  units second ;
                }

                leaf tpid-desc {
                  description 'The description of TPID.' ;
                  type ncd:string-all {
                    length 0..127 ;

                  }

                  ncd:revise-date 2024-05-23 ;
                }

                ncd:revise-date 2015-12-28 ;
                ncd:select "checkpoint-type perfcode tpid-class tpid-length tpid-matcher tpid-mask" ;
              }

              list analogdatum {
                status obsolete {
                  ncd:revise-date 2015-12-28 ;
                }

                description 'Current data about analog check points.' ;
                key 'inner-index checkpoint-type tpid perfcode tpid-class' ;
                leaf inner-index {
                  description 'JID Inner Index.' ;
                  type uint16 ;

                }

                leaf checkpoint-type {
                  description 'TPID type. 0xFFFF indicates that the query all type of check-point.' ;
                  type uint16 {
                    range 1..65535 ;

                  }

                }

                leaf tpid {
                  description 'The tpid of detection point.' ;
                  type binary {
                    length 1..128 ;

                  }

                }

                leaf tpid-matcher {
                  description 'As a conditions tpid, used with tpid-mask.' ;
                  type binary {
                    length 1..128 ;

                  }

                }

                leaf tpid-mask {
                  description "Mask bit of attribute 'tpid-matcher'. Length is always 8 bytes." ;
                  type binary {
                    length 1..16 ;

                  }

                }

                leaf perfcode {
                  description 'The performance code of this tpid. 0xFFFF indicates any performance items.' ;
                  type uint16 {
                    range 1..65535 ;

                  }

                }

                leaf value {
                  description 'The performance value.' ;
                  type binary {
                    length 10 ;

                  }

                }

                leaf max-value {
                  description 'So far the maximum.' ;
                  type binary {
                    length 10 ;

                  }

                }

                leaf min-value {
                  description 'So far the minimum value.' ;
                  type binary {
                    length 10 ;

                  }

                }

                leaf avg-value {
                  description 'So far the average value.' ;
                  type binary {
                    length 10 ;

                  }

                }

                leaf isdoubt {
                  description 'Indicates whether the suspect, if the performance test cycle affect the calculation of the events occurred, they sign into doubt.' ;
                  type boolean ;

                }

                leaf elapsetime {
                  description 'Elapsed time. From the query performance calculation cycle until the time of the current performance elapsed time.' ;
                  type uint32 ;

                  units second ;
                }

                leaf tpid-class {
                  description 'The class of TPID.' ;
                  type enumeration {
                    enum board {
                      value 1 ;
                    }

                    enum CPU {
                      value 2 ;
                    }

                    enum system {
                      value 3 ;
                    }

                    enum all {
                      value 255 ;
                    }

                  }

                }

                leaf tpid-length {
                  description 'The length of TPID.' ;
                  type uint8 {
                    range 1..128 ;

                  }

                }

                ncd:select "checkpoint-type tpid-matcher tpid-mask perfcode tpid-class tpid-length" ;
              }

            }

          }

          container self-defined-minutes {
            container digitaldata {
              list zxr10digitaldatum {
                leaf inner-index {
                  type uint16 ;

                  description 'JID Inner Index.' ;
                }

                leaf checkpoint-type {
                  type uint16 {
                    range 1..65535 ;

                  }

                  description 'TPID type. 0xFFFF indicates that the query all type of check-point.' ;
                }

                leaf tpid {
                  type binary {
                    length 62..128 ;

                  }

                  description 'The TPID of detection point.' ;
                }

                leaf perfcode {
                  type uint16 {
                    range 1..65535 ;

                  }

                  description 'The performance code of this tpid. 0xFFFF indicates any performance items.' ;
                }

                leaf tpid-class {
                  type enumeration {
                    enum board {
                      value 1 ;
                    }

                    enum CPU {
                      value 2 ;
                    }

                    enum system {
                      value 3 ;
                    }

                    enum all {
                      value 255 ;
                    }

                  }

                  description 'The class of TPID.' ;
                }

                leaf tpid-length {
                  type uint8 {
                    range 62..128 ;

                  }

                  description 'The length of TPID.' ;
                }

                leaf tpid-matcher {
                  type binary {
                    length 62..128 ;

                  }

                  description "As a conditions tpid, used with 'tpid-mask'." ;
                }

                leaf tpid-mask {
                  type binary {
                    length 8..16 ;

                  }

                  description "Mask bit of attribute 'tpid-matcher'. Length is always 8 bytes." ;
                }

                leaf value {
                  type binary {
                    length 10 ;

                  }

                  description 'The performance value.' ;
                }

                leaf isdoubt {
                  type boolean ;

                  description 'Indicates whether the suspect, if the performance test cycle affect the calculation of the events occurred, they sign into doubt.' ;
                }

                leaf elapsetime {
                  type uint32 ;

                  description 'Elapsed time. From the query performance calculation cycle until the time of the current performance elapsed time.' ;
                  units second ;
                }

                leaf tpid-desc {
                  description 'The description of TPID.' ;
                  type ncd:string-all {
                    length 0..127 ;

                  }

                  ncd:revise-date 2024-05-23 ;
                }

                description 'Current data about digital performance.' ;
                key 'inner-index checkpoint-type tpid perfcode tpid-class tpid-length' ;
                ncd:select "checkpoint-type perfcode tpid-class tpid-length tpid-matcher tpid-mask" ;
              }

              description 'Current data about digital performance.' ;
            }

            container analogdata {
              list zxr10analogdatum {
                leaf inner-index {
                  type uint16 ;

                  description 'JID Inner Index.' ;
                }

                leaf checkpoint-type {
                  type uint16 {
                    range 1..65535 ;

                  }

                  description 'TPID type. 0xFFFF indicates that the query all type of check-point.' ;
                }

                leaf tpid {
                  type binary {
                    length 62..128 ;

                  }

                  description 'The TPID of detection point.' ;
                }

                leaf perfcode {
                  type uint16 {
                    range 1..65535 ;

                  }

                  description 'The performance code of this tpid. 0xFFFF indicates any performance items.' ;
                }

                leaf tpid-class {
                  type enumeration {
                    enum board {
                      value 1 ;
                    }

                    enum CPU {
                      value 2 ;
                    }

                    enum system {
                      value 3 ;
                    }

                    enum all {
                      value 255 ;
                    }

                  }

                  description 'The class of TPID.' ;
                }

                leaf tpid-length {
                  type uint8 {
                    range 62..128 ;

                  }

                  description 'The length of TPID.' ;
                }

                leaf tpid-matcher {
                  type binary {
                    length 62..128 ;

                  }

                  description "As a conditions tpid, used with 'tpid-mask'." ;
                }

                leaf tpid-mask {
                  type binary {
                    length 8..16 ;

                  }

                  description "Mask bit of attribute 'tpid-matcher'. Length is always 8 bytes." ;
                }

                leaf value {
                  type binary {
                    length 10 ;

                  }

                  description 'The performance value.' ;
                }

                leaf max-value {
                  type binary {
                    length 10 ;

                  }

                  description 'So far the maximum.' ;
                }

                leaf min-value {
                  type binary {
                    length 10 ;

                  }

                  description 'So far the minimum value.' ;
                }

                leaf avg-value {
                  type binary {
                    length 10 ;

                  }

                  description 'So far the average value.' ;
                }

                leaf isdoubt {
                  type boolean ;

                  description 'Indicates whether the suspect, if the performance test cycle affect the calculation of the events occurred, they sign into doubt.' ;
                }

                leaf elapsetime {
                  type uint32 ;

                  description 'Elapsed time. From the query performance calculation cycle until the time of the current performance elapsed time.' ;
                  units second ;
                }

                leaf tpid-desc {
                  description 'The description of TPID.' ;
                  type ncd:string-all {
                    length 0..127 ;

                  }

                  ncd:revise-date 2024-05-23 ;
                }

                key 'inner-index checkpoint-type tpid perfcode tpid-class tpid-length' ;
                description 'Current data about analog performance.' ;
                ncd:select "checkpoint-type perfcode tpid-class tpid-length tpid-matcher tpid-mask" ;
              }

              description 'Current data about analog performance.' ;
            }

            description 'Current data for self defined minutes performance items. The actual performance items depend on the self-defined-five-minutes configuration. ' ;
            if-feature self-defined-minutes {
              ncd:revise-date 2024-02-20 ;
            }

            ncd:revise-date 2024-02-20 ;
          }

        }

        container historydata {
          description 'Statistics info about history data.' ;
          container fifteen-mins {
            description 'History data for minute cycle. The actual cycle value depends on the minute-cycle configuration.' ;
            container digitaldata {
              description 'History data about digital checkpoints' ;
              list zxr10digitaldatum {
                description 'Used to query the history digital performance.' ;
                key 'checkpoint-type tpid perfcode cycle-end-time tpid-class tpid-length inner-index' ;
                leaf checkpoint-type {
                  description 'TPID type. 0xFFFF indicates that the query all type of check-point.' ;
                  type uint16 {
                    range 1..65535 ;

                  }

                }

                leaf tpid {
                  description 'The TPID of detection point.' ;
                  type binary {
                    length 62..128 ;

                  }

                }

                leaf perfcode {
                  description 'The performance code of this TPID. 0xFFFF indicates any performance items.' ;
                  type uint16 {
                    range 1..65535 ;

                  }

                }

                leaf cycle-end-time {
                  description 'The end of the cycle. UTC.' ;
                  type ncd:datetime ;

                }

                leaf tpid-class {
                  description 'The class of TPID.' ;
                  type enumeration {
                    enum board {
                      value 1 ;
                    }

                    enum CPU {
                      value 2 ;
                    }

                    enum system {
                      value 3 ;
                    }

                    enum all {
                      value 255 ;
                    }

                  }

                }

                leaf tpid-length {
                  description 'The length of TPID.' ;
                  type uint8 {
                    range 62..128 ;

                  }

                }

                leaf inner-index {
                  description 'JID inner index.' ;
                  type uint16 ;

                }

                leaf tpid-matcher {
                  description "As a conditions tpid, used with 'tpid-mask'." ;
                  type binary {
                    length 62..128 ;

                  }

                }

                leaf tpid-mask {
                  description "Mask bit of attribute 'tpid-matcher'. Length is always 8 bytes." ;
                  type binary {
                    length 8..16 ;

                  }

                }

                leaf begin-time {
                  description 'Start time for query. UTC. End of the cycle time within the time period is selected.' ;
                  type ncd:datetime ;

                }

                leaf end-time {
                  description 'End time for query. UTC. End of the cycle time within the time period is selected.' ;
                  type ncd:datetime ;

                }

                leaf value {
                  description 'The performance value.' ;
                  type binary {
                    length 10 ;

                  }

                }

                leaf isdoubt {
                  description 'Indicates whether the suspect, if the performance test cycle affect the calculation of the events occurred, they sign into doubt.' ;
                  type boolean ;

                }

                leaf tpid-desc {
                  description 'The description of TPID.' ;
                  type ncd:string-all {
                    length 0..127 ;

                  }

                  ncd:revise-date 2024-05-23 ;
                }

                ncd:revise-date 2015-12-28 ;
                ncd:select "checkpoint-type perfcode tpid-class tpid-length tpid-matcher tpid-mask begin-time end-time" ;
              }

              list digitaldatum {
                status obsolete {
                  ncd:revise-date 2015-12-28 ;
                }

                description 'Used to query the history digital performance.' ;
                key 'checkpoint-type tpid perfcode cycle-end-time tpid-class inner-index' ;
                leaf checkpoint-type {
                  description 'TPID type. 0xFFFF indicates that the query all type of check-point.' ;
                  type uint16 {
                    range 1..65535 ;

                  }

                }

                leaf tpid {
                  description 'The tpid of detection point.' ;
                  type binary {
                    length 1..128 ;

                  }

                }

                leaf tpid-matcher {
                  description 'As a conditions tpid, used with tpid-mask.' ;
                  type binary {
                    length 1..128 ;

                  }

                }

                leaf tpid-mask {
                  description "Mask bit of attribute 'tpid-matcher'. Length is always 8 bytes." ;
                  type binary {
                    length 1..16 ;

                  }

                }

                leaf perfcode {
                  description 'The performance code of this tpid. 0xFFFF indicates any performance items.' ;
                  type uint16 {
                    range 1..65535 ;

                  }

                }

                leaf cycle-end-time {
                  description 'The end of the cycle. UTC.' ;
                  type ncd:datetime ;

                }

                leaf begin-time {
                  description 'Start time for query. UTC. End of the cycle time within the time period is selected.' ;
                  type ncd:datetime ;

                }

                leaf end-time {
                  description 'End time for query. UTC. End of the cycle time within the time period is selected.' ;
                  type ncd:datetime ;

                }

                leaf value {
                  description 'The performance value.' ;
                  type binary {
                    length 10 ;

                  }

                }

                leaf isdoubt {
                  description 'Indicates whether the suspect, if the performance test cycle affect the calculation of the events occurred, they sign into doubt.' ;
                  type boolean ;

                }

                leaf tpid-class {
                  description 'The class of TPID.' ;
                  type enumeration {
                    enum board {
                      value 1 ;
                    }

                    enum CPU {
                      value 2 ;
                    }

                    enum system {
                      value 3 ;
                    }

                    enum all {
                      value 255 ;
                    }

                  }

                }

                leaf tpid-length {
                  description 'The length of TPID.' ;
                  type uint8 {
                    range 1..128 ;

                  }

                }

                leaf inner-index {
                  description 'JID inner index.' ;
                  type uint16 ;

                }

                ncd:select "checkpoint-type tpid-matcher tpid-mask perfcode begin-time end-time tpid-class tpid-length" ;
              }

            }

            container analogdata {
              description 'History data about analog checkpoints.' ;
              list zxr10analogdatum {
                description 'History data about analog check points.' ;
                key 'checkpoint-type tpid perfcode cycle-end-time tpid-class tpid-length inner-index' ;
                leaf checkpoint-type {
                  description 'TPID type. 0xFFFF indicates that the query all type of check-point.' ;
                  type uint16 {
                    range 1..65535 ;

                  }

                }

                leaf tpid {
                  description 'The TPID of detection point.' ;
                  type binary {
                    length 62..128 ;

                  }

                }

                leaf perfcode {
                  description 'The performance code of this TPID. 0xFFFF indicates any performance items.' ;
                  type uint16 {
                    range 1..65535 ;

                  }

                }

                leaf cycle-end-time {
                  description 'The end of the cycle. UTC.' ;
                  type ncd:datetime ;

                }

                leaf tpid-class {
                  description 'The class of TPID.' ;
                  type enumeration {
                    enum board {
                      value 1 ;
                    }

                    enum CPU {
                      value 2 ;
                    }

                    enum system {
                      value 3 ;
                    }

                    enum all {
                      value 255 ;
                    }

                  }

                }

                leaf tpid-length {
                  description 'The length of TPID.' ;
                  type uint8 {
                    range 62..128 ;

                  }

                }

                leaf inner-index {
                  description 'JID inner index.' ;
                  type uint16 ;

                }

                leaf tpid-matcher {
                  description "As a conditions tpid, used with 'tpid-mask'." ;
                  type binary {
                    length 62..128 ;

                  }

                }

                leaf tpid-mask {
                  description "Mask bit of attribute 'tpid-matcher'. Length is always 8 bytes." ;
                  type binary {
                    length 8..16 ;

                  }

                }

                leaf begin-time {
                  description 'Start time for query. UTC. End of the cycle time within the time period is selected.' ;
                  type ncd:datetime ;

                }

                leaf end-time {
                  description 'End time for query. UTC. End of the cycle time within the time period is selected.' ;
                  type ncd:datetime ;

                }

                leaf value {
                  description 'The performance value.' ;
                  type binary {
                    length 10 ;

                  }

                }

                leaf max-value {
                  description 'The maximum value of this cycle.' ;
                  type binary {
                    length 10 ;

                  }

                }

                leaf min-value {
                  description 'The minimum value of this cycle.' ;
                  type binary {
                    length 10 ;

                  }

                }

                leaf avg-value {
                  description 'The average value of this cycle.' ;
                  type binary {
                    length 10 ;

                  }

                }

                leaf isdoubt {
                  description 'Indicates whether the suspect, if the performance test cycle affect the calculation of the events occurred, they sign into doubt.' ;
                  type boolean ;

                }

                leaf max-value-time {
                  description 'The time of max value. UTC.' ;
                  type ncd:datetime ;

                }

                leaf tpid-desc {
                  description 'The description of TPID.' ;
                  type ncd:string-all {
                    length 0..127 ;

                  }

                  ncd:revise-date 2024-05-23 ;
                }

                ncd:revise-date 2015-12-28 ;
                ncd:select "checkpoint-type perfcode tpid-class tpid-length tpid-matcher tpid-mask begin-time end-time" ;
              }

              list analogdatum {
                status obsolete {
                  ncd:revise-date 2015-12-28 ;
                }

                description 'History data about analog check points.' ;
                key 'checkpoint-type tpid perfcode cycle-end-time tpid-class inner-index' ;
                leaf checkpoint-type {
                  description 'TPID type. 0xFFFF indicates that the query all type of check-point.' ;
                  type uint16 {
                    range 1..65535 ;

                  }

                }

                leaf tpid {
                  description 'The tpid of detection point.' ;
                  type binary {
                    length 1..128 ;

                  }

                }

                leaf tpid-matcher {
                  description 'As a conditions tpid, used with tpid-mask.' ;
                  type binary {
                    length 1..128 ;

                  }

                }

                leaf tpid-mask {
                  description "Mask bit of attribute 'tpid-matcher'. Length is always 8 bytes." ;
                  type binary {
                    length 1..16 ;

                  }

                }

                leaf perfcode {
                  description 'The performance code of this tpid. 0xFFFF indicates any performance items.' ;
                  type uint16 {
                    range 1..65535 ;

                  }

                }

                leaf cycle-end-time {
                  description 'The end of the cycle. UTC.' ;
                  type ncd:datetime ;

                }

                leaf begin-time {
                  description 'Start time for query. UTC. End of the cycle time within the time period is selected.' ;
                  type ncd:datetime ;

                }

                leaf end-time {
                  description 'End time for query. UTC. End of the cycle time within the time period is selected.' ;
                  type ncd:datetime ;

                }

                leaf value {
                  description 'The performance value.' ;
                  type binary {
                    length 10 ;

                  }

                }

                leaf max-value {
                  description 'The maximum value of this cycle.' ;
                  type binary {
                    length 10 ;

                  }

                }

                leaf min-value {
                  description 'The minimum value of this cycle.' ;
                  type binary {
                    length 10 ;

                  }

                }

                leaf avg-value {
                  description 'The average value of this cycle.' ;
                  type binary {
                    length 10 ;

                  }

                }

                leaf isdoubt {
                  description 'Indicates whether the suspect, if the performance test cycle affect the calculation of the events occurred, they sign into doubt.' ;
                  type boolean ;

                }

                leaf tpid-class {
                  description 'The class of TPID.' ;
                  type enumeration {
                    enum board {
                      value 1 ;
                    }

                    enum CPU {
                      value 2 ;
                    }

                    enum system {
                      value 3 ;
                    }

                    enum all {
                      value 255 ;
                    }

                  }

                }

                leaf tpid-length {
                  description 'The length of TPID.' ;
                  type uint8 {
                    range 1..128 ;

                  }

                }

                leaf inner-index {
                  description 'JID inner index.' ;
                  type uint16 ;

                }

                leaf max-value-time {
                  description 'The time of max value. UTC.' ;
                  type ncd:datetime ;

                  ncd:revise-date 2015-08-12 ;
                }

                ncd:select "checkpoint-type tpid-matcher tpid-mask perfcode begin-time end-time tpid-class tpid-length" ;
              }

            }

          }

          container twenty-four-hours {
            description 'History data for twenty four hours.' ;
            container digitaldata {
              description 'History data about digital checkpoints.' ;
              list zxr10digitaldatum {
                description 'Used to query the history digital performance.' ;
                key 'checkpoint-type tpid perfcode cycle-end-time tpid-class tpid-length inner-index' ;
                leaf checkpoint-type {
                  description 'TPID type. 0xFFFF indicates that the query all type of check-point.' ;
                  type uint16 {
                    range 1..65535 ;

                  }

                }

                leaf tpid {
                  description 'The TPID of detection point.' ;
                  type binary {
                    length 62..128 ;

                  }

                }

                leaf perfcode {
                  description 'The performance code of this TPID. 0xFFFF indicates any performance items.' ;
                  type uint16 {
                    range 1..65535 ;

                  }

                }

                leaf cycle-end-time {
                  description 'The end of the cycle. UTC.' ;
                  type ncd:datetime ;

                }

                leaf tpid-class {
                  description 'The class of TPID.' ;
                  type enumeration {
                    enum board {
                      value 1 ;
                    }

                    enum CPU {
                      value 2 ;
                    }

                    enum system {
                      value 3 ;
                    }

                    enum all {
                      value 255 ;
                    }

                  }

                }

                leaf tpid-length {
                  description 'The length of TPID.' ;
                  type uint8 {
                    range 62..128 ;

                  }

                }

                leaf inner-index {
                  description 'JID inner index.' ;
                  type uint16 ;

                }

                leaf tpid-matcher {
                  description "As a conditions TPID, used with 'tpid-mask'." ;
                  type binary {
                    length 62..128 ;

                  }

                }

                leaf tpid-mask {
                  description "Mask bit of attribute 'tpid-matcher'. Length is always 8 bytes." ;
                  type binary {
                    length 8..16 ;

                  }

                }

                leaf begin-time {
                  description 'Start time for query. UTC. End of the cycle time within the time period is selected.' ;
                  type ncd:datetime ;

                }

                leaf end-time {
                  description 'End time for query. UTC. End of the cycle time within the time period is selected.' ;
                  type ncd:datetime ;

                }

                leaf value {
                  description 'The performance value.' ;
                  type binary {
                    length 10 ;

                  }

                }

                leaf isdoubt {
                  description 'Indicates whether the suspect, if the performance test cycle affect the calculation of the events occurred, they sign into doubt.' ;
                  type boolean ;

                }

                leaf tpid-desc {
                  description 'The description of TPID.' ;
                  type ncd:string-all {
                    length 0..127 ;

                  }

                  ncd:revise-date 2024-05-23 ;
                }

                ncd:revise-date 2015-12-28 ;
                ncd:select "checkpoint-type perfcode tpid-class tpid-length tpid-matcher tpid-mask begin-time end-time" ;
              }

              list digitaldatum {
                status obsolete {
                  ncd:revise-date 2015-12-28 ;
                }

                description 'Used to query the history digital performance.' ;
                key 'checkpoint-type tpid perfcode cycle-end-time tpid-class inner-index' ;
                leaf checkpoint-type {
                  description 'TPID type. 0xFFFF indicates that the query all type of check-point.' ;
                  type uint16 {
                    range 1..65535 ;

                  }

                }

                leaf tpid {
                  description 'The tpid of detection point.' ;
                  type binary {
                    length 1..128 ;

                  }

                }

                leaf tpid-matcher {
                  description 'As a conditions tpid, used with tpid-mask.' ;
                  type binary {
                    length 1..128 ;

                  }

                }

                leaf tpid-mask {
                  description "Mask bit of attribute 'tpid-matcher'. Length is always 8 bytes." ;
                  type binary {
                    length 1..16 ;

                  }

                }

                leaf perfcode {
                  description 'The performance code of this tpid. 0xFFFF indicates any performance items.' ;
                  type uint16 {
                    range 1..65535 ;

                  }

                }

                leaf cycle-end-time {
                  description 'The end of the cycle. UTC.' ;
                  type ncd:datetime ;

                }

                leaf begin-time {
                  description 'Start time for query. UTC. End of the cycle time within the time period is selected.' ;
                  type ncd:datetime ;

                }

                leaf end-time {
                  description 'End time for query. UTC. End of the cycle time within the time period is selected.' ;
                  type ncd:datetime ;

                }

                leaf value {
                  description 'The performance value.' ;
                  type binary {
                    length 10 ;

                  }

                }

                leaf isdoubt {
                  description 'Indicates whether the suspect, if the performance test cycle affect the calculation of the events occurred, they sign into doubt.' ;
                  type boolean ;

                }

                leaf tpid-class {
                  description 'The class of TPID.' ;
                  type enumeration {
                    enum board {
                      value 1 ;
                    }

                    enum CPU {
                      value 2 ;
                    }

                    enum system {
                      value 3 ;
                    }

                    enum all {
                      value 255 ;
                    }

                  }

                }

                leaf tpid-length {
                  description 'The length of TPID.' ;
                  type uint8 {
                    range 1..128 ;

                  }

                }

                leaf inner-index {
                  description 'JID inner index.' ;
                  type uint16 ;

                }

                ncd:select "checkpoint-type tpid-matcher tpid-mask perfcode begin-time end-time tpid-class tpid-length" ;
              }

            }

            container analogdata {
              description 'History data about analog checkpoints.' ;
              list zxr10analogdatum {
                description 'History data about analog check points.' ;
                key 'checkpoint-type tpid perfcode cycle-end-time tpid-class tpid-length inner-index' ;
                leaf checkpoint-type {
                  description 'TPID type. 0xFFFF indicates that the query all type of check-point.' ;
                  type uint16 {
                    range 1..65535 ;

                  }

                }

                leaf tpid {
                  description 'The tpid of detection point.' ;
                  type binary {
                    length 62..128 ;

                  }

                }

                leaf perfcode {
                  description 'The performance code of this TPID. 0xFFFF indicates any performance items.' ;
                  type uint16 {
                    range 1..65535 ;

                  }

                }

                leaf cycle-end-time {
                  description 'The end of the cycle. UTC.' ;
                  type ncd:datetime ;

                }

                leaf tpid-class {
                  description 'The class of TPID.' ;
                  type enumeration {
                    enum board {
                      value 1 ;
                    }

                    enum CPU {
                      value 2 ;
                    }

                    enum system {
                      value 3 ;
                    }

                    enum all {
                      value 255 ;
                    }

                  }

                }

                leaf tpid-length {
                  description 'The length of TPID.' ;
                  type uint8 {
                    range 62..128 ;

                  }

                }

                leaf inner-index {
                  description 'JID inner index.' ;
                  type uint16 ;

                }

                leaf tpid-matcher {
                  description "As a conditions tpid, used with 'tpid-mask'." ;
                  type binary {
                    length 62..128 ;

                  }

                }

                leaf tpid-mask {
                  description "Mask bit of attribute 'tpid-matcher'. Length is always 8 bytes." ;
                  type binary {
                    length 8..16 ;

                  }

                }

                leaf begin-time {
                  description 'Start time for query. UTC. End of the cycle time within the time period is selected.' ;
                  type ncd:datetime ;

                }

                leaf end-time {
                  description 'End time for query. UTC. End of the cycle time within the time period is selected.' ;
                  type ncd:datetime ;

                }

                leaf value {
                  description 'The performance value.' ;
                  type binary {
                    length 10 ;

                  }

                }

                leaf max-value {
                  description 'The maximum value of this cycle.' ;
                  type binary {
                    length 10 ;

                  }

                }

                leaf min-value {
                  description 'The minimum value of this cycle.' ;
                  type binary {
                    length 10 ;

                  }

                }

                leaf avg-value {
                  description 'The average value of this cycle.' ;
                  type binary {
                    length 10 ;

                  }

                }

                leaf isdoubt {
                  description 'Indicates whether the suspect, if the performance test cycle affect the calculation of the events occurred, they sign into doubt.' ;
                  type boolean ;

                }

                leaf tpid-desc {
                  description 'The description of TPID.' ;
                  type ncd:string-all {
                    length 0..127 ;

                  }

                  ncd:revise-date 2024-05-23 ;
                }

                ncd:revise-date 2015-12-28 ;
                ncd:select "checkpoint-type perfcode tpid-class tpid-length tpid-matcher tpid-mask begin-time end-time" ;
              }

              list analogdatum {
                status obsolete {
                  ncd:revise-date 2015-12-28 ;
                }

                description 'History data about analog check points.' ;
                key 'checkpoint-type tpid perfcode cycle-end-time tpid-class inner-index' ;
                leaf checkpoint-type {
                  description 'TPID type. 0xFFFF indicates that the query all type of check-point.' ;
                  type uint16 {
                    range 1..65535 ;

                  }

                }

                leaf tpid {
                  description 'The tpid of detection point.' ;
                  type binary {
                    length 1..128 ;

                  }

                }

                leaf tpid-matcher {
                  description 'As a conditions tpid, used with tpid-mask.' ;
                  type binary {
                    length 1..128 ;

                  }

                }

                leaf tpid-mask {
                  description "Mask bit of attribute 'tpid-matcher'. Length is always 8 bytes." ;
                  type binary {
                    length 1..16 ;

                  }

                }

                leaf perfcode {
                  description 'The performance code of this tpid. 0xFFFF indicates any performance items.' ;
                  type uint16 {
                    range 1..65535 ;

                  }

                }

                leaf cycle-end-time {
                  description 'The end of the cycle. UTC.' ;
                  type ncd:datetime ;

                }

                leaf begin-time {
                  description 'Start time for query. UTC. End of the cycle time within the time period is selected.' ;
                  type ncd:datetime ;

                }

                leaf end-time {
                  description 'End time for query. UTC. End of the cycle time within the time period is selected.' ;
                  type ncd:datetime ;

                }

                leaf value {
                  description 'The performance value.' ;
                  type binary {
                    length 10 ;

                  }

                }

                leaf max-value {
                  description 'The maximum value of this cycle.' ;
                  type binary {
                    length 10 ;

                  }

                }

                leaf min-value {
                  description 'The minimum value of this cycle.' ;
                  type binary {
                    length 10 ;

                  }

                }

                leaf avg-value {
                  description 'The average value of this cycle.' ;
                  type binary {
                    length 10 ;

                  }

                }

                leaf isdoubt {
                  description 'Indicates whether the suspect, if the performance test cycle affect the calculation of the events occurred, they sign into doubt.' ;
                  type boolean ;

                }

                leaf tpid-class {
                  description 'The class of TPID.' ;
                  type enumeration {
                    enum board {
                      value 1 ;
                    }

                    enum CPU {
                      value 2 ;
                    }

                    enum system {
                      value 3 ;
                    }

                    enum all {
                      value 255 ;
                    }

                  }

                }

                leaf tpid-length {
                  description 'The length of TPID.' ;
                  type uint8 {
                    range 1..128 ;

                  }

                }

                leaf inner-index {
                  description 'JID inner index.' ;
                  type uint16 ;

                }

                ncd:select "checkpoint-type tpid-matcher tpid-mask perfcode begin-time end-time tpid-class tpid-length" ;
              }

            }

          }

          container self-defined-minutes {
            container digitaldata {
              list zxr10digitaldatum {
                leaf checkpoint-type {
                  type uint16 {
                    range 1..65535 ;

                  }

                  description 'TPID type. 0xFFFF indicates that the query all type of check-point.' ;
                }

                leaf tpid {
                  type binary {
                    length 62..128 ;

                  }

                  description 'The TPID of detection point.' ;
                }

                leaf perfcode {
                  type uint16 {
                    range 1..65535 ;

                  }

                  description 'The performance code of this tpid. 0xFFFF indicates any performance items.' ;
                }

                leaf cycle-end-time {
                  type ncd:datetime ;

                  description 'The end of the cycle. UTC.' ;
                }

                leaf tpid-class {
                  type enumeration {
                    enum board {
                      value 1 ;
                    }

                    enum CPU {
                      value 2 ;
                    }

                    enum system {
                      value 3 ;
                    }

                    enum all {
                      value 255 ;
                    }

                  }

                  description 'The class of TPID.' ;
                }

                leaf tpid-length {
                  type uint8 {
                    range 62..128 ;

                  }

                  description 'The length of TPID.' ;
                }

                leaf inner-index {
                  type uint16 ;

                  description 'JID inner index.' ;
                }

                leaf tpid-matcher {
                  type binary {
                    length 62..128 ;

                  }

                  description "As a conditions tpid, used with 'tpid-mask'." ;
                }

                leaf tpid-mask {
                  type binary {
                    length 8..16 ;

                  }

                  description "Mask bit of attribute 'tpid-matcher'. Length is always 8 bytes." ;
                }

                leaf begin-time {
                  type ncd:datetime ;

                  description 'Start time for query. UTC. End of the cycle time within the time period is selected.' ;
                }

                leaf end-time {
                  type ncd:datetime ;

                  description 'End time for query. UTC. End of the cycle time within the time period is selected.' ;
                }

                leaf value {
                  type binary {
                    length 10 ;

                  }

                  description 'The performance value.' ;
                }

                leaf isdoubt {
                  type boolean ;

                  description 'Indicates whether the suspect, if the performance test cycle affect the calculation of the events occurred, they sign into doubt.' ;
                }

                leaf tpid-desc {
                  description 'The description of TPID.' ;
                  type ncd:string-all {
                    length 0..127 ;

                  }

                  ncd:revise-date 2024-05-23 ;
                }

                description 'History data about digital performance.' ;
                key 'checkpoint-type tpid perfcode cycle-end-time tpid-class tpid-length inner-index' ;
                ncd:select "checkpoint-type perfcode tpid-class tpid-length tpid-matcher tpid-mask begin-time end-time" ;
              }

              description 'History data about digital performance.' ;
            }

            container analogdata {
              list zxr10analogdatum {
                leaf checkpoint-type {
                  type uint16 {
                    range 1..65535 ;

                  }

                  description 'TPID type. 0xFFFF indicates that the query all type of check-point.' ;
                }

                leaf tpid {
                  type binary {
                    length 62..128 ;

                  }

                  description 'The TPID of detection point.' ;
                }

                leaf perfcode {
                  type uint16 {
                    range 1..65535 ;

                  }

                  description 'The performance code of this tpid. 0xFFFF indicates any performance items.' ;
                }

                leaf cycle-end-time {
                  type ncd:datetime ;

                  description 'The end of the cycle. UTC.' ;
                }

                leaf tpid-class {
                  type enumeration {
                    enum board {
                      value 1 ;
                    }

                    enum CPU {
                      value 2 ;
                    }

                    enum system {
                      value 3 ;
                    }

                    enum all {
                      value 255 ;
                    }

                  }

                  description 'The class of TPID.' ;
                }

                leaf tpid-length {
                  type uint8 {
                    range 62..128 ;

                  }

                  description 'The length of TPID.' ;
                }

                leaf inner-index {
                  type uint16 ;

                  description 'JID inner index.' ;
                }

                leaf tpid-matcher {
                  type binary {
                    length 62..128 ;

                  }

                  description "As a conditions tpid, used with 'tpid-mask'." ;
                }

                leaf tpid-mask {
                  type binary {
                    length 8..16 ;

                  }

                  description "Mask bit of attribute 'tpid-matcher'. Length is always 8 bytes." ;
                }

                leaf begin-time {
                  type ncd:datetime ;

                  description 'Start time for query. UTC. End of the cycle time within the time period is selected.' ;
                }

                leaf end-time {
                  type ncd:datetime ;

                  description 'End time for query. UTC. End of the cycle time within the time period is selected.' ;
                }

                leaf value {
                  type binary {
                    length 10 ;

                  }

                  description 'The performance value.' ;
                }

                leaf max-value {
                  type binary {
                    length 10 ;

                  }

                  description 'The maximum value of this cycle.' ;
                }

                leaf min-value {
                  type binary {
                    length 10 ;

                  }

                  description 'The minimum value of this cycle.' ;
                }

                leaf avg-value {
                  type binary {
                    length 10 ;

                  }

                  description 'The average value of this cycle.' ;
                }

                leaf isdoubt {
                  type boolean ;

                  description 'Indicates whether the suspect, if the performance test cycle affect the calculation of the events occurred, they sign into doubt.' ;
                }

                leaf max-value-time {
                  type ncd:datetime ;

                  description 'The time of max value. UTC.' ;
                }

                leaf tpid-desc {
                  description 'The description of TPID.' ;
                  type ncd:string-all {
                    length 0..127 ;

                  }

                  ncd:revise-date 2024-05-23 ;
                }

                key 'checkpoint-type tpid perfcode cycle-end-time tpid-class tpid-length inner-index' ;
                description 'History data about analog performance.' ;
                ncd:select "checkpoint-type perfcode tpid-class tpid-length tpid-matcher tpid-mask begin-time end-time" ;
              }

              description 'History data about analog performance.' ;
            }

            description 'History data for self defined minutes performance items. The actual performance items depend on the self-defined-five-minutes configuration. ' ;
            if-feature self-defined-minutes {
              ncd:revise-date 2024-02-20 ;
            }

            ncd:revise-date 2024-02-20 ;
          }

        }

      }

      container monitor {
        description 'The state info about real-time monitor.' ;
        container perfdata {
          description 'The collect data about real-time monitor.' ;
          list zxr10perfdatum {
            description 'The performance data of real-time monitor.' ;
            key 'taskid checkpoint-type tpid perfcode cycle-end-time tpid-length' ;
            leaf taskid {
              description 'Monitor task ID.' ;
              type uint32 ;

            }

            leaf checkpoint-type {
              description 'TPID type.' ;
              type uint16 {
                range 1..65535 ;

              }

            }

            leaf tpid {
              description 'TPID value.' ;
              type binary {
                length 62..128 ;

              }

            }

            leaf perfcode {
              description 'The performance code of this tpid.' ;
              type uint16 {
                range 1..65535 ;

              }

            }

            leaf cycle-end-time {
              description 'The end time of sampling period. UTC.' ;
              type ncd:datetime ;

            }

            leaf tpid-length {
              description 'The length of tpid.' ;
              type uint8 {
                range 62..128 ;

              }

            }

            leaf cycle {
              description 'Sampling period.' ;
              type uint16 {
                range 5..900 ;

              }

              units second ;
              default 30 ;
            }

            leaf value {
              description 'The performance value of this sampling period. Effective for digital item.' ;
              type binary {
                length 10 ;

              }

            }

            leaf max-value {
              description 'Tthe maximum value of this period. Effective for analog item.' ;
              type binary {
                length 10 ;

              }

            }

            leaf min-value {
              description 'Tthe minimum value of this period. Effective for analog item.' ;
              type binary {
                length 10 ;

              }

            }

            leaf avg-value {
              description 'Tthe average value of this period. Effective for analog item.' ;
              type binary {
                length 10 ;

              }

            }

            leaf isdoubt {
              description 'Performance value is doubtful? If the performance test cycle affect the calculation of the events occurred, they sign into doubt.' ;
              type boolean ;

            }

            leaf first-cycle {
              description 'Queries the first sample value.' ;
              type boolean ;

            }

            leaf begin-time {
              description 'Start time for query. UTC. End of the cycle time within the time period is selected.' ;
              type ncd:datetime ;

            }

            leaf end-time {
              description 'End time for query. UTC. End of the cycle time within the time period is selected.' ;
              type ncd:datetime ;

            }

            leaf perf-type {
              description 'Digital or analog.' ;
              type enumeration {
                enum digital {
                  value 1 ;
                }

                enum analog {
                  value 2 ;
                }

              }

            }

            ncd:revise-date 2015-12-28 ;
            ncd:select "taskid checkpoint-type tpid perfcode tpid-length first-cycle" ;
            ncd:select "taskid checkpoint-type tpid perfcode tpid-length begin-time end-time" ;
          }

          list perfdatum {
            status obsolete {
              ncd:revise-date 2015-12-28 ;
            }

            description 'The performance data of real-time monitor.' ;
            key 'taskid checkpoint-type tpid perfcode cycle-end-time' ;
            leaf taskid {
              description 'Monitor task ID.' ;
              type uint32 ;

            }

            leaf cycle {
              description 'Sampling period.' ;
              type uint16 {
                range 5..900 ;

              }

              units second ;
              default 30 ;
            }

            leaf checkpoint-type {
              description 'TPID type.' ;
              type uint16 {
                range 1..65535 ;

              }

            }

            leaf tpid {
              description 'TPID value.' ;
              type binary {
                length 1..128 ;

              }

            }

            leaf perfcode {
              description 'The performance code of this TPID.' ;
              type uint16 {
                range 1..65535 ;

              }

            }

            leaf cycle-end-time {
              description 'The end time of sampling period. UTC.' ;
              type ncd:datetime ;

            }

            leaf value {
              description 'The performance value of this sampling period. Effective for digital item.' ;
              type binary {
                length 10 ;

              }

            }

            leaf max-value {
              description 'Tthe maximum value of this period. Effective for analog item.' ;
              type binary {
                length 10 ;

              }

            }

            leaf min-value {
              description 'Tthe minimum value of this period. Effective for analog item.' ;
              type binary {
                length 10 ;

              }

            }

            leaf avg-value {
              description 'Tthe average value of this period. Effective for analog item.' ;
              type binary {
                length 10 ;

              }

            }

            leaf isdoubt {
              description 'Performance value is doubtful? If the performance test cycle affect the calculation of the events occurred, they sign into doubt.' ;
              type boolean ;

            }

            leaf first-cycle {
              description 'Queries the first sample value.' ;
              type boolean ;

            }

            leaf begin-time {
              description 'Start time for query. UTC. End of the cycle time within the time period is selected.' ;
              type ncd:datetime ;

            }

            leaf end-time {
              description 'End time for query. UTC. End of the cycle time within the time period is selected.' ;
              type ncd:datetime ;

            }

            leaf perf-type {
              description 'Digital or analog.' ;
              type enumeration {
                enum digital {
                  value 1 ;
                }

                enum analog {
                  value 2 ;
                }

              }

            }

            leaf tpid-length {
              description 'The length of TPID.' ;
              type uint8 {
                range 1..128 ;

              }

            }

            ncd:select "taskid checkpoint-type tpid perfcode first-cycle tpid-length" ;
            ncd:select "taskid checkpoint-type tpid perfcode begin-time end-time tpid-length" ;
          }

        }

      }

      container threshold {
        description 'Performance threshold query.' ;
        container default-thresholds {
          description 'Info about default-thresholds.' ;
          list zxr10analog-default-threshold {
            description "(1) Selects:checkpoint-type+tpid+perfcode+tpid-length:

            1.1 Specify the slot number included in the tpid. Now, 'checkpoint-type' and 'perfcode' are 0xFF.

            1.2 Do not specify the conditions that get all. Now, 'checkpoint-type', 'tpid' and 'perfcode' are 0xFF.

            1.3 Specify the 'tpid' with the wild card 0xFF.



            (2) Selects:checkpoint-type+tpid+perfcode+tpid-length+tpid-mask:

            In this case, specify the 'tpid' with 'tpid-mask'." ;
            key 'checkpoint-type tpid perfcode tpid-length' ;
            leaf checkpoint-type {
              description 'TPID type. 0xFFFF indicates that the query all type of check-point.' ;
              type uint16 {
                range 1..65535 ;

              }

            }

            leaf tpid {
              description 'TPID value. Full 0xFF match all.' ;
              type binary {
                length 62..128 ;

              }

            }

            leaf perfcode {
              description 'The performance code of this TPID. 0xFFFF indicates any performance items.' ;
              type uint16 {
                range 1..65535 ;

              }

            }

            leaf tpid-length {
              description 'The length of TPID.' ;
              type uint8 {
                range 62..128 ;

              }

            }

            leaf tpid-mask {
              description "Mask bit of attribute 'tpid'. Length is always 8 to 16 bytes." ;
              type binary {
                length 8..16 ;

              }

              ncd:revise-date 2016-11-16 ;
            }

            leaf low {
              description 'Value for default low threshold.' ;
              type binary {
                length 10 ;

              }

            }

            leaf high {
              description 'Value for default high threshold.' ;
              type binary {
                length 10 ;

              }

            }

            leaf warnlow {
              description 'Value for default warn-low threshold.' ;
              type binary {
                length 10 ;

              }

            }

            leaf warnhigh {
              description 'Value for default warn-high threshold.' ;
              type binary {
                length 10 ;

              }

            }

            leaf curlow {
              description 'Value for current low threshold.' ;
              type binary {
                length 10 ;

              }

            }

            leaf curhigh {
              description 'Value for current high threshold.' ;
              type binary {
                length 10 ;

              }

            }

            leaf curwarnlow {
              description 'Value for current warn-low threshold.' ;
              type binary {
                length 10 ;

              }

            }

            leaf curwarnhigh {
              description 'Value for current warn-high threshold.' ;
              type binary {
                length 10 ;

              }

            }

            leaf minvalue {
              description 'The minimum detectable value. Not used.' ;
              type binary {
                length 10 ;

              }

            }

            leaf maxvalue {
              description 'The maximum detectable value. Not used.' ;
              type binary {
                length 10 ;

              }

            }

            ncd:revise-date 2015-12-28 ;
            ncd:select "checkpoint-type tpid perfcode tpid-length" ;
            ncd:select "checkpoint-type tpid perfcode tpid-length tpid-mask" ;
          }

          list analog-default-threshold {
            status obsolete {
              ncd:revise-date 2015-12-28 ;
            }

            description "Default threshold of analog performance item. Query condition: (1) Slot number. Note: Included in the tpid. Now, 'checkpoint-type' and 'perfcode' are 0xFF. (2) Do not specify the conditions that get all. Now, 'checkpoint-type', 'tpid' and 'perfcode' are 0xFF." ;
            key 'checkpoint-type tpid perfcode' ;
            leaf checkpoint-type {
              description 'TPID type. 0xFFFF indicates that the query all type of check-point.' ;
              type uint16 {
                range 1..65535 ;

              }

            }

            leaf tpid {
              description 'TPID value. Full 0xFF match all.' ;
              type binary {
                length 1..128 ;

              }

            }

            leaf perfcode {
              description 'The performance code of this TPID. 0xFFFF indicates any performance items.' ;
              type uint16 {
                range 1..65535 ;

              }

            }

            leaf low {
              description 'Value for default low threshold.' ;
              type binary {
                length 10 ;

              }

            }

            leaf high {
              description 'Value for default high threshold.' ;
              type binary {
                length 10 ;

              }

            }

            leaf warnlow {
              description 'Value for default warn-low threshold.' ;
              type binary {
                length 10 ;

              }

            }

            leaf warnhigh {
              description 'Value for default warn-high threshold.' ;
              type binary {
                length 10 ;

              }

            }

            leaf curlow {
              description 'Value for current low threshold.' ;
              type binary {
                length 10 ;

              }

            }

            leaf curhigh {
              description 'Value for current high threshold.' ;
              type binary {
                length 10 ;

              }

            }

            leaf curwarnlow {
              description 'Value for current warn-low threshold.' ;
              type binary {
                length 10 ;

              }

            }

            leaf curwarnhigh {
              description 'Value for current warn-high threshold.' ;
              type binary {
                length 10 ;

              }

            }

            leaf minvalue {
              description 'The minimum detectable value. Not used.' ;
              type binary {
                length 10 ;

              }

            }

            leaf maxvalue {
              description 'The maximum detectable value. Not used.' ;
              type binary {
                length 10 ;

              }

            }

            leaf tpid-length {
              description 'The length of TPID.' ;
              type uint8 {
                range 1..128 ;

              }

            }

            ncd:select "checkpoint-type tpid perfcode tpid-length" ;
          }

        }

        container satellite-current-thresholds {
          list analog-current-threshold {
            leaf checkpoint-type {
              type uint16 {
                range 1..65534 ;

              }

              description 'TPID type. ' ;
            }

            leaf tpid {
              type binary {
                length 62..128 ;

              }

              description 'TPID value. ' ;
            }

            leaf perfcode {
              type uint16 {
                range 1..65534 ;

              }

              description 'The performance code of this TPID. ' ;
            }

            leaf tpid-length {
              type uint8 {
                range 62..128 ;

              }

              description 'The length of TPID.' ;
            }

            leaf cur-low {
              type binary {
                length 10 ;

              }

              description 'Value for current low threshold.' ;
            }

            leaf cur-high {
              type binary {
                length 10 ;

              }

              description 'Value for current high threshold.' ;
            }

            leaf cur-warn-low {
              type binary {
                length 10 ;

              }

              description 'Value for current warn-low threshold.' ;
            }

            leaf cur-warn-high {
              type binary {
                length 10 ;

              }

              description 'Value for current warn-high threshold.' ;
            }

            leaf low-state {
              type uint8 ;

              description 'Low threshold state.' ;
            }

            leaf high-state {
              type uint8 ;

              description 'High threshold state.' ;
            }

            leaf warn-low-state {
              type uint8 ;

              description 'Warn-low threshold state.' ;
            }

            leaf warn-high-state {
              type uint8 ;

              description 'Warn-high threshold state.' ;
            }

            key 'checkpoint-type tpid perfcode tpid-length' ;
            description "Only supports queries for specified 'checkpoint-type' ,'tpid’and 'perfcode' . Does not support wild queries." ;
            leaf result {
              type uint8 {
                range 0..255 ;

              }

              description 'Query result.' ;
            }

            ncd:select "checkpoint-type tpid perfcode tpid-length" ;
          }

          description 'Query the current threshold on the satellite device. At present, it is only used to construct xml message for querying from the center to the satellite, and does not support querying directly from the node to the device.' ;
          ncd:revise-date 2024-12-09 ;
        }

      }

    }

  }

  container operation {
    description 'Operation info. ' ;
    config false ;
    container performance {
      description 'Performance operation.' ;
      container clear {
        description 'Cleared performance data.The performance alarm will immediately disappear.' ;
        container currentdata {
          description 'Cleared current performance data.' ;
          list currentdatum {
            description 'Used to clear current performance value.' ;
            key 'cycle checkpoint-type tpid-matcher tpid-mask perfcode tpid-class' ;
            leaf cycle {
              description 'Performance cycle.' ;
              type enumeration {
                enum fifteen-minutes {
                  value 1 ;
                  description 'Minute cycle. The actual cycle value depends on the minute-cycle configuration.' ;
                }

                enum twenty-four-hours {
                  value 2 ;
                }

              }

            }

            leaf checkpoint-type {
              description 'TPID type. 0xFFFF for all.' ;
              type uint16 {
                range 1..65535 ;

              }

            }

            leaf tpid-matcher {
              description 'As a conditions TPID, used with tpid-mask.' ;
              type binary {
                length 62..128 ;

              }

            }

            leaf tpid-mask {
              description "Mask bit of attribute 'tpid-matcher'. Length is always 8 bytes." ;
              type binary {
                length 8..16 ;

              }

            }

            leaf perfcode {
              description 'The specified performance code. 0xFFFF for all.' ;
              type uint16 {
                range 1..65535 ;

              }

            }

            leaf tpid-class {
              description 'The class of TPID.' ;
              type enumeration {
                enum board {
                  value 1 ;
                }

                enum CPU {
                  value 2 ;
                }

                enum system {
                  value 3 ;
                }

                enum all {
                  value 255 ;
                }

              }

            }

            leaf tpid-length {
              description 'The length of TPID.' ;
              type uint8 {
                range 62..128 ;

              }

            }

          }

        }

      }

      container monitor {
        description 'The real-time performance monitoring task operation.' ;
        container start-up {
          description 'Start (i.e., create or generate) real-time performance monitoring tasks.' ;
          list task {
            description 'Real-time monitor task.' ;
            key taskid ;
            leaf taskid {
              description 'Monitor task ID.' ;
              type uint32 ;

            }

            leaf cycle {
              description 'Sampling period.' ;
              type uint16 {
                range 5..900 ;

              }

              units second ;
              default 30 ;
            }

            leaf total-time {
              description 'Total duration of monitoring tasks. When filling 0xFFFFFFFF that the total duration of uncertainty triggered by the user manually stopped.' ;
              type uint32 ;

              units second ;
            }

            leaf auto-report {
              description 'Whether to automatically reported. Only support false.' ;
              type boolean ;

              default false ;
            }

            container checkpoints {
              description 'Performance Item List.' ;
              list checkpoint {
                description 'The performance code of this tpid.' ;
                min-elements 1 ;
                key 'type tpid perfcode' ;
                leaf type {
                  description 'TPID type.' ;
                  type uint16 ;

                }

                leaf tpid {
                  description 'The TPID specified.' ;
                  type binary {
                    length 62..128 ;

                  }

                }

                leaf perfcode {
                  description 'Performance item code.' ;
                  type uint16 {
                    range 1..65535 ;

                  }

                }

                leaf tpid-length {
                  description 'The length of TPID.' ;
                  type uint8 {
                    range 62..128 ;

                  }

                }

              }

            }

          }

        }

        container stop {
          description 'Stop (i.e., delete or cancel) real-time performance monitoring tasks.' ;
          list task {
            description 'Real-time monitor tasks.' ;
            key taskid ;
            leaf taskid {
              description 'Monitor task ID. 0xFFFFFFFF indicates that stop all monitor task.' ;
              type uint32 ;

            }

          }

        }

      }

    }

  }

}
