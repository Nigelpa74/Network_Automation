module zxr10-ntp-af {
  namespace "http://www.zte.com.cn/zxr10/netconf/schema/rosng/ntp-af" ;
  prefix ntp-af ;
  yang-version 1 ;
  import zxr10-netconf-defs {
    prefix ncd ;
  }

  organization "ZTE Corporation" ;
  contact "ZTE Corporation  
     Nanjing Institute of ZTE Corporation 
     No.68 Zijinghua Rd. Yuhuatai District, Nanjing, China 
     Tel: +86-25-52870000" ;
  description 'The netconf module to describe NTP.' ;
  revision 2024-11-22 {
    description 'Modify the ntp/ntp-server status to deprecated' ;
  }

  revision 2022-08-30 {
    description 'Modify the ntp-global/enable status to deprecated' ;
  }

  revision 2021-06-24 {
    description 'Add ntp-af:state' ;
  }

  revision 2020-12-05 ;

  container configuration {
    description 'The configuration of NTP.' ;
    container af-nodes {
      description 'AF node configurations of NTP.' ;
      list af-node {
        description 'AF node list of NTP.' ;
        key name ;
        leaf name {
          description 'AF node name.' ;
          type ncd:af-name {
            length 1..32 ;

          }

        }

        container ntp {
          description 'The node of NTP.' ;
          container ntp-global {
            description 'The node of NTP global configuration.' ;
            leaf enable {
              status deprecated ;

              description 'Invalid leaf,reserved for compatibility.' ;
              type enumeration {
                enum disable {
                  value 0 ;
                  description 'The NTP is disabled.' ;
                }

                enum enable {
                  value 1 ;
                  description 'The NTP is enabled.' ;
                }

              }

              default disable ;
            }

          }

          container ntp-server {
            description 'The node of NTP server configuration.' ;
            status deprecated ;
            container ntp-server-ipv4 {
              description 'The NTP IPv4 server configuration.' ;
              list ntp-ipv4-list {
                description 'The NTP IPv4 server list.' ;
                key ip-address ;
                leaf ip-address {
                  description 'The NTP server IPv4 address.' ;
                  type ncd:ipv4-address ;

                  status deprecated ;

                }

                leaf port {
                  description 'NTP server UDP port.' ;
                  type uint16 {
                    range "123 | 1025..65535" ;

                  }

                  default 123 ;
                  status deprecated ;

                }

                status deprecated ;

              }

              list ntp-ipv4-mng-list {
                description 'The NTP IPv4 MNG server list.' ;
                key ip-address ;
                leaf ip-address {
                  description 'The NTP server IPv4 address.' ;
                  type ncd:ipv4-address ;

                  status deprecated ;

                }

                leaf port {
                  description 'NTP server UDP port.' ;
                  type uint16 {
                    range "123 | 1025..65535" ;

                  }

                  default 123 ;
                  status deprecated ;

                }

                status deprecated ;

              }

              list ntp-ipv4-vrf-list {
                description 'The NTP IPv4 VRF server list.' ;
                key 'vrf-name ip-address' ;
                leaf vrf-name {
                  description 'VRF name.' ;
                  type string {
                    length 1..32 {
                      description 'VRF name.' ;
                    }

                  }

                  status deprecated ;

                }

                leaf ip-address {
                  description 'The NTP server IPv4 address.' ;
                  type ncd:ipv4-address ;

                  status deprecated ;

                }

                leaf port {
                  description 'NTP server UDP port.' ;
                  type uint16 {
                    range "123 | 1025..65535" ;

                  }

                  default 123 ;
                  status deprecated ;

                }

                status deprecated ;

              }

              status deprecated ;

            }

            container ntp-server-ipv6 {
              description 'The NTP IPv6 server configuration.' ;
              list ntp-ipv6-list {
                description 'The NTP IPv6 server list.' ;
                key ipv6-address ;
                leaf ipv6-address {
                  description 'The NTP server IPv6 address.' ;
                  type ncd:ipv6-address ;

                  status deprecated ;

                }

                leaf port {
                  description 'NTP server UDP port.' ;
                  type uint16 {
                    range "123 | 1025..65535" ;

                  }

                  default 123 ;
                  status deprecated ;

                }

                status deprecated ;

              }

              list ntp-ipv6-mng-list {
                description 'The NTP IPv6 MNG server list.' ;
                key ipv6-address ;
                leaf ipv6-address {
                  description 'The NTP server IPv6 address.' ;
                  type ncd:ipv6-address ;

                  status deprecated ;

                }

                leaf port {
                  description 'NTP server UDP port.' ;
                  type uint16 {
                    range "123 | 1025..65535" ;

                  }

                  default 123 ;
                  status deprecated ;

                }

                status deprecated ;

              }

              list ntp-ipv6-vrf-list {
                description 'The NTP IPv6 VRF server list.' ;
                key 'vrf-name ipv6-address' ;
                leaf vrf-name {
                  description 'VRF name.' ;
                  type string {
                    length 1..32 {
                      description 'VRF name.' ;
                    }

                  }

                  status deprecated ;

                }

                leaf ipv6-address {
                  description 'The NTP server IPv6 address.' ;
                  type ncd:ipv6-address ;

                  status deprecated ;

                }

                leaf port {
                  description 'NTP server UDP port.' ;
                  type uint16 {
                    range "123 | 1025..65535" ;

                  }

                  default 123 ;
                  status deprecated ;

                }

                status deprecated ;

              }

              status deprecated ;

            }

          }

        }

      }

    }

  }

  container state {
    config false ;
    description 'The state of NTP.' ;
    container ntp {
      description 'The node of NTP.' ;
      container ntp-current-status {
        description 'The current status of NTP.' ;
        list af-node {
          description 'AF node list of NTP.' ;
          key name ;
          leaf name {
            description 'AF node name.' ;
            type ncd:af-name {
              length 1..32 ;

            }

          }

          leaf current-time {
            description 'The current system time.' ;
            type string ;

          }

          leaf ntp-type {
            description 'The NTP type of local.' ;
            type enumeration {
              enum not-running {
                value 1 ;
                description 'NTP is not running.' ;
              }

              enum not-synchronized {
                value 2 ;
                description 'NTP is not synchronized.' ;
              }

              enum none-configured {
                value 3 ;
                description 'NTP is not configured.' ;
              }

              enum synctolocal {
                value 4 ;
                description 'NTP is synchronized to local.' ;
              }

              enum synctoremoteserver {
                value 5 ;
                description 'NTP is synchronized to remote server.' ;
              }

            }

          }

          leaf current-stratum {
            description 'The current local stratum.' ;
            type uint8 {
              range 0..16 ;

            }

          }

          leaf current-server {
            description 'The current server IP and VRF name.' ;
            type string ;

          }

          ncd:select name ;
        }

      }

    }

    ncd:revise-date 2021-06-24 ;
  }

}
