module zxr10-qos {
  namespace "http://www.zte.com.cn/zxr10/netconf/schema/rosng/qos" ;
  prefix qos ;
  yang-version 1 ;
  import zxr10-netconf-defs {
    prefix ncd ;
  }

  import zxr10-cps {
    prefix cps ;
  }

  organization "ZTE Corporation" ;
  contact "ZTE Corporation
  Nanjing Institute of ZTE Corporation
  No.68 Zijinghua Rd. Yuhuatai District, Nanjing, China
  Tel: +86-25-52870000" ;
  description 'The netconf module to describe QoS services info.It contains state and configuration info.' ;
  revision 2025-08-08 {
    description '1. Add the SWITCH.5960X product label to the following feature: rocev2-cnp-feature,rocev2-nak-feature.' ;
  }

  revision 2025-06-06 {
    description '1. Add the ROSNG-V.VEG product label to the following feature: policy-action-rediret-route-map,traffic-policy.' ;
  }

  revision 2025-05-26 {
    description '1. Add the SWITCH.99X,SWITCH.59X-ES product label to the following feature: class-match-rocev2-udf.' ;
  }

  revision 2025-04-07 {
    description '1. Delete the MSR.ASR,MSR.ZSRV2,OTN.M721,PTN.61V5_1 product label from the following feature: policy-action-rediret-route-map.' ;
  }

  revision 2025-03-10 {
    description '1. Add feature policy-ecmp-mode to select the action load-sharing ecmp-hash function effective product.
2. Add ecmp-mode container below /qos:configuration/qos:qos/qos:policy-map/qos:traffic-based/qos:policy-maps/qos:policy-map/qos:class-maps/qos:class-map/qos:load-sharing and /qos:configuration/qos:qos/qos:policy-map/qos:traffic-based/qos:policy-maps/qos:policy-map/qos:class-maps/qos:class-default/qos:load-sharing.' ;
  }

  revision 2025-03-05 {
    description 'Description polishing.' ;
  }

  revision 2025-02-11 {
    description '1. Add feature class-match-rocev2-udf to select the match RoCEv2 user defined function effective product.
2. Add udf container below /qos:configuration/qos:qos/qos:class-map/qos:traffic-based/qos:class-maps/qos:class-map/qos:match/qos:ipv4-rocev2 and /qos:configuration/qos:qos/qos:class-map/qos:traffic-based/qos:class-maps/qos:class-map/qos:match/qos:ipv6-rocev2.' ;
  }

  revision 2024-09-02 {
    description '1. nsh of SFC' ;
  }

  revision 2024-07-17 {
    description '1. Add feature traffic-match-vrf to select the match vrf-name function effective product.' ;
  }

  revision 2024-06-11 {
    description '1.Support configure fields of RoCEv2 packets as CNP, NAK, add follow containers:
/configuration/qos/class-map/traffic-based/class-maps/class-map/match/ipv4-rocev2/opcode/cnp/cnp;
/configuration/qos/class-map/traffic-based/class-maps/class-map/match/ipv4-rocev2/opcode/nak/nak;
/configuration/qos/class-map/traffic-based/class-maps/class-map/match/ipv6-rocev2/opcode/cnp/cnp;
/configuration/qos/class-map/traffic-based/class-maps/class-map/match/ipv6-rocev2/opcode/nak/nak.' ;
  }

  revision 2024-05-09 {
    description '1. Support QoS IF-CAR stats switch with feature qos-car-stats-if, add container:
/qos:configuration/qos:qos/qos:qos-car-stats
2. Support clear QoS IF-CAR stats data with feature qos-car-stats-if, add container:
/qos:operation/qos:qos/qos:qos-car-stats-clear' ;
  }

  revision 2024-04-01 {
    description '1.Support QoS statistical share global switch, add nodes:
/qos:configuration/qos:qos/qos:qos-statistical-share-globals' ;
  }

  revision 2024-03-07 {
    description 'Modify the feature queue-depth-adaptive : add PTN.61V5_1 label.' ;
  }

  revision 2024-02-27 {
    description 'Add enumeration value to node:
/configuration/qos/queue-templates/queue-template/queue-nos/queue-no/queue-limit/queue-depth' ;
  }

  revision 2023-09-12 {
    description '1.Support coupling-flag、adjust in rate-limit, add node:
/qos:configuration/qos:qos/qos:rate-limit/qos:unicasts/qos:unicast/qos:coupling-flag;
/qos:configuration/qos:qos/qos:rate-limit/qos:unicasts/qos:unicast/qos:adjust;
/qos:configuration/qos:qos/qos:rate-limit/qos:unknown-unicasts/qos:unknown-unicast/qos:coupling-flag;
/qos:configuration/qos:qos/qos:rate-limit/qos:unknown-unicasts/qos:unknown-unicast/qos:adjust;
/qos:configuration/qos:qos/qos:rate-limit/qos:multicasts/qos:multicast/qos:coupling-flag;
/qos:configuration/qos:qos/qos:rate-limit/qos:multicasts/qos:multicast/qos:adjust;
/qos:configuration/qos:qos/qos:rate-limit/qos:unknown-multicasts/qos:unknown-multicast/qos:coupling-flag;
/qos:configuration/qos:qos/qos:rate-limit/qos:unknown-multicasts/qos:unknown-multicast/qos:adjust;
/qos:configuration/qos:qos/qos:rate-limit/qos:broadcasts/qos:broadcast/qos:coupling-flag;
/qos:configuration/qos:qos/qos:rate-limit/qos:broadcasts/qos:broadcast/qos:adjust;
/qos:configuration/qos:qos/qos:rate-limit/qos:unknowns/qos:unknown/qos:coupling-flag;
/qos:configuration/qos:qos/qos:rate-limit/qos:unknowns/qos:unknown/qos:adjust;
/qos:configuration/qos:qos/qos:rate-limit/qos:localports/qos:localport/qos:coupling-flag;
/qos:configuration/qos:qos/qos:rate-limit/qos:localports/qos:localport/qos:adjust;
/qos:configuration/qos:qos/qos:rate-limit/qos:dscps/qos:dscp/qos:coupling-flag;
/qos:configuration/qos:qos/qos:rate-limit/qos:dscps/qos:dscp/qos:adjust;
/qos:configuration/qos:qos/qos:rate-limit/qos:precedences/qos:precedence/qos:coupling-flag;
/qos:configuration/qos:qos/qos:rate-limit/qos:precedences/qos:precedence/qos:adjust;
/qos:configuration/qos:qos/qos:rate-limit/qos:mpls-exps/qos:mpls-exp/qos:coupling-flag;
/qos:configuration/qos:qos/qos:rate-limit/qos:mpls-exps/qos:mpls-exp/qos:adjust;
/qos:configuration/qos:qos/qos:rate-limit/qos:inner-vlans/qos:inner-vlan/qos:coupling-flag;
/qos:configuration/qos:qos/qos:rate-limit/qos:inner-vlans/qos:inner-vlan/qos:adjust;
/qos:configuration/qos:qos/qos:rate-limit/qos:outer-vlans/qos:outer-vlan/qos:coupling-flag;
/qos:configuration/qos:qos/qos:rate-limit/qos:outer-vlans/qos:outer-vlan/qos:adjust;
/qos:configuration/qos:qos/qos:rate-limit/qos:multi-vlans/qos:multi-vlan/qos:coupling-flag;
/qos:configuration/qos:qos/qos:rate-limit/qos:multi-vlans/qos:multi-vlan/qos:adjust;
/qos:configuration/qos:qos/qos:rate-limit/qos:inner-8021ps/qos:inner-8021p/qos:coupling-flag;
/qos:configuration/qos:qos/qos:rate-limit/qos:inner-8021ps/qos:inner-8021p/qos:adjust;
/qos:configuration/qos:qos/qos:rate-limit/qos:outer-8021ps/qos:outer-8021p/qos:coupling-flag;
/qos:configuration/qos:qos/qos:rate-limit/qos:outer-8021ps/qos:outer-8021p/qos:adjust;
/qos:configuration/qos:qos/qos:rate-limit/qos:multi-8021ps/qos:multi-8021p/qos:coupling-flag;
/qos:configuration/qos:qos/qos:rate-limit/qos:multi-8021ps/qos:multi-8021p/qos:adjust;
/qos:configuration/qos:qos/qos:rate-limit/qos:qos-groups/qos:qos-group/qos:coupling-flag;
/qos:configuration/qos:qos/qos:rate-limit/qos:qos-groups/qos:qos-group/qos:adjust;
/qos:configuration/qos:qos/qos:rate-limit/qos:access-lists/qos:access-list/qos:coupling-flag;
/qos:configuration/qos:qos/qos:rate-limit/qos:access-lists/qos:access-list/qos:adjust;
/qos:configuration/qos:qos/qos:rate-limit/qos:bums/qos:bum/qos:coupling-flag;
/qos:configuration/qos:qos/qos:rate-limit/qos:bums/qos:bum/qos:adjust;
/qos:configuration/qos:qos/qos:rate-limit/qos:bus/qos:bu/qos:coupling-flag;
/qos:configuration/qos:qos/qos:rate-limit/qos:bus/qos:bu/qos:adjust
2.Modify the range of node:
/qos:configuration/qos:qos/qos:rate-limit/qos:unicasts/qos:unicast/qos:cir from 8..4294967295 to 0..4294967295;
/qos:configuration/qos:qos/qos:rate-limit/qos:unicasts/qos:unicast/qos:pir from 8..4294967295 to 0..4294967295;
/qos:configuration/qos:qos/qos:rate-limit/qos:unicasts/qos:unicast/qos:cbs from 1..4294967295 to 0..4294967294;
/qos:configuration/qos:qos/qos:rate-limit/qos:unicasts/qos:unicast/qos:pbs from 1..4294967295 to 0..4294967294;
/qos:configuration/qos:qos/qos:rate-limit/qos:unknown-unicasts/qos:unknown-unicast/qos:cir from 8..4294967295 to 0..4294967295;
/qos:configuration/qos:qos/qos:rate-limit/qos:unknown-unicasts/qos:unknown-unicast/qos:pir from 8..4294967295 to 0..4294967295;
/qos:configuration/qos:qos/qos:rate-limit/qos:unknown-unicasts/qos:unknown-unicast/qos:cbs from 1..4294967295 to 0..4294967294;
/qos:configuration/qos:qos/qos:rate-limit/qos:unknown-unicasts/qos:unknown-unicast/qos:pbs from 1..4294967295 to 0..4294967294;
/qos:configuration/qos:qos/qos:rate-limit/qos:multicasts/qos:multicast/qos:cir from 8..4294967295 to 0..4294967295;
/qos:configuration/qos:qos/qos:rate-limit/qos:multicasts/qos:multicast/qos:pir from 8..4294967295 to 0..4294967295;
/qos:configuration/qos:qos/qos:rate-limit/qos:multicasts/qos:multicast/qos:cbs from 1..4294967295 to 0..4294967294;
/qos:configuration/qos:qos/qos:rate-limit/qos:multicasts/qos:multicast/qos:pbs from 1..4294967295 to 0..4294967294;
/qos:configuration/qos:qos/qos:rate-limit/qos:unknown-multicasts/qos:unknown-multicast/qos:cir from 8..4294967295 to 0..4294967295;
/qos:configuration/qos:qos/qos:rate-limit/qos:unknown-multicasts/qos:unknown-multicast/qos:pir from 8..4294967295 to 0..4294967295;
/qos:configuration/qos:qos/qos:rate-limit/qos:unknown-multicasts/qos:unknown-multicast/qos:cbs from 1..4294967295 to 0..4294967294;
/qos:configuration/qos:qos/qos:rate-limit/qos:unknown-multicasts/qos:unknown-multicast/qos:pbs from 1..4294967295 to 0..4294967294;
/qos:configuration/qos:qos/qos:rate-limit/qos:broadcasts/qos:broadcast/qos:cir from 8..4294967295 to 0..4294967295;
/qos:configuration/qos:qos/qos:rate-limit/qos:broadcasts/qos:broadcast/qos:pir from 8..4294967295 to 0..4294967295;
/qos:configuration/qos:qos/qos:rate-limit/qos:broadcasts/qos:broadcast/qos:cbs from 1..4294967295 to 0..4294967294;
/qos:configuration/qos:qos/qos:rate-limit/qos:broadcasts/qos:broadcast/qos:pbs from 1..4294967295 to 0..4294967294;
/qos:configuration/qos:qos/qos:rate-limit/qos:unknowns/qos:unknown/qos:cir from 8..4294967295 to 0..4294967295;
/qos:configuration/qos:qos/qos:rate-limit/qos:unknowns/qos:unknown/qos:pir from 8..4294967295 to 0..4294967295;
/qos:configuration/qos:qos/qos:rate-limit/qos:unknowns/qos:unknown/qos:cbs from 1..4294967295 to 0..4294967294;
/qos:configuration/qos:qos/qos:rate-limit/qos:unknowns/qos:unknown/qos:pbs from 1..4294967295 to 0..4294967294;
/qos:configuration/qos:qos/qos:rate-limit/qos:localports/qos:localport/qos:cir from 8..4294967295 to 0..4294967295;
/qos:configuration/qos:qos/qos:rate-limit/qos:localports/qos:localport/qos:pir from 8..4294967295 to 0..4294967295;
/qos:configuration/qos:qos/qos:rate-limit/qos:localports/qos:localport/qos:cbs from 1..4294967295 to 0..4294967294;
/qos:configuration/qos:qos/qos:rate-limit/qos:localports/qos:localport/qos:pbs from 1..4294967295 to 0..4294967294;
/qos:configuration/qos:qos/qos:rate-limit/qos:dscps/qos:dscp/qos:cir from 8..4294967295 to 0..4294967295;
/qos:configuration/qos:qos/qos:rate-limit/qos:dscps/qos:dscp/qos:pir from 8..4294967295 to 0..4294967295;
/qos:configuration/qos:qos/qos:rate-limit/qos:dscps/qos:dscp/qos:cbs from 1..4294967295 to 0..4294967294;
/qos:configuration/qos:qos/qos:rate-limit/qos:dscps/qos:dscp/qos:pbs from 1..4294967295 to 0..4294967294;
/qos:configuration/qos:qos/qos:rate-limit/qos:precedences/qos:precedence/qos:cir from 8..4294967295 to 0..4294967295;
/qos:configuration/qos:qos/qos:rate-limit/qos:precedences/qos:precedence/qos:pir from 8..4294967295 to 0..4294967295;
/qos:configuration/qos:qos/qos:rate-limit/qos:precedences/qos:precedence/qos:cbs from 1..4294967295 to 0..4294967294;
/qos:configuration/qos:qos/qos:rate-limit/qos:precedences/qos:precedence/qos:pbs from 1..4294967295 to 0..4294967294;
/qos:configuration/qos:qos/qos:rate-limit/qos:mpls-exps/qos:mpls-exp/qos:cir from 8..4294967295 to 0..4294967295;
/qos:configuration/qos:qos/qos:rate-limit/qos:mpls-exps/qos:mpls-exp/qos:pir from 8..4294967295 to 0..4294967295;
/qos:configuration/qos:qos/qos:rate-limit/qos:mpls-exps/qos:mpls-exp/qos:cbs from 1..4294967295 to 0..4294967294;
/qos:configuration/qos:qos/qos:rate-limit/qos:mpls-exps/qos:mpls-exp/qos:pbs from 1..4294967295 to 0..4294967294;
/qos:configuration/qos:qos/qos:rate-limit/qos:inner-vlans/qos:inner-vlan/qos:cir from 8..4294967295 to 0..4294967295;
/qos:configuration/qos:qos/qos:rate-limit/qos:inner-vlans/qos:inner-vlan/qos:pir from 8..4294967295 to 0..4294967295;
/qos:configuration/qos:qos/qos:rate-limit/qos:inner-vlans/qos:inner-vlan/qos:cbs from 1..4294967295 to 0..4294967294;
/qos:configuration/qos:qos/qos:rate-limit/qos:inner-vlans/qos:inner-vlan/qos:pbs from 1..4294967295 to 0..4294967294;
/qos:configuration/qos:qos/qos:rate-limit/qos:outer-vlans/qos:outer-vlan/qos:cir from 8..4294967295 to 0..4294967295;
/qos:configuration/qos:qos/qos:rate-limit/qos:outer-vlans/qos:outer-vlan/qos:pir from 8..4294967295 to 0..4294967295;
/qos:configuration/qos:qos/qos:rate-limit/qos:outer-vlans/qos:outer-vlan/qos:cbs from 1..4294967295 to 0..4294967294;
/qos:configuration/qos:qos/qos:rate-limit/qos:outer-vlans/qos:outer-vlan/qos:pbs from 1..4294967295 to 0..4294967294;
/qos:configuration/qos:qos/qos:rate-limit/qos:multi-vlans/qos:multi-vlan/qos:cir from 8..4294967295 to 0..4294967295;
/qos:configuration/qos:qos/qos:rate-limit/qos:multi-vlans/qos:multi-vlan/qos:pir from 8..4294967295 to 0..4294967295;
/qos:configuration/qos:qos/qos:rate-limit/qos:multi-vlans/qos:multi-vlan/qos:cbs from 1..4294967295 to 0..4294967294;
/qos:configuration/qos:qos/qos:rate-limit/qos:multi-vlans/qos:multi-vlan/qos:pbs from 1..4294967295 to 0..4294967294;
/qos:configuration/qos:qos/qos:rate-limit/qos:inner-8021ps/qos:inner-8021p/qos:cir from 8..4294967295 to 0..4294967295;
/qos:configuration/qos:qos/qos:rate-limit/qos:inner-8021ps/qos:inner-8021p/qos:pir from 8..4294967295 to 0..4294967295;
/qos:configuration/qos:qos/qos:rate-limit/qos:inner-8021ps/qos:inner-8021p/qos:cbs from 1..4294967295 to 0..4294967294;
/qos:configuration/qos:qos/qos:rate-limit/qos:inner-8021ps/qos:inner-8021p/qos:pbs from 1..4294967295 to 0..4294967294;
/qos:configuration/qos:qos/qos:rate-limit/qos:outer-8021ps/qos:outer-8021p/qos:cir from 8..4294967295 to 0..4294967295;
/qos:configuration/qos:qos/qos:rate-limit/qos:outer-8021ps/qos:outer-8021p/qos:pir from 8..4294967295 to 0..4294967295;
/qos:configuration/qos:qos/qos:rate-limit/qos:outer-8021ps/qos:outer-8021p/qos:cbs from 1..4294967295 to 0..4294967294;
/qos:configuration/qos:qos/qos:rate-limit/qos:outer-8021ps/qos:outer-8021p/qos:pbs from 1..4294967295 to 0..4294967294;
/qos:configuration/qos:qos/qos:rate-limit/qos:multi-8021ps/qos:multi-8021p/qos:cir from 8..4294967295 to 0..4294967295;
/qos:configuration/qos:qos/qos:rate-limit/qos:multi-8021ps/qos:multi-8021p/qos:pir from 8..4294967295 to 0..4294967295;
/qos:configuration/qos:qos/qos:rate-limit/qos:multi-8021ps/qos:multi-8021p/qos:cbs from 1..4294967295 to 0..4294967294;
/qos:configuration/qos:qos/qos:rate-limit/qos:multi-8021ps/qos:multi-8021p/qos:pbs from 1..4294967295 to 0..4294967294;
/qos:configuration/qos:qos/qos:rate-limit/qos:qos-groups/qos:qos-group/qos:cir from 8..4294967295 to 0..4294967295;
/qos:configuration/qos:qos/qos:rate-limit/qos:qos-groups/qos:qos-group/qos:pir from 8..4294967295 to 0..4294967295;
/qos:configuration/qos:qos/qos:rate-limit/qos:qos-groups/qos:qos-group/qos:cbs from 1..4294967295 to 0..4294967294;
/qos:configuration/qos:qos/qos:rate-limit/qos:qos-groups/qos:qos-group/qos:pbs from 1..4294967295 to 0..4294967294;
/qos:configuration/qos:qos/qos:rate-limit/qos:access-lists/qos:access-list/qos:cir from 8..4294967295 to 0..4294967295;
/qos:configuration/qos:qos/qos:rate-limit/qos:access-lists/qos:access-list/qos:pir from 8..4294967295 to 0..4294967295;
/qos:configuration/qos:qos/qos:rate-limit/qos:access-lists/qos:access-list/qos:cbs from 1..4294967295 to 0..4294967294;
/qos:configuration/qos:qos/qos:rate-limit/qos:access-lists/qos:access-list/qos:pbs from 1..4294967295 to 0..4294967294;
/qos:configuration/qos:qos/qos:rate-limit/qos:bums/qos:bum/qos:cir from 8..4294967295 to 0..4294967295;
/qos:configuration/qos:qos/qos:rate-limit/qos:bums/qos:bum/qos:pir from 8..4294967295 to 0..4294967295;
/qos:configuration/qos:qos/qos:rate-limit/qos:bums/qos:bum/qos:cbs from 1..4294967295 to 0..4294967294;
/qos:configuration/qos:qos/qos:rate-limit/qos:bums/qos:bum/qos:pbs from 1..4294967295 to 0..4294967294;
/qos:configuration/qos:qos/qos:rate-limit/qos:bus/qos:bu/qos:cir from 8..4294967295 to 0..4294967295;
/qos:configuration/qos:qos/qos:rate-limit/qos:bus/qos:bu/qos:pir from 8..4294967295 to 0..4294967295;
/qos:configuration/qos:qos/qos:rate-limit/qos:bus/qos:bu/qos:cbs from 1..4294967295 to 0..4294967294;
/qos:configuration/qos:qos/qos:rate-limit/qos:bus/qos:bu/qos:pbs from 1..4294967295 to 0..4294967294' ;
  }

  revision 2023-09-08 {
    description '1、Modify the scope of next leaf nodes:
/qos:configuration/qos:qos/qos:rate-limit/qos:unicasts/qos:unicast/qos:buket-value-percent/qos:buket-value/qos:c-buket/qos:cir-value/qos:cir
/qos:configuration/qos:qos/qos:rate-limit/qos:unknown-unicasts/qos:unknown-unicast/qos:buket-value-percent/qos:buket-value/qos:c-buket/qos:cir-value/qos:cir
/qos:configuration/qos:qos/qos:rate-limit/qos:multicasts/qos:multicast/qos:buket-value-percent/qos:buket-value/qos:c-buket/qos:cir-value/qos:cir
/qos:configuration/qos:qos/qos:rate-limit/qos:unknown-multicasts/qos:unknown-multicast/qos:buket-value-percent/qos:buket-value/qos:c-buket/qos:cir-value/qos:cir
/qos:configuration/qos:qos/qos:rate-limit/qos:broadcasts/qos:broadcast/qos:buket-value-percent/qos:buket-value/qos:c-buket/qos:cir-value/qos:cir
/qos:configuration/qos:qos/qos:rate-limit/qos:localports/qos:localport/qos:buket-value-percent/qos:buket-value/qos:c-buket/qos:cir-value/qos:cir .
2、Added devitation of above leaf nodes.' ;
  }

  revision 2023-08-01 {
    description 'Unsupport hqos stats global switch on pw, te, bgpad, delete nodes:
/qos:configuration/qos:qos/qos:pw-schedule-stats/qos:stats-switches-global
/qos:configuration/qos:qos/qos:te-schedule-stats/qos:stats-switches-global
/qos:configuration/qos:qos/qos:bgpad-schedule-stats/qos:stats-switches-global' ;
  }

  revision 2023-07-19 {
    description '1、move container /configuration/qos/queue-templates/queue-template/queue-nos/queue-no/wfq-weight to /configuration/qos/queue-templates/queue-template/queue-nos/queue-no/weight-schedul/wfq-weight.
2、Add new choice container:/configuration/qos/queue-templates/queue-template/queue-nos/queue-no/weight-schedul/wfq-weight.' ;
  }

  revision 2023-07-03 {
    description '1.Support hqos stats global switch, add nodes:
/qos:configuration/qos:qos/qos:qos-stats/stats-switch-global
2.Support hqos stats switch status, add nodes:
/qos:configuration/qos:qos/qos:qos-stats/qos:stats-switch/qos:stats-switches/qos:status
/qos:configuration/qos:qos/qos:pw-schedule-stats/qos:stats-switches/qos:stats-switch/qos:status
/qos:configuration/qos:qos/qos:pw-schedule-stats/qos:stats-switch-ins/qos:stats-switch-in/qos:status
/qos:configuration/qos:qos/qos:te-schedule-stats/qos:stats-switches/qos:stats-switch/qos:status
/qos:configuration/qos:qos/qos:te-schedule-stats/qos:stats-switch-reverses/qos:stats-switch-reverse/qos:status
/qos:configuration/qos:qos/qos:bgpad-schedule-stats/qos:stats-switches/qos:stats-switches/qos:status' ;
  }

  revision 2023-06-20 {
    description '1. Add rate-unit with feature qos-shape-unit：
/configuration/qos/policy-map/normal/policy-maps/policy-map/class-maps/class-map/shape/rate-unit;
/configuration/qos/policy-map/normal/policy-maps/policy-map/class-maps/class-default/shape/rate-unit.
2. Modify range of rate in traffic shape：
/configuration/qos/traffic-shapes/traffic-shape/rate;
/configuration/qos/traffic-shape-dirs/traffic-shape-dir/rate.
3. Modify range of rate in service-policy:
/configuration/qos/service-policys/service-policy/shape/rate.
4. Add queue-depth-adaptive with feature queue-depth-adaptive:
/configuration/qos/policy-map/normal/policy-maps/policy-map/class-maps/class-map/queue-depth-adaptive;
/configuration/qos/policy-map/normal/policy-maps/policy-map/class-maps/class-default/queue-depth-adaptive.' ;
  }

  revision 2023-06-16 {
    description 'Modify the status of the node to obsolete:
/qos:configuration/qos:qos/qos:qos-if-slice' ;
  }

  revision 2023-05-10 {
    description 'Support QoS traffic-shape cir min value perfId, add perfId:
/configuration/qos/traffic-shapes/traffic-shape' ;
  }

  revision 2023-04-18 {
    description 'Support to configure the interface priority mark function, add container:
/qos:configuration/qos:qos/qos:qos-mark-if-prioritys' ;
  }

  revision 2023-04-12 {
    description 'Modify the range of follow nodes:
/qos:configuration/qos:qos/qos:policy-map/qos:normal/qos:policy-maps/qos:policy-map/qos:class-maps/qos:class-map/qos:latency-time-threshold/qos:value
/qos:configuration/qos:qos/qos:policy-map/qos:normal/qos:policy-maps/qos:policy-map/qos:class-maps/qos:class-map/qos:bandwidth-threshold/qos:value
/qos:configuration/qos:qos/qos:policy-map/qos:normal/qos:policy-maps/qos:policy-map/qos:class-maps/qos:class-default/qos:latency-time-threshold/qos:value
/qos:configuration/qos:qos/qos:policy-map/qos:normal/qos:policy-maps/qos:policy-map/qos:class-maps/qos:class-default/qos:bandwidth-threshold/qos:value' ;
  }

  revision 2023-04-03 {
    description '1. Support QoS priority-level max value perfId for policy map phb-based, add perfId:
/configuration/qos/policy-map/phb-based/policy-maps/policy-map/class-maps/class-map/priority-level.
/configuration/qos/policy-map/phb-based/policy-maps/policy-map/class-maps/class-default/priority-level.
2. Support QoS queue-limit configuration and perfId for policy map phb-based, add container and perfId:
/configuration/qos/policy-map/phb-based/policy-maps/policy-map/class-maps/class-map/queue-limit.
/configuration/qos/policy-map/phb-based/policy-maps/policy-map/class-maps/class-default/queue-limit.
3. Modify the range of node:
/configuration/qos/policy-map/phb-based/policy-maps/policy-map/class-maps/class-map/priority-level from 1-4 to 1-8.
/configuration/qos/policy-map/phb-based/policy-maps/policy-map/class-maps/class-default/priority-level from 1-4 to 1-8.' ;
  }

  revision 2023-03-28 {
    description '1.Modify the range of follow nodes:
/qos:configuration/qos:qos/qos:policy-map/qos:normal/qos:policy-maps/qos:policy-map/qos:class-maps/qos:class-map/qos:priority-level/qos:priority-value
/qos:configuration/qos:qos/qos:policy-map/qos:normal/qos:policy-maps/qos:policy-map/qos:class-maps/qos:class-default/qos:priority-level/qos:priority-value
/qos:configuration/qos:qos/qos:queue-templates/qos:queue-template/qos:queue-nos/qos:queue-no/qos:wfq-weight/qos:percentage
/qos:configuration/qos:qos/qos:class-map/qos:class-map-id/qos:class-maps/qos:class-map/qos:cmap-id
/qos:configuration/qos:qos/qos:policy-map/qos:policy-map-id/qos:policy-maps/qos:policy-map/qos:pmap-id
/qos:configuration/qos:qos/qos:service-policys/qos:service-policy/qos:share-group
/qos:configuration/qos:qos/qos:policy-map/qos:car-action/qos:policy-maps/qos:policy-map/qos:class-maps/qos:class-default/qos:police/qos:cir
/qos:configuration/qos:qos/qos:policy-map/qos:car-action/qos:policy-maps/qos:policy-map/qos:class-maps/qos:class-default/qos:police/qos:cbs
/qos:configuration/qos:qos/qos:policy-map/qos:car-action/qos:policy-maps/qos:policy-map/qos:class-maps/qos:class-default/qos:police/qos:pir
/qos:configuration/qos:qos/qos:policy-map/qos:car-action/qos:policy-maps/qos:policy-map/qos:class-maps/qos:class-default/qos:police/qos:pbs
2.Modify the description of follow nodes:
/qos:configuration/qos:qos/qos:policy-map/qos:normal/qos:policy-maps/qos:policy-map/qos:class-maps/qos:class-map/qos:priority-level/qos:priority-value
/qos:configuration/qos:qos/qos:policy-map/qos:normal/qos:policy-maps/qos:policy-map/qos:class-maps/qos:class-default/qos:priority-level/qos:priority-value
/qos:configuration/qos:qos/qos:policy-map/qos:car-action/qos:policy-maps/qos:policy-map/qos:class-maps/qos:class-map/qos:police/qos:cir
/qos:configuration/qos:qos/qos:policy-map/qos:car-action/qos:policy-maps/qos:policy-map/qos:class-maps/qos:class-map/qos:police/qos:cbs
/qos:configuration/qos:qos/qos:policy-map/qos:car-action/qos:policy-maps/qos:policy-map/qos:class-maps/qos:class-map/qos:police/qos:pir
/qos:configuration/qos:qos/qos:policy-map/qos:car-action/qos:policy-maps/qos:policy-map/qos:class-maps/qos:class-map/qos:police/qos:pbs
/qos:configuration/qos:qos/qos:policy-map/qos:car-action/qos:policy-maps/qos:policy-map/qos:class-maps/qos:class-default/qos:police/qos:cir
/qos:configuration/qos:qos/qos:policy-map/qos:car-action/qos:policy-maps/qos:policy-map/qos:class-maps/qos:class-default/qos:police/qos:cbs
/qos:configuration/qos:qos/qos:policy-map/qos:car-action/qos:policy-maps/qos:policy-map/qos:class-maps/qos:class-default/qos:police/qos:pir
/qos:configuration/qos:qos/qos:policy-map/qos:car-action/qos:policy-maps/qos:policy-map/qos:class-maps/qos:class-default/qos:police/qos:pbs
/qos:configuration/qos:qos/qos:queue-templates/qos:queue-template/qos:queue-nos/qos:queue-no/qos:priority-level/qos:priority-value
/qos:configuration/qos:qos/qos:queue-templates/qos:queue-template/qos:queue-nos/qos:queue-no/qos:wfq-weight/qos:percentage' ;
  }

  revision 2022-12-26 {
    description '1. Support received-bits-rate statistics data obtain,add node:
/qos:state/qos:qos/qos:statistics/qos:statistic/qos:queues/qos:queue/qos:received-bits-rate.' ;
  }

  revision 2022-12-09 {
    description 'Support to configure the switch of the best effort function of the flowspec excess rule, add container:
/qos:configuration/qos:qos/qos:flowspec/rule-excess-effect' ;
  }

  revision 2022-12-05 {
    description '1. Support configure fields of RoCEv2 packets as match criteria, add follow containers:
/qos:configuration/qos:qos/qos:class-map/qos:traffic-based/qos:class-maps/qos:class-map/qos:match/qos:ipv4-rocev2;
/qos:configuration/qos:qos/qos:class-map/qos:traffic-based/qos:class-maps/qos:class-map/qos:match/qos:ipv6-rocev2.
2. Modify the description of follow nodes:
/qos:state/qos:qos/qos:flowspec-vrf-stats/qos:flowspec-vrf-stat/qos:match/qos:tcp-flags/qos:tcp-flag/qos:ack;
/qos:state/qos:qos/qos:flowspec-vrf-stats/qos:flowspec-vrf-stat/qos:match/qos:tcp-flags/qos:tcp-flag/qos:psh;
/qos:state/qos:qos/qos:flowspec-vrf-stats/qos:flowspec-vrf-stat/qos:match/qos:tcp-flags/qos:tcp-flag/qos:rst;
/qos:state/qos:qos/qos:flowspec-vrf-stats/qos:flowspec-vrf-stat/qos:match/qos:tcp-flags/qos:tcp-flag/qos:syn;
/qos:state/qos:qos/qos:flowspec-vrf-stats/qos:flowspec-vrf-stat/qos:match/qos:tcp-flags/qos:tcp-flag/qos:fin;
/qos:state/qos:qos/qos:flowspec-ip-stats/qos:flowspec-ip-stat/qos:match/qos:tcp-flags/qos:tcp-flag/qos:ack;
/qos:state/qos:qos/qos:flowspec-ip-stats/qos:flowspec-ip-stat/qos:match/qos:tcp-flags/qos:tcp-flag/qos:psh;
/qos:state/qos:qos/qos:flowspec-ip-stats/qos:flowspec-ip-stat/qos:match/qos:tcp-flags/qos:tcp-flag/qos:rst;
/qos:state/qos:qos/qos:flowspec-ip-stats/qos:flowspec-ip-stat/qos:match/qos:tcp-flags/qos:tcp-flag/qos:syn;
/qos:state/qos:qos/qos:flowspec-ip-stats/qos:flowspec-ip-stat/qos:match/qos:tcp-flags/qos:tcp-flag/qos:fin.' ;
  }

  revision 2022-11-03 {
    description 'Unsupport some traffic-policy telemetry fields, delete following leaf:
/state/qos/traffic-policy-if-stats/traffic-policy-if-stat/used-queue-depth-pkts
/state/qos/traffic-policy-if-stats/traffic-policy-if-stat/used-queue-depth
/state/qos/traffic-policy-if-stats/traffic-policy-if-stat/pkts-loss-rate
/state/qos/traffic-policy-if-stats/traffic-policy-if-stat/octets-loss-rate' ;
  }

  revision 2022-10-10 {
    description 'Support flowspec interface group,add containers as follow:
/qos:configuration/qos:qos/qos:policy-map/qos:flowspec-based/qos:policy-maps/qos:policy-map/qos:class-maps/qos:class-map/qos:if-group
/qos:configuration/qos:qos/qos:flowspec-if-groups
/qos:state/qos:qos/qos:flowspec-vrf-stats/qos:flowspec-vrf-stat/qos:if-groups
/qos:state/qos:qos/qos:flowspec-ip-stats/qos:flowspec-ip-stat/qos:if-groups' ;
  }

  revision 2022-10-09 {
    description 'Support to configure match GRE or IPP(ip-in-ip) inner layer, add containers:
1. /configuration/qos/class-map/traffic-based/class-maps/class-map/match/gre-inner-ipv4-acls.
2. /configuration/qos/class-map/traffic-based/class-maps/class-map/match/gre-inner-ipv6-acls.
3. /configuration/qos/class-map/traffic-based/class-maps/class-map/match/ipp-inner-ipv4-acls.
4. /configuration/qos/class-map/traffic-based/class-maps/class-map/match/ipp-inner-ipv6-acls.' ;
  }

  revision 2022-09-26 {
    description '1. Support QoS redirect next-hop srv6-be configuration for policy map flowspec-based, add container:
/configuration/qos/policy-map/flowspec-based/policy-maps/policy-map/class-maps/class-map/redirect-nexthop/srv6-be.
2. Support flow specification statistics data obtain,add container:
/qos:state/qos:qos/qos:flowspec-vrf-stats/qos:flowspec-vrf-stat/qos:action/qos:redirect-nexthop/qos:srv6-be;
/qos:state/qos:qos/qos:flowspec-ip-stats/qos:flowspec-ip-stat/qos:action/qos:redirect-nexthop/qos:srv6-be.' ;
  }

  revision 2022-09-19 {
    description 'Support traffic-policy telemetry,add following leaf:
/state/qos/traffic-policy-if-stats/traffic-policy-if-stat/if
/state/qos/traffic-policy-if-stats/traffic-policy-if-stat/dir

/state/qos/traffic-policy-if-stats/traffic-policy-if-stat/pname
/state/qos/traffic-policy-if-stats/traffic-policy-if-stat/cname
/state/qos/traffic-policy-if-stats/traffic-policy-if-stat/transmit-pkts-rate
/state/qos/traffic-policy-if-stats/traffic-policy-if-stat/transmit-octets-rate
/state/qos/traffic-policy-if-stats/traffic-policy-if-stat/dropped-pkts-rate
/state/qos/traffic-policy-if-stats/traffic-policy-if-stat/dropped-octets-rate
/state/qos/traffic-policy-if-stats/traffic-policy-if-stat/used-queue-depth-pkts
/state/qos/traffic-policy-if-stats/traffic-policy-if-stat/used-queue-depth
/state/qos/traffic-policy-if-stats/traffic-policy-if-stat/pkts-loss-rate
/state/qos/traffic-policy-if-stats/traffic-policy-if-stat/octets-loss-rate' ;
  }

  revision 2022-09-08 {
    description '1. Support configuration of reverse direction TE schedule, add containers:
/qos:configuration/qos:qos/qos:qos-schedule/qos:te-reverses;
/qos:configuration/qos:qos/qos:te-schedule-stats/qos:stats-switch-reverses;
/qos:operation/qos:qos/qos:stats-clear/qos:te-reverse-schedules.' ;
  }

  revision 2022-08-23 {
    description 'Support hqos and queue telemetry,add following leaf:
/state/qos/hqosstats/hqosstat/transmit-octets-rate
/state/qos/hqosstats/hqosstat/dropped-pkts-rate
/state/qos/hqosstats/hqosstat/dropped-octets-rate
/state/qos/hqosstats/hqosstat/used-queue-depth-pkts
/state/qos/hqosstats/hqosstat/used-queue-depth
/state/qos/hqosstats/hqosstat/pkts-loss-rate
/state/qos/hqosstats/hqosstat/octets-loss-rate

/state/qos/statistics/statistic/queues/queue/transmit-octets-rate
/state/qos/statistics/statistic/queues/queue/transmit-bits-rate
/state/qos/statistics/statistic/queues/queue/dropped-pkts-rate
/state/qos/statistics/statistic/queues/queue/dropped-bits-rate
/state/qos/statistics/statistic/queues/queue/used-queue-depth-pkts
/state/qos/statistics/statistic/queues/queue/pkts-loss-rate
/state/qos/statistics/statistic/queues/queue/octets-loss-rate

/state/qos/statistics/statistic/queues/queue/real-time-usage' ;
  }

  revision 2022-07-11 {
    description 'Support port-queue drop ratio alarm,add containers as follow:

/qos:configuration/qos:qos/qos:queue-if-stats/qos:alarm-switch
/qos:configuration/qos:qos/qos:queue-if-stats/qos:drop-ratio-detect-period
/qos:configuration/qos:qos/qos:queue-if-stats/qos:drop-ratio-threshold-percentage' ;
  }

  revision 2022-06-27 {
    description '1. Support WRED template configuration, add container:
/configuration/qos/wred-templates.
2. Support WRED template for policy-map, add container:
/configuration/qos/policy-map/normal/policy-maps/policy-map/class-maps/class-map/wred-template.
/configuration/qos/policy-map/normal/policy-maps/policy-map/class-maps/class-default/wred-template.' ;
  }

  revision 2022-06-13 {
    description '1. Support configuration of interface rate limit based on matching bum(broadcast, unknown unicast and unknown multicast) and bu(broadcast and unknown unicast),add containers:
/qos:configuration/qos:qos/qos:rate-limit/bums;
/qos:configuration/qos:qos/qos:rate-limit/bus.' ;
  }

  revision 2022-05-07 {
    description '1. Support flow specification statistics data obtain,add container:
/qos:state/qos:qos/qos:flowspec-vrf-stats;
/qos:state/qos:qos/qos:flowspec-ip-stats.' ;
  }

  revision 2022-04-27 {
    description '1. Support QoS match tcp-flag-value configuration for class map flowspec-based, add container:
/configuration/qos/class-map/flowspec-based/class-maps/class-map/match/tcp-flag-values.' ;
  }

  revision 2022-03-18 {
    description 'Support queue if stats switch,add container:
/qos:configuration/qos:qos/qos:queue-if-stats' ;
  }

  revision 2022-03-10 {
    description '1. Support to configure the switch to store QoS statistics information in CSV format, add container:
/qos:configuration/qos:qos/qos:qos-stats-save.' ;
  }

  revision 2022-02-19 {
    description '1. Support QoS match application configuration for class map traffic-based, add container:
/configuration/qos/class-map/traffic-based/class-maps/class-map/match/applications.' ;
  }

  revision 2021-12-17 {
    description '1. Support QoS traffic policy statistics switch configuration for policy map, add container:
/qos:configuration/qos:qos/qos:traffic-policy-stats/qos:stats-switch-policy-maps.
2. Support QoS traffic policy statistic data clear for policy map, add container:
/qos:operation/qos:qos/qos:traffic-policy-stats-clear/qos:stats-clear-policy-maps.' ;
  }

  revision 2021-11-22 {
    description 'Support shared or unshared mode of policy-map traffic-based,add container as follow:
/configuration/qos/policy-map/traffic-based/policy-maps/policy-map/share-mode' ;
  }

  revision 2021-11-19 {
    description 'Support to set cachetime of WRED based on precedence in policy-map, add note:
/configuration/qos/policy-map/normal/policy-maps/policy-map/class-maps/class-map/random-detect/precedences/precedence/threshold/threshold-cachetime
/configuration/qos/policy-map/normal/policy-maps/policy-map/class-maps/class-default/random-detect/precedences/precedence/threshold/threshold-cachetime
/configuration/qos/policy-map/phb-based/policy-maps/policy-map/class-maps/class-map/random-detect/precedences/precedence/threshold/threshold-cachetime
/configuration/qos/policy-map/phb-based/policy-maps/policy-map/class-maps/class-default/random-detect/precedences/precedence/threshold/threshold-cachetime
/configuration/qos/policy-map/switch-fabric-based/policy-maps/policy-map/class-maps/class-map/random-detect/precedences/precedence/threshold/threshold-cachetime
/configuration/qos/policy-map/switch-fabric-based/policy-maps/policy-map/class-maps/class-default/random-detect/precedences/precedence/threshold/threshold-cachetime' ;
  }

  revision 2021-11-08 {
    description 'Support to configure traffic policy vlan, add container:
/qos:configuration/qos:qos/qos:traffic-policy-vlan' ;
  }

  revision 2021-10-11 {
    description 'Support to configure interface network slice and bandwidth, add container:
/qos:configuration/qos:qos/qos:qos-if-slice;' ;
  }

  revision 2021-09-15 {
    description 'Support queue telemetry,add following leaf:
/state/qos/statistics/statistic/queues/queue/total-queue-depth
/state/qos/statistics/statistic/queues/queue/used-queue-depth' ;
  }

  revision 2021-08-23 {
    description 'Support queue telemetry,add following node:
/state/qos/queue-resource-stats' ;
  }

  revision 2021-08-11 {
    description 'Support queue telemetry,add following node:
/state/qos/statistics' ;
  }

  revision 2021-08-10 {
    description '1.Support switch-fabric in service-policy, add node:
/qos:configuration/qos:qos/qos:service-policys/qos:service-policy/qos:switch-fabric;
2.Support configure description of the QoS policys bind to the interface, add node:
/qos:configuration/qos:qos/qos:traffic-policy-interfaces/qos:traffic-policy-interface/qos:description.' ;
  }

  revision 2021-08-03 {
    description 'Support to set interface in policy-map traffic-based, add node:
/configuration/qos/policy-map/traffic-based/policy-maps/policy-map/class-maps/class-map/set/interface
/configuration/qos/policy-map/traffic-based/policy-maps/policy-map/class-maps/class-default/set/interface' ;
  }

  revision 2021-06-04 {
    description '1.Support telemetry,add following node:
/state
2.Modify the description of the following nodes:
type qos-bucket-unit-type;
/qos:configuration/qos:qos/qos:policy-map/qos:traffic-based/qos:policy-maps/qos:policy-map/qos:class-maps/qos:class-map/qos:police/qos:c-buket/qos:cbs-value/qos:cbs;
/qos:configuration/qos:qos/qos:policy-map/qos:traffic-based/qos:policy-maps/qos:policy-map/qos:class-maps/qos:class-map/qos:police/qos:p-buket/qos:pbs-value/qos:pbs;
/qos:configuration/qos:qos/qos:policy-map/qos:traffic-based/qos:policy-maps/qos:policy-map/qos:class-maps/qos:class-default/qos:police/qos:c-buket/qos:cbs-value/qos:cbs;
/qos:configuration/qos:qos/qos:policy-map/qos:traffic-based/qos:policy-maps/qos:policy-map/qos:class-maps/qos:class-default/qos:police/qos:p-buket/qos:pbs-value/qos:pbs;' ;
  }

  revision 2021-05-25 {
    description 'Support to set encapsulated DSCP as mark type in policy-map, add node:
/configuration/qos/policy-map/normal/policy-maps/policy-map/class-maps/class-map/set/encap-dscp;
/configuration/qos/policy-map/normal/policy-maps/policy-map/class-maps/class-default/set/encap-dscp.' ;
  }

  revision 2021-04-18 {
    description 'Support cps-based class-map and policy-map, add nodes:
/qos:configuration/qos:qos/qos:class-map/qos:cps-based;
/qos:configuration/qos:qos/qos:policy-map/qos:cps-based.' ;
  }

  revision 2021-04-16 {
    description 'Modify the pattern of packet-length-value node to avoid inputting error value:
/configuration/qos/class-map/flowspec-based/class-maps/class-map/match/packet-length/packet-length-value.' ;
  }

  revision 2021-03-24 {
    description 'Support statistical-group in QoS statistics, add node:
1./qos:configuration/qos:qos/qos:qos-stats/qos:stats-switch/qos:stats-switches/qos:statistics-group;
2./qos:configuration/qos:qos/qos:pw-schedul-stats/qos:stats-switches/qos:stats-switch/qos:statistics-group;
3./qos:configuration/qos:qos/qos:pw-schedul-stats/qos:stats-switch-ins/qos:stats-switch-in/qos:statistics-group;
4./qos:configuration/qos:qos/qos:bgpad-schedul-stats/qos:stats-switches/qos:stats-switch/qos:statistics-group;
5./qos:configuration/qos:qos/qos:qos-schedule/qos:tes;
6./qos:configuration/qos:qos/qos:te-schedul-stats;
7./qos:operation/qos:qos/qos:stats-clear/qos:te-schedules;
8./qos:operation/qos:qos/qos:stats-clear/qos:interfaces;
Delete features on following nodes:
1./configuration/qos/policy-map/traffic-based/policy-maps/policy-map/class-maps/class-map/drop;
2./configuration/qos/policy-map/traffic-based/policy-maps/policy-map/class-maps/class-default/drop;
3./configuration/qos/policy-map/traffic-based/policy-maps/policy-map/class-maps/class-map/police/mode;
4./configuration/qos/policy-map/traffic-based/policy-maps/policy-map/class-maps/class-default/police/mode;
5./configuration/qos/mls-qos-modes/mls-qos-mode/pipe/servclass-color;
6./configuration/qos/mls-qos-modes/mls-qos-mode/short-pipe/servclass-color.' ;
  }

  revision 2021-03-22 {
    description 'Support shape of sub-interface,add node:
/configuration/qos/service-policys/service-policy/shape' ;
  }

  revision 2021-03-04 {
    description 'Support statistical-share in PW schedule, add node:
1./qos:configuration/qos:qos/qos:qos-schedule/qos:pws/qos:pw/qos:statistical-share;
2./qos:configuration/qos:qos/qos:qos-schedule/qos:pw-ins/qos:pw-in/qos:statistical-share.' ;
  }

  revision 2021-01-25 {
    description '1.Support traffic-based class-map, add nodes:
/qos:configuration/qos:qos/qos:class-map/qos:traffic-based.
2.Support vlan-stacking, add node:
/configuration/qos/policy-map/traffic-based/policy-maps/policy-map/class-maps/class-map/vlan-stacking
/configuration/qos/policy-map/traffic-based/policy-maps/policy-map/class-maps/class-default/vlan-stacking
3.Support reidrect route-map, add node:
/configuration/qos/policy-map/traffic-based/policy-maps/policy-map/class-maps/class-map/redirect/route-map
/configuration/qos/policy-map/traffic-based/policy-maps/policy-map/class-maps/class-default/redirect/route-map
4.Support match interface in normal class-map, add nodes:
/qos:configuration/qos:qos/qos:class-map/qos:normal/qos:class-maps/qos:class-map/qos:match/qos:interface.
5. Support ipv4-vxlan-acl and ipv6-vxlan-acl, add nodes:
/qos:configuration/qos:qos/qos:class-map/qos:normal/qos:class-maps/qos:class-map/qos:match/qos:ipv4-vxlan-acls
/qos:configuration/qos:qos/qos:class-map/qos:normal/qos:class-maps/qos:class-map/qos:match/qos:ipv6-vxlan-acls
6. Support qos-global-priority-remark configuration,add node:

/qos:configuration/qos:qos/qos:qos-global-prioritys-remark.
7. Modify the range of node: 
/qos:configuration/qos:qos/qos:qos-prioritys-remark/qos:qos-priority-remark/qos:priority-type from 1-2 to 1-3, add type MPLS-EXP.
8. Support enable-switch of interface priority remark,add node:
/qos:configuration/qos:qos/qos:qos-prioritys-remark/qos:qos-priority-remark/qos:enable-switch.
9. Support optional pir in rate-limit, some nodes are added:
/qos:configuration/qos:qos/qos:rate-limit/qos:unicasts/qos:unicast/qos:buket-value-percent;
/qos:configuration/qos:qos/qos:rate-limit/qos:unknown-unicasts/qos:unknown-unicast/qos:buket-value-percent;
/qos:configuration/qos:qos/qos:rate-limit/qos:multicasts/qos:multicast/qos:buket-value-percent;
/qos:configuration/qos:qos/qos:rate-limit/qos:unknown-multicasts/qos:unknown-multicast/qos:buket-value-percent;
/qos:configuration/qos:qos/qos:rate-limit/qos:broadcasts/qos:broadcast/qos:buket-value-percent;
/qos:configuration/qos:qos/qos:rate-limit/qos:localports/qos:localport/qos:buket-value-percent.
10.Change configuration/qos/queue-templates/queue-template/queue-nos/queue-no/wfq-weight/percentage,use perfmpara as max value.
Change configuration/qos/queue-templates/queue-template/queue-nos/queue-no/priority-level/priority-value,the range is 1-8.
Add /qos:configuration/qos:qos/qos:queue-templates/qos:queue-template/qos:queue-nos/qos:queue-no/qos:random-detect/qos:weight.
Add /qos:configuration/qos:qos/qos:queue-templates/qos:queue-template/qos:queue-nos/qos:queue-no/qos:shape/qos:pir-pbs.
Add /qos:configuration/qos:qos/qos:queue-templates/qos:queue-template/qos:queue-nos/qos:queue-no/qos:shape/qos:pir-percentage.
11.Support traffic-policy interface, add nodes:
/configuration/qos/traffic-policy-interfaces/traffic-policy-interface.
12. Support statistics of traffic policy with feature traffic-policy.
Add node: /configuration/qos/traffic-policy-stats.
13. Support clear statistics of traffic policy with feature traffic-policy.
Add node: /operation/qos/traffic-policy-stats-clear.
14.Support traffic-based policy-map, add nodes:
/configuration/qos/policy-map/traffic-based/policy-maps/policy-map/class-maps/class-map/set/dscp
/configuration/qos/policy-map/traffic-based/policy-maps/policy-map/class-maps/class-map/set/precedence
/configuration/qos/policy-map/traffic-based/policy-maps/policy-map/class-maps/class-map/set/pri-8021p
/configuration/qos/policy-map/traffic-based/policy-maps/policy-map/class-maps/class-map/set/mpls-exp
/configuration/qos/policy-map/traffic-based/policy-maps/policy-map/class-maps/class-map/set/vlan-id
/configuration/qos/policy-map/traffic-based/policy-maps/policy-map/class-maps/class-default/set/dscp
/configuration/qos/policy-map/traffic-based/policy-maps/policy-map/class-maps/class-default/set/precedence
/configuration/qos/policy-map/traffic-based/policy-maps/policy-map/class-maps/class-default/set/pri-8021p
/configuration/qos/policy-map/traffic-based/policy-maps/policy-map/class-maps/class-default/set/mpls-exp
/configuration/qos/policy-map/traffic-based/policy-maps/policy-map/class-maps/class-default/set/vlan-id.
15. Support the PW interface diffserv domain template configuration, add nodes:
/qos:configuration/qos:qos/qos:qos-pw-ds-domains/qos:qos-pw-ds-domain/qos:pw-name
/qos:configuration/qos:qos/qos:qos-pw-ds-domains/qos:qos-pw-ds-domain/qos:ds-domain-name.' ;
  }

  revision 2021-01-18 {
    description '1. Support match service-class range, service-class leaf node are changed to choice-case node, and service-class-range node is added:
/qos:configuration/qos:qos/qos:class-map/qos:normal/qos:class-maps/qos:class-map/qos:match/qos:service-class;
/qos:configuration/qos:qos/qos:class-map/qos:phb-based/qos:class-maps/qos:class-map/qos:match/qos:service-class.
2. Support WRED precedence and weight, add nodes as follows:
/qos:configuration/qos:qos/qos:policy-map/qos:phb-based/qos:policy-maps/qos:policy-map/qos:class-maps/qos:class-map/qos:random-detect/qos:colors/qos:color/qos:threshold;
/qos:configuration/qos:qos/qos:policy-map/qos:phb-based/qos:policy-maps/qos:policy-map/qos:class-maps/qos:class-map/qos:random-detect/qos:precedences;
/qos:configuration/qos:qos/qos:policy-map/qos:phb-based/qos:policy-maps/qos:policy-map/qos:class-maps/qos:class-map/qos:random-detect/qos:weight.
3. Support set service-class color in normal and car-action policy-map, service-class node is added:
/qos:configuration/qos:qos/qos:policy-map/qos:normal/qos:policy-maps/qos:policy-map/qos:class-maps/qos:class-map/qos:set/qos:service-class;
/qos:configuration/qos:qos/qos:policy-map/qos:normal/qos:policy-maps/qos:policy-map/qos:class-maps/qos:class-default/qos:set/qos:service-class;
/qos:configuration/qos:qos/qos:policy-map/qos:car-action/qos:policy-maps/qos:policy-map/qos:class-maps/qos:class-map/qos:set/qos:service-class/qos:color-type;
/qos:configuration/qos:qos/qos:policy-map/qos:car-action/qos:policy-maps/qos:policy-map/qos:class-maps/qos:class-default/qos:set/qos:service-class/qos:color-type.
4. Support share group ID in service policy, add node:
/qos:configuration/qos:qos/qos:service-policys/qos:service-policy/qos:share-group.
5. Support statistical-share in traffic-shape, add node:
/qos:configuration/qos:qos/qos:traffic-shapes/qos:traffic-shape/qos:statistical-share;
/qos:configuration/qos:qos/qos:traffic-shape-dirs/qos:traffic-shape-dir/qos:statistical-share;
6. Support PW ingress in QoS schedule, add node:
/qos:configuration/qos:qos/qos:qos-schedule/qos:pw-ins;
/qos:configuration/qos:qos/qos:pw-schedule-stats/qos:stats-switch-ins;
/qos:operation/qos:qos/qos:stats-clear/qos:pw-in-schedules.
7. In order to describing traffic-based policy map, a new node is added as follows:
/qos:configuration/qos:qos/qos:policy-map/qos:traffic-based/qos:policy-maps/qos:policy-map/qos:pmap-description.' ;
  }

  revision 2021-01-11 {
    description '1. Support scheduling policy for BGP-AD.
Add node: /configuration/qos/qos-schedule/bgp-ads.
2. Support statistics of scheduling policy for BGP-AD.
Add node: /configuration/qos/bgpad-schedule-stats.
3. Support clear statistics of scheduling policy for BGP-AD.
Add node: /operation/qos/stats-clear/bgpad-schedules.
4. Support match child for cmap phb-based.
/configuration/qos/class-map/phb-based/class-maps/class-map/match/child.
5. Support service policy for pmap phb-based.
/configuration/qos/policy-map/phb-based/policy-maps/policy-map/class-maps/class-map/service-policy.
/configuration/qos/policy-map/phb-based/policy-maps/policy-map/class-maps/class-default/service-policy.
6. Support drop function of traffic-based policy-map, add node:
/configuration/qos/policy-map/traffic-based/policy-maps/policy-map/class-maps/class-map/drop
/configuration/qos/policy-map/traffic-based/policy-maps/policy-map/class-maps/class-default/drop.' ;
  }

  revision 2020-12-23 {
    description '1. Support ipv6-mixed-acl, add node:
/configuration/qos/class-map/normal/class-maps/class-map/match/ipv6-mixed-acls.
2. Support traffic-based policy-map, add node:
/configuration/qos/policy-map/traffic-based.
3. Support cir and pir percentage, add node:
/configuration/qos/rate-limit/unicasts/unicast/cir-percentage

/configuration/qos/rate-limit/unicasts/unicast/pir-percentage

/configuration/qos/rate-limit/unknown-unicasts/unknown-unicast/cir-percentage
/configuration/qos/rate-limit/unknown-unicasts/unknown-unicast/pir-percentage
/configuration/qos/rate-limit/multicasts/multicast/cir-percentage
/configuration/qos/rate-limit/multicasts/multicast/pir-percentage
/configuration/qos/rate-limit/unknown-multicasts/unknown-multicast/cir-percentage
/configuration/qos/rate-limit/unknown-multicasts/unknown-multicast/pir-percentage
/configuration/qos/rate-limit/broadcasts/broadcast/cir-percentage
/configuration/qos/rate-limit/broadcasts/broadcast/pir-percentage
/configuration/qos/rate-limit/unknowns/unknown/cir-percentage

/configuration/qos/rate-limit/unknowns/unknown/pir-percentage

/configuration/qos/rate-limit/localports/localport/cir-percentage
/configuration/qos/rate-limit/localports/localport/pir-percentage
/configuration/qos/rate-limit/dscps/dscp/cir-percentage
/configuration/qos/rate-limit/dscps/dscp/pir-percentage
/configuration/qos/rate-limit/precedences/precedence/cir-percentage
/configuration/qos/rate-limit/precedences/precedence/pir-percentage
/configuration/qos/rate-limit/mpls-exps/mpls-exp/cir-percentage
/configuration/qos/rate-limit/mpls-exps/mpls-exp/pir-percentage
/configuration/qos/rate-limit/inner-vlans/inner-vlan/cir-percentage
/configuration/qos/rate-limit/inner-vlans/inner-vlan/pir-percentage
/configuration/qos/rate-limit/outer-vlans/outer-vlan/cir-percentage
/configuration/qos/rate-limit/outer-vlans/outer-vlan/pir-percentage
/configuration/qos/rate-limit/multi-vlans/multi-vlan/cir-percentage
/configuration/qos/rate-limit/multi-vlans/multi-vlan/pir-percentage
/configuration/qos/rate-limit/inner-8021ps/inner-8021p/cir-percentage
/configuration/qos/rate-limit/inner-8021ps/inner-8021p/pir-percentage
/configuration/qos/rate-limit/outer-8021ps/outer-8021p/cir-percentage
/configuration/qos/rate-limit/outer-8021ps/outer-8021p/pir-percentage
/configuration/qos/rate-limit/multi-8021ps/multi-8021p/cir-percentage
/configuration/qos/rate-limit/multi-8021ps/multi-8021p/pir-percentage
/configuration/qos/rate-limit/qos-groups/qos-group/cir-percentage
/configuration/qos/rate-limit/qos-groups/qos-group/pir-percentage
/configuration/qos/rate-limit/access-lists/access-list/cir-percentage
/configuration/qos/rate-limit/access-lists/access-list/pir-percentage' ;
  }

  revision 2020-12-02 {
    description 'Support flowspec redirect tunnel-id, add node:
/configuration/qos/policy-map/flowspec-based/policy-maps/policy-map/class-maps/class-map/redirect-tunnel-id
Obsolete flowspec redirect rsvp-te and sr-te, obsolete node:
/configuration/qos/policy-map/flowspec-based/policy-maps/policy-map/class-maps/class-map/redirect-rsvp-te
/configuration/qos/policy-map/flowspec-based/policy-maps/policy-map/class-maps/class-map/redirect-sr-te' ;
  }

  revision 2020-11-11 {
    description 'Support WRED threshold percentage config in queue-template.
1 Add choice threshold:
/configuration/qos/queue-templates/queue-template/queue-nos/queue-no/random-detect/color/green/threshold;
/configuration/qos/queue-templates/queue-template/queue-nos/queue-no/random-detect/color/yellow/threshold;
/configuration/qos/queue-templates/queue-template/queue-nos/queue-no/random-detect/color/red/threshold.
2 Move min-threshode and max-threshold to new case threshold-value:
/configuration/qos/queue-templates/queue-template/queue-nos/queue-no/random-detect/color/green/min-threshold;
/configuration/qos/queue-templates/queue-template/queue-nos/queue-no/random-detect/color/green/max-threshold;
/configuration/qos/queue-templates/queue-template/queue-nos/queue-no/random-detect/color/yellow/min-threshold;
/configuration/qos/queue-templates/queue-template/queue-nos/queue-no/random-detect/color/yellow/max-threshold;
/configuration/qos/queue-templates/queue-template/queue-nos/queue-no/random-detect/color/red/min-threshold;
/configuration/qos/queue-templates/queue-template/queue-nos/queue-no/random-detect/color/red/max-threshold.' ;
  }

  revision 2020-11-02 {
    description 'Set cir-percentage node mandatory true:
/configuration/qos/policy-map/normal/policy-maps/policy-map/class-maps/class-map/police/cir-pir-percentage/cir-percentage;
/configuration/qos/policy-map/normal/policy-maps/policy-map/class-maps/class-default/police/cir-pir-percentage/cir-percentage.' ;
  }

  revision 2020-10-20 {
    description '1. Support redirect next-hop ipv6-address color and prefix-sid, add node:
/configuration/qos/policy-map/flowspec-based/policy-maps/policy-map/class-maps/class-map/redirect-nexthop/next-hop/ipv6-address/ipv6-address/ipaddr-nexthop/color-sid.' ;
  }

  revision 2020-08-25 {
    description 'Support H-QoS switch fabric policy bind based on interface:
/configuration/qos/switch-fabrics/interfaces.' ;
  }

  revision 2020-07-17 {
    description '1. Support redirect next-hop ipv6-address, add node:
/configuration/qos/policy-map/flowspec-based/policy-maps/policy-map/class-maps/class-map/redirect-nexthop/next-hop/ipv6-address.
2. Support copy in redirect next-hop ip-address, add node:
/configuration/qos/policy-map/flowspec-based/policy-maps/policy-map/class-maps/class-map/redirect-nexthop/next-hop/ip-address/ip-address/copy.' ;
  }

  revision 2020-06-23 {
    description 'Support set service-class of policy-map car-action-type, add nodes:
/configuration/qos/policy-map/car-action/policy-maps/policy-map/class-maps/class-map/police/conform-action/service-class-value
/configuration/qos/policy-map/car-action/policy-maps/policy-map/class-maps/class-map/police/exceed-action/service-class-value
/configuration/qos/policy-map/car-action/policy-maps/policy-map/class-maps/class-map/police/violate-action/service-class-value
/configuration/qos/policy-map/car-action/policy-maps/policy-map/class-maps/class-default/police/conform-action/service-class-value
/configuration/qos/policy-map/car-action/policy-maps/policy-map/class-maps/class-default/police/exceed-action/service-class-value
/configuration/qos/policy-map/car-action/policy-maps/policy-map/class-maps/class-default/police/violate-action/service-class-value' ;
  }

  revision 2020-06-18 {
    description 'In order to describing policy map, class map, rate limit and flow behavior application, some new nodes are added as follows:
1./qos:configuration/qos:qos/qos:class-map/qos:normal/qos:class-maps/qos:class-map/qos:cmap-description;
2./qos:configuration/qos:qos/qos:class-map/qos:phb-based/qos:class-maps/qos:class-map/qos:cmap-description;
3./qos:configuration/qos:qos/qos:class-map/qos:sub-interface-based/qos:class-maps/qos:class-map/qos:cmap-description;
4./qos:configuration/qos:qos/qos:class-map/qos:flowspec-based/qos:class-maps/qos:class-map/qos:cmap-description;
5./qos:configuration/qos:qos/qos:class-map/qos:flow-feature/qos:class-maps/qos:class-map/qos:cmap-description;
6./qos:configuration/qos:qos/qos:policy-map/qos:normal/qos:policy-maps/qos:policy-map/qos:pmap-description;
7./qos:configuration/qos:qos/qos:policy-map/qos:phb-based/qos:policy-maps/qos:policy-map/qos:pmap-description;
8./qos:configuration/qos:qos/qos:policy-map/qos:sub-interface-based/qos:policy-maps/qos:policy-map/qos:pmap-description;
9./qos:configuration/qos:qos/qos:policy-map/qos:flowspec-based/qos:policy-maps/qos:policy-map/qos:pmap-description;
10./qos:configuration/qos:qos/qos:policy-map/qos:flow-behavior/qos:policy-maps/qos:policy-map/qos:pmap-description;
11./qos:configuration/qos:qos/qos:rate-limit/qos:unicasts/qos:unicast/qos:rate-limit-desc;
12./qos:configuration/qos:qos/qos:rate-limit/qos:unknown-unicasts/qos:unknown-unicast/qos:rate-limit-desc;
13./qos:configuration/qos:qos/qos:rate-limit/qos:multicasts/qos:multicast/qos:rate-limit-desc;
14./qos:configuration/qos:qos/qos:rate-limit/qos:unknown-multicasts/qos:unknown-multicast/qos:rate-limit-desc;
15./qos:configuration/qos:qos/qos:rate-limit/qos:broadcasts/qos:broadcast/qos:rate-limit-desc;
16./qos:configuration/qos:qos/qos:rate-limit/qos:unknowns/qos:unknown/qos:rate-limit-desc;
17./qos:configuration/qos:qos/qos:rate-limit/qos:localports/qos:localport/qos:rate-limit-desc;
18./qos:configuration/qos:qos/qos:rate-limit/qos:dscps/qos:dscp/qos:rate-limit-desc;
19./qos:configuration/qos:qos/qos:rate-limit/qos:precedences/qos:precedence/qos:rate-limit-desc;
20./qos:configuration/qos:qos/qos:rate-limit/qos:mpls-exps/qos:mpls-exp/qos:rate-limit-desc;
21./qos:configuration/qos:qos/qos:rate-limit/qos:inner-vlans/qos:inner-vlan/qos:rate-limit-desc;
22./qos:configuration/qos:qos/qos:rate-limit/qos:outer-vlans/qos:outer-vlan/qos:rate-limit-desc;
23./qos:configuration/qos:qos/qos:rate-limit/qos:multi-vlans/qos:multi-vlan/qos:rate-limit-desc;
24./qos:configuration/qos:qos/qos:rate-limit/qos:inner-8021ps/qos:inner-8021p/qos:rate-limit-desc;
25./qos:configuration/qos:qos/qos:rate-limit/qos:outer-8021ps/qos:outer-8021p/qos:rate-limit-desc;
26./qos:configuration/qos:qos/qos:rate-limit/qos:multi-8021ps/qos:multi-8021p/qos:rate-limit-desc;
27./qos:configuration/qos:qos/qos:rate-limit/qos:qos-groups/qos:qos-group/qos:rate-limit-desc;
28./qos:configuration/qos:qos/qos:rate-limit/qos:access-lists/qos:access-list/qos:rate-limit-desc;
29./qos:configuration/qos:qos/qos:flow-behavior-application/qos:flow-behavior-apply-global/qos:flow-behavior-apply-desc;
30./qos:configuration/qos:qos/qos:flow-behavior-application/qos:flow-behavior-apply-vrfs/qos:flow-behavior-apply-vrf/qos:flow-behavior-apply-desc.' ;
  }

  revision 2020-06-09 {
    description 'Support percentage of CIR and PIR, add nodes:
/configuration/qos/policy-map/normal/policy-maps/policy-map/class-maps/class-map/police/cir-pir-percentage
/configuration/qos/policy-map/normal/policy-maps/policy-map/class-maps/class-default/police/cir-pir-percentage' ;
  }

  revision 2020-06-02 {
    description 'Support network header length of traffic-shape, add nodes:
/configuration/qos/traffic-shapes/traffic-shape/network-header-len
/configuration/qos/traffic-shape-dirs/traffic-shape-dir/network-header-len' ;
  }

  revision 2020-05-18 {
    description 'Support set service-class, add nodes:
/configuration/qos/rate-limit/unicasts/unicast/conform-action/set-service-class-transmit
/configuration/qos/rate-limit/unicasts/unicast/exceed-action/set-service-class-transmit
/configuration/qos/rate-limit/unicasts/unicast/violate-action/set-service-class-transmit
/configuration/qos/rate-limit/unknown-unicasts/unknown-unicast/conform-action/set-service-class-transmit
/configuration/qos/rate-limit/unknown-unicasts/unknown-unicast/exceed-action/set-service-class-transmit
/configuration/qos/rate-limit/unknown-unicasts/unknown-unicast/violate-action/set-service-class-transmit
/configuration/qos/rate-limit/multicasts/multicast/conform-action/set-service-class-transmit
/configuration/qos/rate-limit/multicasts/multicast/exceed-action/set-service-class-transmit
/configuration/qos/rate-limit/multicasts/multicast/violate-action/set-service-class-transmit
/configuration/qos/rate-limit/unknown-multicasts/unknown-multicast/conform-action/set-service-class-transmit
/configuration/qos/rate-limit/unknown-multicasts/unknown-multicast/exceed-action/set-service-class-transmit
/configuration/qos/rate-limit/unknown-multicasts/unknown-multicast/violate-action/set-service-class-transmit
/configuration/qos/rate-limit/broadcasts/broadcast/conform-action/set-service-class-transmit
/configuration/qos/rate-limit/broadcasts/broadcast/exceed-action/set-service-class-transmit
/configuration/qos/rate-limit/broadcasts/broadcast/violate-action/set-service-class-transmit
/configuration/qos/rate-limit/unknowns/unknown/conform-action/set-service-class-transmit
/configuration/qos/rate-limit/unknowns/unknown/exceed-action/set-service-class-transmit
/configuration/qos/rate-limit/unknowns/unknown/violate-action/set-service-class-transmit
/configuration/qos/rate-limit/localports/localport/conform-action/set-service-class-transmit
/configuration/qos/rate-limit/localports/localport/exceed-action/set-service-class-transmit
/configuration/qos/rate-limit/localports/localport/violate-action/set-service-class-transmit
/configuration/qos/rate-limit/dscps/dscp/conform-action/set-service-class-transmit
/configuration/qos/rate-limit/dscps/dscp/exceed-action/set-service-class-transmit
/configuration/qos/rate-limit/dscps/dscp/violate-action/set-service-class-transmit
/configuration/qos/rate-limit/precedences/precedence/conform-action/set-service-class-transmit
/configuration/qos/rate-limit/precedences/precedence/exceed-action/set-service-class-transmit
/configuration/qos/rate-limit/precedences/precedence/violate-action/set-service-class-transmit
/configuration/qos/rate-limit/mpls-exps/mpls-exp/conform-action/set-service-class-transmit
/configuration/qos/rate-limit/mpls-exps/mpls-exp/exceed-action/set-service-class-transmit
/configuration/qos/rate-limit/mpls-exps/mpls-exp/violate-action/set-service-class-transmit
/configuration/qos/rate-limit/inner-vlans/inner-vlan/conform-action/set-service-class-transmit
/configuration/qos/rate-limit/inner-vlans/inner-vlan/exceed-action/set-service-class-transmit
/configuration/qos/rate-limit/inner-vlans/inner-vlan/violate-action/set-service-class-transmit
/configuration/qos/rate-limit/outer-vlans/outer-vlan/conform-action/set-service-class-transmit
/configuration/qos/rate-limit/outer-vlans/outer-vlan/exceed-action/set-service-class-transmit
/configuration/qos/rate-limit/outer-vlans/outer-vlan/violate-action/set-service-class-transmit
/configuration/qos/rate-limit/multi-vlans/multi-vlan/conform-action/set-service-class-transmit
/configuration/qos/rate-limit/multi-vlans/multi-vlan/exceed-action/set-service-class-transmit
/configuration/qos/rate-limit/multi-vlans/multi-vlan/violate-action/set-service-class-transmit
/configuration/qos/rate-limit/inner-8021ps/inner-8021p/conform-action/set-service-class-transmit
/configuration/qos/rate-limit/inner-8021ps/inner-8021p/exceed-action/set-service-class-transmit
/configuration/qos/rate-limit/inner-8021ps/inner-8021p/violate-action/set-service-class-transmit
/configuration/qos/rate-limit/outer-8021ps/outer-8021p/conform-action/set-service-class-transmit
/configuration/qos/rate-limit/outer-8021ps/outer-8021p/exceed-action/set-service-class-transmit
/configuration/qos/rate-limit/outer-8021ps/outer-8021p/violate-action/set-service-class-transmit
/configuration/qos/rate-limit/multi-8021ps/multi-8021p/conform-action/set-service-class-transmit
/configuration/qos/rate-limit/multi-8021ps/multi-8021p/exceed-action/set-service-class-transmit
/configuration/qos/rate-limit/multi-8021ps/multi-8021p/violate-action/set-service-class-transmit
/configuration/qos/rate-limit/qos-groups/qos-group/conform-action/set-service-class-transmit
/configuration/qos/rate-limit/qos-groups/qos-group/exceed-action/set-service-class-transmit
/configuration/qos/rate-limit/qos-groups/qos-group/violate-action/set-service-class-transmit
/configuration/qos/rate-limit/access-lists/access-list/conform-action/set-service-class-transmit
/configuration/qos/rate-limit/access-lists/access-list/exceed-action/set-service-class-transmit
/configuration/qos/rate-limit/access-lists/access-list/violate-action/set-service-class-transmit' ;
  }

  revision 2020-04-06 {
    description 'Support latency time threshold, bandwidth threshold and drop rate threshold, add nodes:
/configuration/qos/policy-maps/class-maps/class-map/latency-time-threshold;
/configuration/qos/policy-maps/class-maps/class-map/bandwidth-threshold;
/configuration/qos/policy-maps/class-maps/class-map/drop-rate-threshold;
/configuration/qos/policy-maps/class-maps/class-default/latency-time-threshold;
/configuration/qos/policy-maps/class-maps/class-default/bandwidth-threshold;
/configuration/qos/policy-maps/class-maps/class-default/drop-rate-threshold;' ;
  }

  revision 2020-03-24 {
    description 'Support global TTL, add node:
/configuration/qos/ttl-mode-global' ;
  }

  revision 2020-03-05 {
    description 'Support IPv6 vxlan, add node:
/configuration/qos/class-map/flow-feature/class-maps/class-map/match/vxlan-ipv6
/configuration/qos/policy-map/flow-behavior/policy-maps/policy-map/class-maps/class-map/set/vxlan/ipv6' ;
  }

  revision 2020-02-03 {
    description 'Support flowspec IPv6, add node:
/configuration/qos/class-map/flowspec-based/class-maps/class-map/match/flow-label
/configuration/qos/class-map/flowspec-based/class-maps/class-map/match/destination-ipv6-addr
/configuration/qos/class-map/flowspec-based/class-maps/class-map/match/source-ipv6-addr
/configuration/qos/class-map/flowspec-based/class-maps/class-map/match/ipv6-icmp-code
/configuration/qos/class-map/flowspec-based/class-maps/class-map/match/ipv6-icmp-type
/configuration/qos/class-map/flowspec-based/class-maps/class-map/match/next-header
/configuration/qos/policy-map/flowspec-based/policy-maps/policy-map/class-maps/class-map/redirect-rsvp-te
/configuration/qos/policy-map/flowspec-based/policy-maps/policy-map/class-maps/class-map/redirect-sr-te
Add enumeration value to follow node:
/configuration/qos/class-map/flowspec-based/class-maps/class-map/match/dscps/dscp/ip-type
/configuration/qos/flowspec/address-family-ips/address-family-ip/ip-type
/configuration/qos/flowspec/address-family-vrfs/address-family-vrf/ip-type' ;
  }

  revision 2019-12-10 {
    description 'Suppport ipv4-mixed-acl and ipv6-mixed-acl,nodes modified as follow:
/configuration/qos/rate-limit/access-lists/access-list/acl-type' ;
  }

  revision 2019-10-28 {
    description 'Support the configuration of token bucket ID,add new leaf as follows:
/configuration/qos/rate-limit/unicasts/unicast/token-bucket-id
/configuration/qos/rate-limit/unknown-unicasts/unknown-unicast/token-bucket-id
/configuration/qos/rate-limit/multicasts/multicast/token-bucket-id
/configuration/qos/rate-limit/unknown-multicasts/unknown-multicast/token-bucket-id
/configuration/qos/rate-limit/broadcasts/broadcast/token-bucket-id
/configuration/qos/rate-limit/unknowns/unknown/token-bucket-id
/configuration/qos/rate-limit/localports/localport/token-bucket-id
/configuration/qos/rate-limit/dscps/dscp/token-bucket-id
/configuration/qos/rate-limit/precedences/precedence/token-bucket-id
/configuration/qos/rate-limit/mpls-exps/mpls-exp/token-bucket-id
/configuration/qos/rate-limit/inner-vlans/inner-vlan/token-bucket-id
/configuration/qos/rate-limit/outer-vlans/outer-vlan/token-bucket-id
/configuration/qos/rate-limit/multi-vlans/multi-vlan/token-bucket-id
/configuration/qos/rate-limit/inner-8021ps/inner-8021p/token-bucket-id
/configuration/qos/rate-limit/outer-8021ps/outer-8021p/token-bucket-id
/configuration/qos/rate-limit/multi-8021ps/multi-8021p/token-bucket-id
/configuration/qos/rate-limit/qos-groups/qos-group/token-bucket-id
/configuration/qos/rate-limit/access-lists/access-list/token-bucket-id' ;
  }

  revision 2019-09-03 {
    description 'Remove mandatory attribute of these nodes:
/configuration/qos/policy-map/normal/policy-maps/policy-map/class-maps/class-map/police/cbs
/configuration/qos/policy-map/normal/policy-maps/policy-map/class-maps/class-map/police/pir-pbs/pbs
/configuration/qos/policy-map/normal/policy-maps/policy-map/class-maps/class-default/police/cbs
/configuration/qos/policy-map/normal/policy-maps/policy-map/class-maps/class-default/police/pir-pbs/pbs
/configuration/qos/policy-map/car-action/policy-maps/policy-map/class-maps/class-map/police/cbs
/configuration/qos/policy-map/car-action/policy-maps/policy-map/class-maps/class-map/police/pbs
/configuration/qos/policy-map/car-action/policy-maps/policy-map/class-maps/class-default/police/cbs
/configuration/qos/policy-map/car-action/policy-maps/policy-map/class-maps/class-default/police/pbs
/configuration/qos/policy-map/phb-based/policy-maps/policy-map/class-maps/class-map/police/cbs
/configuration/qos/policy-map/phb-based/policy-maps/policy-map/class-maps/class-map/police/pir-pbs/pbs
/configuration/qos/policy-map/phb-based/policy-maps/policy-map/class-maps/class-default/police/cbs
/configuration/qos/policy-map/phb-based/policy-maps/policy-map/class-maps/class-default/police/pir-pbs/pbs
/configuration/qos/policy-map/sub-interface-based/policy-maps/policy-map/class-maps/class-map/police/cbs
/configuration/qos/policy-map/sub-interface-based/policy-maps/policy-map/class-maps/class-map/police/pir-pbs/pbs
/configuration/qos/policy-map/sub-interface-based/policy-maps/policy-map/class-maps/class-default/police/cbs
/configuration/qos/policy-map/sub-interface-based/policy-maps/policy-map/class-maps/class-default/police/pir-pbs/pbs' ;
  }

  revision 2019-08-19 {
    description 'Support the configuration of queue value and queue cache time,add new container as follows:
/configuration/qos/policy-map/normal/policy-maps/policy-map/class-maps/class-map/queue-limit/queue-value/queue-value
/configuration/qos/policy-map/normal/policy-maps/policy-map/class-maps/class-map/queue-limit/queue-cache-time/queue-cache-time
/configuration/qos/policy-map/normal/policy-maps/policy-map/class-maps/class-default/queue-limit/queue-value/queue-value
/configuration/qos/policy-map/normal/policy-maps/policy-map/class-maps/class-default/queue-limit/queue-cache-time/queue-cache-time' ;
  }

  revision 2019-08-05 {
    description 'Support WRED percentage.
Add new container as follows:
/configuration/qos/policy-map/normal/policy-maps/policy-map/class-maps/class-map/random-detect/colors/color/threshold-percentage
/configuration/qos/policy-map/normal/policy-maps/policy-map/class-maps/class-map/random-detect/precedences/precedence/threshold-percentage
/configuration/qos/policy-map/normal/policy-maps/policy-map/class-maps/class-default/random-detect/colors/color/threshold-percentage
/configuration/qos/policy-map/normal/policy-maps/policy-map/class-maps/class-default/random-detect/precedences/precedence/threshold-percentage
/configuration/qos/policy-map/phb-based/policy-maps/policy-map/class-maps/class-map/random-detect/colors/color/threshold-percentage
/configuration/qos/policy-map/phb-based/policy-maps/policy-map/class-maps/class-default/random-detect/colors/color/threshold-percentage
Obsolete nodes as follows:
/configuration/qos/policy-map/phb-based/policy-maps/policy-map/class-maps/class-map/random-detect/colors/color/mim-threshold
/configuration/qos/policy-map/phb-based/policy-maps/policy-map/class-maps/class-map/random-detect/colors/color/max-threshold
/configuration/qos/policy-map/phb-based/policy-maps/policy-map/class-maps/class-default/random-detect/colors/color/min-threshold
/configuration/qos/policy-map/phb-based/policy-maps/policy-map/class-maps/class-default/random-detect/colors/color/max-threshold' ;
  }

  revision 2019-06-27 {
    description 'Support set next-hop ipv6-address, node modified as follows:
/configuration/qos/policy-map/flow-behavior/policy-maps/policy-map/class-maps/class-map/set/next-hop' ;
  }

  revision 2019-06-13 {
    description '1.Support the multiple level qos of service-policy, add new enum node:
/configuration/qos/service-policys/service-policy/bound-type
2.Support WRED of queue template, add new container as follows:
/configuration/qos/queue-templates/queue-template/queue-nos/queue-no/random-detecet
3.Support shape percentage of queue template, node modified as follows:
/configuration/qos/queue-templates/queue-template/queue-nos/queue-no/shape
4.Complement the queue depth of queue template, node modified as follows:
/configuration/qos/queue-templates/queue-template/queue-nos/queue-no/queue-limit/queue-depth' ;
  }

  revision 2019-06-11 {
    description 'Complement the queue depth,nodes modified as follows:
/configuration/qos/policy-map/normal/policy-maps/policy-map/class-maps/class-map/queue-limit/queue-depth.
/configuration/qos/policy-map/normal/policy-maps/policy-map/class-maps/class-default/queue-limit/queue-depth.' ;
  }

  revision 2019-04-15 {
    description '1.Support to configure class-map flow-feature, add new containers as follows:
/configuration/qos/class-map/flow-feature.
2.Support to configure policy-map flow-behavior, add new containers as follows:
/configuration/qos/policy-map/flow-behavior.' ;
  }

  revision 2018-09-19 {
    description '1.Support to configure set actions for policy-map car-action-based, add new containers as follows:
/configuration/qos/policy-map/car-action/policy-maps/policy-map/class-maps/class-map/set.
/configuration/qos/policy-map/car-action/policy-maps/policy-map/class-maps/class-default/set.
2.Support to configure bound-type for DS-domian, add new leaf as follows:
/configuration/qos/qos-ds-domains/qos-ds-domain/bound-type' ;
  }

  revision 2018-08-30 {
    description 'Support to configure queue template, add new containers as follows:
/configuration/qos/queue-templates.
/configuration/qos/queue-interfaces.' ;
  }

  revision 2018-08-18 {
    description '1.Support to configure the type of priority remarked by QoS,add new containers as follows:
/configuration/qos/qos-prioritys-remark.
2.Support to configure WRED(Weighted Random Early Detection) information under phb-based mode,notes modified as follows:
/configuration/qos/policy-map/phb-based/policy-maps/policy-map/class-maps/class-map/random-detect
/configuration/qos/policy-map/phb-based/policy-maps/policy-map/class-maps/class-default/random-detect.' ;
  }

  revision 2017-09-16 {
    description '1.Extended value range of partial nodes, notes modified as follows:
/configuration/qos/policy-map/*/policy-maps/policy-map/class-maps/class-map/random-detect/precedences/precedence/min-threshold
/configuration/qos/policy-map/*/policy-maps/policy-map/class-maps/class-map/random-detect/precedences/precedence/max-threshold
/configuration/qos/policy-map/*/policy-maps/policy-map/class-maps/class-default/random-detect/precedences/precedence/min-threshold
/configuration/qos/policy-map/*/policy-maps/policy-map/class-maps/class-default/random-detect/precedences/precedence/max-threshold
/configuration/qos/policy-map/*/policy-maps/policy-map/class-maps/class-map/police/cir
/configuration/qos/policy-map/*/policy-maps/policy-map/class-maps/class-map/police/cbs
/configuration/qos/policy-map/*/policy-maps/policy-map/class-maps/class-map/police/pir-pbs/pir
/configuration/qos/policy-map/*/policy-maps/policy-map/class-maps/class-map/police/pir-pbs/pbs
/configuration/qos/policy-map/*/policy-maps/policy-map/class-maps/class-default/police/cir
/configuration/qos/policy-map/*/policy-maps/policy-map/class-maps/class-default/police/cbs
/configuration/qos/policy-map/*/policy-maps/policy-map/class-maps/class-default/police/pir-pbs/pir
/configuration/qos/policy-map/*/policy-maps/policy-map/class-maps/class-default/police/pir-pbs/pbs
"*" means normal, car-action, phb-based, sub-interface-based, switch-fabric-based
/configuration/qos/rate-limit/*s/*/cir
/configuration/qos/rate-limit/*s/*/cbs
/configuration/qos/rate-limit/*s/*/pir
/configuration/qos/rate-limit/*s/*/pbs
"*" means unicast, multicast, broadcast, unknown, localport, dscp, precedence, mpls-exp, inner-vlan,
    outer-vlan, multi-vlan, inner-8021p, outer-8021p, multi-8021p, qos-group, access-list' ;
  }

  revision 2017-06-12 {
    description '1.Support to configure address family for flowspec, add new containers as follows:
/configuration/qos/flowspec.
2.Support configuration H-QoS class and policy map related based on the pattern of flowspec,add new containers as follows:
typedef:qos-port-range.
/configuration/qos/class-map/flowspec-based
/configuration/qos/policy-map/flowspec-based.
3.Support to specify service-type and effect-order of class-map, add new containers as follows:
/configuration/qos/class-map/normal/class-maps/class-map/service-type
/configuration/qos/class-map/normal/class-maps/class-map/service-type/effect-order.
4.Support to configure PQ and LLQ of policy-map car-action-based, add new containers as follows:
/configuration/qos/policy-map/car-action/policy-maps/policy-map/class-maps/class-map/priority-level
/configuration/qos/policy-map/car-action/policy-maps/policy-map/class-maps/class-map/priority-llq
/configuration/qos/policy-map/car-action/policy-maps/policy-map/class-maps/class-default/priority-level
/configuration/qos/policy-map/car-action/policy-maps/policy-map/class-maps/class-default/priority-llq.' ;
  }

  revision 2017-04-14 {
    description 'These if_features support M6000-S as follows:
switch-fabric-mode
policy-action-wred-color
qos-vni-instance
traffic-shape-dir' ;
  }

  revision 2017-02-20 {
    description 'Support set service function chaining, new notes added as follows:
/configuration/qos/policy-map/normal/policy-maps/policy-map/class-maps/class-map/set/vlan-id
/configuration/qos/policy-map/normal/policy-maps/policy-map/class-maps/class-map/set/service-query
/configuration/qos/policy-map/normal/policy-maps/policy-map/class-maps/class-map/set/interface
/configuration/qos/policy-map/normal/policy-maps/policy-map/class-maps/class-default/set/vlan-id
/configuration/qos/policy-map/normal/policy-maps/policy-map/class-maps/class-default/set/service-query
/configuration/qos/policy-map/normal/policy-maps/policy-map/class-maps/class-default/set/interface
/configuration/qos/class-map/normal/class-maps/class-map/match/ipv4-mixed-acls' ;
  }

  revision 2017-01-16 {
    description 'Support set interface traffic shape on the specific direction , new notes added as follows:
/configuration/qos/traffic-shape-dirs' ;
  }

  revision 2017-01-10 {
    description 'Support set inner and outer flag of set 8021p, new notes added as follows:
/configuration/qos/policy-map/normal/policy-maps/policy-map/class-maps/class-map/set/pri-8021p/set-value/inner-outer
/configuration/qos/policy-map/normal/policy-maps/policy-map/class-maps/class-map/set/pri-8021p/inherit/inner-outer
/configuration/qos/policy-map/normal/policy-maps/policy-map/class-maps/class-default/set/pri-8021p/set-value/inner-outer
/configuration/qos/policy-map/normal/policy-maps/policy-map/class-maps/class-default/set/pri-8021p/inherit/inner-outer
/configuration/qos/rate-limit/unicasts/unicast/conform-action/set-8021p-transmit/inner-outer
/configuration/qos/rate-limit/unknown-unicasts/unknown-unicast/conform-action/set-8021p-transmit/inner-outer
/configuration/qos/rate-limit/multicasts/multicast/conform-action/set-8021p-transmit/inner-outer
/configuration/qos/rate-limit/unknown-multicasts/unknown-multicast/conform-action/set-8021p-transmit/inner-outer
/configuration/qos/rate-limit/broadcasts/broadcast/conform-action/set-8021p-transmit/inner-outer
/configuration/qos/rate-limit/unknowns/unknown/conform-action/set-8021p-transmit/inner-outer
/configuration/qos/rate-limit/localports/localport/conform-action/set-8021p-transmit/inner-outer
/configuration/qos/rate-limit/dscps/dscp/conform-action/set-8021p-transmit/inner-outer
/configuration/qos/rate-limit/precedences/precedence/conform-action/set-8021p-transmit/inner-outer
/configuration/qos/rate-limit/mpls-exps/mpls-exp/conform-action/set-8021p-transmit/inner-outer
/configuration/qos/rate-limit/inner-vlans/inner-vlan/conform-action/set-8021p-transmit/inner-outer
/configuration/qos/rate-limit/outer-vlans/outer-vlan/conform-action/set-8021p-transmit/inner-outer
/configuration/qos/rate-limit/multi-vlans/multi-vlan/conform-action/set-8021p-transmit/inner-outer
/configuration/qos/rate-limit/inner-8021ps/inner-8021p/conform-action/set-8021p-transmit/inner-outer
/configuration/qos/rate-limit/outer-8021ps/outer-8021p/conform-action/set-8021p-transmit/inner-outer
/configuration/qos/rate-limit/multi-8021ps/multi-8021p/conform-action/set-8021p-transmit/inner-outer
/configuration/qos/rate-limit/qos-groups/qos-group/conform-action/set-8021p-transmit/inner-outer
/configuration/qos/rate-limit/access-lists/access-list/conform-action/set-8021p-transmit/inner-outer
/configuration/qos/rate-limit/unicasts/unicast/exceed-action/set-8021p-transmit/inner-outer
/configuration/qos/rate-limit/unknown-unicasts/unknown-unicast/exceed-action/set-8021p-transmit/inner-outer
/configuration/qos/rate-limit/multicasts/multicast/exceed-action/set-8021p-transmit/inner-outer
/configuration/qos/rate-limit/unknown-multicasts/unknown-multicast/exceed-action/set-8021p-transmit/inner-outer
/configuration/qos/rate-limit/broadcasts/broadcast/exceed-action/set-8021p-transmit/inner-outer
/configuration/qos/rate-limit/unknowns/unknown/exceed-action/set-8021p-transmit/inner-outer
/configuration/qos/rate-limit/localports/localport/exceed-action/set-8021p-transmit/inner-outer
/configuration/qos/rate-limit/dscps/dscp/exceed-action/set-8021p-transmit/inner-outer
/configuration/qos/rate-limit/precedences/precedence/exceed-action/set-8021p-transmit/inner-outer
/configuration/qos/rate-limit/mpls-exps/mpls-exp/exceed-action/set-8021p-transmit/inner-outer
/configuration/qos/rate-limit/inner-vlans/inner-vlan/exceed-action/set-8021p-transmit/inner-outer
/configuration/qos/rate-limit/outer-vlans/outer-vlan/exceed-action/set-8021p-transmit/inner-outer
/configuration/qos/rate-limit/multi-vlans/multi-vlan/exceed-action/set-8021p-transmit/inner-outer
/configuration/qos/rate-limit/inner-8021ps/inner-8021p/exceed-action/set-8021p-transmit/inner-outer
/configuration/qos/rate-limit/outer-8021ps/outer-8021p/exceed-action/set-8021p-transmit/inner-outer
/configuration/qos/rate-limit/multi-8021ps/multi-8021p/exceed-action/set-8021p-transmit/inner-outer
/configuration/qos/rate-limit/qos-groups/qos-group/exceed-action/set-8021p-transmit/inner-outer
/configuration/qos/rate-limit/access-lists/access-list/exceed-action/set-8021p-transmit/inner-outer
/configuration/qos/rate-limit/unicasts/unicast/violate-action/set-8021p-transmit/inner-outer
/configuration/qos/rate-limit/unknown-unicasts/unknown-unicast/violate-action/set-8021p-transmit/inner-outer
/configuration/qos/rate-limit/multicasts/multicast/violate-action/set-8021p-transmit/inner-outer
/configuration/qos/rate-limit/unknown-multicasts/unknown-multicast/violate-action/set-8021p-transmit/inner-outer
/configuration/qos/rate-limit/broadcasts/broadcast/violate-action/set-8021p-transmit/inner-outer
/configuration/qos/rate-limit/unknowns/unknown/violate-action/set-8021p-transmit/inner-outer
/configuration/qos/rate-limit/localports/localport/violate-action/set-8021p-transmit/inner-outer
/configuration/qos/rate-limit/dscps/dscp/violate-action/set-8021p-transmit/inner-outer
/configuration/qos/rate-limit/precedences/precedence/violate-action/set-8021p-transmit/inner-outer
/configuration/qos/rate-limit/mpls-exps/mpls-exp/violate-action/set-8021p-transmit/inner-outer
/configuration/qos/rate-limit/inner-vlans/inner-vlan/violate-action/set-8021p-transmit/inner-outer
/configuration/qos/rate-limit/outer-vlans/outer-vlan/violate-action/set-8021p-transmit/inner-outer
/configuration/qos/rate-limit/multi-vlans/multi-vlan/violate-action/set-8021p-transmit/inner-outer
/configuration/qos/rate-limit/inner-8021ps/inner-8021p/violate-action/set-8021p-transmit/inner-outer
/configuration/qos/rate-limit/outer-8021ps/outer-8021p/violate-action/set-8021p-transmit/inner-outer
/configuration/qos/rate-limit/multi-8021ps/multi-8021p/violate-action/set-8021p-transmit/inner-outer
/configuration/qos/rate-limit/qos-groups/qos-group/violate-action/set-8021p-transmit/inner-outer
/configuration/qos/rate-limit/access-lists/access-list/violate-action/set-8021p-transmit/inner-outer' ;
  }

  revision 2016-12-20 {
    description '1.Support priority(MPLS-EXP,DSCP,802.1p) range configuration, mapped to Per Hop Behavior, and in order to compatible with previous versions, add new priority(MPLS-EXP,DSCP,802.1p) single configuration containers, discard the old containers in this version, new notes added as follows:
/configuration/qos/diffserv/ds-domains/ds-domain/map/pri-8021p-singles
/configuration/qos/diffserv/ds-domains/ds-domain/map/pri-8021p-ranges
/configuration/qos/diffserv/ds-domains/ds-domain/map/mpls-exp-singles
/configuration/qos/diffserv/ds-domains/ds-domain/map/mpls-exp-ranges
/configuration/qos/diffserv/ds-domains/ds-domain/map/ipv4-dscp-singles
/configuration/qos/diffserv/ds-domains/ds-domain/map/ipv4-dscp-ranges
/configuration/qos/diffserv/ds-domains/ds-domain/map/ipv6-dscp-singles
/configuration/qos/diffserv/ds-domains/ds-domain/map/ipv6-dscp-ranges.
discard notes as follows:
/configuration/qos/diffserv/ds-domains/ds-domain/map/pri-8021ps
/configuration/qos/diffserv/ds-domains/ds-domain/map/mpls-exps
/configuration/qos/diffserv/ds-domains/ds-domain/map/ipv4-dscps
/configuration/qos/diffserv/ds-domains/ds-domain/map/ipv6-dscps' ;
  }

  revision 2016-07-20 {
    description 'Modify switch-fabric 
/configuration/qos/switch-fabric/normals/normal/mode          delete switch-port type
/configuration/qos/switch-fabric/subslots/group1s/group1/mode delete switch-port type
/configuration/qos/switch-fabric/subslots/group2s/group2/mode delete switch-port type
/configuration/qos/switch-fabric/subslots/ports/port/mode     add switch-port type' ;
  }

  revision 2016-06-30 {
    description '1.Support setting dscp inherit-from pay-load 8021p
add new type pay-load 8021p to inherit-type:
/configuration/qos/policy-map/normal/policy-maps/class-maps/class-map/set/dscp/inherit/inherit-type
/configuration/qos/policy-map/normal/policy-maps/class-default/set/dscp/inherit/inherit-type
2.Support binding policy-map to vni-instance
add new containers as follow:
/configuration/qos/vni-instances/vni-instance' ;
  }

  revision 2016-05-03 {
    description '1.Support PW schedule statistic switch, and support to clear PW schedule statistic data, add new containers as follows:
/configuration/qos/pw-schedule-stats/stats-switches
/operation/qos/stats-clear/pw-schedules' ;
  }

  revision 2015-11-04 {
    description '1. Support VNI (VXLAN Network Identifier) for class-map match item, add new nodes as follow:
container  /qos:configuration/qos:qos/qos:class-map/qos:normal/qos:class-maps/qos:class-map/qos:match/qos:vni
2. Support the switch of QoS flow statistics, add new nodes as follow:
container  /qos:configuration/qos:qos/qos:qos-stats' ;
  }

  revision 2015-10-28 {
    description '1.Support matching unknown-multicast, unknown-unicast for rate limit, add new containers as follows:
/configuration/qos/rate-limit/unknown-unicasts
/configuration/qos/rate-limit/unknown-multicasts' ;
  }

  revision 2015-04-15 {
    description '1.In order to compatible with previous versions, add a new container [qos-policy-exs], discard the old container [qos-policys] in this version, modify as follows,
discard the container:
  /configuration/qos/qos-policys
the new container:
  /configuration/qos/qos-policy-exs' ;
  }

  revision 2015-03-31 {
    description '1.In order to support graphical display for NM, add new container notes as follow:
  container: /configuration/qos/class-map/class-map-id
  container: /configuration/qos/policy-map/policy-map-id' ;
  }

  revision 2015-03-27 {
    description '1.Expand the max range value (10G modified to 100G) of rate,refering to traffic-shape, modifying as follows:
/configuration/qos/traffic-shapes/traffic-shape/rate' ;
  }

  revision 2015-02-09 {
    description '1.Modify to support [not] opposite range flag for class-map match DSCP/PRECEDENCE item, add new nodes as follow:
  leaf: /configuration/qos/class-map/normal/class-maps/class-map/match/dscps/dscp/not
  leaf: /configuration/qos/class-map/normal/class-maps/class-map/match/precedences/precedence/not
  
2.modify to convert removing queue-schedule[container] to resetting priority-level/wfq-weight, set DELETE2RESET OperationChangeType for the path notes as follow:
  container: /configuration/qos/qos-schedules/interfaces/interface/schedule/sche-group/queue-schedule
  choice: /configuration/qos/qos-schedules/interfaces/interface/schedule/sche-group/queue-schedule/queue-schedule
  case: /configuration/qos/qos-schedules/interfaces/interface/schedule/sche-group/queue-schedule/queue-schedule/pq
  case: /configuration/qos/qos-schedules/interfaces/interface/schedule/sche-group/queue-schedule/queue-schedule/wfq
  
  container: /configuration/qos/qos-schedules/pws/pw/schedule/sche-group/queue-schedule
  choice: /configuration/qos/qos-schedules/pws/pw/schedule/sche-group/queue-schedule/queue-schedule
  case: /configuration/qos/qos-schedules/pws/pw/schedule/sche-group/queue-schedule/queue-schedule/pq
  case: /configuration/qos/qos-schedules/pws/pw/schedule/sche-group/queue-schedule/queue-schedule/wfq' ;
  }

  revision 2014-10-20 {
    description "1.'.'as illegal named character ,modify all node names involving 802.1p, specific as follows:

    -802.1p       convert to  -8021p   e.g. in-802.1p-value  convert to in-8021p-value;

    _802.1p-value convert to  value-8021p;

    _802.1p       convert to  pri-8021p;

    enum 802.1p   convert to  enum 8021p;

    2. WRED,police and car support unit selection, add new nodes as follow:

    Add typedef: qos-rate-unit-type,qos-bucket-unit-type,qos-threshold-unit-type

    Add unit selection nodes:

    /configuration/qos/policy-map/*/policy-maps/policy-map/class-maps/class-map/random-detect/precedences/precedence/min-threshold-unit

    /configuration/qos/policy-map/*/policy-maps/policy-map/class-maps/class-map/random-detect/precedences/precedence/max-threshold-unit

    /configuration/qos/policy-map/*/policy-maps/policy-map/class-maps/class-default/random-detect/precedences/precedence/min-threshold-unit

    /configuration/qos/policy-map/*/policy-maps/policy-map/class-maps/class-default/random-detect/precedences/precedence/max-threshold-unit

    /configuration/qos/policy-map/*/policy-maps/policy-map/class-maps/class-map/police/cir-unit

    /configuration/qos/policy-map/*/policy-maps/policy-map/class-maps/class-map/police/cbs-unit

    /configuration/qos/policy-map/*/policy-maps/policy-map/class-maps/class-map/police/pir-pbs/pir-unit

    /configuration/qos/policy-map/*/policy-maps/policy-map/class-maps/class-map/police/pir-pbs/pbs-unit

    /configuration/qos/policy-map/*/policy-maps/policy-map/class-maps/class-default/police/cir-unit

    /configuration/qos/policy-map/*/policy-maps/policy-map/class-maps/class-default/police/cbs-unit

    /configuration/qos/policy-map/*/policy-maps/policy-map/class-maps/class-default/police/pir-pbs/pir-unit

    /configuration/qos/policy-map/*/policy-maps/policy-map/class-maps/class-default/police/pir-pbs/pbs-unit

    \"*\" means normal, car-action, phb-based, sub-interface-based, switch-fabric-based

    /configuration/qos/rate-limit/*s/*/cir-unit

    /configuration/qos/rate-limit/*s/*/pir-unit

    \"*\" means unicast, multicast, broadcast, unknown, localport, dscp, precedence, mpls-exp, inner-vlan,

    outer-vlan, multi-vlan, inner-8021p, outer-8021p, multi-8021p, qos-group, access-list

    3. Car supports the configuration of inner and outer MPLS-EXP:

    /configuration/qos/policy-map/car-action/policy-maps/policy-map/class-maps/class-map/police/conform-action/ca-mpls-exp/mpls-label-type

    /configuration/qos/policy-map/car-action/policy-maps/policy-map/class-maps/class-map/police/conform-action/ca-multi-exp-transmit

    /configuration/qos/policy-map/car-action/policy-maps/policy-map/class-maps/class-map/police/exceed-action/ea-mpls-exp/mpls-label-type

    /configuration/qos/policy-map/car-action/policy-maps/policy-map/class-maps/class-map/police/exceed-action/ea-multi-exp-transmit

    /configuration/qos/policy-map/car-action/policy-maps/policy-map/class-maps/class-map/police/violate-action/va-mpls-exp/mpls-label-type

    /configuration/qos/policy-map/car-action/policy-maps/policy-map/class-maps/class-map/police/violate-action/va-multi-exp-transmit

    /configuration/qos/policy-map/car-action/policy-maps/policy-map/class-maps/class-default/police/conform-action/ca-mpls-exp/mpls-label-type

    /configuration/qos/policy-map/car-action/policy-maps/policy-map/class-maps/class-default/police/conform-action/ca-multi-exp-transmit

    /configuration/qos/policy-map/car-action/policy-maps/policy-map/class-maps/class-default/police/exceed-action/ea-mpls-exp/mpls-label-type

    /configuration/qos/policy-map/car-action/policy-maps/policy-map/class-maps/class-default/police/exceed-action/ea-multi-exp-transmit

    /configuration/qos/policy-map/car-action/policy-maps/policy-map/class-maps/class-default/police/violate-action/va-mpls-exp/mpls-label-type

    /configuration/qos/policy-map/car-action/policy-maps/policy-map/class-maps/class-default/police/violate-action/va-multi-exp-transmit

    /configuration/qos/rate-limit/*s/*/conform-action/ca-mpls-exp/set-exp-transmit/mpls-label-type

    /configuration/qos/rate-limit/*s/*/conform-action/ca-multi-exp/set-multi-exp-transmit

    /configuration/qos/rate-limit/*s/*/exceed-action/ea-mpls-exp/set-exp-transmit/mpls-label-type

    /configuration/qos/rate-limit/*s/*/exceed-action/ea-multi-exp/set-multi-exp-transmit

    /configuration/qos/rate-limit/*s/*/violate-action/va-mpls-exp/set-exp-transmit/mpls-label-type

    /configuration/qos/rate-limit/*s/*/violate-action/va-multi-exp/set-multi-exp-transmit

    \"*\" means unicast, multicast, broadcast, unknown, localport, dscp, precedence, mpls-exp, inner-vlan,

    outer-vlan, multi-vlan, inner-8021p, outer-8021p, multi-8021p, qos-group, access-list

    4. Modify the configuration of switch-fabrics:

    /configuration/qos/switch-fabrics/normals/normal

    /configuration/qos/switch-fabrics/subslots/subslot

    /configuration/qos/switch-fabrics/subslots/group1s/group1

    /configuration/qos/switch-fabrics/subslots/group2s/group2

    /configuration/qos/switch-fabrics/subslots/ports/port

    5. Modify the configuration of qos-dot1p, support cvlan-out, add new nodes as follow:

    /configuration/qos/qos-dot1p/cvlan-outs/cvlan-outs" ;
  }

  revision 2014-04-30 {
    description 'Initial version' ;
  }

  feature phb-mode {
    description 'Support configuration H-QoS class and policy map related based on the pattern of PHB' ;
  }

  feature sub-interface-mode {
    description 'Support configuration H-QoS class and policy map related based on the pattern of sub-interface' ;
  }

  feature switch-fabric-mode {
    description 'Support configuration H-QoS class and policy map related based on the pattern of switch-fabric' ;
  }

  feature car-action-mode {
    description 'Support configuration H-QoS policy map related based on the pattern of car-action' ;
  }

  feature normal-mode {
    description 'Support configuration H-QoS class and policy map related based on normal pattern' ;
  }

  feature diffserv {
    description 'Support the configuration of differentiated Services' ;
  }

  feature qos-ds-domains {
    description 'Configure the used diffserv domain template' ;
  }

  feature qos-prioritys {
    description 'Configure the type of priority trusted by QoS' ;
  }

  feature qos-schedule {
    description 'Support scheduling policy for a certain transmitting entity' ;
  }

  feature switch-fabric {
    description 'Configure H-QoS switch fabric policy bind' ;
  }

  feature traffic-shape {
    description 'Support configuration traffic shape related' ;
  }

  feature service-policy {
    description 'Support configuration about binding H-QoS policys to the interface' ;
  }

  feature class-match-dscp-ex {
    description 'Support to set DSCP value as match criteria in PHB mode' ;
  }

  feature class-match-link-acl {
    description 'Support to configure link ACL as match criteria' ;
  }

  feature class-match-protocol {
    description 'Support to configure DPI protocol as match criteria' ;
  }

  feature policy-action-drop {
    description 'Support to configure policy action, such as drop' ;
  }

  feature policy-action-shape {
    description 'Support to configure policy action, such as shape' ;
  }

  feature policy-action-wred-color {
    description 'Support to configure policy action, such as WRED based on color' ;
  }

  feature policy-action-set-label {
    description 'Support to configure policy action, such as set, specify MPLS-EXP label position' ;
  }

  feature policy-action-set-multi-exp {
    description 'Support to configure policy action, such as set multiple MPLS-EXP' ;
  }

  feature qos-car-mode {
    description 'Support color mode information, such as Color-Blind and Color-Aware mode' ;
  }

  feature qos-vni-instance {
    description 'Support configuration about binding H-QoS policys to the vni-instance' ;
  }

  feature traffic-shape-dir {
    description 'Support configuration interface traffic shape on the specific direction' ;
  }

  feature qos-prioritys-remark {
    description 'Configure the type of priority remarked by QoS' ;
  }

  feature policy-action-rediret-route-map {
    description 'Support to configure policy action, such as redirect route-map' ;
  }

  feature policy-action-redirect-nsh {
    description 'Support to configure policy action, such as redirect nsh' ;
    ncd:revise-date 2024-09-02 ;
  }

  feature policy-action-vlan-stacking {
    description 'Support to configure policy action, such as vlan-stacking' ;
  }

  feature qos-global-prioritys-remark {
    description 'Configure the type of global priority and the global modification enable switch of QoS.' ;
  }

  feature ds-interf-priority-remark-enable {
    description 'Configure the interface priority modification is enabled or disable.' ;
  }

  feature car-buket-value-percent {
    description 'Support cir, pir, cbs and pbs, both in numerical form and percentage form.' ;
  }

  feature traffic-policy {
    description 'Support configuration about binding QoS policys to the interface' ;
  }

  feature qos-pw-ds-domains {
    description 'Configure the used diffserv domain template by PW interface.' ;
  }

  feature qos-if-slice-bw {
    status obsolete {
      ncd:revise-date 2023-06-16 ;
    }

    description 'Support to configure interface network slice and bandwidth.' ;
  }

  feature policy-action-wred-precedence-cachetime {
    description 'Support to configure policy action, such as cachetime of WRED based on precedence' ;
    ncd:revise-date 2021-11-19 ;
  }

  feature qos-stats-save {
    description 'Configuring the switch to store QoS statistics information.' ;
    ncd:revise-date 2022-03-10 ;
  }

  feature wred-template {
    ncd:revise-date 2022-06-27 ;
  }

  feature qos-queue-alarm {
    ncd:revise-date 2022-07-11 ;
  }

  feature schedule-te-reverse {
    description 'Support configuration of reverse direction TE schedule.' ;
    ncd:revise-date 2022-09-08 ;
  }

  feature policy-action-rediret-nexthop-srv6be {
    description 'Support to configure policy action, such as redirect next-hop srv6be.' ;
    ncd:revise-date 2022-09-26 ;
  }

  feature class-match-gre-ipp-inner-acl {
    description 'Support to configure IPv4 or IPv6 acl as match criteria of GRE or IPP inner layer.' ;
    ncd:revise-date 2022-10-09 ;
  }

  feature flowspec-if-group {
    ncd:revise-date 2022-10-10 ;
  }

  feature match-rocev2 {
    description 'Select fields of RoCEv2 packets as match criteria.' ;
    ncd:revise-date 2022-12-05 ;
  }

  feature rule-excess-effect {
    ncd:revise-date 2022-12-09 ;
  }

  feature phb-pmap-action-queue-limit {
    ncd:revise-date 2023-04-03 ;
  }

  feature qos-mark-if-priority {
    ncd:revise-date 2023-04-18 ;
  }

  feature qos-shape-unit {
    description 'Support shape rate unit.' ;
    ncd:revise-date 2023-06-20 ;
  }

  feature queue-depth-adaptive {
    description 'Support adaptive queue depth.' ;
    ncd:revise-date 2023-06-20 ;
  }

  feature hqos-stats-switch-status-off {
    ncd:revise-date 2023-07-03 ;
  }

  feature qos-stats-global-switch {
    ncd:revise-date 2023-07-03 ;
  }

  feature qos-queue-dwrr {
    description 'Support DWRR weight.' ;
    ncd:revise-date 2023-07-19 ;
  }

  feature qos-car-cf {
    description 'Support coupling flag information.' ;
    ncd:revise-date 2023-09-12 ;
  }

  feature qos-car-adjust {
    description 'Support adjustment information.' ;
    ncd:revise-date 2023-09-12 ;
  }

  feature qos-statistical-share-global {
    description 'Support QoS statistical share global information.' ;
    ncd:revise-date 2024-04-01 ;
  }

  feature qos-car-stats-if {
    description 'Support QoS IF-CAR flow statistics.' ;
    ncd:revise-date 2024-05-09 ;
  }

  feature rocev2-cnp-feature {
    description 'Select fields of RoCEv2 CNK packets as match criteria.' ;
    ncd:revise-date 2024-06-11 ;
  }

  feature rocev2-nak-feature {
    description 'Select fields of RoCEv2 NAK packets as match criteria.' ;
    ncd:revise-date 2024-06-11 ;
  }

  feature traffic-match-vrf {
    description 'Support to match vrf-name of traffic-based cmap.' ;
    ncd:revise-date 2024-07-17 ;
  }

  feature class-match-rocev2-udf {
    description 'Select fields of RoCEv2 user defined packets as match criteria.' ;
    ncd:revise-date 2025-02-11 ;
  }

  feature policy-ecmp-hash {
    description 'Select fields of policy-ecmp-hash mode.' ;
    ncd:revise-date 2025-03-10 ;
  }

  typedef qos-dscp-bitmap {
    type ncd:bitmap {
      pattern "(((((([1-9][0-9]{0,0})|0|([1-5][0-9]{1,1})|(6[0-2])|63)-(([1-9][0-9]{0,0})|0|([1-5][0-9]{1,1})|(6[0-2])|63))|(([1-9][0-9]{0,0})|0|([1-5][0-9]{1,1})|(6[0-2])|63)),){0,3}(((([1-9][0-9]{0,0})|0|([1-5][0-9]{1,1})|(6[0-2])|63)-(([1-9][0-9]{0,0})|0|([1-5][0-9]{1,1})|(6[0-2])|63))|(([1-9][0-9]{0,0})|0|([1-5][0-9]{1,1})|(6[0-2])|63)){1,1})" {
        description 'Configure DSCP in range mode, support single DSCP value or range(max num:4;spacing mark:,) in <0-63>.' ;
      }

    }

    description 'The definition of QoS dscp in range mode, support single DSCP value or range(max num:4;spacing mark:,) in <0-63>. For example,"6,10-30,40,50-60",etc.' ;
  }

  typedef qos-prec-bitmap {
    type ncd:bitmap {
      pattern "(((([0-7]-[0-7])|[0-7]),){0,3}(([0-7]-[0-7])|([0-7])){1,1})" {
        description 'Configure IP-Precedence in range mode, support single precedence value or range(max num:4;spacing mark:,) in <0-7>.' ;
      }

    }

    description 'The definition of QoS IP-Precedence in range mode, support single precedence value or range(max num:4;spacing mark:,) in <0-7>. For example,"0,4-7",etc.' ;
  }

  typedef qos-vlan-bitmap {
    type ncd:bitmap {
      pattern "(((((([1-9][0-9]{1,2})|([2-9][0-9]{0,0})|1|([1-3][0-9]{3,3})|(40[0-8][0-9]{1,1})|(409[0-3])|4094)-(([1-9][0-9]{1,2})|([2-9][0-9]{0,0})|1|([1-3][0-9]{3,3})|(40[0-8][0-9]{1,1})|(409[0-3])|4094))|(([1-9][0-9]{1,2})|([2-9][0-9]{0,0})|1|([1-3][0-9]{3,3})|(40[0-8][0-9]{1,1})|(409[0-3])|4094)),){0,3}(((([1-9][0-9]{1,2})|([2-9][0-9]{0,0})|1|([1-3][0-9]{3,3})|(40[0-8][0-9]{1,1})|(409[0-3])|4094)-(([1-9][0-9]{1,2})|([2-9][0-9]{0,0})|1|([1-3][0-9]{3,3})|(40[0-8][0-9]{1,1})|(409[0-3])|4094))|(([1-9][0-9]{1,2})|([2-9][0-9]{0,0})|1|([1-3][0-9]{3,3})|(40[0-8][0-9]{1,1})|(409[0-3])|4094)){1,1})" {
        description 'Configure VLAN in range mode, support single VLAN value or range(max num:4;spacing mark:,) in <1-4094>.' ;
      }

    }

    description 'The definition of QoS VLAN in range mode, support single VLAN value or range(max num:4;spacing mark:,) in <1-4094>. For example,"1-300,400,450-500",etc.' ;
  }

  typedef qos-mpls-bitmap {
    type ncd:bitmap {
      pattern "(((([0-7]-[0-7])|[0-7]),){0,3}(([0-7]-[0-7])|([0-7])){1,1})" {
        description 'Configure MPLS-EXP in range mode, support single MPLS-EXP value or range(max num:4;spacing mark:,) in <0-7>.' ;
      }

    }

    description 'The definition of QoS MPLS-EXP in range mode, support single MPLS-EXP value or range(max num:4;spacing mark:,) in <0-7>. For example,"0,3-5,7",etc.' ;
  }

  typedef qos-8021p-bitmap {
    type ncd:bitmap {
      pattern "(((([0-7]-[0-7])|[0-7]),){0,3}(([0-7]-[0-7])|([0-7])){1,1})" {
        description 'Configure 802.1p in range mode, support single 802.1p value or range(max num:4;spacing mark:,) in <0-7>.' ;
      }

    }

    description 'The definition of QoS 802.1p in range mode, support single 802.1p value or range(max num:4;spacing mark:,) in <0-7>. For example,"0,3-5,7",etc.' ;
  }

  typedef qos-vlan-range {
    type ncd:range {
      pattern "(((((([1-9][0-9]{1,2})|([2-9][0-9]{0,0})|1|([1-3][0-9]{3,3})|(40[0-8][0-9]{1,1})|(409[0-3])|4094)-(([1-9][0-9]{1,2})|([2-9][0-9]{0,0})|1|([1-3][0-9]{3,3})|(40[0-8][0-9]{1,1})|(409[0-3])|4094))|(([1-9][0-9]{1,2})|([2-9][0-9]{0,0})|1|([1-3][0-9]{3,3})|(40[0-8][0-9]{1,1})|(409[0-3])|4094)),){0,3}(((([1-9][0-9]{1,2})|([2-9][0-9]{0,0})|1|([1-3][0-9]{3,3})|(40[0-8][0-9]{1,1})|(409[0-3])|4094)-(([1-9][0-9]{1,2})|([2-9][0-9]{0,0})|1|([1-3][0-9]{3,3})|(40[0-8][0-9]{1,1})|(409[0-3])|4094))|(([1-9][0-9]{1,2})|([2-9][0-9]{0,0})|1|([1-3][0-9]{3,3})|(40[0-8][0-9]{1,1})|(409[0-3])|4094)){1,1})" {
        description 'Configure VLAN in range mode, support single VLAN value or range(max num:4;spacing mark:,) in <1-4094>.' ;
      }

    }

    description 'The definition of QoS VLAN in range mode, support single VLAN value or range(max num:4;spacing mark:,) in <1-4094>. For example,"1-300,400,450-500",etc.' ;
  }

  typedef qos-service-class {
    type enumeration {
      enum be {
        value 1 ;
        description 'Best effort' ;
      }

      enum af1 {
        value 2 ;
        description 'Assured forwarding class 1' ;
      }

      enum af2 {
        value 3 ;
        description 'Assured forwarding class 2' ;
      }

      enum af3 {
        value 4 ;
        description 'Assured forwarding class 3' ;
      }

      enum af4 {
        value 5 ;
        description 'Assured forwarding class 4' ;
      }

      enum ef {
        value 6 ;
        description 'Expedited forward' ;
      }

      enum cs6 {
        value 7 ;
        description 'Internetwork control service class' ;
      }

      enum cs7 {
        value 8 ;
        description 'Network control service class' ;
      }

    }

    description 'The definition of server class of PHB info, see below:
             be (1) Best effort
             af1(2) Assured forwarding class 1
             af2(3) Assured forwarding class 2
             af3(4) Assured forwarding class 3
             af4(5) Assured forwarding class 4
             ef (6) Expedited forward
             cs6(7) Internetwork control service class
             cs7(8) Network control service class' ;
  }

  typedef qos-color-type {
    type enumeration {
      enum green {
        value 1 ;
        description 'Green packets' ;
      }

      enum yellow {
        value 2 ;
        description 'Yellow packets' ;
      }

      enum red {
        value 3 ;
        description 'Red packets' ;
      }

    }

    description 'The definition of color type of PHB info, see below:
             green  (1) Green packets
             yellow (2) Yellow packets
             red    (3) Red packets' ;
  }

  typedef qos-reserved-words {
    type enumeration {
      enum default {
        value 0 ;
        description 'Match packets with default dscp (000000)' ;
      }

      enum af11 {
        value 10 ;
        description 'Match packets with AF11 dscp (001010)' ;
      }

      enum af12 {
        value 12 ;
        description 'Match packets with AF12 dscp (001100)' ;
      }

      enum af13 {
        value 14 ;
        description 'Match packets with AF13 dscp (001110)' ;
      }

      enum af21 {
        value 18 ;
        description 'Match packets with AF21 dscp (010010)' ;
      }

      enum af22 {
        value 20 ;
        description 'Match packets with AF22 dscp (010100)' ;
      }

      enum af23 {
        value 22 ;
        description 'Match packets with AF23 dscp (010110)' ;
      }

      enum af31 {
        value 26 ;
        description 'Match packets with AF31 dscp (011010)' ;
      }

      enum af32 {
        value 28 ;
        description 'Match packets with AF32 dscp (011100)' ;
      }

      enum af33 {
        value 30 ;
        description 'Match packets with AF33 dscp (011110)' ;
      }

      enum af41 {
        value 34 ;
        description 'Match packets with AF41 dscp (100010)' ;
      }

      enum af42 {
        value 36 ;
        description 'Match packets with AF42 dscp (100100)' ;
      }

      enum af43 {
        value 38 ;
        description 'Match packets with AF43 dscp (100110)' ;
      }

      enum ef {
        value 46 ;
        description 'Match packets with EF dscp (101110)' ;
      }

      enum cs1 {
        value 8 ;
        description 'Match packets with CS1(precedence 1) dscp (001000)' ;
      }

      enum cs2 {
        value 16 ;
        description 'Match packets with CS2(precedence 2) dscp (010000)' ;
      }

      enum cs3 {
        value 24 ;
        description 'Match packets with CS3(precedence 3) dscp (011000)' ;
      }

      enum cs4 {
        value 32 ;
        description 'Match packets with CS4(precedence 4) dscp (100000)' ;
      }

      enum cs5 {
        value 40 ;
        description 'Match packets with CS5(precedence 5) dscp (101000)' ;
      }

      enum cs6 {
        value 48 ;
        description 'Match packets with CS6(precedence 6) dscp (110000)' ;
      }

      enum cs7 {
        value 56 ;
        description 'Match packets with CS7(precedence 7) dscp (111000)' ;
      }

    }

    description 'The definition of resserved words of DSCP info ,see below:
      default(0) Match packets with default dscp (000000)      
      af11(10)   Match packets with AF11 dscp (001010)                                
      af12(12)   Match packets with AF12 dscp (001100)                                
      af13(14)   Match packets with AF13 dscp (001110)                                
      af21(18)   Match packets with AF21 dscp (010010)                                
      af22(20)   Match packets with AF22 dscp (010100)                                
      af23(22)   Match packets with AF23 dscp (010110)                                
      af31(26)   Match packets with AF31 dscp (011010)                                
      af32(28)   Match packets with AF32 dscp (011100)                                
      af33(30)   Match packets with AF33 dscp (011110)                                
      af41(34)   Match packets with AF41 dscp (100010)                                
      af42(36)   Match packets with AF42 dscp (100100)                                
      af43(38)   Match packets with AF43 dscp (100110)   
      ef(46)     Match packets with EF dscp (101110)                             
      cs1(8)     Match packets with CS1(precedence 1) dscp (001000)                   
      cs2(16)    Match packets with CS2(precedence 2) dscp (010000)                   
      cs3(24)    Match packets with CS3(precedence 3) dscp (011000)                   
      cs4(32)    Match packets with CS4(precedence 4) dscp (100000)                   
      cs5(40)    Match packets with CS5(precedence 5) dscp (101000)                   
      cs6(48)    Match packets with CS6(precedence 6) dscp (110000)                   
      cs7(56)    Match packets with CS7(precedence 7) dscp (111000)' ;
  }

  typedef qos-ip-type {
    type enumeration {
      enum any {
        value 0 ;
        description 'Based on any IP' ;
      }

      enum ipv4 {
        value 1 ;
        description 'Based on IPv4' ;
      }

      enum ipv6 {
        value 2 ;
        description 'Based on IPv6' ;
      }

    }

    description 'Configure based on IP, see below:
      any  Packets based on any IP;
      ipv4 Packets based on IPv4;
      ipv6 Packets based on IPv6;' ;
  }

  typedef qos-rate-unit-type {
    type enumeration {
      enum kbps {
        value 1 ;
        description 'Kilobits per second' ;
      }

      enum mbps {
        value 2 ;
        description 'Megabits per second' ;
      }

      enum gbps {
        value 3 ;
        description 'Gigabits per second' ;
      }

    }

    description 'The definition of rate unit of police car info, see below:
             kbps  (1) Kilobits per second
             mbps  (2) Megabits per second
             gbps  (3) Gigabits per second' ;
  }

  typedef qos-bucket-unit-type {
    type enumeration {
      enum kb {
        value 1 ;
        description 'Kilobits' ;
      }

      enum mb {
        value 2 ;
        description 'Megabits' ;
      }

      enum gb {
        value 3 ;
        description 'Gigabits' ;
      }

    }

    description 'The definition of bucket unit of police car info, see below:
             kb  (1) Kilobyte
             mb  (2) Megabyte
             gb  (3) Gigabyte' ;
  }

  typedef qos-threshold-unit-type {
    type enumeration {
      enum kbytes {
        value 1 ;
        description 'Kilobytes' ;
      }

      enum mbytes {
        value 2 ;
        description 'Megabytes' ;
      }

      enum gbytes {
        value 3 ;
        description 'Gigabytes' ;
      }

    }

    description 'The definition of threshold unit of wred info, see below:
             kb  (1) Kilobytes
             mb  (2) Megabytes
             gb  (3) Gigabytes' ;
  }

  typedef qos-direction {
    type enumeration {
      enum input {
        value 1 ;
        description 'input  Attaches to the input flow' ;
      }

      enum output {
        value 2 ;
        description 'output Attaches to the output flow' ;
      }

    }

    description 'The flow direction, as follows,
     input  Attaches to the input flow
     output Attaches to the output flow' ;
  }

  typedef qos-port-range {
    type ncd:range {
      pattern "(((((([1-9][0-9]{1,3})|([1-9][0-9]{0,0})|0|([1-5][0-9]{4,4})|(6[0-4][0-9]{3,3})|(65[0-4][0-9]{2,2})|(655[0-2][0-9]{1,1})|(6553[0-4])|65535)-(([1-9][0-9]{1,3})|([1-9][0-9]{0,0})|0|([1-5][0-9]{4,4})|(6[0-4][0-9]{3,3})|(65[0-4][0-9]{2,2})|(655[0-2][0-9]{1,1})|(6553[0-4])|65535))|(([1-9][0-9]{1,3})|([1-9][0-9]{0,0})|0|([1-5][0-9]{4,4})|(6[0-4][0-9]{3,3})|(65[0-4][0-9]{2,2})|(655[0-2][0-9]{1,1})|(6553[0-4])|65535)),){0,3}(((([1-9][0-9]{1,3})|([1-9][0-9]{0,0})|0|([1-5][0-9]{4,4})|(6[0-4][0-9]{3,3})|(65[0-4][0-9]{2,2})|(655[0-2][0-9]{1,1})|(6553[0-4])|65535)-(([1-9][0-9]{1,3})|([1-9][0-9]{0,0})|0|([1-5][0-9]{4,4})|(6[0-4][0-9]{3,3})|(65[0-4][0-9]{2,2})|(655[0-2][0-9]{1,1})|(6553[0-4])|65535))|(([1-9][0-9]{1,3})|([1-9][0-9]{0,0})|0|([1-5][0-9]{4,4})|(6[0-4][0-9]{3,3})|(65[0-4][0-9]{2,2})|(655[0-2][0-9]{1,1})|(6553[0-4])|65535)){1,1})" {
        description 'Configure port in range mode, support single port value or range(max num:4;spacing mark:,) in <0-65535>.' ;
      }

    }

    description 'The definition of port in range mode, support single port value or range(max num:4;spacing mark:,) in <0-65535>. For example,"1-300,400,450-500",etc.' ;
  }

  typedef qos-rate-unit-type-ex {
    type enumeration {
      enum kbps {
        value 1 ;
        description 'Kilobits per second' ;
      }

      enum mbps {
        value 2 ;
        description 'Megabits per second' ;
      }

      enum gbps {
        value 3 ;
        description 'Gigabits per second' ;
      }

      enum pps {
        value 4 ;
        description 'Packets per second' ;
      }

    }

    description 'The definition of rate unit of police car info, see below:
             kbps  (1) Kilobits per second
             mbps  (2) Megabits per second
             gbps  (3) Gigabits per second
             pps   (4) Packets per second' ;
  }

  typedef qos-phb-bitmap {
    type ncd:bitmap {
      pattern "(((([0-7]-[0-7])|[0-7]),){0,3}(([0-7]-[0-7])|([0-7])){1,1})" {
        description 'Configure phb in range mode, support single phb value or range(max num:4;spacing mark:,) in <0-7>.' ;
      }

    }

    description 'The definition of phb in range mode, support single phb value or range(max num:4;spacing mark:,) in <0-7>. For example,"0,4-7",etc.' ;
  }

  typedef qos-stats-switch-status {
    type enumeration {
      enum on {
        value 0 ;
        description 'Switch on' ;
      }

    }

    description 'Swtich status:
  0: swtich on.' ;
  }

  typedef hqos-stats-switch-status {
    type enumeration {
      enum on {
        value 1 ;
        description 'Switch on' ;
      }

      enum off {
        value 3 ;
        description 'Switch off' ;
      }

    }

    description 'Swtich status:
  1: swtich on.
  3: swtich off.' ;
  }

  typedef qos-stats-global-switch-status {
    type enumeration {
      enum on {
        value 1 ;
        description 'Switch on' ;
      }

    }

    description 'Switch status:
  1: switch on.' ;
  }

  typedef if-car-stats-clear-match-type {
    type enumeration {
      enum localport {
        description 'match localport.' ;
        value 1 ;
      }

      enum ipv4-access-list {
        value 5 ;
        description 'match IPv4 ACL.' ;
      }

      enum ipv6-access-list {
        description 'match IPv6 ACL.' ;
        value 6 ;
      }

      enum link-access-list {
        value 15 ;
        description 'match link ACL.' ;
      }

    }

    description 'IF-CAR match type:
  1: localport.
  5: ipv4-access-list.
  6: ipv6-access-list.
  15: link-access-list.' ;
  }

  container configuration {
    description 'Configuration information.' ;
    container qos {
      description 'Configuration about QoS.' ;
      container class-map {
        description 'Configure QoS class map.' ;
        container normal {
          if-feature normal-mode ;

          description 'Class map based on normal.' ;
          container class-maps {
            description 'Configure H-QoS class map lists.' ;
            list class-map {
              description 'Configure H-QoS class map list.' ;
              key cmap-name ;
              leaf cmap-name {
                description 'Name of the class map, support 1-31 characters.' ;
                type string {
                  length 1..31 {
                    description 'Name of the class map, support 1-31 characters' ;
                  }

                }

              }

              leaf match-relation {
                description 'The type of packets matching, see bellow:
match-all Packets meet all of the match criteria;
match-any Packets meet any of the match criteria.' ;
                type enumeration {
                  enum match-all {
                    value 1 ;
                    description 'Packets meet all of the match criteria' ;
                  }

                  enum match-any {
                    value 2 ;
                    description 'Packets meet any of the match criteria' ;
                  }

                }

                mandatory true ;
              }

              container service-type {
                description 'The same value represents the same class-map.' ;
                presence "To set the service type value" ;
                leaf service-type {
                  description 'The same service type value represents the same class-map.' ;
                  type uint32 {
                    range 1..255 {
                      description 'The same service type value represents the same class-map.' ;
                    }

                  }

                  mandatory true ;
                }

                container effect-order {
                  description 'The value specify the class effect order in the policy map.' ;
                  presence "To set the effect order value" ;
                  leaf effect-order {
                    description 'The value specify the class effect order in the policy map.' ;
                    type uint32 {
                      range 1..255 {
                        description 'The value specify the class effect order in the policy map.' ;
                      }

                    }

                    mandatory true ;
                  }

                }

                ncd:revise-date 2017-06-12 ;
              }

              container match {
                description 'Configure matching criteria for a class map.' ;
                container dscps {
                  description 'Select DSCP as matching criteria.' ;
                  list dscp {
                    description 'Set DSCP as matching criteria.' ;
                    key ip-type ;
                    leaf ip-type {
                      description 'Configure DSCP value Based on IP, see below:
any  Packets based on any IP;
ipv4 Packets based on IPv4;
ipv6 Packets based on IPv6.' ;
                      type qos-ip-type ;

                    }

                    leaf not {
                      description 'Configure the opposite range flag:
true  Match opposite range;
false Match current range.' ;
                      type boolean ;

                      default false ;
                    }

                    leaf dscp-value {
                      description 'Configure QoS dscp in range mode, support single DSCP value or range(max num:4;spacing mark:,) in <0-63>. For example,"6,10-30,40,50-60",etc.' ;
                      type qos-dscp-bitmap ;

                      mandatory true ;
                    }

                  }

                }

                container dscp-exs {
                  if-feature class-match-dscp-ex ;

                  description 'Select the identification code mapped from DSCP to PHB (Per Hop Behavior), that is, reserve keywords as matching criteria.' ;
                  list dscp-ex {
                    description 'Set  the reserved keyword as matching criteria.' ;
                    key 'ip-type reserved-words' ;
                    leaf ip-type {
                      description 'Configure DSCP value Based on IP, see below:
any  Packets based on any IP;
ipv4 Packets based on IPv4;
ipv6 Packets based on IPv6.' ;
                      type qos-ip-type ;

                    }

                    leaf reserved-words {
                      description 'Configure the reserved keyword.' ;
                      type qos-reserved-words ;

                    }

                  }

                }

                container precedences {
                  description 'Select IP-Precedence as matching criteria.' ;
                  list precedence {
                    description 'Set IP Precedence value as matching criteria.' ;
                    key ip-type ;
                    leaf ip-type {
                      description 'Configure DSCP value Based on IP, see below:
any  Packets based on any IP;
ipv4 Packets based on IPv4;
ipv6 Packets based on IPv6.' ;
                      type qos-ip-type ;

                    }

                    leaf not {
                      description 'Configure the opposite range flag:
true  Match opposite range;
false Match current range.' ;
                      type boolean ;

                      default false ;
                    }

                    leaf prec-value {
                      description 'Configure QoS IP Precedence in range mode, support single precedence value or range(max num:4;spacing mark:,) in <0-7>. For example,"0,2-4,7",etc.' ;
                      type qos-prec-bitmap ;

                      mandatory true ;
                    }

                  }

                }

                container mpls-exp {
                  description 'Select MPLS-EXP as matching criteria.' ;
                  presence "Select MPLS-EXP as match criteria" ;
                  leaf mpls-exp-value {
                    description 'Configure QoS MPLS-EXP value in range mode, support single MPLS-EXP value or range(max num:4;spacing mark:,) in <0-7>. For example,"0,2-4,7",etc.' ;
                    type qos-mpls-bitmap ;

                    mandatory true ;
                  }

                }

                container in-vlan {
                  description 'Select inner-VLAN as matching criteria.' ;
                  presence "Select inner-VLAN as match criteria" ;
                  leaf vlan-value {
                    description 'Configure inner-VLAN value in range mode, support single inner-VLAN value or range(max num:4;spacing mark:,) in <1-4094>. For example,"1,300-400,1000,2000-4000",etc.' ;
                    type qos-vlan-bitmap ;

                    mandatory true ;
                  }

                }

                container out-vlan {
                  description 'Select outer-VLAN as matching criteria.' ;
                  presence "Select outer-VLAN as match criteria" ;
                  leaf vlan-value {
                    description 'Configure outer-VLAN value in range mode, support single outer-VLAN value or range(max num:4;spacing mark:,) in <1-4094>. For example,"1,300-400,1000,2000-4000",etc.' ;
                    type qos-vlan-bitmap ;

                    mandatory true ;
                  }

                }

                container in-8021p {
                  description 'Select inner 802.1p as matching criteria.' ;
                  presence "Select inner 802.1p as match criteria" ;
                  leaf in-8021p-value {
                    description 'Configure inner 802.1p value in range mode, support single 802.1p value or range(max num:4;spacing mark:,) in <0-7>. For example,"0,2-4,7",etc.' ;
                    type qos-8021p-bitmap ;

                    mandatory true ;
                  }

                }

                container out-8021p {
                  description 'Select outer 802.1p as matching criteria.' ;
                  presence "Select outer 802.1p as match criteria" ;
                  leaf out-8021p-value {
                    description 'Configure outer 802.1p value in range mode, support single 802.1p value or range(max num:4;spacing mark:,) in <0-7>. For example,"0,2-4,7",etc.' ;
                    type qos-8021p-bitmap ;

                    mandatory true ;
                  }

                }

                container qos-group {
                  description 'Select qos-group as matching criteria.' ;
                  presence "Select qos-group as match criteria" ;
                  leaf qos-id {
                    description 'Set qos-group number, support <1-65535>.' ;
                    type uint16 {
                      range 1..65535 ;

                    }

                    mandatory true ;
                  }

                }

                container vrf-name {
                  description 'Select vrf-name as matching criteria.' ;
                  presence "Select vrf-name as match criteria" ;
                  leaf vrf-name {
                    description 'Set vrf name, support 1-32 characters.' ;
                    type string {
                      length 1..32 {
                        description 'Vrf name, support 1-32 characters' ;
                      }

                    }

                    mandatory true ;
                  }

                }

                container uni-cast {
                  description 'Select unicast as matching criteria.' ;
                  presence "Select unicast as match criteria" ;
                  leaf uni-cast {
                    description 'Set unicast.' ;
                    type empty ;

                    mandatory true ;
                  }

                }

                container multi-cast {
                  description 'Select multicast as matching criteria.' ;
                  presence "Select multicast as match criteria" ;
                  leaf multi-cast {
                    description 'Set multicast.' ;
                    type empty ;

                    mandatory true ;
                  }

                }

                container mac-addr {
                  description 'Select mac-address as matching criteria.' ;
                  presence "Select mac-address as match criteria" ;
                  leaf mac-address {
                    description 'Configure mac-address.' ;
                    type ncd:mac-address ;

                    mandatory true ;
                  }

                }

                container child {
                  description 'Set the mark of null class.' ;
                  presence "Set the mark of null class" ;
                  leaf child {
                    description 'Set the mark of null class.' ;
                    type empty ;

                    mandatory true ;
                  }

                }

                container ipv4-acls {
                  description 'Select IPv4 ACL name as matching criteria.' ;
                  list ipv4-acl {
                    description 'Set IPv4 ACL name as matching criteria.' ;
                    key acl-name ;
                    leaf acl-name {
                      description 'Set ipv4-access-list name, support 1-31 characters.' ;
                      type string {
                        length 1..31 {
                          description 'Name of ACL, support 1-31 characters' ;
                        }

                      }

                    }

                  }

                }

                container ipv6-acls {
                  description 'Select IPv6 ACL name as matching criteria.' ;
                  list ipv6-acl {
                    description 'Set IPv6 ACL name as matching criteria.' ;
                    key acl-name ;
                    leaf acl-name {
                      description 'Set ipv6-access-list name, support 1-31 characters.' ;
                      type string {
                        length 1..31 {
                          description 'Name of ACL, support 1-31 characters' ;
                        }

                      }

                    }

                  }

                }

                container link-acls {
                  if-feature class-match-link-acl ;

                  description 'Select link ACL name as matching criteria.' ;
                  list link-acl {
                    description 'Set link ACL name as matching criteria.' ;
                    key acl-name ;
                    leaf acl-name {
                      description 'Set link-access-list name, support 1-31 characters.' ;
                      type string {
                        length 1..31 {
                          description 'Name of ACL, support 1-31 characters' ;
                        }

                      }

                    }

                  }

                }

                container vpws {
                  description 'Select VPWS instance name as matching criteria.' ;
                  presence "Select VPWS instance name as match criteria" ;
                  leaf vpws-name {
                    description 'Set VPWS instance name, support 1-32 characters.' ;
                    type string {
                      length 1..32 {
                        description 'VPWS instance name, support 1-32 characters' ;
                      }

                    }

                    mandatory true ;
                  }

                }

                container vpls {
                  description 'Select VPLS instance name as matching criteria.' ;
                  presence "Select VPLS instance name as match criteria" ;
                  leaf vpls-name {
                    description 'Set VPLS instance name, support 1-32 characters.' ;
                    type string {
                      length 1..32 {
                        description 'VPLS instance name, support 1-32 characters' ;
                      }

                    }

                    mandatory true ;
                  }

                }

                container service-class {
                  if-feature phb-mode ;

                  description 'Select PHB as matching criteria.' ;
                  presence "Select PHB as match criteria" ;
                  choice value-or-range {
                    description 'Select PHB value or range as matching criteria.' ;
                    case value {
                      description 'Select PHB value as matching criteria.' ;
                      leaf service-class {
                        description 'Select service class of PHB info.' ;
                        type qos-service-class ;

                        mandatory true ;
                      }

                    }

                    case range {
                      description 'Select PHB range as matching criteria.' ;
                      container range {
                        description 'Select PHB range as matching criteria.' ;
                        leaf service-class-range {
                          description 'Configure service class in range mode, support value or range(max num:4;spacing mark:,) in <0-7>. For example,"0,2-4,7",etc.' ;
                          type qos-phb-bitmap ;

                          mandatory true ;
                        }

                      }

                      ncd:revise-date 2021-01-18 ;
                    }

                  }

                }

                container protocol {
                  if-feature class-match-protocol ;

                  description 'Select protocol as matching criteria.' ;
                  container unclassifieds {
                    description 'Match unclassified category.' ;
                    list unclassified {
                      description 'Set protocol in unclassified category.' ;
                      key prodpi-id ;
                      leaf prodpi-id {
                        description 'Set protocol in unclassified category.' ;
                        type enumeration {
                          enum unknown {
                            value 1 ;
                            description 'Unclassified category, UNKNOWN, PID 1' ;
                          }

                        }

                      }

                    }

                  }

                  container emails {
                    description 'Match electronic mail category.' ;
                    list email {
                      description 'Select protocol in electronic mail category.' ;
                      key prodpi-id ;
                      leaf prodpi-id {
                        description 'Set protocol in electronic mail category.' ;
                        type enumeration {
                          enum pop3 {
                            value 2 ;
                            description 'EMAIL category, POP3, PID 2' ;
                          }

                          enum smtp {
                            value 13 ;
                            description 'EMAIL category, SMTP, PID 13' ;
                          }

                          enum smtp-ssl {
                            value 15 ;
                            description 'EMAIL category, SMTP-SSL, PID 15' ;
                          }

                          enum imap {
                            value 16 ;
                            description 'EMAIL category, IMAP, PID 16' ;
                          }

                          enum imap-ssl {
                            value 308 ;
                            description 'EMAIL category, IMAP-SSL, PID 308' ;
                          }

                          enum pop3-ssl {
                            value 310 ;
                            description 'EMAIL category, POP3-SSL, PID 310' ;
                          }

                        }

                      }

                    }

                  }

                  container ims {
                    description 'Match instant messaging category.' ;
                    list im {
                      description 'Select protocol in instant messaging category.' ;
                      key prodpi-id ;
                      leaf prodpi-id {
                        description 'Set protocol in instant messaging category.' ;
                        type enumeration {
                          enum gtalk {
                            value 4 ;
                            description 'IM category, GTALK, PID 4' ;
                          }

                          enum ali-wangwang {
                            value 21 ;
                            description 'IM category, ALI-WANGWANG, PID 21' ;
                          }

                          enum msn {
                            value 35 ;
                            description 'IM category, MSN, PID 35' ;
                          }

                          enum yahoo-messenger {
                            value 92 ;
                            description 'IM category, YAHOO-MESSENGER, PID 92' ;
                          }

                          enum qq {
                            value 107 ;
                            description 'IM category, QQ, PID 107' ;
                          }

                          enum fetion {
                            value 239 ;
                            description 'IM category, FETION, PID 239' ;
                          }

                        }

                      }

                    }

                  }

                  container terminals {
                    description 'Match terminal category.' ;
                    list terminal {
                      description 'Select protocol in terminal category.' ;
                      key prodpi-id ;
                      leaf prodpi-id {
                        description 'Set protocol in terminal category.' ;
                        type enumeration {
                          enum ssh {
                            value 39 ;
                            description 'TERMINAL category, SSH, PID 39' ;
                          }

                          enum telnet {
                            value 47 ;
                            description 'TERMINAL category, TELNET, PID 47' ;
                          }

                          enum ms-rdp {
                            value 101 ;
                            description 'TERMINAL category, MS-RDP, PID 101' ;
                          }

                        }

                      }

                    }

                  }

                  container networks {
                    description 'Match network category.' ;
                    list network {
                      description 'Select protocol in network category.' ;
                      key prodpi-id ;
                      leaf prodpi-id {
                        description 'Set protocol in network category,.' ;
                        type enumeration {
                          enum netbios {
                            value 53 ;
                            description 'NETWORK category, NETBIOS, PID 53' ;
                          }

                          enum ntp {
                            value 86 ;
                            description 'NETWORK category, NTP, PID 86' ;
                          }

                          enum syslog {
                            value 91 ;
                            description 'NETWORK category, SYSLOG, PID 91' ;
                          }

                          enum radius {
                            value 100 ;
                            description 'NETWORK category, RADIUS, PID 100' ;
                          }

                          enum dns {
                            value 109 ;
                            description 'NETWORK category, DNS, PID 109' ;
                          }

                          enum snmp {
                            value 185 ;
                            description 'NETWORK category, SNMP, PID 185' ;
                          }

                        }

                      }

                    }

                  }

                  container p2ps {
                    description 'Match peer-to-peer category.' ;
                    list p2p {
                      description 'Select protocol in peer-to-peer category.' ;
                      key prodpi-id ;
                      leaf prodpi-id {
                        description 'Set protocol in peer-to-peer category.' ;
                        type enumeration {
                          enum edk {
                            value 83 ;
                            description 'P2P category, EDK, PID 83' ;
                          }

                          enum bt {
                            value 94 ;
                            description 'P2P category, BT, PID 94' ;
                          }

                          enum thunder {
                            value 96 ;
                            description 'P2P category, THUNDER, PID 96' ;
                          }

                          enum kad {
                            value 97 ;
                            description 'P2P category, KAD, PID 97' ;
                          }

                          enum qq-download {
                            value 105 ;
                            description 'P2P category, QQ-DOWNLOAD, PID 105' ;
                          }

                          enum dht {
                            value 169 ;
                            description 'P2P category, DHT, PID 169' ;
                          }

                          enum web-thunder {
                            value 234 ;
                            description 'P2P category, WEB-THUNDER, PID 234' ;
                          }

                        }

                      }

                    }

                  }

                  container webs {
                    description 'Match world wide web category.' ;
                    list web {
                      description 'Select protocol in world wide web category.' ;
                      key prodpi-id ;
                      leaf prodpi-id {
                        description 'Set protocol in world wide web category.' ;
                        type enumeration {
                          enum http {
                            value 48 ;
                            description 'WEB category, HTTP, PID 48' ;
                          }

                          enum http-range {
                            value 49 ;
                            description 'WEB category, HTTP-RANGE, PID 49' ;
                          }

                          enum http-proxy {
                            value 50 ;
                            description 'WEB category, HTTP-PROXY, PID 50' ;
                          }

                          enum http-download {
                            value 51 ;
                            description 'WEB category, HTTP-DOWNLOAD, PID 51' ;
                          }

                        }

                      }

                    }

                  }

                  container filetrans {
                    description 'Match file transfer category.' ;
                    list filetran {
                      description 'Select protocol in file transfer category.' ;
                      key prodpi-id ;
                      leaf prodpi-id {
                        description 'Set protocol in file transfer category.' ;
                        type enumeration {
                          enum smb {
                            value 54 ;
                            description 'FILETRANS category, SMB, PID 54' ;
                          }

                          enum tftp-control {
                            value 66 ;
                            description 'FILETRANS category, TFTP-CONTROL, PID 66' ;
                          }

                          enum tftp-data {
                            value 67 ;
                            description 'FILETRANS category, TFTP-DATA, PID 67' ;
                          }

                          enum ftp-control {
                            value 103 ;
                            description 'FILETRANS category, FTP-CONTROL, PID 103' ;
                          }

                          enum ftp-data {
                            value 104 ;
                            description 'FILETRANS category, FTP-DATA, PID 104' ;
                          }

                        }

                      }

                    }

                  }

                  container voips {
                    description 'Match voice over internet phone category.' ;
                    list voip {
                      description 'Select protocol in voice over internet phone category.' ;
                      key prodpi-id ;
                      leaf prodpi-id {
                        description 'Set protocol in voice over internet phone category.' ;
                        type enumeration {
                          enum skype {
                            value 93 ;
                            description 'VOIP category, SKYPE, PID 93' ;
                          }

                          enum sip {
                            value 112 ;
                            description 'VOIP category, SIP, PID 112' ;
                          }

                          enum h248 {
                            value 336 ;
                            description 'VOIP category, H248, PID 336' ;
                          }

                        }

                      }

                    }

                  }

                  container games {
                    description 'Match game category.' ;
                    list game {
                      description 'Select protocol in game category.' ;
                      key prodpi-id ;
                      leaf prodpi-id {
                        description 'Set protocol in game category.' ;
                        type enumeration {
                          enum qqgame {
                            value 190 ;
                            description 'GAME category, QQGAME, PID 190' ;
                          }

                          enum qq-crossfire {
                            value 192 ;
                            description 'GAME category, QQ-CROSSFIRE, PID 192' ;
                          }

                          enum qq-xuanwu {
                            value 193 ;
                            description 'GAME category, QQ-XUANWU, PID 193' ;
                          }

                          enum qq-feiche {
                            value 194 ;
                            description 'GAME category, QQ-FEICHE, PID 194' ;
                          }

                          enum qq-huanxiangshijie {
                            value 201 ;
                            description 'GAME category, QQ-HUANXIANGSHIJIE, PID 201' ;
                          }

                          enum qq-fo-ffo {
                            value 231 ;
                            description 'GAME category, QQ-FO-FFO, PID 231' ;
                          }

                          enum qq-doudizhu {
                            value 266 ;
                            description 'GAME category, QQ-DOUDIZHU, PID 266' ;
                          }

                          enum qq-farm {
                            value 286 ;
                            description 'GAME category, QQ-FARM, PID 286' ;
                          }

                        }

                      }

                    }

                  }

                  container softwares {
                    description 'Match software category.' ;
                    list software {
                      description 'Select protocol in software category.' ;
                      key prodpi-id ;
                      leaf prodpi-id {
                        description 'Set protocol in software category.' ;
                        type enumeration {
                          enum windows-update {
                            value 20 ;
                            description 'SOFTWARE category, WINDOWS-UPDATE, PID 20' ;
                          }

                        }

                      }

                    }

                  }

                  container secures {
                    description 'Match secure category.' ;
                    list secure {
                      description 'Select protocol in secure category.' ;
                      key prodpi-id ;
                      leaf prodpi-id {
                        description 'Set protocol in secure category.' ;
                        type enumeration {
                          enum https {
                            value 305 ;
                            description 'SECURE category, HTTPS, PID 305' ;
                          }

                        }

                      }

                    }

                  }

                  container webvideos {
                    description 'Match webvideo category.' ;
                    list webvideo {
                      description 'Select protocol in webvideo category.' ;
                      key prodpi-id ;
                      leaf prodpi-id {
                        description 'Set protocol in webvideo category.' ;
                        type enumeration {
                          enum qq-multimedia {
                            value 106 ;
                            description 'WEBVIDEO category, QQ-MULTIMEDIA, PID 106' ;
                          }

                          enum msn-video {
                            value 145 ;
                            description 'WEBVIDEO category, MSN-VIDEO, PID 145' ;
                          }

                        }

                      }

                    }

                  }

                  container streamings {
                    description 'Match streaming category.' ;
                    list streaming {
                      description 'Select protocol in streaming category.' ;
                      key prodpi-id ;
                      leaf prodpi-id {
                        description 'Set protocol in streaming category.' ;
                        type enumeration {
                          enum thunder-kankan {
                            value 70 ;
                            description 'STREAMING category, THUNDER-KANKAN, PID 70' ;
                          }

                          enum ppstream {
                            value 75 ;
                            description 'STREAMING category, PPSTREAM, PID 75' ;
                          }

                          enum pplive {
                            value 113 ;
                            description 'STREAMING category, PPLIVE, PID 113' ;
                          }

                        }

                      }

                    }

                  }

                }

                container vni {
                  description 'To select VNI (VXLAN Network Identifier) as matching criteria.' ;
                  presence "To select VNI as match criteria" ;
                  leaf vni-range1-start {
                    description 'The starting-value of the first VNI range.' ;
                    type uint32 {
                      range 1..16777215 ;

                    }

                    mandatory true ;
                  }

                  leaf vni-range1-end {
                    description 'The ending-value of the first VNI range.' ;
                    type uint32 {
                      range 1..16777215 ;

                    }

                    mandatory true ;
                  }

                  container vni-range2 {
                    description 'To select the second VNI range.' ;
                    presence "The configuration of the second VNI range" ;
                    leaf vni-range2-start {
                      description 'The starting-value of the second VNI range.' ;
                      type uint32 {
                        range 1..16777215 ;

                      }

                      mandatory true ;
                    }

                    leaf vni-range2-end {
                      description 'The ending-value of the second VNI range.' ;
                      type uint32 {
                        range 1..16777215 ;

                      }

                      mandatory true ;
                    }

                    container vni-range3 {
                      description 'To select the third VNI range.' ;
                      presence "The configuration of the third VNI range" ;
                      leaf vni-range3-start {
                        description 'The starting-value of the third VNI range.' ;
                        type uint32 {
                          range 1..16777215 ;

                        }

                        mandatory true ;
                      }

                      leaf vni-range3-end {
                        description 'The ending-value of the third VNI range.' ;
                        type uint32 {
                          range 1..16777215 ;

                        }

                        mandatory true ;
                      }

                      container vni-range4 {
                        description 'To select the fourth VNI range.' ;
                        presence "The configuration of the fourth VNI range" ;
                        leaf vni-range4-start {
                          description 'The starting-value of the fourth VNI range.' ;
                          type uint32 {
                            range 1..16777215 ;

                          }

                          mandatory true ;
                        }

                        leaf vni-range4-end {
                          description 'The ending-value of the fourth VNI range.' ;
                          type uint32 {
                            range 1..16777215 ;

                          }

                          mandatory true ;
                        }

                      }

                    }

                  }

                  ncd:revise-date 2015-11-04 ;
                }

                container ipv4-mixed-acls {
                  description 'Select IPv4 mixed ACL name as matching criteria.' ;
                  list ipv4-mixed-acl {
                    description 'Set IPv4 mixed ACL name as matching criteria.' ;
                    key acl-name ;
                    leaf acl-name {
                      description 'Set ipv4-mixed-access-list name, support 1-31 characters.' ;
                      type string {
                        length 1..31 {
                          description 'Name of ACL, support 1-31 characters' ;
                        }

                      }

                    }

                  }

                  ncd:revise-date 2017-02-20 ;
                }

                container ipv6-mixed-acls {
                  description 'Select IPv6 mixed ACL name as matching criteria.' ;
                  list ipv6-mixed-acl {
                    description 'Set IPv6 mixed ACL name as matching criteria.' ;
                    key acl-name ;
                    leaf acl-name {
                      description 'Set ipv6-mixed-access-list name, support 1-31 characters.' ;
                      type string {
                        length 1..31 {
                          description 'Name of ACL, support 1-31 characters' ;
                        }

                      }

                    }

                  }

                  ncd:revise-date 2020-12-23 ;
                }

                container ipv4-vxlan-acls {
                  description 'Select IPv4 vxlan ACL name as matching criteria.' ;
                  list ipv4-vxlan-acl {
                    description 'Set IPv4 vxlan ACL name as matching criteria.' ;
                    key acl-name ;
                    leaf acl-name {
                      description 'Set ipv4-vxlan-access-list name, support 1-31 characters.' ;
                      type string {
                        length 1..31 {
                          description 'Name of ACL, support 1-31 characters.' ;
                        }

                      }

                    }

                  }

                  ncd:revise-date 2021-01-25 ;
                }

                container ipv6-vxlan-acls {
                  description 'Select IPv6 vxlan ACL name as matching criteria.' ;
                  list ipv6-vxlan-acl {
                    description 'Set IPv6 vxlan ACL name as matching criteria.' ;
                    key acl-name ;
                    leaf acl-name {
                      description 'Set ipv6-vxlan-access-list name, support 1-31 characters.' ;
                      type string {
                        length 1..31 {
                          description 'Name of ACL, support 1-31 characters.' ;
                        }

                      }

                    }

                  }

                  ncd:revise-date 2021-01-25 ;
                }

                container interface {
                  description 'Select interface name as matching criteria.' ;
                  presence "Select interface name as match criteria" ;
                  leaf if-name {
                    description 'Set interface name.' ;
                    type ncd:ifname {
                      length 1..31 {
                        description 'Name of the interface, support 1-31 characters' ;
                      }

                    }

                    mandatory true ;
                  }

                  ncd:revise-date 2021-01-25 ;
                }

              }

              container cmap-description {
                description 'Description of a class map, support 1-79 characters.' ;
                presence "Specify description of class map" ;
                leaf cmap-description {
                  description 'Description of a class map, support 1-79 characters.' ;
                  type ncd:string-with-blank {
                    length 1..79 {
                      description 'Description of a class map, support 1-79 characters.' ;
                    }

                  }

                  mandatory true ;
                }

                ncd:revise-date 2020-06-18 ;
              }

            }

          }

        }

        container phb-based {
          if-feature phb-mode ;

          description 'Class map based on phb.' ;
          container class-maps {
            description 'Configure QoS class map lists.' ;
            list class-map {
              description 'Configure QoS class map list.' ;
              key cmap-name ;
              leaf cmap-name {
                description 'Name of the class map, support 1-31 characters.' ;
                type string {
                  length 1..31 {
                    description 'Name of the class map, support 1-31 characters' ;
                  }

                }

              }

              container match {
                description 'Configure matching criteria for a class map.' ;
                container service-class {
                  description 'Select PHB as matching criteria.' ;
                  presence "Select PHB as match criteria" ;
                  choice value-or-range {
                    description 'Select PHB value or range as matching criteria.' ;
                    case value {
                      description 'Select PHB value as matching criteria.' ;
                      leaf service-class {
                        description 'Select service class of PHB info.' ;
                        type qos-service-class ;

                        mandatory true ;
                      }

                    }

                    case range {
                      description 'Select PHB range as matching criteria.' ;
                      container range {
                        description 'Select PHB range as matching criteria.' ;
                        leaf service-class-range {
                          description 'Configure service class in range mode, support value or range(max num:4;spacing mark:,) in <0-7>. For example,"0,2-4,7",etc.' ;
                          type qos-phb-bitmap ;

                          mandatory true ;
                        }

                      }

                      ncd:revise-date 2021-01-18 ;
                    }

                  }

                }

                container child {
                  description 'Set the mark of null class.' ;
                  presence "Select child as match criteria" ;
                  leaf child {
                    description 'Set the mark of null class.' ;
                    type empty ;

                    mandatory true ;
                  }

                  ncd:revise-date 2021-01-11 ;
                }

              }

              container cmap-description {
                description 'Description of a class map, support 1-79 characters.' ;
                presence "Specify description of class map" ;
                leaf cmap-description {
                  description 'Description of a class map, support 1-79 characters.' ;
                  type ncd:string-with-blank {
                    length 1..79 {
                      description 'Description of a class map, support 1-79 characters.' ;
                    }

                  }

                  mandatory true ;
                }

                ncd:revise-date 2020-06-18 ;
              }

            }

          }

        }

        container sub-interface-based {
          if-feature sub-interface-mode ;

          description 'Class map based on sub-interface.' ;
          container class-maps {
            description 'Configure QoS class map lists.' ;
            list class-map {
              description 'Configure QoS class map list.' ;
              key cmap-name ;
              leaf cmap-name {
                description 'Name of the class map, support 1-31 characters.' ;
                type string {
                  length 1..31 {
                    description 'Name of the class map, support 1-31 characters' ;
                  }

                }

              }

              container match {
                description 'Configure matching criteria for a class map.' ;
                container interface {
                  description 'Select interface name as matching criteria.' ;
                  presence "Select interface name as match criteria" ;
                  leaf if-name {
                    description 'Set interface name.' ;
                    type ncd:ifname {
                      length 1..31 {
                        description 'Name of the interface, support 1-31 characters' ;
                      }

                    }

                    mandatory true ;
                  }

                }

                container localport {
                  description 'Select localport as matching criteria.' ;
                  presence "Select localport as match criteria" ;
                  leaf localport {
                    description 'Specify localport.' ;
                    type empty ;

                    mandatory true ;
                  }

                }

              }

              container cmap-description {
                description 'Description of a class map, support 1-79 characters.' ;
                presence "Specify description of class map" ;
                leaf cmap-description {
                  description 'Description of a class map, support 1-79 characters.' ;
                  type ncd:string-with-blank {
                    length 1..79 {
                      description 'Description of a class map, support 1-79 characters.' ;
                    }

                  }

                  mandatory true ;
                }

                ncd:revise-date 2020-06-18 ;
              }

            }

          }

        }

        container switch-fabric-based {
          if-feature switch-fabric-mode ;

          description 'Class map based on switch-fabric.' ;
          container class-maps {
            description 'Configure QoS class map lists.' ;
            list class-map {
              description 'Configure QoS class map list.' ;
              key cmap-name ;
              leaf cmap-name {
                description 'Name of the class map, support 1-31 characters.' ;
                type string {
                  length 1..31 {
                    description 'Name of the class map, support 1-31 characters' ;
                  }

                }

              }

              container match {
                description 'Configure matching criteria for a class map.' ;
                container precedence {
                  description 'Select IP-Precedence as matching criteria.' ;
                  presence "Select IP-Precedence as match criteria" ;
                  leaf prec-value {
                    description 'Configure QoS IP Precedence in range mode, support single precedence value or range(max num:4;spacing mark:,) in <0-7>. For example,"0,2-4,7",etc.' ;
                    type qos-prec-bitmap ;

                    mandatory true ;
                  }

                }

                container mpls-exp {
                  description 'Select MPLS-EXP as matching criteria.' ;
                  presence "Select MPLS-EXP as match criteria" ;
                  leaf mpls-exp-value {
                    description 'Configure QoS MPLS-EXP value in range mode, support single MPLS-EXP value or range(max num:4;spacing mark:,) in <0-7>. For example,"0,2-4,7",etc.' ;
                    type qos-mpls-bitmap ;

                    mandatory true ;
                  }

                }

                container uni-cast {
                  description 'Select unicast as matching criteria.' ;
                  presence "Select unicast as match criteria" ;
                  leaf uni-cast {
                    description 'Set unicast.' ;
                    type empty ;

                    mandatory true ;
                  }

                  leaf unicast-priority {
                    description 'Specify the priority of queue, such as high, middle, normal, low.' ;
                    type enumeration {
                      enum high {
                        value 1 ;
                        description 'Specify the high priority queue' ;
                      }

                      enum middle {
                        value 2 ;
                        description 'Specify the middle priority queue' ;
                      }

                      enum normal {
                        value 3 ;
                        description 'Specify the normal priority queue' ;
                      }

                      enum low {
                        value 4 ;
                        description 'Specify the low priority queue' ;
                      }

                    }

                  }

                }

                container multi-cast {
                  description 'Select multicast as matching criteria.' ;
                  presence "Select multicast as match criteria" ;
                  leaf multi-cast {
                    description 'Set multicast.' ;
                    type empty ;

                    mandatory true ;
                  }

                  leaf multicast-priority {
                    description 'Specify the priority of queue, such as high, middle, normal, low.' ;
                    type enumeration {
                      enum high {
                        value 1 ;
                        description 'Specify the high priority queue' ;
                      }

                      enum middle {
                        value 2 ;
                        description 'Specify the middle priority queue' ;
                      }

                      enum normal {
                        value 3 ;
                        description 'Specify the normal priority queue' ;
                      }

                      enum low {
                        value 4 ;
                        description 'Specify the low priority queue' ;
                      }

                    }

                  }

                }

                container child {
                  description 'Set the mark of null class.' ;
                  presence "Set the mark of null class" ;
                  leaf child {
                    description 'Set the mark of null class.' ;
                    type empty ;

                    mandatory true ;
                  }

                }

              }

            }

          }

        }

        container flowspec-based {
          description 'Class map based on flowspec.' ;
          container class-maps {
            description 'Configure QoS class map lists.' ;
            list class-map {
              description 'Configure QoS class map list.' ;
              key cmap-name ;
              leaf cmap-name {
                description 'Name of the class map, support 1-31 characters.' ;
                type string {
                  length 1..31 {
                    description 'Name of the class map, support 1-31 characters' ;
                  }

                }

              }

              container match {
                description 'Configure matching criteria for a class map.' ;
                container port {
                  description 'Select port as matching criteria.' ;
                  presence "Select port as match criteria" ;
                  leaf port-value {
                    description 'Configure port value in range mode, support single port value or range(max num:4;spacing mark:,) in <0-65535>. For example,"1,300-400,1000,2000-4000",etc.Specifically, port value 0 can only be configured in a single value format.' ;
                    type qos-port-range ;

                    mandatory true ;
                  }

                }

                container destination-port {
                  description 'Select destination-port as matching criteria.' ;
                  presence "Select destination-port as match criteria" ;
                  leaf dst-port-value {
                    description 'Configure destination-port value in range mode, support single destination-port value or range(max num:4;spacing mark:,) in <0-65535>. For example,"1,300-400,1000,2000-4000",etc.Specifically, port value 0 can only be configured in a single value format.' ;
                    type qos-port-range ;

                    mandatory true ;
                  }

                }

                container source-port {
                  description 'Select source-port as matching criteria.' ;
                  presence "Select source-port as match criteria" ;
                  leaf src-port-value {
                    description 'Configure soure-port value in range mode, support single soure-port value or range(max num:4;spacing mark:,) in <0-65535>. For example,"1,300-400,1000,2000-4000",etc.Specifically, port value 0 can only be configured in a single value format.' ;
                    type qos-port-range ;

                    mandatory true ;
                  }

                }

                container fragment-type {
                  description 'Select fragment-type as matching criteria.' ;
                  presence "Select fragment-type as match criteria" ;
                  leaf not {
                    description 'Logical negation of operation:
true  Match opposite;
false Match current.' ;
                    type boolean ;

                    default false ;
                  }

                  leaf match-relation {
                    description 'The rule of matching, see bellow:                
all  Match all of the fragment type;
any  Match any of the fragment type.' ;
                    type enumeration {
                      enum all {
                        value 0 ;
                        description 'Match all of the fragment type.' ;
                      }

                      enum any {
                        value 1 ;
                        description 'Match any of the fragment type.' ;
                      }

                    }

                    mandatory true ;
                  }

                  choice fragment-option {
                    description 'Fragment type.' ;
                    mandatory true ;
                    case fragment {
                      description 'Fragment type.' ;
                      leaf dont-fragment {
                        description 'Match dont-fragment.' ;
                        type boolean ;

                        default false ;
                      }

                      leaf first-fragment {
                        description 'Match first-fragment.' ;
                        type boolean ;

                        default false ;
                      }

                      leaf is-fragment {
                        description 'Match is-fragment.' ;
                        type boolean ;

                        default false ;
                      }

                      leaf last-fragment {
                        description 'Match last-fragment.' ;
                        type boolean ;

                        default false ;
                      }

                    }

                  }

                }

                container destination-ipv4-addr {
                  description 'Select destination-address as matching criteria.' ;
                  presence "Select destination-address as match criteria" ;
                  leaf dst-address {
                    description 'Destination address.' ;
                    type ncd:ipv4-address ;

                    mandatory true ;
                  }

                  leaf dst-address-mask {
                    description 'Destination maskcard bits, positive mask.' ;
                    type ncd:ipv4-mask ;

                    mandatory true ;
                  }

                }

                container source-ipv4-addr {
                  description 'Select source-address as matching criteria.' ;
                  presence "Select source-address as match criteria" ;
                  leaf src-address {
                    description 'Source address.' ;
                    type ncd:ipv4-address ;

                    mandatory true ;
                  }

                  leaf src-address-mask {
                    description 'Source maskcard bits, positive mask.' ;
                    type ncd:ipv4-mask ;

                    mandatory true ;
                  }

                }

                container dscps {
                  description 'Select DSCP as matching criteria.' ;
                  list dscp {
                    description 'Set DSCP value as matching criteria.' ;
                    key ip-type ;
                    leaf ip-type {
                      description 'Configure DSCP value Based on IP, see below:
ipv4 Packets based on IPv4;
ipv6 Packets based on IPv6.' ;
                      type enumeration {
                        enum ipv4 {
                          value 1 ;
                          description 'IPv4 type.' ;
                        }

                        enum ipv6 {
                          value 2 ;
                          description 'IPv6 type.' ;
                        }

                      }

                    }

                    leaf not {
                      description 'Configure the opposite range flag,
true  Match opposite range;
false Match current range.' ;
                      type boolean ;

                      default false ;
                    }

                    leaf dscp-value {
                      description 'Configure QoS dscp in range mode, support single DSCP value or range(max num:4;spacing mark:,) in <0-63>. For example,"6,10-30,40,50-60",etc.' ;
                      type qos-dscp-bitmap ;

                      mandatory true ;
                    }

                  }

                }

                container icmp-code {
                  description 'Select icmp-code as matching criteria.' ;
                  presence "Select icmp-code as match criteria" ;
                  leaf icmp-code-value {
                    description 'Configure icmp code in range mode, support single icmp-code value or range(max num:4;spacing mark:,) in <0-255>. For example,"6,10-30,40,50-60",etc.' ;
                    type ncd:bitmap {
                      pattern "(((((([1-9][0-9]{1,1})|([1-9][0-9]{0,0})|0|([1-1][0-9]{2,2})|(2[0-4][0-9]{1,1})|(25[0-4])|255)-(([1-9][0-9]{1,1})|([1-9][0-9]{0,0})|0|([1-1][0-9]{2,2})|(2[0-4][0-9]{1,1})|(25[0-4])|255))|(([1-9][0-9]{1,1})|([1-9][0-9]{0,0})|0|([1-1][0-9]{2,2})|(2[0-4][0-9]{1,1})|(25[0-4])|255)),){0,3}(((([1-9][0-9]{1,1})|([1-9][0-9]{0,0})|0|([1-1][0-9]{2,2})|(2[0-4][0-9]{1,1})|(25[0-4])|255)-(([1-9][0-9]{1,1})|([1-9][0-9]{0,0})|0|([1-1][0-9]{2,2})|(2[0-4][0-9]{1,1})|(25[0-4])|255))|(([1-9][0-9]{1,1})|([1-9][0-9]{0,0})|0|([1-1][0-9]{2,2})|(2[0-4][0-9]{1,1})|(25[0-4])|255)){1,1})" {
                        description 'Configure icmp-code in range mode, support single icmp-code value or range(max num:4;spacing mark:,) in <0-255>.' ;
                      }

                    }

                    mandatory true ;
                  }

                }

                container icmp-type {
                  description 'Select icmp-type as matching criteria.' ;
                  presence "Select icmp-type as match criteria" ;
                  leaf icmp-type-value {
                    description 'Configure icmp type in range mode, support single icmp-type value or range(max num:4;spacing mark:,) in <0-255>. For example,"6,10-30,40,50-60",etc.' ;
                    type ncd:bitmap {
                      pattern "(((((([1-9][0-9]{1,1})|([1-9][0-9]{0,0})|0|([1-1][0-9]{2,2})|(2[0-4][0-9]{1,1})|(25[0-4])|255)-(([1-9][0-9]{1,1})|([1-9][0-9]{0,0})|0|([1-1][0-9]{2,2})|(2[0-4][0-9]{1,1})|(25[0-4])|255))|(([1-9][0-9]{1,1})|([1-9][0-9]{0,0})|0|([1-1][0-9]{2,2})|(2[0-4][0-9]{1,1})|(25[0-4])|255)),){0,3}(((([1-9][0-9]{1,1})|([1-9][0-9]{0,0})|0|([1-1][0-9]{2,2})|(2[0-4][0-9]{1,1})|(25[0-4])|255)-(([1-9][0-9]{1,1})|([1-9][0-9]{0,0})|0|([1-1][0-9]{2,2})|(2[0-4][0-9]{1,1})|(25[0-4])|255))|(([1-9][0-9]{1,1})|([1-9][0-9]{0,0})|0|([1-1][0-9]{2,2})|(2[0-4][0-9]{1,1})|(25[0-4])|255)){1,1})" {
                        description 'Configure icmp-type in range mode, support single icmp-type value or range(max num:4;spacing mark:,) in <0-255>.' ;
                      }

                    }

                    mandatory true ;
                  }

                }

                container packet-length {
                  description 'Select packet-length as matching criteria.' ;
                  presence "Select packet-length as match criteria" ;
                  leaf packet-length-value {
                    description 'Configure packet-length in range mode, support single packet-length value or range(max num:4;spacing mark:,) in <1-65535>. For example,"6,10-30,40,50-60",etc.' ;
                    type ncd:range {
                      pattern "(((([1-9][0-9]{1,3})|([1-9])|([1-5][0-9]{4,4})|(6[0-4][0-9]{3,3})|(65[0-4][0-9]{2,2})|(655[0-2][0-9]{1,1})|(6553[0-5]))(-(([1-9][0-9]{1,3})|([1-9])|([1-5][0-9]{4,4})|(6[0-4][0-9]{3,3})|(65[0-4][0-9]{2,2})|(655[0-2][0-9]{1,1})|(6553[0-5]))){0,1})((,)(([1-9][0-9]{1,3})|([1-9])|([1-5][0-9]{4,4})|(6[0-4][0-9]{3,3})|(65[0-4][0-9]{2,2})|(655[0-2][0-9]{1,1})|(6553[0-5]))(-(([1-9][0-9]{1,3})|([1-9])|([1-5][0-9]{4,4})|(6[0-4][0-9]{3,3})|(65[0-4][0-9]{2,2})|(655[0-2][0-9]{1,1})|(6553[0-5]))){0,1}){0,3})" {
                        description 'Configure packet-length in range mode, support single packet-length value or range(max num:4;spacing mark:,) in <1-65535>. For example,"6,10-30,40,50-60",etc.' ;
                      }

                    }

                    mandatory true ;
                  }

                }

                container protocol {
                  description 'Select protocol as matching criteria.' ;
                  presence "Select protocol as match criteria" ;
                  leaf not {
                    description 'Configure the opposite range flag:
true  Match opposite range;
false Match current range.' ;
                    type boolean ;

                    default false ;
                  }

                  leaf protocol-value {
                    description 'Configure protocol in range mode, support single protocol value or range(max num:4;spacing mark:,) in <0-255>. For example,"6,10-30,40,50-60",etc.' ;
                    type ncd:bitmap {
                      pattern "(((((([1-9][0-9]{1,1})|([1-9][0-9]{0,0})|0|([1-1][0-9]{2,2})|(2[0-4][0-9]{1,1})|(25[0-4])|255)-(([1-9][0-9]{1,1})|([1-9][0-9]{0,0})|0|([1-1][0-9]{2,2})|(2[0-4][0-9]{1,1})|(25[0-4])|255))|(([1-9][0-9]{1,1})|([1-9][0-9]{0,0})|0|([1-1][0-9]{2,2})|(2[0-4][0-9]{1,1})|(25[0-4])|255)),){0,3}(((([1-9][0-9]{1,1})|([1-9][0-9]{0,0})|0|([1-1][0-9]{2,2})|(2[0-4][0-9]{1,1})|(25[0-4])|255)-(([1-9][0-9]{1,1})|([1-9][0-9]{0,0})|0|([1-1][0-9]{2,2})|(2[0-4][0-9]{1,1})|(25[0-4])|255))|(([1-9][0-9]{1,1})|([1-9][0-9]{0,0})|0|([1-1][0-9]{2,2})|(2[0-4][0-9]{1,1})|(25[0-4])|255)){1,1})" {
                        description 'Configure protocol in range mode, support single protocol value or range(max num:4;spacing mark:,).' ;
                      }

                    }

                    mandatory true ;
                  }

                }

                container tcp-flag {
                  description 'Select tcp-flag as matching criteria.' ;
                  presence "Select tcp-flag as match criteria" ;
                  leaf not {
                    description 'Logical negation of operation:
true  Match opposite;
false Match current.' ;
                    type boolean ;

                    default false ;
                  }

                  leaf match-relation {
                    description 'The rule of matching, see bellow:                
all  Match all of the tcp flag;
any  Match any of the tcp flag.' ;
                    type enumeration {
                      enum all {
                        value 0 ;
                        description 'Match all of the tcp flag.' ;
                      }

                      enum any {
                        value 1 ;
                        description 'Match any of the tcp flag.' ;
                      }

                    }

                    mandatory true ;
                  }

                  choice tcp-flag-option {
                    description 'TCP Flag.' ;
                    mandatory true ;
                    case tcp-flag {
                      description 'TCP Flag.' ;
                      leaf rst {
                        description 'Match on the RST bit.' ;
                        type boolean ;

                        default false ;
                      }

                      leaf ack {
                        description 'Match on the ACK bit.' ;
                        type boolean ;

                        default false ;
                      }

                      leaf fin {
                        description 'Match on the FIN bit.' ;
                        type boolean ;

                        default false ;
                      }

                      leaf syn {
                        description 'Match on the SYN bit.' ;
                        type boolean ;

                        default false ;
                      }

                      leaf psh {
                        description 'Match on the PSH bit.' ;
                        type boolean ;

                        default false ;
                      }

                      leaf urg {
                        description 'Match on the URG bit.' ;
                        type boolean ;

                        default false ;
                      }

                      leaf ece {
                        description 'Match on the ECE bit.' ;
                        type boolean ;

                        default false ;
                      }

                      leaf cwr {
                        description 'Match on the CWR bit.' ;
                        type boolean ;

                        default false ;
                      }

                    }

                  }

                }

                container flow-label {
                  description 'Select flow-label as matching criteria.' ;
                  presence "Select flow-label as match criteria" ;
                  leaf flow-label-value {
                    description 'Set flow label value.' ;
                    type uint32 {
                      range 0..1048575 ;

                    }

                    mandatory true ;
                  }

                  ncd:revise-date 2020-02-03 ;
                }

                container destination-ipv6-addr {
                  description 'Select IPv6 destination address as matching criteria.' ;
                  presence "Select IPv6 destination address as match criteria" ;
                  leaf dst-ipv6-addr {
                    description 'IPv6 destination address.' ;
                    type ncd:ipv6-address ;

                    mandatory true ;
                  }

                  leaf dst-ipv6-addr-prefix {
                    description 'IPv6 destination maskcard length, positive mask.' ;
                    type ncd:ipv6-mask-length ;

                    mandatory true ;
                  }

                  ncd:revise-date 2020-02-03 ;
                }

                container source-ipv6-addr {
                  description 'Select IPv6 source-address as matching criteria.' ;
                  presence "Select IPv6 source-address as match criteria" ;
                  leaf src-ipv6-addr {
                    description 'IPv6 source address.' ;
                    type ncd:ipv6-address ;

                    mandatory true ;
                  }

                  leaf src-ipv6-addr-prefix {
                    description 'IPv6 source maskcard length, positive mask.' ;
                    type ncd:ipv6-mask-length ;

                    mandatory true ;
                  }

                  ncd:revise-date 2020-02-03 ;
                }

                container ipv6-icmp-code {
                  description 'Select IPv6 icmp-code as matching criteria.' ;
                  presence "Select IPv6 icmp-code as match criteria" ;
                  leaf icmp-code-value {
                    description 'Configure icmp code in range mode, support single icmp-code value or range(max num:4;spacing mark:,) in <0-255>. For example,"6,10-30,40,50-60",etc.' ;
                    type ncd:bitmap {
                      pattern "(((((([1-9][0-9]{1,1})|([1-9][0-9]{0,0})|0|([1-1][0-9]{2,2})|(2[0-4][0-9]{1,1})|(25[0-4])|255)-(([1-9][0-9]{1,1})|([1-9][0-9]{0,0})|0|([1-1][0-9]{2,2})|(2[0-4][0-9]{1,1})|(25[0-4])|255))|(([1-9][0-9]{1,1})|([1-9][0-9]{0,0})|0|([1-1][0-9]{2,2})|(2[0-4][0-9]{1,1})|(25[0-4])|255)),){0,3}(((([1-9][0-9]{1,1})|([1-9][0-9]{0,0})|0|([1-1][0-9]{2,2})|(2[0-4][0-9]{1,1})|(25[0-4])|255)-(([1-9][0-9]{1,1})|([1-9][0-9]{0,0})|0|([1-1][0-9]{2,2})|(2[0-4][0-9]{1,1})|(25[0-4])|255))|(([1-9][0-9]{1,1})|([1-9][0-9]{0,0})|0|([1-1][0-9]{2,2})|(2[0-4][0-9]{1,1})|(25[0-4])|255)){1,1})" {
                        description 'Configure icmp-code in range mode, support single icmp-code value or range(max num:4;spacing mark:,) in <0-255>.' ;
                      }

                    }

                    mandatory true ;
                  }

                  ncd:revise-date 2020-02-03 ;
                }

                container ipv6-icmp-type {
                  description 'Select IPv6 icmp-type as matching criteria.' ;
                  presence "Select IPv6 icmp-type as match criteria" ;
                  leaf icmp-type-value {
                    description 'Configure icmp type in range mode, support single icmp-type value or range(max num:4;spacing mark:,) in <0-255>. For example,"6,10-30,40,50-60",etc.' ;
                    type ncd:bitmap {
                      pattern "(((((([1-9][0-9]{1,1})|([1-9][0-9]{0,0})|0|([1-1][0-9]{2,2})|(2[0-4][0-9]{1,1})|(25[0-4])|255)-(([1-9][0-9]{1,1})|([1-9][0-9]{0,0})|0|([1-1][0-9]{2,2})|(2[0-4][0-9]{1,1})|(25[0-4])|255))|(([1-9][0-9]{1,1})|([1-9][0-9]{0,0})|0|([1-1][0-9]{2,2})|(2[0-4][0-9]{1,1})|(25[0-4])|255)),){0,3}(((([1-9][0-9]{1,1})|([1-9][0-9]{0,0})|0|([1-1][0-9]{2,2})|(2[0-4][0-9]{1,1})|(25[0-4])|255)-(([1-9][0-9]{1,1})|([1-9][0-9]{0,0})|0|([1-1][0-9]{2,2})|(2[0-4][0-9]{1,1})|(25[0-4])|255))|(([1-9][0-9]{1,1})|([1-9][0-9]{0,0})|0|([1-1][0-9]{2,2})|(2[0-4][0-9]{1,1})|(25[0-4])|255)){1,1})" {
                        description 'Configure icmp-type in range mode, support single icmp-type value or range(max num:4;spacing mark:,) in <0-255>.' ;
                      }

                    }

                    mandatory true ;
                  }

                  ncd:revise-date 2020-02-03 ;
                }

                container next-header {
                  description 'Select next-header as matching criteria.' ;
                  presence "Select next-header as match criteria" ;
                  leaf not {
                    description 'Configure the opposite range flag.' ;
                    type empty ;

                  }

                  leaf next-header-value {
                    description 'Configure next-header in range mode, support single value or range(max num:4;spacing mark:,) in <0-255>. For example,"6,10-30,40,50-60",etc.' ;
                    type ncd:bitmap {
                      pattern "(((((([1-9][0-9]{1,1})|([1-9][0-9]{0,0})|0|([1-1][0-9]{2,2})|(2[0-4][0-9]{1,1})|(25[0-4])|255)-(([1-9][0-9]{1,1})|([1-9][0-9]{0,0})|0|([1-1][0-9]{2,2})|(2[0-4][0-9]{1,1})|(25[0-4])|255))|(([1-9][0-9]{1,1})|([1-9][0-9]{0,0})|0|([1-1][0-9]{2,2})|(2[0-4][0-9]{1,1})|(25[0-4])|255)),){0,3}(((([1-9][0-9]{1,1})|([1-9][0-9]{0,0})|0|([1-1][0-9]{2,2})|(2[0-4][0-9]{1,1})|(25[0-4])|255)-(([1-9][0-9]{1,1})|([1-9][0-9]{0,0})|0|([1-1][0-9]{2,2})|(2[0-4][0-9]{1,1})|(25[0-4])|255))|(([1-9][0-9]{1,1})|([1-9][0-9]{0,0})|0|([1-1][0-9]{2,2})|(2[0-4][0-9]{1,1})|(25[0-4])|255)){1,1})" {
                        description 'Configure protocol in range mode, support single protocol value or range(max num:4;spacing mark:,).' ;
                      }

                    }

                    mandatory true ;
                  }

                  ncd:revise-date 2020-02-03 ;
                }

                container tcp-flag-values {
                  description 'Select tcp-flag-value as matching criteria.' ;
                  list tcp-flag-value {
                    description 'Select tcp-flag-value as matching criteria.' ;
                    key value ;
                    leaf not {
                      description 'Logical negation of operation:
true  Match opposite;
false Match current.' ;
                      type boolean ;

                      default false ;
                    }

                    leaf match-relation {
                      description 'The rule of matching, see bellow:                
all  Match all of the tcp flag value;
any  Match any of the tcp flag value.' ;
                      type enumeration {
                        enum all {
                          value 0 ;
                          description 'Match all of the tcp flag value.' ;
                        }

                        enum any {
                          value 1 ;
                          description 'Match any of the tcp flag value.' ;
                        }

                      }

                      mandatory true ;
                    }

                    leaf value {
                      description 'The value of tcp flag.' ;
                      type uint8 {
                        range 1..255 {
                          description 'The value of tcp flag.' ;
                        }

                      }

                    }

                    leaf item-logic {
                      description 'Logical relationship of tcp flag value, see bellow:
or     Logical or relationship of tcp flag value;
and  Logical and relationship of tcp flag value.' ;
                      type enumeration {
                        enum and {
                          value 1 ;
                          description 'Logical and relationship of tcp flag value.' ;
                        }

                        enum or {
                          value 2 ;
                          description 'Logical or relationship of tcp flag value.' ;
                        }

                      }

                      mandatory true ;
                    }

                  }

                  ncd:revise-date 2022-04-27 ;
                }

              }

              container cmap-description {
                description 'Description of a class map, support 1-79 characters.' ;
                presence "Specify description of class map" ;
                leaf cmap-description {
                  description 'Description of a class map, support 1-79 characters.' ;
                  type ncd:string-with-blank {
                    length 1..79 {
                      description 'Description of a class map, support 1-79 characters.' ;
                    }

                  }

                  mandatory true ;
                }

                ncd:revise-date 2020-06-18 ;
              }

            }

          }

          ncd:revise-date 2017-06-12 ;
        }

        container class-map-id {
          description 'QoS class map lists id, this configuration is for internal use only and for external inquiry only.' ;
          container class-maps {
            description 'QoS class map lists.' ;
            list class-map {
              description 'QoS class map list.' ;
              key cmap-name ;
              leaf cmap-name {
                description 'Name of the class map, support 1-31 characters.' ;
                type string {
                  length 1..31 {
                    description 'Name of the class map, support 1-31 characters' ;
                  }

                }

              }

              leaf cmap-id {
                description 'H-QoS class map lists id.' ;
                type uint32 {
                  range 1..16000 {
                    description 'H-QoS class map lists id' ;
                  }

                }

              }

            }

          }

          ncd:revise-date 2015-03-31 ;
        }

        container flow-feature {
          description 'Class map flow feature defination.' ;
          container class-maps {
            description 'Configure QoS class map lists.' ;
            list class-map {
              description 'Configure QoS class map list.' ;
              key cmap-name ;
              leaf cmap-name {
                description 'Name of the class map, support 1-31 characters.' ;
                type string {
                  length 1..31 {
                    description 'Name of the class map, support 1-31 characters' ;
                  }

                }

              }

              container effect-order {
                description 'The value specify the class effect order in the policy map.' ;
                presence "To set the effect order value" ;
                leaf effect-order {
                  description 'The value specify the class effect order in the policy map.' ;
                  type uint32 {
                    range 1..255 {
                      description 'The value specify the class effect order in the policy map.' ;
                    }

                  }

                  mandatory true ;
                }

              }

              container match {
                description 'Configure matching criteria for a class map.' ;
                container destination-port {
                  description 'Select destination-port as matching criteria.' ;
                  presence "Select destination-port as match criteria" ;
                  leaf dst-port-value {
                    description 'Configure destination-port value in range mode, support single destination-port value or range(max num:4;spacing mark:,) in <0-65535>. For example,"1,300-400,1000,2000-4000",etc.Specifically, port value 0 can only be configured in a single value format.' ;
                    type qos-port-range ;

                    mandatory true ;
                  }

                }

                container source-port {
                  description 'Select source-port as matching criteria.' ;
                  presence "Select source-port as match criteria" ;
                  leaf src-port-value {
                    description 'Configure source-port value in range mode, support single source-port value or range(max num:4;spacing mark:,) in <0-65535>. For example,"1,300-400,1000,2000-4000",etc.Specifically, port value 0 can only be configured in a single value format.' ;
                    type qos-port-range ;

                    mandatory true ;
                  }

                }

                container destination-ipv4-addr {
                  description 'Select destination-address as matching criteria.' ;
                  presence "Select destination-address as match criteria" ;
                  leaf dst-address {
                    description 'Destination address.' ;
                    type ncd:ipv4-address ;

                    mandatory true ;
                  }

                  leaf dst-address-mask {
                    description 'Destination maskcard bits, positive mask.' ;
                    type ncd:ipv4-mask ;

                    mandatory true ;
                  }

                }

                container source-ipv4-addr {
                  description 'Select source-address as matching criteria.' ;
                  presence "Select source-address as match criteria" ;
                  leaf src-address {
                    description 'Source address.' ;
                    type ncd:ipv4-address ;

                    mandatory true ;
                  }

                  leaf src-address-mask {
                    description 'Source maskcard bits, positive mask.' ;
                    type ncd:ipv4-mask ;

                    mandatory true ;
                  }

                }

                container protocol {
                  description 'Select protocol as matching criteria.' ;
                  presence "Select protocol as match criteria" ;
                  leaf not {
                    description 'Configure the opposite range flag:
true  Match opposite range;
false Match current range.' ;
                    type boolean ;

                  }

                  leaf protocol-value {
                    description 'Configure protocol in range mode, support single protocol value or range(max num:4;spacing mark:,) in <0-255>. For example,"6,10-30,40,50-60",etc.' ;
                    type ncd:bitmap {
                      pattern "(((((([1-9][0-9]{1,1})|([1-9][0-9]{0,0})|0|([1-1][0-9]{2,2})|(2[0-4][0-9]{1,1})|(25[0-4])|255)-(([1-9][0-9]{1,1})|([1-9][0-9]{0,0})|0|([1-1][0-9]{2,2})|(2[0-4][0-9]{1,1})|(25[0-4])|255))|(([1-9][0-9]{1,1})|([1-9][0-9]{0,0})|0|([1-1][0-9]{2,2})|(2[0-4][0-9]{1,1})|(25[0-4])|255)),){0,3}(((([1-9][0-9]{1,1})|([1-9][0-9]{0,0})|0|([1-1][0-9]{2,2})|(2[0-4][0-9]{1,1})|(25[0-4])|255)-(([1-9][0-9]{1,1})|([1-9][0-9]{0,0})|0|([1-1][0-9]{2,2})|(2[0-4][0-9]{1,1})|(25[0-4])|255))|(([1-9][0-9]{1,1})|([1-9][0-9]{0,0})|0|([1-1][0-9]{2,2})|(2[0-4][0-9]{1,1})|(25[0-4])|255)){1,1})" {
                        description 'Configure protocol in range mode, support single protocol value or range(max num:4;spacing mark:,).' ;
                      }

                    }

                    mandatory true ;
                  }

                }

                container destination-ipv6-addr {
                  description 'Select IPv6 destination-address as matching criteria.' ;
                  presence "Select destination-address as match criteria" ;
                  leaf dst-address {
                    description 'IPv6 destination address.' ;
                    type ncd:ipv6-address ;

                    mandatory true ;
                  }

                  leaf dst-address-mask {
                    description 'IPv6 destination maskcard bits, positive mask.' ;
                    type uint8 {
                      range 0..128 {
                        description 'Destination maskcard bits.' ;
                      }

                    }

                    mandatory true ;
                  }

                }

                container source-ipv6-addr {
                  description 'Select IPv6 source-address as matching criteria.' ;
                  presence "Select source-address as match criteria" ;
                  leaf src-address {
                    description 'IPv6 source address.' ;
                    type ncd:ipv6-address ;

                    mandatory true ;
                  }

                  leaf src-address-mask {
                    description 'IPv6 source maskcard bits, positive mask.' ;
                    type uint8 {
                      range 0..128 {
                        description 'Source maskcard bits.' ;
                      }

                    }

                    mandatory true ;
                  }

                }

                container interface {
                  description 'Select interface name as matching criteria.' ;
                  presence "Select interface name as match criteria" ;
                  leaf if-name {
                    description 'Set interface name.' ;
                    type ncd:ifname {
                      length 1..31 {
                        description 'Name of the interface, support 1-31 characters' ;
                      }

                    }

                    mandatory true ;
                  }

                }

                container vxlan-ipv4 {
                  description 'Select VXLAN tunnel as matching criteria.' ;
                  presence "Select VXLAN tunnel as match criteria" ;
                  leaf src-address {
                    description 'Source address.' ;
                    type ncd:ipv4-address ;

                    mandatory true ;
                  }

                  leaf dst-address {
                    description 'Destination address.' ;
                    type ncd:ipv4-address ;

                    mandatory true ;
                  }

                }

                container vni {
                  description 'Select VNI (VXLAN Network Identifier) as matching criteria.' ;
                  presence "To select VNI as match criteria" ;
                  leaf vni-range1-start {
                    description 'The starting-value of the first VNI range.' ;
                    type uint32 {
                      range 1..16777215 ;

                    }

                    mandatory true ;
                  }

                  leaf vni-range1-end {
                    description 'The ending-value of the first VNI range.' ;
                    type uint32 {
                      range 1..16777215 ;

                    }

                    mandatory true ;
                  }

                  container vni-range2 {
                    description 'To select the second VNI range.' ;
                    presence "The configuration of the second VNI range" ;
                    leaf vni-range2-start {
                      description 'The starting-value of the second VNI range.' ;
                      type uint32 {
                        range 1..16777215 ;

                      }

                      mandatory true ;
                    }

                    leaf vni-range2-end {
                      description 'The ending-value of the second VNI range.' ;
                      type uint32 {
                        range 1..16777215 ;

                      }

                      mandatory true ;
                    }

                    container vni-range3 {
                      description 'To select the third VNI range.' ;
                      presence "The configuration of the third VNI range" ;
                      leaf vni-range3-start {
                        description 'The starting-value of the third VNI range.' ;
                        type uint32 {
                          range 1..16777215 ;

                        }

                        mandatory true ;
                      }

                      leaf vni-range3-end {
                        description 'The ending-value of the third VNI range.' ;
                        type uint32 {
                          range 1..16777215 ;

                        }

                        mandatory true ;
                      }

                      container vni-range4 {
                        description 'To select the fourth VNI range.' ;
                        presence "The configuration of the fourth VNI range" ;
                        leaf vni-range4-start {
                          description 'The starting-value of the fourth VNI range.' ;
                          type uint32 {
                            range 1..16777215 ;

                          }

                          mandatory true ;
                        }

                        leaf vni-range4-end {
                          description 'The ending-value of the fourth VNI range.' ;
                          type uint32 {
                            range 1..16777215 ;

                          }

                          mandatory true ;
                        }

                      }

                    }

                  }

                }

                container vxlan-ipv6 {
                  description 'Select VXLAN tunnel as matching criteria.' ;
                  presence "Select VXLAN tunnel as match criteria" ;
                  leaf src-address {
                    description 'Source address.' ;
                    type ncd:ipv6-address ;

                    mandatory true ;
                  }

                  leaf dst-address {
                    description 'Destination address.' ;
                    type ncd:ipv6-address ;

                    mandatory true ;
                  }

                  ncd:revise-date 2020-03-05 ;
                }

              }

              container cmap-description {
                description 'Description of a class map, support 1-79 characters.' ;
                presence "Specify description of class map" ;
                leaf cmap-description {
                  description 'Description of a class map, support 1-79 characters.' ;
                  type ncd:string-with-blank {
                    length 1..79 {
                      description 'Description of a class map, support 1-79 characters.' ;
                    }

                  }

                  mandatory true ;
                }

                ncd:revise-date 2020-06-18 ;
              }

            }

          }

          ncd:revise-date 2019-04-15 ;
        }

        container traffic-based {
          description 'Class map based on traffic.' ;
          container class-maps {
            description 'Configure QoS class map lists.' ;
            list class-map {
              description 'Configure QoS class map list.' ;
              key cmap-name ;
              leaf cmap-name {
                description 'Name of the class map, support 1-31 characters.' ;
                type string {
                  length 1..31 {
                    description 'Name of the class map, support 1-31 characters' ;
                  }

                }

              }

              leaf match-relation {
                description 'The type of packets matching, see bellow:                
match-all Packets meet all of the match criteria;
match-any Packets meet any of the match criteria.' ;
                type enumeration {
                  enum match-all {
                    value 1 ;
                    description 'Packets meet all of the match criteria' ;
                  }

                  enum match-any {
                    value 2 ;
                    description 'Packets meet any of the match criteria' ;
                  }

                }

                mandatory true ;
              }

              container match {
                description 'Configure matching criteria for a class map.' ;
                container dscps {
                  description 'Select DSCP as matching criteria.' ;
                  list dscp {
                    description 'Set DSCP value as matching criteria.' ;
                    key ip-type ;
                    leaf ip-type {
                      description 'Configure DSCP value Based on IP, see below:
any  Packets based on any IP;
ipv4 Packets based on IPv4;
ipv6 Packets based on IPv6.' ;
                      type qos-ip-type ;

                    }

                    leaf not {
                      description 'Configure the opposite range flag:
true  Match opposite range;
false Match current range.' ;
                      type boolean ;

                      default false ;
                    }

                    leaf dscp-value {
                      description 'Configure QoS dscp in range mode, support single DSCP value or range(max num:4;spacing mark:,) in <0-63>. For example,"6,10-30,40,50-60",etc.' ;
                      type qos-dscp-bitmap ;

                      mandatory true ;
                    }

                  }

                }

                container dscp-exs {
                  if-feature class-match-dscp-ex ;

                  description 'Select the identification code mapped from DSCP to PHB (Per Hop Behavior), that is, reserve keywords as matching criteria.' ;
                  list dscp-ex {
                    description 'Set  the reserved keyword as matching criteria.' ;
                    key 'ip-type reserved-words' ;
                    leaf ip-type {
                      description 'Configure DSCP value Based on IP, see below:
any  Packets based on any IP;
ipv4 Packets based on IPv4;
ipv6 Packets based on IPv6.' ;
                      type qos-ip-type ;

                    }

                    leaf reserved-words {
                      description 'Configure the reserved keyword.' ;
                      type qos-reserved-words ;

                    }

                  }

                }

                container precedences {
                  description 'Select IP-Precedence as matching criteria.' ;
                  list precedence {
                    description 'Set IP Precedence value as matching criteria.' ;
                    key ip-type ;
                    leaf ip-type {
                      description 'Configure DSCP value Based on IP, see below:
any  Packets based on any IP;
ipv4 Packets based on IPv4;
ipv6 Packets based on IPv6.' ;
                      type qos-ip-type ;

                    }

                    leaf not {
                      description 'Configure the opposite range flag:
true  Match opposite range;
false Match current range.' ;
                      type boolean ;

                      default false ;
                    }

                    leaf prec-value {
                      description 'Configure QoS IP Precedence in range mode, support single precedence value or range(max num:4;spacing mark:,) in <0-7>. For example,"0,2-4,7",etc.' ;
                      type qos-prec-bitmap ;

                      mandatory true ;
                    }

                  }

                }

                container mpls-exp {
                  description 'Select MPLS-EXP as matching criteria.' ;
                  presence "Select MPLS-EXP as match criteria" ;
                  leaf mpls-exp-value {
                    description 'Configure QoS MPLS-EXP value in range mode, support single MPLS-EXP value or range(max num:4;spacing mark:,) in <0-7>. For example,"0,2-4,7",etc.' ;
                    type qos-mpls-bitmap ;

                    mandatory true ;
                  }

                }

                container in-vlan {
                  description 'Select inner-VLAN as matching criteria.' ;
                  presence "Select inner-VLAN as match criteria" ;
                  leaf vlan-value {
                    description 'Configure inner-VLAN value in range mode, support single inner-VLAN value or range(max num:4;spacing mark:,) in <1-4094>. For example,"1,300-400,1000,2000-4000",etc.' ;
                    type qos-vlan-bitmap ;

                    mandatory true ;
                  }

                }

                container out-vlan {
                  description 'Select outer-VLAN as matching criteria.' ;
                  presence "Select outer-VLAN as match criteria" ;
                  leaf vlan-value {
                    description 'Configure outer-VLAN value in range mode, support single outer-VLAN value or range(max num:4;spacing mark:,) in <1-4094>. For example,"1,300-400,1000,2000-4000",etc.' ;
                    type qos-vlan-bitmap ;

                    mandatory true ;
                  }

                }

                container in-8021p {
                  description 'Select inner 802.1p as matching criteria.' ;
                  presence "Select inner 802.1p as match criteria" ;
                  leaf in-8021p-value {
                    description 'Configure inner 802.1p value in range mode, support single 802.1p value or range(max num:4;spacing mark:,) in <0-7>. For example,"0,2-4,7",etc.' ;
                    type qos-8021p-bitmap ;

                    mandatory true ;
                  }

                }

                container out-8021p {
                  description 'Select outer 802.1p as matching criteria.' ;
                  presence "Select outer 802.1p as match criteria" ;
                  leaf out-8021p-value {
                    description 'Configure outer 802.1p value in range mode, support single 802.1p value or range(max num:4;spacing mark:,) in <0-7>. For example,"0,2-4,7",etc.' ;
                    type qos-8021p-bitmap ;

                    mandatory true ;
                  }

                }

                container qos-group {
                  description 'Select qos-group as matching criteria.' ;
                  presence "Select qos-group as match criteria" ;
                  leaf qos-id {
                    description 'Set qos-group number, support <1-65535>.' ;
                    type uint16 {
                      range 1..65535 ;

                    }

                    mandatory true ;
                  }

                }

                container vrf-name {
                  description 'Select vrf-name as matching criteria.' ;
                  presence "Select vrf-name as match criteria" ;
                  leaf vrf-name {
                    description 'Set vrf name, support 1-32 characters.' ;
                    type string {
                      length 1..32 {
                        description 'Vrf name, support 1-32 characters' ;
                      }

                    }

                    mandatory true ;
                  }

                  if-feature traffic-match-vrf {
                    ncd:revise-date 2024-07-17 ;
                  }

                }

                container uni-cast {
                  description 'Select unicast as matching criteria.' ;
                  presence "Select unicast as match criteria" ;
                  leaf uni-cast {
                    description 'Set unicast.' ;
                    type empty ;

                    mandatory true ;
                  }

                }

                container multi-cast {
                  description 'Select multicast as matching criteria.' ;
                  presence "Select multicast as match criteria" ;
                  leaf multi-cast {
                    description 'Set multicast.' ;
                    type empty ;

                    mandatory true ;
                  }

                }

                container mac-addr {
                  description 'Select mac-address as matching criteria.' ;
                  presence "Select mac-address as match criteria" ;
                  leaf mac-address {
                    description 'Configure mac-address.' ;
                    type ncd:mac-address ;

                    mandatory true ;
                  }

                }

                container ipv4-acls {
                  description 'Select IPv4 ACL name as matching criteria.' ;
                  list ipv4-acl {
                    description 'Set IPv4 ACL name as matching criteria.' ;
                    key acl-name ;
                    leaf acl-name {
                      description 'Set ipv4-access-list name, support 1-31 characters.' ;
                      type string {
                        length 1..31 {
                          description 'Name of ACL, support 1-31 characters' ;
                        }

                      }

                    }

                  }

                }

                container ipv6-acls {
                  description 'Select IPv6 ACL name as matching criteria.' ;
                  list ipv6-acl {
                    description 'Set IPv6 ACL name as matching criteria.' ;
                    key acl-name ;
                    leaf acl-name {
                      description 'Set ipv6-access-list name, support 1-31 characters.' ;
                      type string {
                        length 1..31 {
                          description 'Name of ACL, support 1-31 characters' ;
                        }

                      }

                    }

                  }

                }

                container link-acls {
                  if-feature class-match-link-acl ;

                  description 'Select link ACL name as matching criteria.' ;
                  list link-acl {
                    description 'Set link ACL name as matching criteria.' ;
                    key acl-name ;
                    leaf acl-name {
                      description 'Set link-access-list name, support 1-31 characters.' ;
                      type string {
                        length 1..31 {
                          description 'Name of ACL, support 1-31 characters' ;
                        }

                      }

                    }

                  }

                }

                container vpws {
                  description 'Select VPWS instance name as matching criteria.' ;
                  presence "Select VPWS instance name as match criteria" ;
                  leaf vpws-name {
                    description 'Set VPWS instance name, support 1-32 characters.' ;
                    type string {
                      length 1..32 {
                        description 'VPWS instance name, support 1-32 characters' ;
                      }

                    }

                    mandatory true ;
                  }

                }

                container vpls {
                  description 'Select VPLS instance name as matching criteria.' ;
                  presence "Select VPLS instance name as match criteria" ;
                  leaf vpls-name {
                    description 'Set VPLS instance name, support 1-32 characters.' ;
                    type string {
                      length 1..32 {
                        description 'VPLS instance name, support 1-32 characters' ;
                      }

                    }

                    mandatory true ;
                  }

                }

                container service-class {
                  if-feature phb-mode ;

                  description 'Select PHB as matching criteria.' ;
                  presence "Select PHB as match criteria" ;
                  leaf service-class {
                    description 'Select service class of PHB info.' ;
                    type qos-service-class ;

                    mandatory true ;
                  }

                }

                container vni {
                  description 'To select VNI (VXLAN Network Identifier) as matching criteria.' ;
                  presence "To select VNI as match criteria" ;
                  leaf vni-range1-start {
                    description 'The starting-value of the first VNI range.' ;
                    type uint32 {
                      range 1..16777215 ;

                    }

                    mandatory true ;
                  }

                  leaf vni-range1-end {
                    description 'The ending-value of the first VNI range.' ;
                    type uint32 {
                      range 1..16777215 ;

                    }

                    mandatory true ;
                  }

                  container vni-range2 {
                    description 'To select the second VNI range.' ;
                    presence "The configuration of the second VNI range" ;
                    leaf vni-range2-start {
                      description 'The starting-value of the second VNI range.' ;
                      type uint32 {
                        range 1..16777215 ;

                      }

                      mandatory true ;
                    }

                    leaf vni-range2-end {
                      description 'The ending-value of the second VNI range.' ;
                      type uint32 {
                        range 1..16777215 ;

                      }

                      mandatory true ;
                    }

                    container vni-range3 {
                      description 'To select the third VNI range.' ;
                      presence "The configuration of the third VNI range" ;
                      leaf vni-range3-start {
                        description 'The starting-value of the third VNI range.' ;
                        type uint32 {
                          range 1..16777215 ;

                        }

                        mandatory true ;
                      }

                      leaf vni-range3-end {
                        description 'The ending-value of the third VNI range.' ;
                        type uint32 {
                          range 1..16777215 ;

                        }

                        mandatory true ;
                      }

                      container vni-range4 {
                        description 'To select the fourth VNI range.' ;
                        presence "The configuration of the fourth VNI range" ;
                        leaf vni-range4-start {
                          description 'The starting-value of the fourth VNI range.' ;
                          type uint32 {
                            range 1..16777215 ;

                          }

                          mandatory true ;
                        }

                        leaf vni-range4-end {
                          description 'The ending-value of the fourth VNI range.' ;
                          type uint32 {
                            range 1..16777215 ;

                          }

                          mandatory true ;
                        }

                      }

                    }

                  }

                }

                container ipv4-mixed-acls {
                  description 'Select IPv4 mixed ACL name as matching criteria.' ;
                  list ipv4-mixed-acl {
                    description 'Set IPv4 mixed ACL name as matching criteria.' ;
                    key acl-name ;
                    leaf acl-name {
                      description 'Set ipv4-mixed-access-list name, support 1-31 characters.' ;
                      type string {
                        length 1..31 {
                          description 'Name of ACL, support 1-31 characters' ;
                        }

                      }

                    }

                  }

                }

                container ipv6-mixed-acls {
                  description 'Select IPv6 mixed ACL name as matching criteria.' ;
                  list ipv6-mixed-acl {
                    description 'Set IPv6 mixed ACL name as matching criteria.' ;
                    key acl-name ;
                    leaf acl-name {
                      description 'Set ipv6-mixed-access-list name, support 1-31 characters.' ;
                      type string {
                        length 1..31 {
                          description 'Name of ACL, support 1-31 characters' ;
                        }

                      }

                    }

                  }

                }

                container ipv4-vxlan-acls {
                  description 'Select IPv4 vxlan ACL name as matching criteria.' ;
                  list ipv4-vxlan-acl {
                    description 'Set IPv4 vxlan ACL name as matching criteria.' ;
                    key acl-name ;
                    leaf acl-name {
                      description 'Set ipv4-vxlan-access-list name, support 1-31 characters.' ;
                      type string {
                        length 1..31 {
                          description 'Name of ACL, support 1-31 characters.' ;
                        }

                      }

                    }

                  }

                }

                container ipv6-vxlan-acls {
                  description 'Select IPv6 vxlan ACL name as matching criteria.' ;
                  list ipv6-vxlan-acl {
                    description 'Set IPv6 vxlan ACL name as matching criteria.' ;
                    key acl-name ;
                    leaf acl-name {
                      description 'Set ipv6-vxlan-access-list name, support 1-31 characters.' ;
                      type string {
                        length 1..31 {
                          description 'Name of ACL, support 1-31 characters.' ;
                        }

                      }

                    }

                  }

                }

                container applications {
                  description 'Select application as matching criteria.' ;
                  list application {
                    description 'Select application as matching criteria.' ;
                    key application-name ;
                    leaf application-name {
                      description 'Set application name, support 1-31 characters.' ;
                      type string {
                        length 1..31 {
                          description 'Name of the application, support 1-31 characters' ;
                        }

                      }

                    }

                    leaf application-id {
                      description 'Set application id, support <1-65535>.' ;
                      type uint32 {
                        range 1..65535 ;

                      }

                      mandatory true ;
                    }

                  }

                  ncd:revise-date 2022-02-19 ;
                }

                container gre-inner-ipv4-acls {
                  if-feature class-match-gre-ipp-inner-acl ;

                  description 'Select IPv4 ACL name as matching criteria of GRE inner layer.' ;
                  list gre-inner-ipv4-acl {
                    description 'Set IPv4 ACL name as matching criteria of GRE inner layer.' ;
                    key acl-name ;
                    leaf acl-name {
                      description 'Set ipv4-access-list name, support 1-31 characters.' ;
                      type string {
                        length 1..31 {
                          description 'Name of ACL, support 1-31 characters.' ;
                        }

                      }

                    }

                  }

                  ncd:revise-date 2022-10-09 ;
                }

                container gre-inner-ipv6-acls {
                  if-feature class-match-gre-ipp-inner-acl ;

                  description 'Select IPv6 ACL name as matching criteria of GRE inner layer.' ;
                  list gre-inner-ipv6-acl {
                    description 'Set IPv6 ACL name as matching criteria of GRE inner layer.' ;
                    key acl-name ;
                    leaf acl-name {
                      description 'Set ipv6-access-list name, support 1-31 characters.' ;
                      type string {
                        length 1..31 {
                          description 'Name of ACL, support 1-31 characters.' ;
                        }

                      }

                    }

                  }

                  ncd:revise-date 2022-10-09 ;
                }

                container ipp-inner-ipv4-acls {
                  if-feature class-match-gre-ipp-inner-acl ;

                  description 'Select IPv4 ACL name as matching criteria of IPP(ip-in-ip) inner layer.' ;
                  list ipp-inner-ipv4-acl {
                    description 'Set IPv4 ACL name as matching criteria of IPP(ip-in-ip) inner layer.' ;
                    key acl-name ;
                    leaf acl-name {
                      description 'Set ipv4-access-list name, support 1-31 characters.' ;
                      type string {
                        length 1..31 {
                          description 'Name of ACL, support 1-31 characters.' ;
                        }

                      }

                    }

                  }

                  ncd:revise-date 2022-10-09 ;
                }

                container ipp-inner-ipv6-acls {
                  if-feature class-match-gre-ipp-inner-acl ;

                  description 'Select IPv6 ACL name as matching criteria of IPP(ip-in-ip) inner layer.' ;
                  list ipp-inner-ipv6-acl {
                    description 'Set IPv6 ACL name as matching criteria of IPP(ip-in-ip) inner layer.' ;
                    key acl-name ;
                    leaf acl-name {
                      description 'Set ipv6-access-list name, support 1-31 characters.' ;
                      type string {
                        length 1..31 {
                          description 'Name of ACL, support 1-31 characters.' ;
                        }

                      }

                    }

                  }

                  ncd:revise-date 2022-10-09 ;
                }

                container ipv4-rocev2 {
                  if-feature match-rocev2 ;

                  description 'Select IPv4 type RoCEv2 packets as matching criteria.' ;
                  choice opcode {
                    description 'Configure the message type of RoCEv2 that indicate the operation mode of it.' ;
                    case value {
                      description 'Configure the opcode value of RoCEv2.' ;
                      leaf opcode-value {
                        description 'Configure the opcode value of RoCEv2.' ;
                        type uint16 {
                          range 0..255 {
                            description 'The opcode value, support <0-255>.' ;
                          }

                        }

                      }

                    }

                    case cnp {
                      description 'Configure the RoCEv2 opcode as CNP.' ;
                      leaf cnp {
                        description 'Configure the RoCEv2 opcode as CNP.' ;
                        type empty ;

                      }

                      if-feature rocev2-cnp-feature ;

                      ncd:revise-date 2024-06-11 ;
                    }

                    case nak {
                      description 'Configure the RoCEv2 opcode as NAK.' ;
                      leaf nak {
                        description 'Configure the RoCEv2 opcode as NAK.' ;
                        type empty ;

                      }

                      if-feature rocev2-nak-feature ;

                      ncd:revise-date 2024-06-11 ;
                    }

                  }

                  leaf qpair-value {
                    description 'Configure the queue pair value of RoCEv2.' ;
                    type uint32 {
                      range 0..16777215 {
                        description 'The queue pair value, support <0-16777215>.' ;
                      }

                    }

                  }

                  container udf {
                    leaf udf-data {
                      type string {
                        length 10 {
                          description 'udf data, supports exactly 10 characters.' ;
                        }

                      }

                      description 'Set user defined hexadecimal string data,as follows:
0x00000000-0xffffffff.' ;
                      mandatory true ;
                    }

                    leaf udf-mask {
                      type string {
                        length 10 {
                          description 'udf mask, supports exactly 10 characters.' ;
                        }

                      }

                      description 'Set user defined hexadecimal string wildcard mask,as follows:
0x00000000-0xffffffff.' ;
                      mandatory true ;
                    }

                    leaf offset-value {
                      type uint8 {
                        range 8..20 {
                          description 'udf offset value, support 8-20.' ;
                        }

                      }

                      description 'Set user defined offset value.' ;
                      mandatory true ;
                    }

                    if-feature class-match-rocev2-udf ;

                    description 'Configure user defined base l4-head value.' ;
                    presence udf ;
                    ncd:revise-date 2025-02-11 ;
                  }

                  ncd:revise-date 2022-12-05 ;
                }

                container ipv6-rocev2 {
                  if-feature match-rocev2 ;

                  description 'Select IPv6 type RoCEv2 packets as matching criteria.' ;
                  choice opcode {
                    case value {
                      leaf opcode-value {
                        type uint16 {
                          range 0..255 {
                            description 'The opcode value, support <0-255>.' ;
                          }

                        }

                        description 'Configure the opcode value of RoCEv2.' ;
                      }

                      description 'Configure the opcode value of RoCEv2.' ;
                    }

                    case cnp {
                      leaf cnp {
                        type empty ;

                        description 'Configure the RoCEv2 opcode as CNP.' ;
                      }

                      if-feature rocev2-cnp-feature ;

                      description 'Configure the RoCEv2 opcode as CNP.' ;
                      ncd:revise-date 2024-06-11 ;
                    }

                    case nak {
                      leaf nak {
                        type empty ;

                        description 'Configure the RoCEv2 opcode as NAK.' ;
                      }

                      if-feature rocev2-nak-feature ;

                      description 'Configure the RoCEv2 opcode as NAK.' ;
                      ncd:revise-date 2024-06-11 ;
                    }

                    description 'Configure the message type of RoCEv2 that indicate the operation mode of it.' ;
                  }

                  leaf qpair-value {
                    description 'Configure the queue pair value of RoCEv2.' ;
                    type uint32 {
                      range 0..16777215 {
                        description 'The queue pair value, support <0-16777215>.' ;
                      }

                    }

                  }

                  container udf {
                    leaf udf-data {
                      type string {
                        length 10 {
                          description 'udf data, supports exactly 10 characters.' ;
                        }

                      }

                      description 'Set user defined hexadecimal string data,as follows:
0x00000000-0xffffffff.' ;
                      mandatory true ;
                    }

                    leaf udf-mask {
                      type string {
                        length 10 {
                          description 'udf mask, supports exactly 10 characters.' ;
                        }

                      }

                      description 'Set user defined hexadecimal string wildcard mask,as follows:
0x00000000-0xffffffff.' ;
                      mandatory true ;
                    }

                    leaf offset-value {
                      type uint8 {
                        range 8..20 {
                          description 'udf offset value, support 8-20.' ;
                        }

                      }

                      description 'Set user defined offset value.' ;
                      mandatory true ;
                    }

                    if-feature class-match-rocev2-udf ;

                    description 'Configure user defined base l4-head value.' ;
                    presence udf ;
                    ncd:revise-date 2025-02-11 ;
                  }

                  ncd:revise-date 2022-12-05 ;
                }

              }

              container cmap-description {
                description 'Description of a class map, support 1-79 characters.' ;
                presence "Specify description of class map" ;
                leaf cmap-description {
                  description 'Description of a class map, support 1-79 characters.' ;
                  type ncd:string-with-blank {
                    length 1..79 {
                      description 'Description of a class map, support 1-79 characters.' ;
                    }

                  }

                  mandatory true ;
                }

              }

            }

          }

          ncd:revise-date 2021-01-25 ;
        }

        container cps-based {
          description 'Class map based on control-plane-security.' ;
          container class-maps {
            description 'Configure QoS class map lists.' ;
            list class-map {
              description 'Configure QoS class map list.' ;
              key cmap-name ;
              leaf cmap-name {
                description 'Name of the class map, support 1-31 characters.' ;
                type string {
                  length 1..31 {
                    description 'Name of the class map, support 1-31 characters' ;
                  }

                }

              }

              leaf match-relation {
                description 'The type of packets matching, see bellow:                
match-all Packets meet all of the match criteria;
match-any Packets meet any of the match criteria.' ;
                type enumeration {
                  enum match-all {
                    value 1 ;
                    description 'Packets meet all of the match criteria' ;
                  }

                  enum match-any {
                    value 2 ;
                    description 'Packets meet any of the match criteria' ;
                  }

                }

                mandatory true ;
              }

              container match {
                description 'Configure matching criteria for a class map.' ;
                container in-vlan {
                  description 'Select inner-VLAN as matching criteria.' ;
                  presence "Select inner-VLAN as match criteria" ;
                  leaf vlan-value {
                    description 'Configure inner-VLAN value in range mode, support single inner-VLAN value or range(max num:4;spacing mark:,) in <1-4094>. For example,"1,300-400,1000,2000-4000",etc.' ;
                    type qos-vlan-bitmap ;

                    mandatory true ;
                  }

                }

                container out-vlan {
                  description 'Select outer-VLAN as matching criteria.' ;
                  presence "Select outer-VLAN as match criteria" ;
                  leaf vlan-value {
                    description 'Configure outer-VLAN value in range mode, support single outer-VLAN value or range(max num:4;spacing mark:,) in <1-4094>. For example,"1,300-400,1000,2000-4000",etc.' ;
                    type qos-vlan-bitmap ;

                    mandatory true ;
                  }

                }

                container ipv4-acls {
                  description 'Select IPv4 ACL name as matching criteria.' ;
                  list ipv4-acl {
                    description 'Set IPv4 ACL name as matching criteria.' ;
                    key acl-name ;
                    leaf acl-name {
                      description 'Set ipv4-access-list name, support 1-31 characters.' ;
                      type string {
                        length 1..31 {
                          description 'Name of ACL, support 1-31 characters' ;
                        }

                      }

                    }

                  }

                }

                container ipv6-acls {
                  description 'Select IPv6 ACL name as matching criteria.' ;
                  list ipv6-acl {
                    description 'Set IPv6 ACL name as matching criteria.' ;
                    key acl-name ;
                    leaf acl-name {
                      description 'Set ipv6-access-list name, support 1-31 characters.' ;
                      type string {
                        length 1..31 {
                          description 'Name of ACL, support 1-31 characters' ;
                        }

                      }

                    }

                  }

                }

                container link-acls {
                  description 'Select link ACL name as matching criteria.' ;
                  list link-acl {
                    description 'Set link ACL name as matching criteria.' ;
                    key acl-name ;
                    leaf acl-name {
                      description 'Set link-access-list name, support 1-31 characters.' ;
                      type string {
                        length 1..31 {
                          description 'Name of ACL, support 1-31 characters' ;
                        }

                      }

                    }

                  }

                }

                container flowtypes {
                  description 'Select flowtype name as matching criteria.' ;
                  list flowtype {
                    description 'Set flowtype name as matching criteria.' ;
                    key flowtype-name ;
                    leaf flowtype-name {
                      description 'Set flowtype-name.' ;
                      type cps:flowtype-name-ex ;

                    }

                  }

                }

              }

              container cmap-description {
                description 'Description of a class map, support 1-79 characters.' ;
                presence "Specify description of class map" ;
                leaf cmap-description {
                  description 'Description of a class map, support 1-79 characters.' ;
                  type ncd:string-with-blank {
                    length 1..79 {
                      description 'Description of a class map, support 1-79 characters.' ;
                    }

                  }

                  mandatory true ;
                }

              }

            }

          }

          ncd:revise-date 2021-04-18 ;
        }

      }

      container policy-map {
        description 'Configure QoS policy map.' ;
        container normal {
          if-feature normal-mode ;

          description 'Policy map based on normal.' ;
          container policy-maps {
            description 'Configure H-QoS policy map lists.' ;
            list policy-map {
              description 'Configure H-QoS policy maps.' ;
              key pmap-name ;
              leaf pmap-name {
                description 'Name of the policy map, support 1-31 characters.' ;
                type string {
                  length 1..31 {
                    description 'Name of the policy map, support 1-31 characters' ;
                  }

                }

              }

              container class-maps {
                description 'Configure H-QoS policy class.' ;
                list class-map {
                  description 'Configure H-QoS policy class.' ;
                  key cmap-name ;
                  leaf cmap-name {
                    description 'Name of the class map, support 1-31 characters.' ;
                    type string {
                      length 1..31 {
                        description 'Name of the class map, support 1-31 characters' ;
                      }

                    }

                  }

                  container bandwidth {
                    description 'Configure minimum guaranteed bandwidth.' ;
                    presence "Configure minimum guaranteed bandwidth" ;
                    leaf percentage {
                      description 'Set the exact bandwidth percentage, support <1-100>.' ;
                      type uint16 {
                        range 1..100 {
                          description 'The exact bandwidth percentage, support <1-100>' ;
                        }

                      }

                      mandatory true ;
                    }

                  }

                  container bandwidth-remaining {
                    description 'Configure leftover bandwidth.' ;
                    presence "Configure leftover bandwidth" ;
                    leaf percentage {
                      description 'Set the leftover bandwidth percentage, support <1-100>.' ;
                      type uint16 {
                        range 1..100 {
                          description 'The guaranteed percentage, support <1-100>' ;
                        }

                      }

                      mandatory true ;
                    }

                  }

                  container priority-level {
                    description 'Configure PQ(Priority Queuing) priority level.' ;
                    presence "Configure PQ priority level" ;
                    leaf priority-value {
                      description 'Set the priority level of PQ.' ;
                      type uint16 {
                        range 1..8 {
                          description 'The priority level of PQ' ;
                        }

                      }

                      mandatory true ;
                    }

                  }

                  container priority-llq {
                    description 'Configure LLQ(Low Latency Queuing) priority.' ;
                    presence "Configure LLQ priority" ;
                    leaf priority-llq {
                      description 'Specify LLQ.' ;
                      type empty ;

                      mandatory true ;
                    }

                  }

                  container queue-limit {
                    description 'Configure queue depth.' ;
                    presence "Configure queue depth" ;
                    choice queue-limit {
                      description 'Configure queue depth.' ;
                      case queue-depth {
                        description 'Set queue depth.' ;
                        leaf queue-depth {
                          description 'Set queue depth.' ;
                          type enumeration {
                            enum 16 {
                              value 1 ;
                              description 'Set queue depth to 16KB' ;
                            }

                            enum 24 {
                              value 2 ;
                              description 'Set queue depth to 24KB' ;
                            }

                            enum 64 {
                              value 3 ;
                              description 'Set queue depth to 64KB' ;
                            }

                            enum 512 {
                              value 4 ;
                              description 'Set queue depth to 512KB' ;
                            }

                            enum 2000 {
                              value 5 ;
                              description 'Set queue depth to 2000KB' ;
                            }

                            enum 8000 {
                              value 6 ;
                              description 'Set queue depth to 8000KB' ;
                            }

                            enum 7 {
                              value 7 ;
                              description 'Set queue depth to 7KB' ;
                            }

                            enum 1000 {
                              value 20 ;
                              description 'Set queue depth to 1000KB' ;
                            }

                            enum 8000000 {
                              value 21 ;
                              description 'Set queue depth to 8000000KB' ;
                            }

                            enum 1000000 {
                              value 13 ;
                              description 'Set queue depth to 1000000KB' ;
                            }

                            enum 128000 {
                              value 11 ;
                              description 'Set queue depth to 128000KB' ;
                            }

                            enum 16000 {
                              value 8 ;
                              description 'Set queue depth to 16000KB' ;
                            }

                            enum 24000 {
                              value 9 ;
                              description 'Set queue depth to 24000KB' ;
                            }

                            enum 512000 {
                              value 12 ;
                              description 'Set queue depth to 512000KB' ;
                            }

                            enum 64000 {
                              value 10 ;
                              description 'Set queue depth to 64000KB' ;
                            }

                          }

                          units KB ;
                          mandatory true ;
                        }

                      }

                      case queue-value {
                        description 'Set queue depth value(default:KB).' ;
                        container queue-value {
                          description 'Set queue depth value(default:KB).' ;
                          leaf queue-value {
                            description 'Set queue depth value(default:KB).' ;
                            type uint32 {
                              range 7..8000000 {
                                description 'Set queue depth value(default:KB)' ;
                              }

                            }

                            mandatory true ;
                          }

                        }

                        ncd:revise-date 2019-08-19 ;
                      }

                      case queue-cache-time {
                        description 'Configure cache time of the queue.' ;
                        container queue-cache-time {
                          description 'Configure cache time of the queue.' ;
                          leaf queue-cache-time {
                            description 'Set cache time(default:us).' ;
                            type uint32 {
                              range 1..100000 {
                                description 'Set cache time(default:us)' ;
                              }

                            }

                            mandatory true ;
                          }

                        }

                        ncd:revise-date 2019-08-19 ;
                      }

                    }

                  }

                  container random-detect {
                    description 'Configure WRED(Weighted Random Early Detection) information.' ;
                    container enable {
                      description 'Enable/disable WRED function.' ;
                      presence "Configure WRED enable" ;
                      leaf enable {
                        description 'Enable WRED.' ;
                        type empty ;

                        mandatory true ;
                      }

                    }

                    container colors {
                      if-feature policy-action-wred-color ;

                      description 'Configure WRED thresholds based on color.' ;
                      list color {
                        description 'Configure WRED thresholds based on color.' ;
                        key color-type ;
                        leaf color-type {
                          description 'Set WRED color, such as green, yellow, red.' ;
                          type qos-color-type ;

                        }

                        choice threshold {
                          description 'Set the threshold.' ;
                          case threshold-value {
                            description 'Set the threshold value.' ;
                            leaf min-threshold {
                              description 'Set the minimum threshold, support <1-1024000>.' ;
                              type uint32 {
                                range 1..1024000 {
                                  description 'The minimum threshold in kilobytes, support <1-1024000>' ;
                                }

                              }

                              units KB ;
                              mandatory true ;
                            }

                            leaf max-threshold {
                              description 'Set the maximum threshold, support <1-1024000>.' ;
                              type uint32 {
                                range 1..1024000 {
                                  description 'The maximum threshold in kilobytes, support <1-1024000>' ;
                                }

                              }

                              units KB ;
                              mandatory true ;
                            }

                          }

                          case threshold-percentage {
                            description 'Set the threshold percentage.' ;
                            container threshold-percentage {
                              description 'Set the threshold percentage.' ;
                              leaf min-threshold-percentage {
                                description 'Set the minimum threshold percentage, support <1-100>.' ;
                                type uint32 {
                                  range 1..100 {
                                    description 'The minimum threshold percentage, support <1-100>' ;
                                  }

                                }

                                mandatory true ;
                              }

                              leaf max-threshold-percentage {
                                description 'Set the maximum threshold percentage, support <1-100>.' ;
                                type uint32 {
                                  range 1..100 {
                                    description 'The maximum threshold percentage, support <1-100>' ;
                                  }

                                }

                                mandatory true ;
                              }

                            }

                          }

                          ncd:revise-date 2019-08-05 ;
                        }

                        leaf probability {
                          description 'Set mark probability denominator, support <1-100>.' ;
                          type uint8 {
                            range 1..100 {
                              description 'Set mark probability denominator, support <1-100>' ;
                            }

                          }

                          mandatory true ;
                        }

                      }

                    }

                    container precedences {
                      description 'Configure WRED thresholds based on precedence.' ;
                      list precedence {
                        description 'Configure WRED thresholds based on precedence.' ;
                        key prec-value ;
                        leaf prec-value {
                          description 'Set the precedence value, such as MPLS EXP, VLAN 802.1p, IP DSCP, IP Precedence, support <0-7>.' ;
                          type uint16 {
                            range 0..7 {
                              description 'The IP-Precedence value, support <0-7>' ;
                            }

                          }

                        }

                        choice threshold {
                          description 'Set the threshold.' ;
                          case threshold-value {
                            description 'Set the threshold value.' ;
                            leaf min-threshold {
                              description 'Set the minimum threshold (default: kilobytes).' ;
                              type uint32 {
                                range 1..4294967295 {
                                  description 'The minimum threshold (default: kilobytes), support <1-4294967295>' ;
                                }

                              }

                              mandatory true ;
                            }

                            leaf min-threshold-unit {
                              description 'Set min-threshold unit, such as kbytes, mbytes, gbytes.' ;
                              type qos-threshold-unit-type ;

                            }

                            leaf max-threshold {
                              description 'Set the maximum threshold (default: kilobytes).' ;
                              type uint32 {
                                range 1..4294967295 {
                                  description 'The maximum threshold (default: kilobytes), support <1-4294967295>.' ;
                                }

                              }

                              mandatory true ;
                            }

                            leaf max-threshold-unit {
                              description 'Set max-threshold unit, such as kbytes, mbytes, gbytes.' ;
                              type qos-threshold-unit-type ;

                            }

                          }

                          case threshold-percentage {
                            description 'Set the threshold percentage.' ;
                            container threshold-percentage {
                              description 'Set the threshold percentage.' ;
                              leaf min-threshold-percentage {
                                description 'Set the minimum threshold percentage, support <1-100>.' ;
                                type uint32 {
                                  range 1..100 {
                                    description 'The minimum threshold percentage, support <1-100>' ;
                                  }

                                }

                                mandatory true ;
                              }

                              leaf max-threshold-percentage {
                                description 'Set the maximum threshold percentage, support <1-100>.' ;
                                type uint32 {
                                  range 1..100 {
                                    description 'The maximum threshold percentage, support <1-100>' ;
                                  }

                                }

                                mandatory true ;
                              }

                            }

                          }

                          case threshold-cachetime {
                            if-feature policy-action-wred-precedence-cachetime ;

                            description 'Set the threshold cachetime.' ;
                            container threshold-cachetime {
                              description 'Set the threshold cachetime.' ;
                              leaf min-threshold-cachetime {
                                description 'Set the minimum threshold cachetime (default: ms).' ;
                                type uint32 {
                                  range 1..1000 {
                                    description 'The minimum threshold cachetime, support <1-1000>' ;
                                  }

                                }

                                mandatory true ;
                              }

                              leaf max-threshold-cachetime {
                                description 'Set the maximum threshold cachetime (default: ms).' ;
                                type uint32 {
                                  range 1..1000 {
                                    description 'The maximum threshold cachetime, support <1-1000>' ;
                                  }

                                }

                                mandatory true ;
                              }

                            }

                            ncd:revise-date 2021-11-19 ;
                          }

                          ncd:revise-date 2019-08-05 ;
                        }

                        leaf probability {
                          description 'Set mark probability denominator, support <1-100>.' ;
                          type uint32 {
                            range 1..100 {
                              description 'Set mark probability denominator, support <1-100>' ;
                            }

                          }

                          mandatory true ;
                        }

                      }

                    }

                    container weight {
                      description 'Configure WRED exponential weight factor.' ;
                      presence "Configure WRED exponential weight factor" ;
                      leaf weight-value {
                        description 'Specify exponent used in weighted average calculation, support <1-16>.' ;
                        type uint16 {
                          range 1..16 {
                            description 'Exponent used in weighted average calculation' ;
                          }

                        }

                        mandatory true ;
                      }

                    }

                  }

                  container service-policy {
                    description 'Configure hierarchical service policy.' ;
                    presence "Configure hierarchical service policy" ;
                    leaf hpolicy-name {
                      description 'Name of the hierarchical policy, support 1-31 characters.' ;
                      type string {
                        length 1..31 {
                          description 'Name of the hierarchical policy, support 1-31 characters' ;
                        }

                      }

                      mandatory true ;
                    }

                  }

                  container shape {
                    if-feature policy-action-shape ;

                    description 'Configure flow shape.' ;
                    presence "Configure flow shape" ;
                    leaf shape-type {
                      description 'Set shape type, such as peak, average.' ;
                      type enumeration {
                        enum average {
                          value 1 ;
                          description 'Set average as shape type' ;
                        }

                        enum peak {
                          value 2 ;
                          description 'Set peak as shape type' ;
                        }

                      }

                      mandatory true ;
                    }

                    choice shape-method {
                      description 'Select rate or rate percentage as shape unit.' ;
                      mandatory true ;
                      case rate {
                        description 'Select the average or peak rate.' ;
                        leaf rate-value {
                          description 'Set the average or peak rate.' ;
                          type uint32 {
                            range 1..4294967295 {
                              description 'The average or peak rate in kbps, support <1-4294967295>' ;
                            }

                          }

                          units kbps ;
                          mandatory true ;
                        }

                        leaf rate-unit {
                          type qos-rate-unit-type ;

                          description 'Specify rate unit.' ;
                          if-feature qos-shape-unit ;

                          ncd:revise-date 2023-06-20 ;
                        }

                      }

                      case percent {
                        description 'Select rate percent as shape unit.' ;
                        leaf percentage {
                          description 'Set the exact rate percentage, support <1-100>.' ;
                          type uint16 {
                            range 1..100 {
                              description 'The exact rate percentage, support <1-100>' ;
                            }

                          }

                          mandatory true ;
                        }

                      }

                    }

                    container burst-rate {
                      description 'Configure sustained and excessive burst rates.' ;
                      presence "Configure committed burst and peak rate" ;
                      leaf bc-value {
                        description 'Set the bc value.' ;
                        type uint32 {
                          range 1..4294967295 {
                            description 'The committed burst information rate in kilobits per second, support <1-4294967295>' ;
                          }

                        }

                        units kbps ;
                        mandatory true ;
                      }

                      leaf be-value {
                        description 'Set the be value.' ;
                        type uint32 {
                          range 1..4294967295 {
                            description 'The peak information rate in kilobits per second, support <1-4294967295>' ;
                          }

                        }

                        units kbps ;
                        mandatory true ;
                      }

                    }

                  }

                  container police {
                    description 'Configure traffic policing.' ;
                    presence "Configure traffic policing" ;
                    choice cir-pir-value-percentage {
                      description 'Configure CIR CBS PIR and PBS.' ;
                      mandatory true ;
                      case cir-pir-value {
                        description 'Configure CIR and PIR with value form.' ;
                        leaf cir {
                          description 'Configure the CIR (Committed Information Rate) value, default: kilobits per second.' ;
                          type uint32 {
                            range 8..4294967295 {
                              description 'The CIR value (default: kilobits per second),support <8-4294967295>.' ;
                            }

                          }

                          mandatory true ;
                        }

                        leaf cir-unit {
                          description 'Set CIR unit, such as kbps, mbps, gbps.' ;
                          type qos-rate-unit-type ;

                        }

                        leaf cbs {
                          description 'Configure the CBS(Committed Burst Size) size, default: KB.' ;
                          type uint32 {
                            range 1..4294967295 {
                              description 'The CBS(Committed Burst Size) size (default: KB), support <1-4294967295>' ;
                            }

                          }

                        }

                        leaf cbs-unit {
                          description 'Set CBS unit, such as kb, mb, gb.' ;
                          type qos-bucket-unit-type ;

                        }

                        container pir-pbs {
                          description 'Configure PIR and PBS.' ;
                          presence "Configure pir and pbs" ;
                          leaf pir {
                            description 'Configure the PIR(Peak Information Rate) value, default: kilobits per second.' ;
                            type uint32 {
                              range 8..4294967295 {
                                description 'The PIR(Peak Information Rate) value (default: kilobits per second), support <8-4294967295>' ;
                              }

                            }

                            mandatory true ;
                          }

                          leaf pir-unit {
                            description 'Set PIR unit, such as kbps, mbps, gbps.' ;
                            type qos-rate-unit-type ;

                          }

                          leaf pbs {
                            description 'Configure the PBS(Peak Burst Size) size, default: KB.' ;
                            type uint32 {
                              range 1..4294967295 {
                                description 'The PBS(Peak Burst Size) size (default: KB), support <1-4294967295>' ;
                              }

                            }

                          }

                          leaf pbs-unit {
                            description 'Set PBS unit, such as kb, mb, gb.' ;
                            type qos-bucket-unit-type ;

                          }

                        }

                      }

                      case cir-pir-percentage {
                        description 'Configure CIR and PIR with percentage form.' ;
                        container cir-pir-percentage {
                          description 'Configure CIR and PIR with percentage form.' ;
                          leaf cir-percentage {
                            description 'Configure CIR with percentage form.' ;
                            type uint8 {
                              range 1..100 {
                                description 'Configure CIR with percentage form' ;
                              }

                            }

                            mandatory true ;
                          }

                          container pir-percentage {
                            description 'Configure PIR with percentage form.' ;
                            presence "Configure PIR with percentage form" ;
                            leaf pir-percentage {
                              description 'Configure PIR with percentage form.' ;
                              type uint8 {
                                range 1..100 {
                                  description 'Configure PIR with percentage form' ;
                                }

                              }

                              mandatory true ;
                            }

                          }

                        }

                        ncd:revise-date 2020-06-09 ;
                      }

                    }

                    container action {
                      description 'Set monitoring action  for each measurement evaluation packet.' ;
                      presence "Configure action to packets" ;
                      container conform-action {
                        description 'Action to packets that conform to the rate limit.' ;
                        choice conform-action {
                          description 'Specify action to packets that conform to the rate limit.' ;
                          mandatory true ;
                          case ca-drop {
                            description 'Drop packet in conform-action.' ;
                            leaf drop {
                              description 'Specify action to drop packet.' ;
                              type empty ;

                              mandatory true ;
                            }

                          }

                          case ca-transmit {
                            description 'Transmit packet in conform-action.' ;
                            leaf transmit {
                              description 'Specify action to transmit packet.' ;
                              type empty ;

                              mandatory true ;
                            }

                          }

                          case ca-mpls-exp {
                            description 'Rewrite packet MPLS-EXP and transmit the packet.' ;
                            leaf set-exp-transmit {
                              description 'Specify action to rewrite packet MPLS-EXP and transmit it.' ;
                              type empty ;

                              mandatory true ;
                            }

                            leaf mpls-exp-value {
                              description 'Reset MPLS-EXP value in conform-action, support <0-7>.' ;
                              type uint8 {
                                range 0..7 {
                                  description 'The MPLS-EXP value, support <0-7>' ;
                                }

                              }

                              mandatory true ;
                            }

                          }

                          case ca-precedence {
                            description 'Rewrite packet precedence and transmit the packet.' ;
                            leaf set-prec-transmit {
                              description 'Specify action to rewrite packet precedence and transmit it.' ;
                              type empty ;

                              mandatory true ;
                            }

                            leaf prec-value {
                              description 'Reset the IP-Precedence value in conform-action, support <0-7>.' ;
                              type uint8 {
                                range 0..7 {
                                  description 'The IP-Precedence value, support <0-7>' ;
                                }

                              }

                              mandatory true ;
                            }

                          }

                          case ca-dscp {
                            description 'Rewrite packet DSCP and transmit the packet.' ;
                            leaf set-dscp-transmit {
                              description 'Specify action to rewrite packet DSCP and transmit it.' ;
                              type empty ;

                              mandatory true ;
                            }

                            leaf dscp-value {
                              description 'Reset DSCP in conform-action, support <0-63>.' ;
                              type uint8 {
                                range 0..63 {
                                  description 'The DSCP value, support <0-63>' ;
                                }

                              }

                              mandatory true ;
                            }

                          }

                          case ca-8021p {
                            description 'Rewrite packet 802.1p and transmit the packet.' ;
                            leaf set-8021p-transmit {
                              description 'Specify action to rewrite packet 802.1p and transmit it.' ;
                              type empty ;

                              mandatory true ;
                            }

                            leaf value-8021p {
                              description 'Reset 802.1p in conform-action, support <0-7>.' ;
                              type uint8 {
                                range 0..7 {
                                  description 'The 802.1p value, support <0-7>' ;
                                }

                              }

                              mandatory true ;
                            }

                          }

                          case ca-priority {
                            description 'Rewrite packet priority and transmit the packet.' ;
                            leaf set-priority-transmit {
                              description 'Specify action to rewrite packet priority and transmit it.' ;
                              type empty ;

                              mandatory true ;
                            }

                            leaf priority-value {
                              description 'Reset priority in conform-action, support <1-4>.' ;
                              type uint8 {
                                range 1..4 {
                                  description 'The priority value, support <1-4>' ;
                                }

                              }

                              mandatory true ;
                            }

                          }

                        }

                      }

                      container exceed-action {
                        description 'Action to packets that exceed the rate limit.' ;
                        choice exceed-action {
                          description 'Specify action to packets that exceed the rate limit.' ;
                          mandatory true ;
                          case ea-drop {
                            description 'Drop packet in exceed-action.' ;
                            leaf drop {
                              description 'Specify action to drop packet.' ;
                              type empty ;

                              mandatory true ;
                            }

                          }

                          case ea-transmit {
                            description 'Transmit packet in exceed-action.' ;
                            leaf transmit {
                              description 'Specify action to transmit packet.' ;
                              type empty ;

                              mandatory true ;
                            }

                          }

                          case ea-mpls-exp {
                            description 'Rewrite packet MPLS-EXP and transmit the packet.' ;
                            leaf set-exp-transmit {
                              description 'Specify action to rewrite packet MPLS-EXP and transmit it.' ;
                              type empty ;

                              mandatory true ;
                            }

                            leaf mpls-exp-value {
                              description 'Reset MPLS-EXP value in exceed-action, support <0-7>.' ;
                              type uint8 {
                                range 0..7 {
                                  description 'The MPLS-EXP value, support <0-7>' ;
                                }

                              }

                              mandatory true ;
                            }

                          }

                          case ea-precedence {
                            description 'Rewrite packet precedence and transmit the packet.' ;
                            leaf set-prec-transmit {
                              description 'Specify action to rewrite packet precedence and transmit it.' ;
                              type empty ;

                              mandatory true ;
                            }

                            leaf prec-value {
                              description 'Reset the IP-Precedence value in exceed-action, support <0-7>.' ;
                              type uint8 {
                                range 0..7 {
                                  description 'The IP-Precedence value, support <0-7>' ;
                                }

                              }

                              mandatory true ;
                            }

                          }

                          case ea-dscp {
                            description 'Rewrite packet DSCP and transmit the packet.' ;
                            leaf set-dscp-transmit {
                              description 'Specify action to rewrite packet DSCP and transmit it.' ;
                              type empty ;

                              mandatory true ;
                            }

                            leaf dscp-value {
                              description 'Reset DSCP in exceed-action, support <0-63>.' ;
                              type uint8 {
                                range 0..63 {
                                  description 'The DSCP value, support <0-63>' ;
                                }

                              }

                              mandatory true ;
                            }

                          }

                          case ea-8021p {
                            description 'Rewrite packet 802.1p and transmit the packet.' ;
                            leaf set-8021p-transmit {
                              description 'Specify action to rewrite packet 802.1p and transmit it.' ;
                              type empty ;

                              mandatory true ;
                            }

                            leaf value-8021p {
                              description 'Reset 802.1p in exceed-action, support <0-7>.' ;
                              type uint8 {
                                range 0..7 {
                                  description 'The 802.1p value, support <0-7>' ;
                                }

                              }

                              mandatory true ;
                            }

                          }

                          case ea-priority {
                            description 'Rewrite packet priority and transmit the packet.' ;
                            leaf set-priority-transmit {
                              description 'Specify action to rewrite packet priority and transmit it.' ;
                              type empty ;

                              mandatory true ;
                            }

                            leaf priority-value {
                              description 'Reset priority in exceed-action, support <1-4>.' ;
                              type uint8 {
                                range 1..4 {
                                  description 'The priority value, support <1-4>' ;
                                }

                              }

                              mandatory true ;
                            }

                          }

                        }

                      }

                      container violate-action {
                        description 'Action to packets that violate the rate limit.' ;
                        choice violate-action {
                          description 'Specify action to packets that violate the rate limit.' ;
                          mandatory true ;
                          case va-drop {
                            description 'Drop packet in violate-action.' ;
                            leaf drop {
                              description 'Specify action to drop packet.' ;
                              type empty ;

                              mandatory true ;
                            }

                          }

                          case va-transmit {
                            description 'Transmit packet in violate-action.' ;
                            leaf transmit {
                              description 'Specify action to transmit packet.' ;
                              type empty ;

                              mandatory true ;
                            }

                          }

                          case va-mpls-exp {
                            description 'Rewrite packet MPLS-EXP and transmit the packet.' ;
                            leaf set-exp-transmit {
                              description 'Specify action to rewrite packet MPLS-EXP and transmit it.' ;
                              type empty ;

                              mandatory true ;
                            }

                            leaf mpls-exp-value {
                              description 'Reset MPLS-EXP value in violate-action, support <0-7>.' ;
                              type uint8 {
                                range 0..7 {
                                  description 'The MPLS-EXP value, support <0-7>' ;
                                }

                              }

                              mandatory true ;
                            }

                          }

                          case va-precedence {
                            description 'Rewrite packet precedence and transmit the packet.' ;
                            leaf set-prec-transmit {
                              description 'Specify action to rewrite packet precedence and transmit it.' ;
                              type empty ;

                              mandatory true ;
                            }

                            leaf prec-value {
                              description 'Reset the IP-Precedence value in violate-action, support <0-7>.' ;
                              type uint8 {
                                range 0..7 {
                                  description 'The IP-Precedence value, support <0-7>' ;
                                }

                              }

                              mandatory true ;
                            }

                          }

                          case va-dscp {
                            description 'Rewrite packet DSCP and transmit the packet.' ;
                            leaf set-dscp-transmit {
                              description 'Specify action to rewrite packet DSCP and transmit it.' ;
                              type empty ;

                              mandatory true ;
                            }

                            leaf dscp-value {
                              description 'Reset DSCP in violate-action, support <0-63>.' ;
                              type uint8 {
                                range 0..63 {
                                  description 'The DSCP value, support <0-63>' ;
                                }

                              }

                              mandatory true ;
                            }

                          }

                          case va-8021p {
                            description 'Rewrite packet 802.1p and transmit the packet.' ;
                            leaf set-8021p-transmit {
                              description 'Specify action to rewrite packet 802.1p and transmit it.' ;
                              type empty ;

                              mandatory true ;
                            }

                            leaf value-8021p {
                              description 'Reset 802.1p in violate-action, support <0-7>.' ;
                              type uint8 {
                                range 0..7 {
                                  description 'The 802.1p value, support <0-7>' ;
                                }

                              }

                              mandatory true ;
                            }

                          }

                          case va-priority {
                            description 'Rewrite packet priority and transmit the packet.' ;
                            leaf set-priority-transmit {
                              description 'Specify action to rewrite packet priority and transmit it.' ;
                              type empty ;

                              mandatory true ;
                            }

                            leaf priority-value {
                              description 'Reset priority in violate-action, support <1-4>.' ;
                              type uint8 {
                                range 1..4 {
                                  description 'The priority value, support <1-4>' ;
                                }

                              }

                              mandatory true ;
                            }

                          }

                        }

                      }

                    }

                  }

                  container set {
                    description 'Mark a packet.' ;
                    container dscp {
                      description 'Select DSCP as mark type.' ;
                      presence "Select DSCP as mark typ" ;
                      choice method {
                        description 'Specify the method to set DSCP.' ;
                        mandatory true ;
                        case set-value {
                          description 'Set the DSCP value directly.' ;
                          container set-value {
                            description 'Set the DSCP value directly.' ;
                            leaf dscp-value {
                              description 'DSCP value, support <0-63>.' ;
                              type uint16 {
                                range 0..63 {
                                  description 'DSCP value, support <0-63>' ;
                                }

                              }

                              mandatory true ;
                            }

                          }

                        }

                        case inherit {
                          description 'Set the DSCP value by inheriting.' ;
                          container inherit {
                            description 'Set the DSCP value by inheriting.' ;
                            leaf inherit-type {
                              description 'Specify the source inherit type, such as precedence, mpls-exp, 8021p, dscp, pay-load 8021p.' ;
                              type enumeration {
                                enum precedence {
                                  value 1 ;
                                  description 'Select precedence as source inherit' ;
                                }

                                enum mpls-exp {
                                  value 2 ;
                                  description 'Select MPLS-EXP as source inherit' ;
                                }

                                enum 8021p {
                                  value 3 ;
                                  description 'Select 802.1p as source inherit' ;
                                }

                                enum dscp {
                                  value 4 ;
                                  description 'Select dscp as source inherit' ;
                                }

                                enum pay-load-8021p {
                                  value 6 ;
                                  description 'Select inner 802.1p as source inherit' ;
                                }

                              }

                              mandatory true ;
                            }

                          }

                        }

                      }

                    }

                    container precedence {
                      description 'Select precedence as mark type.' ;
                      presence "Select precedence as mark type" ;
                      choice method {
                        description 'Specify the method to set IP Precedence.' ;
                        mandatory true ;
                        case set-value {
                          description 'Set the IP Precedence value directly.' ;
                          container set-value {
                            description 'Set the IP Precedence value directly.' ;
                            leaf prec-value {
                              description 'IP Precedence value, support <0-7>.' ;
                              type uint16 {
                                range 0..7 {
                                  description 'IP Precedence value, support <0-7>' ;
                                }

                              }

                              mandatory true ;
                            }

                          }

                        }

                        case inherit {
                          description 'Set the IP Precedence value by inheriting.' ;
                          container inherit {
                            description 'Set the IP Precedence value by inheriting.' ;
                            leaf inherit-type {
                              description 'Specify the source inherit type, such as precedence, mpls-exp, 8021p, dscp.' ;
                              type enumeration {
                                enum precedence {
                                  value 1 ;
                                  description 'Select precedence as source inherit' ;
                                }

                                enum mpls-exp {
                                  value 2 ;
                                  description 'Select MPLS-EXP as source inherit' ;
                                }

                                enum 8021p {
                                  value 3 ;
                                  description 'Select 802.1p as source inherit' ;
                                }

                                enum dscp {
                                  value 4 ;
                                  description 'Select dscp as source inherit' ;
                                }

                              }

                              mandatory true ;
                            }

                          }

                        }

                      }

                    }

                    container pri-8021p {
                      description 'Select 802.1p as mark type.' ;
                      presence "Select 802.1p as mark type" ;
                      choice method {
                        description 'Specify the method to set 802.1p.' ;
                        mandatory true ;
                        case set-value {
                          description 'Set the 802.1p value directly.' ;
                          container set-value {
                            description 'Set the 802.1p value directly.' ;
                            leaf value-8021p {
                              description '802.1p value, support <0-7>.' ;
                              type uint16 {
                                range 0..7 {
                                  description '802.1p value, support <0-7>' ;
                                }

                              }

                              mandatory true ;
                            }

                            leaf inner-outer {
                              description 'Set 8021p inner or outer flag.If vlaue is 0, it means outer flag. If value is 1,it means inner and outer flag.' ;
                              type uint8 {
                                range 0..1 {
                                  description 'Inner or outer flag. 0 is outer. 1 is inner and outer' ;
                                }

                              }

                              default 0 ;
                              ncd:revise-date 2017-01-10 ;
                            }

                          }

                        }

                        case inherit {
                          description 'Set the 802.1p value by inheriting.' ;
                          container inherit {
                            description 'Set the 802.1p value by inheriting.' ;
                            leaf inherit-type {
                              description 'Specify the source inherit type, such as precedence, mpls-exp, 8021p, dscp.' ;
                              type enumeration {
                                enum precedence {
                                  value 1 ;
                                  description 'Select precedence as source inherit' ;
                                }

                                enum mpls-exp {
                                  value 2 ;
                                  description 'Select MPLS-EXP as source inherit' ;
                                }

                                enum 8021p {
                                  value 3 ;
                                  description 'Select 802.1p as source inherit' ;
                                }

                                enum dscp {
                                  value 4 ;
                                  description 'Select dscp as source inherit' ;
                                }

                              }

                              mandatory true ;
                            }

                            leaf inner-outer {
                              description 'Set 8021p inner or outer flag.If vlaue is 0, it means outer flag. If value is 1,it means inner and outer flag.' ;
                              type uint8 {
                                range 0..1 {
                                  description 'Inner or outer flag. 0 is outer. 1 is inner and outer' ;
                                }

                              }

                              default 0 ;
                              ncd:revise-date 2017-01-10 ;
                            }

                          }

                        }

                      }

                    }

                    container mpls-exp {
                      description 'Select MPLS-EXP as mark type.' ;
                      presence "Select MPLS-EXP as mark type" ;
                      leaf label-type {
                        if-feature policy-action-set-label ;

                        description 'Select MPLS-EXP label position, such as default, topmost, imposition, inner.' ;
                        type enumeration {
                          enum topmost {
                            value 1 ;
                            description 'Set the MPLS-EXP value on topmost label' ;
                          }

                          enum imposition {
                            value 2 ;
                            description 'Set the MPLS-EXP value on all imposed labels' ;
                          }

                          enum default {
                            value 0 ;
                            description 'The default for topmost label' ;
                          }

                          enum inner {
                            value 3 ;
                            description 'Set the MPLS-EXP value on inner label' ;
                          }

                        }

                      }

                      choice method {
                        description 'Specify the method to set MPLS-EXP.' ;
                        mandatory true ;
                        case set-value {
                          description 'Set the MPLS-EXP value directly.' ;
                          container set-value {
                            description 'Set the MPLS-EXP value directly.' ;
                            leaf mpls-exp-value {
                              description 'MPLS-EXP value, support <0-7>.' ;
                              type uint16 {
                                range 0..7 {
                                  description 'MPLS-EXP value, support <0-7>' ;
                                }

                              }

                              mandatory true ;
                            }

                          }

                        }

                        case inherit {
                          description 'Set the MPLS-EXP value by inheriting.' ;
                          container inherit {
                            description 'Set the MPLS-EXP value by inheriting.' ;
                            leaf inherit-type {
                              description 'Specify the source inherit type, such as precedence, mpls-exp, 8021p, dscp.' ;
                              type enumeration {
                                enum precedence {
                                  value 1 ;
                                  description 'Select precedence as source inherit' ;
                                }

                                enum mpls-exp {
                                  value 2 ;
                                  description 'Select MPLS-EXP as source inherit' ;
                                }

                                enum 8021p {
                                  value 3 ;
                                  description 'Select 802.1p as source inherit' ;
                                }

                                enum dscp {
                                  value 4 ;
                                  description 'Select dscp as source inherit' ;
                                }

                              }

                              mandatory true ;
                            }

                          }

                        }

                      }

                    }

                    container multi-mpls-exp {
                      if-feature policy-action-set-multi-exp ;

                      description 'Select multi-MPLS-EXP as mark type.' ;
                      presence "Select multi-MPLS-EXP as mark type" ;
                      leaf inner-value {
                        description 'Inner multi-MPLS-EXP value, support <0-7>.' ;
                        type uint8 {
                          range 0..7 {
                            description 'Inner multi-MPLS-EXP value, support <0-7>' ;
                          }

                        }

                        mandatory true ;
                      }

                      leaf outer-value {
                        description 'Outer multi-MPLS-EXP value, support <0-7>.' ;
                        type uint8 {
                          range 0..7 {
                            description 'Outer multi-MPLS-EXP value, support <0-7>' ;
                          }

                        }

                        mandatory true ;
                      }

                    }

                    container interface {
                      description 'Specify interface name.' ;
                      presence "Specify interface name" ;
                      leaf if-name {
                        description 'Specify interface name.' ;
                        type ncd:ifname {
                          length 1..31 {
                            description 'Name of the interface, support 1-31 characters' ;
                          }

                        }

                        mandatory true ;
                      }

                      ncd:revise-date 2017-02-20 ;
                    }

                    container vlan-id {
                      description 'Configure VLAN ID.' ;
                      presence "Configure VLAN ID" ;
                      leaf vlan-value {
                        description 'Set VLAN ID, support <1-4094>.' ;
                        type uint16 {
                          range 1..4094 ;

                        }

                        mandatory true ;
                      }

                      ncd:revise-date 2017-02-20 ;
                    }

                    container service-query {
                      description 'Configure service function path.' ;
                      presence "Configure service function path" ;
                      leaf query-number {
                        description 'Service function path, support <0-255>.' ;
                        type uint8 {
                          range 0..255 ;

                        }

                        mandatory true ;
                      }

                      ncd:revise-date 2017-02-20 ;
                    }

                    container service-class {
                      description 'Configure service class.' ;
                      presence "Configure service function path" ;
                      leaf service-class {
                        description 'Select service class of PHB info.' ;
                        type qos-service-class ;

                        mandatory true ;
                      }

                      leaf color-type {
                        description 'Specify packets color, support <green,yellow,red>.' ;
                        type qos-color-type ;

                      }

                      ncd:revise-date 2021-01-18 ;
                    }

                    container encap-dscp {
                      description 'Select encapsulated DSCP as mark type.' ;
                      presence "Select encapsulated DSCP as mark type" ;
                      leaf dscp-value {
                        description 'DSCP value.' ;
                        type uint16 {
                          range 0..63 ;

                        }

                        mandatory true ;
                      }

                      ncd:revise-date 2021-05-25 ;
                    }

                  }

                  container drop {
                    if-feature policy-action-drop ;

                    description 'Configure drop.' ;
                    presence "Configure drop" ;
                    leaf drop {
                      description 'Specify drop.' ;
                      type empty ;

                      mandatory true ;
                    }

                  }

                  container latency-time-threshold {
                    description 'Configure latency time threshold.' ;
                    presence "Configure latency time threshold" ;
                    leaf value {
                      description 'Set the threshold of latency time.' ;
                      type uint32 {
                        range 0..1000 ;

                      }

                      mandatory true ;
                    }

                    ncd:revise-date 2020-04-06 ;
                  }

                  container bandwidth-threshold {
                    description 'Configure bandwidth threshold.' ;
                    presence "Configure bandwidth threshold" ;
                    leaf value {
                      description 'Set the threshold of bandwidth.' ;
                      type uint32 {
                        range 0..10000000 ;

                      }

                      mandatory true ;
                    }

                    container percentage {
                      description 'Configure percentage of acceleration or deceleration.' ;
                      leaf up {
                        description 'Configure percentage of acceleration (percentage <0.0-100.0>).' ;
                        type decimal64 {
                          fraction-digits 2 ;
                          range 0..100 ;

                        }

                      }

                      leaf down {
                        description 'Configure percentage of deceleration (percentage <0.0-100.0>).' ;
                        type decimal64 {
                          fraction-digits 2 ;
                          range 0..100 ;

                        }

                      }

                    }

                    ncd:revise-date 2020-04-06 ;
                  }

                  container drop-rate-threshold {
                    description 'Configure drop rate threshold.' ;
                    presence "Configure drop rate threshold" ;
                    leaf percentage {
                      description 'Set the threshold of drop rate (percentage <0.0-100.0>).' ;
                      type decimal64 {
                        fraction-digits 2 ;
                        range 0.0..100.0 ;

                      }

                      mandatory true ;
                    }

                    ncd:revise-date 2020-04-06 ;
                  }

                  container wred-template {
                    if-feature wred-template ;

                    description 'Configure WRED(Weighted Random Early Detection) template information.' ;
                    presence "Configure WRED template" ;
                    leaf wred-template-name {
                      description 'Name of the WRED(Weighted Random Early Detection) template, support 1-31 characters.' ;
                      type string {
                        length 1..31 {
                          description 'Name of the WRED template, support 1-31 characters' ;
                        }

                      }

                      mandatory true ;
                    }

                    ncd:revise-date 2022-06-27 ;
                  }

                  container queue-depth-adaptive {
                    leaf adaptive {
                      type empty ;

                      mandatory true ;
                      description 'Configure adaptive queue depth.' ;
                    }

                    if-feature queue-depth-adaptive ;

                    presence "adaptive queue depth" ;
                    description 'Configure adaptive queue depth.' ;
                    ncd:revise-date 2023-06-20 ;
                  }

                }

                container class-default {
                  description 'Select policy association default class.' ;
                  presence "Specify the default class" ;
                  leaf class-default {
                    description 'Specify the default class.' ;
                    type empty ;

                    mandatory true ;
                  }

                  container bandwidth {
                    description 'Configure minimum guaranteed bandwidth.' ;
                    presence "Configure minimum guaranteed bandwidth" ;
                    leaf percentage {
                      description 'Set the exact bandwidth percentage, support <1-100>.' ;
                      type uint16 {
                        range 1..100 {
                          description 'The exact bandwidth percentage, support <1-100>' ;
                        }

                      }

                      mandatory true ;
                    }

                  }

                  container bandwidth-remaining {
                    description 'Configure leftover bandwidth.' ;
                    presence "Configure leftover bandwidth" ;
                    leaf percentage {
                      description 'Set the leftover bandwidth percentage, support <1-100>.' ;
                      type uint16 {
                        range 1..100 {
                          description 'The guaranteed percentage, support <1-100>' ;
                        }

                      }

                      mandatory true ;
                    }

                  }

                  container priority-level {
                    description 'Configure PQ(Priority Queuing) priority level.' ;
                    presence "Configure PQ priority level" ;
                    leaf priority-value {
                      description 'Set the priority level of PQ.' ;
                      type uint16 {
                        range 1..8 {
                          description 'The priority level of PQ' ;
                        }

                      }

                      mandatory true ;
                    }

                  }

                  container priority-llq {
                    description 'Configure LLQ(Low Latency Queuing) priority.' ;
                    presence "Configure LLQ priority" ;
                    leaf priority-llq {
                      description 'Specify LLQ.' ;
                      type empty ;

                      mandatory true ;
                    }

                  }

                  container queue-limit {
                    description 'Configure queue depth.' ;
                    presence "Configure queue depth" ;
                    choice queue-limit {
                      description 'Configure queue depth.' ;
                      case queue-depth {
                        description 'Set queue depth.' ;
                        leaf queue-depth {
                          description 'Set queue depth.' ;
                          type enumeration {
                            enum 16 {
                              value 1 ;
                              description 'Set queue depth to 16KB' ;
                            }

                            enum 24 {
                              value 2 ;
                              description 'Set queue depth to 24KB' ;
                            }

                            enum 64 {
                              value 3 ;
                              description 'Set queue depth to 64KB' ;
                            }

                            enum 512 {
                              value 4 ;
                              description 'Set queue depth to 512KB' ;
                            }

                            enum 2000 {
                              value 5 ;
                              description 'Set queue depth to 2000KB' ;
                            }

                            enum 8000 {
                              value 6 ;
                              description 'Set queue depth to 8000KB' ;
                            }

                            enum 7 {
                              value 7 ;
                              description 'Set queue depth to 7KB' ;
                            }

                            enum 1000 {
                              value 20 ;
                              description 'Set queue depth to 1000KB' ;
                            }

                            enum 8000000 {
                              value 21 ;
                              description 'Set queue depth to 8000000KB' ;
                            }

                            enum 1000000 {
                              value 13 ;
                              description 'Set queue depth to 1000000KB' ;
                            }

                            enum 128000 {
                              value 11 ;
                              description 'Set queue depth to 128000KB' ;
                            }

                            enum 16000 {
                              value 8 ;
                              description 'Set queue depth to 16000KB' ;
                            }

                            enum 24000 {
                              value 9 ;
                              description 'Set queue depth to 24000KB' ;
                            }

                            enum 512000 {
                              value 12 ;
                              description 'Set queue depth to 512000KB' ;
                            }

                            enum 64000 {
                              value 10 ;
                              description 'Set queue depth to 64000KB' ;
                            }

                          }

                          units KB ;
                          mandatory true ;
                        }

                      }

                      case queue-value {
                        description 'Set queue depth value(default:KB).' ;
                        container queue-value {
                          description 'Set queue depth value(default:KB).' ;
                          leaf queue-value {
                            description 'Set queue depth value(default:KB).' ;
                            type uint32 {
                              range 7..8000000 {
                                description 'Set queue depth value(default:KB)' ;
                              }

                            }

                            mandatory true ;
                          }

                        }

                        ncd:revise-date 2019-08-19 ;
                      }

                      case queue-cache-time {
                        description 'Configure cache time of the queue.' ;
                        container queue-cache-time {
                          description 'Configure cache time of the queue.' ;
                          leaf queue-cache-time {
                            description 'Set cache time(default:us).' ;
                            type uint32 {
                              range 1..100000 {
                                description 'Set cache time(default:us)' ;
                              }

                            }

                            mandatory true ;
                          }

                        }

                        ncd:revise-date 2019-08-19 ;
                      }

                    }

                  }

                  container random-detect {
                    description 'Configure WRED(Weighted Random Early Detection) information.' ;
                    container enable {
                      description 'Enable/disable WRED function.' ;
                      presence "Configure WRED enable" ;
                      leaf enable {
                        description 'Enable WRED.' ;
                        type empty ;

                        mandatory true ;
                      }

                    }

                    container colors {
                      if-feature policy-action-wred-color ;

                      description 'Configure WRED thresholds based on color.' ;
                      list color {
                        description 'Configure WRED thresholds based on color.' ;
                        key color-type ;
                        leaf color-type {
                          description 'Set WRED color, such as green, yellow, red.' ;
                          type qos-color-type ;

                        }

                        choice threshold {
                          description 'Set the threshold.' ;
                          case threshold-value {
                            description 'Set the threshold value.' ;
                            leaf min-threshold {
                              description 'Set the minimum threshold, support <1-1024000>.' ;
                              type uint32 {
                                range 1..1024000 {
                                  description 'The minimum threshold in kilobytes, support <1-1024000>' ;
                                }

                              }

                              units KB ;
                              mandatory true ;
                            }

                            leaf max-threshold {
                              description 'Set the maximum threshold, support <1-1024000>.' ;
                              type uint32 {
                                range 1..1024000 {
                                  description 'The maximum threshold in kilobytes, support <1-1024000>' ;
                                }

                              }

                              units KB ;
                              mandatory true ;
                            }

                          }

                          case threshold-percentage {
                            description 'Set the threshold percentage.' ;
                            container threshold-percentage {
                              description 'Set the threshold percentage.' ;
                              leaf min-threshold-percentage {
                                description 'Set the minimum threshold percentage, support <1-100>.' ;
                                type uint32 {
                                  range 1..100 {
                                    description 'The minimum threshold percentage, support <1-100>' ;
                                  }

                                }

                                mandatory true ;
                              }

                              leaf max-threshold-percentage {
                                description 'Set the maximum threshold percentage, support <1-100>.' ;
                                type uint32 {
                                  range 1..100 {
                                    description 'The maximum threshold percentage, support <1-100>' ;
                                  }

                                }

                                mandatory true ;
                              }

                            }

                          }

                          ncd:revise-date 2019-08-05 ;
                        }

                        leaf probability {
                          description 'Set mark probability denominator, support <1-100>.' ;
                          type uint8 {
                            range 1..100 {
                              description 'Set mark probability denominator, support <1-100>' ;
                            }

                          }

                          mandatory true ;
                        }

                      }

                    }

                    container precedences {
                      description 'Configure WRED thresholds based on precedence.' ;
                      list precedence {
                        description 'Configure WRED thresholds based on precedence.' ;
                        key prec-value ;
                        leaf prec-value {
                          description 'Set the precedence value, such as MPLS EXP, VLAN 802.1p, IP DSCP, IP Precedence, support <0-7>.' ;
                          type uint16 {
                            range 0..7 {
                              description 'The precedence value, support <0-7>' ;
                            }

                          }

                        }

                        choice threshold {
                          description 'Set the threshold.' ;
                          case threshold-value {
                            description 'Set the threshold value.' ;
                            leaf min-threshold {
                              description 'Set the minimum threshold (default: kilobytes).' ;
                              type uint32 {
                                range 1..4294967295 {
                                  description 'The minimum threshold (default: kilobytes), support <1-4294967295>' ;
                                }

                              }

                              mandatory true ;
                            }

                            leaf min-threshold-unit {
                              description 'set min-threshold unit, such as kbytes, mbytes, gbytes.' ;
                              type qos-threshold-unit-type ;

                            }

                            leaf max-threshold {
                              description 'Set the maximum threshold (default: kilobytes).' ;
                              type uint32 {
                                range 1..4294967295 {
                                  description 'The maximum threshold (default: kilobytes), support <1-4294967295>' ;
                                }

                              }

                              mandatory true ;
                            }

                            leaf max-threshold-unit {
                              description 'set max-threshold unit, such as kbytes, mbytes, gbytes.' ;
                              type qos-threshold-unit-type ;

                            }

                          }

                          case threshold-percentage {
                            description 'Set the threshold percentage.' ;
                            container threshold-percentage {
                              description 'Set the threshold percentage.' ;
                              leaf min-threshold-percentage {
                                description 'Set the minimum threshold percentage, support <1-100>.' ;
                                type uint32 {
                                  range 1..100 {
                                    description 'The minimum threshold percentage, support <1-100>' ;
                                  }

                                }

                                mandatory true ;
                              }

                              leaf max-threshold-percentage {
                                description 'Set the maximum threshold percentage, support <1-100>.' ;
                                type uint32 {
                                  range 1..100 {
                                    description 'The maximum threshold percentage, support <1-100>' ;
                                  }

                                }

                                mandatory true ;
                              }

                            }

                          }

                          case threshold-cachetime {
                            if-feature policy-action-wred-precedence-cachetime ;

                            description 'Set the threshold cachetime.' ;
                            container threshold-cachetime {
                              description 'Set the threshold cachetime.' ;
                              leaf min-threshold-cachetime {
                                description 'Set the minimum threshold cachetime (default: ms).' ;
                                type uint32 {
                                  range 1..1000 {
                                    description 'The minimum threshold cachetime, support <1-1000>' ;
                                  }

                                }

                                mandatory true ;
                              }

                              leaf max-threshold-cachetime {
                                description 'Set the maximum threshold cachetime (default: ms).' ;
                                type uint32 {
                                  range 1..1000 {
                                    description 'The maximum threshold cachetime, support <1-1000>' ;
                                  }

                                }

                                mandatory true ;
                              }

                            }

                            ncd:revise-date 2021-11-19 ;
                          }

                          ncd:revise-date 2019-08-05 ;
                        }

                        leaf probability {
                          description 'Set mark probability denominator, support <1-100>.' ;
                          type uint32 {
                            range 1..100 {
                              description 'Set mark probability denominator, support <1-100>' ;
                            }

                          }

                          mandatory true ;
                        }

                      }

                    }

                    container weight {
                      description 'Configure WRED exponential weight factor.' ;
                      presence "Configure WRED exponential weight factor" ;
                      leaf weight-value {
                        description 'Specify exponent used in weighted average calculation, support <1-16>.' ;
                        type uint16 {
                          range 1..16 {
                            description 'Exponent used in weighted average calculation' ;
                          }

                        }

                        mandatory true ;
                      }

                    }

                  }

                  container service-policy {
                    description 'Configure hierarchical service policy.' ;
                    presence "Configure hierarchical service policy" ;
                    leaf hpolicy-name {
                      description 'Name of the hierarchical policy, support 1-31 characters.' ;
                      type string {
                        length 1..31 {
                          description 'Name of the hierarchical policy, support 1-31 characters' ;
                        }

                      }

                      mandatory true ;
                    }

                  }

                  container shape {
                    if-feature policy-action-shape ;

                    description 'Configure flow shape.' ;
                    presence "Configure flow shape" ;
                    leaf shape-type {
                      description 'Set shape type, such as peak, average.' ;
                      type enumeration {
                        enum average {
                          value 1 ;
                          description 'Set average as shape type' ;
                        }

                        enum peak {
                          value 2 ;
                          description 'Set peak as shape type' ;
                        }

                      }

                      mandatory true ;
                    }

                    choice shape-method {
                      description 'Select rate or rate percentage as shape unit.' ;
                      mandatory true ;
                      case rate {
                        description 'Select the average or peak rate.' ;
                        leaf rate-value {
                          description 'Set the average or peak rate.' ;
                          type uint32 {
                            range 1..4294967295 {
                              description 'The average or peak rate in kbps, support <1-4294967295>' ;
                            }

                          }

                          units kbps ;
                          mandatory true ;
                        }

                        leaf rate-unit {
                          type qos-rate-unit-type ;

                          description 'Specify rate unit.' ;
                          if-feature qos-shape-unit ;

                          ncd:revise-date 2023-06-20 ;
                        }

                      }

                      case percent {
                        description 'Select rate percent as shape unit.' ;
                        leaf percentage {
                          description 'Set the exact rate percentage, support <1-100>.' ;
                          type uint16 {
                            range 1..100 {
                              description 'The exact rate percentage, support <1-100>' ;
                            }

                          }

                          mandatory true ;
                        }

                      }

                    }

                    container burst-rate {
                      description 'Configure sustained and excessive burst rates.' ;
                      presence "Configure committed burst and peak rate" ;
                      leaf bc-value {
                        description 'Set the bc value.' ;
                        type uint32 {
                          range 1..4294967295 {
                            description 'The committed burst information rate in kilobits per second, support <1-4294967295>' ;
                          }

                        }

                        units kbps ;
                        mandatory true ;
                      }

                      leaf be-value {
                        description 'Set the be value.' ;
                        type uint32 {
                          range 1..4294967295 {
                            description 'The peak information rate in kilobits per second, support <1-4294967295>' ;
                          }

                        }

                        units kbps ;
                        mandatory true ;
                      }

                    }

                  }

                  container police {
                    description 'Configure traffic policing.' ;
                    presence "Configure traffic policing" ;
                    choice cir-pir-value-percentage {
                      description 'Configure CIR CBS PIR and PBS.' ;
                      mandatory true ;
                      case cir-pir-value {
                        description 'Configure CIR and PIR with value form.' ;
                        leaf cir {
                          description 'Configure the CIR (Committed Information Rate) value, default: kilobits per second.' ;
                          type uint32 {
                            range 8..4294967295 {
                              description 'The CIR value (default: kilobits per second),support <8-4294967295>.' ;
                            }

                          }

                          mandatory true ;
                        }

                        leaf cir-unit {
                          description 'Set CIR unit, such as kbps, mbps, gbps.' ;
                          type qos-rate-unit-type ;

                        }

                        leaf cbs {
                          description 'Configure the CBS(Committed Burst Size) size, default: KB.' ;
                          type uint32 {
                            range 1..4294967295 {
                              description 'The CBS(Committed Burst Size) size (default: KB), support <1-4294967295>' ;
                            }

                          }

                        }

                        leaf cbs-unit {
                          description 'Set CBS unit, such as kb, mb, gb.' ;
                          type qos-bucket-unit-type ;

                        }

                        container pir-pbs {
                          description 'Configure PIR and PBS.' ;
                          presence "Configure pir and pbs" ;
                          leaf pir {
                            description 'Configure the PIR(Peak Information Rate) value, default: kilobits per second.' ;
                            type uint32 {
                              range 8..4294967295 {
                                description 'The PIR(Peak Information Rate) value (default: kilobits per second), support <8-4294967295>' ;
                              }

                            }

                            mandatory true ;
                          }

                          leaf pir-unit {
                            description 'Set PIR unit, such as kbps, mbps, gbps.' ;
                            type qos-rate-unit-type ;

                          }

                          leaf pbs {
                            description 'Configure the PBS(Peak Burst Size) size, default: KB.' ;
                            type uint32 {
                              range 1..4294967295 {
                                description 'The PBS(Peak Burst Size) size (default: KB), support <1-4294967295>' ;
                              }

                            }

                          }

                          leaf pbs-unit {
                            description 'Set PBS unit, such as kb, mb, gb.' ;
                            type qos-bucket-unit-type ;

                          }

                        }

                      }

                      case cir-pir-percentage {
                        description 'Configure CIR and PIR with percentage form.' ;
                        container cir-pir-percentage {
                          description 'Configure CIR and PIR with percentage form.' ;
                          leaf cir-percentage {
                            description 'Configure CIR with percentage form.' ;
                            type uint8 {
                              range 1..100 {
                                description 'Configure CIR with percentage form' ;
                              }

                            }

                            mandatory true ;
                          }

                          container pir-percentage {
                            description 'Configure PIR with percentage form.' ;
                            presence "Configure PIR with percentage form" ;
                            leaf pir-percentage {
                              description 'Configure PIR with percentage form.' ;
                              type uint8 {
                                range 1..100 {
                                  description 'Configure PIR with percentage form' ;
                                }

                              }

                              mandatory true ;
                            }

                          }

                        }

                        ncd:revise-date 2020-06-09 ;
                      }

                    }

                    container action {
                      description 'Set monitoring action  for each measurement evaluation packet.' ;
                      presence "Configure action to packets" ;
                      container conform-action {
                        description 'Action to packets that conform to the rate limit.' ;
                        choice conform-action {
                          description 'Specify action to packets that conform to the rate limit.' ;
                          mandatory true ;
                          case ca-drop {
                            description 'Drop packet in conform-action.' ;
                            leaf drop {
                              description 'Specify action to drop packet.' ;
                              type empty ;

                              mandatory true ;
                            }

                          }

                          case ca-transmit {
                            description 'Transmit packet in conform-action.' ;
                            leaf transmit {
                              description 'Specify action to transmit packet.' ;
                              type empty ;

                              mandatory true ;
                            }

                          }

                          case ca-mpls-exp {
                            description 'Rewrite packet MPLS-EXP and transmit the packet.' ;
                            leaf set-exp-transmit {
                              description 'Specify action to rewrite packet MPLS-EXP and transmit it.' ;
                              type empty ;

                              mandatory true ;
                            }

                            leaf mpls-exp-value {
                              description 'Reset MPLS-EXP value in conform-action, support <0-7>.' ;
                              type uint8 {
                                range 0..7 {
                                  description 'The MPLS-EXP value, support <0-7>' ;
                                }

                              }

                              mandatory true ;
                            }

                          }

                          case ca-precedence {
                            description 'Rewrite packet precedence and transmit the packet.' ;
                            leaf set-prec-transmit {
                              description 'Specify action to rewrite packet precedence and transmit it.' ;
                              type empty ;

                              mandatory true ;
                            }

                            leaf prec-value {
                              description 'Reset the IP-Precedence value in conform-action, support <0-7>.' ;
                              type uint8 {
                                range 0..7 {
                                  description 'The IP-Precedence value, support <0-7>' ;
                                }

                              }

                              mandatory true ;
                            }

                          }

                          case ca-dscp {
                            description 'Rewrite packet DSCP and transmit the packet.' ;
                            leaf set-dscp-transmit {
                              description 'Specify action to rewrite packet DSCP and transmit it.' ;
                              type empty ;

                              mandatory true ;
                            }

                            leaf dscp-value {
                              description 'Reset DSCP in conform-action, support <0-63>.' ;
                              type uint8 {
                                range 0..63 {
                                  description 'The DSCP value, support <0-63>' ;
                                }

                              }

                              mandatory true ;
                            }

                          }

                          case ca-8021p {
                            description 'Rewrite packet 802.1p and transmit the packet.' ;
                            leaf set-8021p-transmit {
                              description 'Specify action to rewrite packet 802.1p and transmit it.' ;
                              type empty ;

                              mandatory true ;
                            }

                            leaf value-8021p {
                              description 'Reset 802.1p in conform-action, support <0-7>.' ;
                              type uint8 {
                                range 0..7 {
                                  description 'The 802.1p value, support <0-7>' ;
                                }

                              }

                              mandatory true ;
                            }

                          }

                          case ca-priority {
                            description 'Rewrite packet priority and transmit the packet.' ;
                            leaf set-priority-transmit {
                              description 'Specify action to rewrite packet priority and transmit it.' ;
                              type empty ;

                              mandatory true ;
                            }

                            leaf priority-value {
                              description 'Reset priority in conform-action, support <1-4>.' ;
                              type uint8 {
                                range 1..4 {
                                  description 'The priority value, support <1-4>' ;
                                }

                              }

                              mandatory true ;
                            }

                          }

                        }

                      }

                      container exceed-action {
                        description 'Action to packets that exceed the rate limit.' ;
                        choice exceed-action {
                          description 'Specify action to packets that exceed the rate limit.' ;
                          mandatory true ;
                          case ea-drop {
                            description 'Drop packet in exceed-action.' ;
                            leaf drop {
                              description 'Specify action to drop packet.' ;
                              type empty ;

                              mandatory true ;
                            }

                          }

                          case ea-transmit {
                            description 'Transmit packet in exceed-action.' ;
                            leaf transmit {
                              description 'Specify action to transmit packet.' ;
                              type empty ;

                              mandatory true ;
                            }

                          }

                          case ea-mpls-exp {
                            description 'Rewrite packet MPLS-EXP and transmit the packet.' ;
                            leaf set-exp-transmit {
                              description 'Specify action to rewrite packet MPLS-EXP and transmit it.' ;
                              type empty ;

                              mandatory true ;
                            }

                            leaf mpls-exp-value {
                              description 'Reset MPLS-EXP value in exceed-action, support <0-7>.' ;
                              type uint8 {
                                range 0..7 {
                                  description 'The MPLS-EXP value, support <0-7>' ;
                                }

                              }

                              mandatory true ;
                            }

                          }

                          case ea-precedence {
                            description 'Rewrite packet precedence and transmit the packet.' ;
                            leaf set-prec-transmit {
                              description 'Specify action to rewrite packet precedence and transmit it.' ;
                              type empty ;

                              mandatory true ;
                            }

                            leaf prec-value {
                              description 'Reset the IP-Precedence value in exceed-action, support <0-7>.' ;
                              type uint8 {
                                range 0..7 {
                                  description 'The IP-Precedence value, support <0-7>' ;
                                }

                              }

                              mandatory true ;
                            }

                          }

                          case ea-dscp {
                            description 'Rewrite packet DSCP and transmit the packet.' ;
                            leaf set-dscp-transmit {
                              description 'Specify action to rewrite packet DSCP and transmit it.' ;
                              type empty ;

                              mandatory true ;
                            }

                            leaf dscp-value {
                              description 'Reset DSCP in exceed-action, support <0-63>.' ;
                              type uint8 {
                                range 0..63 {
                                  description 'The DSCP value, support <0-63>' ;
                                }

                              }

                              mandatory true ;
                            }

                          }

                          case ea-8021p {
                            description 'Rewrite packet 802.1p and transmit the packet.' ;
                            leaf set-8021p-transmit {
                              description 'Specify action to rewrite packet 802.1p and transmit the packet.' ;
                              type empty ;

                              mandatory true ;
                            }

                            leaf value-8021p {
                              description 'Reset 802.1p in exceed-action, support <0-7>.' ;
                              type uint8 {
                                range 0..7 {
                                  description 'The 802.1p value, support <0-7>' ;
                                }

                              }

                              mandatory true ;
                            }

                          }

                          case ea-priority {
                            description 'Rewrite packet priority and transmit the packet.' ;
                            leaf set-priority-transmit {
                              description 'Specify action to rewrite packet priority and transmit it.' ;
                              type empty ;

                              mandatory true ;
                            }

                            leaf priority-value {
                              description 'Reset priority in exceed-action, support <1-4>.' ;
                              type uint8 {
                                range 1..4 {
                                  description 'The priority value, support <1-4>' ;
                                }

                              }

                              mandatory true ;
                            }

                          }

                        }

                      }

                      container violate-action {
                        description 'Action to packets that violate the rate limit.' ;
                        choice violate-action {
                          description 'Specify action to packets that violate the rate limit.' ;
                          mandatory true ;
                          case va-drop {
                            description 'Drop packet in violate-action.' ;
                            leaf drop {
                              description 'Specify action to drop packet.' ;
                              type empty ;

                              mandatory true ;
                            }

                          }

                          case va-transmit {
                            description 'Transmit packet in violate-action.' ;
                            leaf transmit {
                              description 'Specify action to transmit packet.' ;
                              type empty ;

                              mandatory true ;
                            }

                          }

                          case va-mpls-exp {
                            description 'Rewrite packet MPLS-EXP and transmit the packet.' ;
                            leaf set-exp-transmit {
                              description 'Specify action to rewrite packet MPLS-EXP and transmit it.' ;
                              type empty ;

                              mandatory true ;
                            }

                            leaf mpls-exp-value {
                              description 'Reset MPLS-EXP value in violate-action, support <0-7>.' ;
                              type uint8 {
                                range 0..7 {
                                  description 'The MPLS-EXP value, support <0-7>' ;
                                }

                              }

                              mandatory true ;
                            }

                          }

                          case va-precedence {
                            description 'Rewrite packet precedence and transmit the packet.' ;
                            leaf set-prec-transmit {
                              description 'Specify action to rewrite packet precedence and transmit it.' ;
                              type empty ;

                              mandatory true ;
                            }

                            leaf prec-value {
                              description 'Reset the IP-Precedence value in violate-action, support <0-7>.' ;
                              type uint8 {
                                range 0..7 {
                                  description 'The IP-Precedence value, support <0-7>' ;
                                }

                              }

                              mandatory true ;
                            }

                          }

                          case va-dscp {
                            description 'Rewrite packet DSCP and transmit the packet.' ;
                            leaf set-dscp-transmit {
                              description 'Specify action to rewrite packet DSCP and transmit it.' ;
                              type empty ;

                              mandatory true ;
                            }

                            leaf dscp-value {
                              description 'Reset DSCP in violate-action, support <0-63>.' ;
                              type uint8 {
                                range 0..63 {
                                  description 'The DSCP value, support <0-63>' ;
                                }

                              }

                              mandatory true ;
                            }

                          }

                          case va-8021p {
                            description 'Rewrite packet 802.1p and transmit the packet.' ;
                            leaf set-8021p-transmit {
                              description 'Specify action to rewrite packet 802.1p and transmit it.' ;
                              type empty ;

                              mandatory true ;
                            }

                            leaf value-8021p {
                              description 'Reset 802.1p in violate-action, support <0-7>.' ;
                              type uint8 {
                                range 0..7 {
                                  description 'The 802.1p value, support <0-7>' ;
                                }

                              }

                              mandatory true ;
                            }

                          }

                          case va-priority {
                            description 'Rewrite packet priority and transmit the packet.' ;
                            leaf set-priority-transmit {
                              description 'Specify action to rewrite packet priority and transmit it.' ;
                              type empty ;

                              mandatory true ;
                            }

                            leaf priority-value {
                              description 'Reset priority in violate-action, support <1-4>.' ;
                              type uint8 {
                                range 1..4 {
                                  description 'The priority value, support <1-4>' ;
                                }

                              }

                              mandatory true ;
                            }

                          }

                        }

                      }

                    }

                  }

                  container set {
                    description 'Mark a packet.' ;
                    container dscp {
                      description 'Select DSCP as mark type.' ;
                      presence "Select DSCP as mark typ" ;
                      choice method {
                        description 'Specify the method to set DSCP.' ;
                        mandatory true ;
                        case set-value {
                          description 'Set the DSCP value directly.' ;
                          container set-value {
                            description 'Set the DSCP value directly.' ;
                            leaf dscp-value {
                              description 'DSCP value, support <0-63>.' ;
                              type uint16 {
                                range 0..63 {
                                  description 'DSCP value, support <0-63>' ;
                                }

                              }

                              mandatory true ;
                            }

                          }

                        }

                        case inherit {
                          description 'Set the DSCP value by inheriting.' ;
                          container inherit {
                            description 'Set the DSCP value by inheriting.' ;
                            leaf inherit-type {
                              description 'Specify the source inherit type, such as precedence, mpls-exp, 8021p, dscp, pay-load 8021p.' ;
                              type enumeration {
                                enum precedence {
                                  value 1 ;
                                  description 'Select precedence as source inherit' ;
                                }

                                enum mpls-exp {
                                  value 2 ;
                                  description 'Select MPLS-EXP as source inherit' ;
                                }

                                enum 8021p {
                                  value 3 ;
                                  description 'Select 802.1p as source inherit' ;
                                }

                                enum dscp {
                                  value 4 ;
                                  description 'Select dscp as source inherit' ;
                                }

                                enum pay-load-8021p {
                                  value 6 ;
                                  description 'Select inner 802.1p as source inherit' ;
                                }

                              }

                              mandatory true ;
                            }

                          }

                        }

                      }

                    }

                    container precedence {
                      description 'Select precedence as mark type.' ;
                      presence "Select precedence as mark type" ;
                      choice method {
                        description 'Specify the method to set IP Precedence.' ;
                        mandatory true ;
                        case set-value {
                          description 'Set the IP Precedence value directly.' ;
                          container set-value {
                            description 'Set the IP Precedence value directly.' ;
                            leaf prec-value {
                              description 'IP Precedence value, support <0-7>.' ;
                              type uint16 {
                                range 0..7 {
                                  description 'IP Precedence value, support <0-7>' ;
                                }

                              }

                              mandatory true ;
                            }

                          }

                        }

                        case inherit {
                          description 'Set the IP Precedence value by inheriting.' ;
                          container inherit {
                            description 'Set the IP Precedence value by inheriting.' ;
                            leaf inherit-type {
                              description 'Specify the source inherit type, such as precedence, mpls-exp, 8021p, dscp.' ;
                              type enumeration {
                                enum precedence {
                                  value 1 ;
                                  description 'Select precedence as source inherit' ;
                                }

                                enum mpls-exp {
                                  value 2 ;
                                  description 'Select MPLS-EXP as source inherit' ;
                                }

                                enum 8021p {
                                  value 3 ;
                                  description 'Select 802.1p as source inherit' ;
                                }

                                enum dscp {
                                  value 4 ;
                                  description 'Select dscp as source inherit' ;
                                }

                              }

                              mandatory true ;
                            }

                          }

                        }

                      }

                    }

                    container pri-8021p {
                      description 'Select 802.1p as mark type.' ;
                      presence "Select 802.1p as mark type" ;
                      choice method {
                        description 'Specify the method to set 802.1p.' ;
                        mandatory true ;
                        case set-value {
                          description 'Set the 802.1p value directly.' ;
                          container set-value {
                            description 'Set the 802.1p value directly.' ;
                            leaf value-8021p {
                              description '802.1p value, support <0-7>.' ;
                              type uint16 {
                                range 0..7 {
                                  description '802.1p value, support <0-7>' ;
                                }

                              }

                              mandatory true ;
                            }

                            leaf inner-outer {
                              description 'Set 8021p inner or outer flag.If vlaue is 0, it means outer flag. If value is 1,it means inner and outer flag.' ;
                              type uint8 {
                                range 0..1 {
                                  description 'Inner or outer flag. 0 is outer. 1 is inner and outer' ;
                                }

                              }

                              default 0 ;
                              ncd:revise-date 2017-01-10 ;
                            }

                          }

                        }

                        case inherit {
                          description 'Set the 802.1p value by inheriting.' ;
                          container inherit {
                            description 'Set the 802.1p value by inheriting.' ;
                            leaf inherit-type {
                              description 'Specify the source inherit type, such as precedence, mpls-exp, 8021p, dscp.' ;
                              type enumeration {
                                enum precedence {
                                  value 1 ;
                                  description 'Select precedence as source inherit' ;
                                }

                                enum mpls-exp {
                                  value 2 ;
                                  description 'Select MPLS-EXP as source inherit' ;
                                }

                                enum 8021p {
                                  value 3 ;
                                  description 'Select 802.1p as source inherit' ;
                                }

                                enum dscp {
                                  value 4 ;
                                  description 'Select dscp as source inherit' ;
                                }

                              }

                              mandatory true ;
                            }

                            leaf inner-outer {
                              description 'Set 8021p inner or outer flag.If vlaue is 0, it means outer flag. If value is 1,it means inner and outer flag.' ;
                              type uint8 {
                                range 0..1 {
                                  description 'Inner or outer flag. 0 is outer. 1 is inner and outer' ;
                                }

                              }

                              default 0 ;
                              ncd:revise-date 2017-01-10 ;
                            }

                          }

                        }

                      }

                    }

                    container mpls-exp {
                      description 'Select MPLS-EXP as mark type.' ;
                      presence "Select MPLS-EXP as mark type" ;
                      leaf label-type {
                        if-feature policy-action-set-label ;

                        description 'Select MPLS-EXP label position, such as default, topmost, imposition, inner.' ;
                        type enumeration {
                          enum topmost {
                            value 1 ;
                            description 'Set the MPLS-EXP value on topmost label' ;
                          }

                          enum imposition {
                            value 2 ;
                            description 'Set the MPLS-EXP value on all imposed labels' ;
                          }

                          enum default {
                            value 0 ;
                            description 'The default for topmost label' ;
                          }

                          enum inner {
                            value 3 ;
                            description 'Set the MPLS-EXP value on inner label' ;
                          }

                        }

                      }

                      choice method {
                        description 'Specify the method to set MPLS-EXP.' ;
                        mandatory true ;
                        case set-value {
                          description 'Set the MPLS-EXP value directly.' ;
                          container set-value {
                            description 'Set the MPLS-EXP value directly.' ;
                            leaf mpls-exp-value {
                              description 'MPLS-EXP value, support <0-7>.' ;
                              type uint16 {
                                range 0..7 {
                                  description 'MPLS-EXP value, support <0-7>' ;
                                }

                              }

                              mandatory true ;
                            }

                          }

                        }

                        case inherit {
                          description 'Set the MPLS-EXP value by inheriting.' ;
                          container inherit {
                            description 'Set the MPLS-EXP value by inheriting.' ;
                            leaf inherit-type {
                              description 'Specify the source inherit type, such as precedence, mpls-exp, 8021p, dscp.' ;
                              type enumeration {
                                enum precedence {
                                  value 1 ;
                                  description 'Select precedence as source inherit' ;
                                }

                                enum mpls-exp {
                                  value 2 ;
                                  description 'Select MPLS-EXP as source inherit' ;
                                }

                                enum 8021p {
                                  value 3 ;
                                  description 'Select 802.1p as source inherit' ;
                                }

                                enum dscp {
                                  value 4 ;
                                  description 'Select dscp as source inherit' ;
                                }

                              }

                              mandatory true ;
                            }

                          }

                        }

                      }

                    }

                    container multi-mpls-exp {
                      if-feature policy-action-set-multi-exp ;

                      description 'Select multi-MPLS-EXP as mark type.' ;
                      presence "Select multi-MPLS-EXP as mark type" ;
                      leaf inner-value {
                        description 'Inner multi-MPLS-EXP value, support <0-7>.' ;
                        type uint8 {
                          range 0..7 {
                            description 'Inner multi-MPLS-EXP value, support <0-7>' ;
                          }

                        }

                        mandatory true ;
                      }

                      leaf outer-value {
                        description 'Outer multi-MPLS-EXP value, support <0-7>.' ;
                        type uint8 {
                          range 0..7 {
                            description 'Outer multi-MPLS-EXP value, support <0-7>' ;
                          }

                        }

                        mandatory true ;
                      }

                    }

                    container interface {
                      description 'Specify interface name.' ;
                      presence "Specify interface name" ;
                      leaf if-name {
                        description 'Specify interface name.' ;
                        type ncd:ifname {
                          length 1..31 {
                            description 'Name of the interface, support 1-31 characters' ;
                          }

                        }

                        mandatory true ;
                      }

                      ncd:revise-date 2017-02-20 ;
                    }

                    container vlan-id {
                      description 'Configure VLAN ID.' ;
                      presence "Configure VLAN ID" ;
                      leaf vlan-value {
                        description 'Set VLAN ID, support <1-4094>.' ;
                        type uint16 {
                          range 1..4094 ;

                        }

                        mandatory true ;
                      }

                      ncd:revise-date 2017-02-20 ;
                    }

                    container service-query {
                      description 'Configure service function path.' ;
                      presence "Configure service function path" ;
                      leaf query-number {
                        description 'Service function path, support <0-255>.' ;
                        type uint8 {
                          range 0..255 ;

                        }

                        mandatory true ;
                      }

                      ncd:revise-date 2017-02-20 ;
                    }

                    container service-class {
                      description 'Configure service class.' ;
                      presence "Configure service function path" ;
                      leaf service-class {
                        description 'Select service class of PHB info.' ;
                        type qos-service-class ;

                        mandatory true ;
                      }

                      leaf color-type {
                        description 'Specify packets color, support <green,yellow,red>.' ;
                        type qos-color-type ;

                      }

                      ncd:revise-date 2021-01-18 ;
                    }

                    container encap-dscp {
                      description 'Select encapsulated DSCP as mark type.' ;
                      presence "Select encapsulated DSCP as mark type" ;
                      leaf dscp-value {
                        description 'DSCP value.' ;
                        type uint16 {
                          range 0..63 ;

                        }

                        mandatory true ;
                      }

                      ncd:revise-date 2021-05-25 ;
                    }

                  }

                  container drop {
                    if-feature policy-action-drop ;

                    description 'Configure drop.' ;
                    presence "Configure drop" ;
                    leaf drop {
                      description 'Specify drop.' ;
                      type empty ;

                      mandatory true ;
                    }

                  }

                  container latency-time-threshold {
                    description 'Configure latency time threshold.' ;
                    presence "Configure latency time threshold" ;
                    leaf value {
                      description 'Set the threshold of latency time.' ;
                      type uint32 {
                        range 0..1000 ;

                      }

                      mandatory true ;
                    }

                    ncd:revise-date 2020-04-06 ;
                  }

                  container bandwidth-threshold {
                    description 'Configure bandwidth threshold.' ;
                    presence "Configure bandwidth threshold" ;
                    leaf value {
                      description 'Set the threshold of bandwidth.' ;
                      type uint32 {
                        range 0..10000000 ;

                      }

                      mandatory true ;
                    }

                    container percentage {
                      description 'Configure percentage of acceleration or deceleration.' ;
                      leaf up {
                        description 'Configure percentage of acceleration (percentage <0.0-100.0>).' ;
                        type decimal64 {
                          fraction-digits 2 ;
                          range 0..100 ;

                        }

                      }

                      leaf down {
                        description 'Configure percentage of deceleration (percentage <0.0-100.0>).' ;
                        type decimal64 {
                          fraction-digits 2 ;
                          range 0..100 ;

                        }

                      }

                    }

                    ncd:revise-date 2020-04-06 ;
                  }

                  container drop-rate-threshold {
                    description 'Configure drop rate threshold.' ;
                    presence "Configure drop rate threshold" ;
                    leaf percentage {
                      description 'Set the threshold of drop rate (percentage <0.0-100.0>).' ;
                      type decimal64 {
                        fraction-digits 2 ;
                        range 0.0..100.0 ;

                      }

                      mandatory true ;
                    }

                    ncd:revise-date 2020-04-06 ;
                  }

                  container wred-template {
                    if-feature wred-template ;

                    description 'Configure WRED(Weighted Random Early Detection) template information.' ;
                    presence "Configure WRED template" ;
                    leaf wred-template-name {
                      description 'Name of the WRED(Weighted Random Early Detection) template, support 1-31 characters.' ;
                      type string {
                        length 1..31 {
                          description 'Name of the WRED template, support 1-31 characters' ;
                        }

                      }

                      mandatory true ;
                    }

                    ncd:revise-date 2022-06-27 ;
                  }

                  container queue-depth-adaptive {
                    if-feature queue-depth-adaptive ;

                    leaf adaptive {
                      type empty ;

                      mandatory true ;
                      description 'Configure adaptive queue depth.' ;
                    }

                    presence "adaptive queue depth" ;
                    description 'Configure adaptive queue depth.' ;
                    ncd:revise-date 2023-06-20 ;
                  }

                }

              }

              container pmap-description {
                description 'Description of a policy map, support 1-79 characters.' ;
                presence "Specify description of policy map" ;
                leaf pmap-description {
                  description 'Description of a policy map, support 1-79 characters.' ;
                  type ncd:string-with-blank {
                    length 1..79 {
                      description 'Description of a policy map, support 1-79 characters.' ;
                    }

                  }

                  mandatory true ;
                }

                ncd:revise-date 2020-06-18 ;
              }

            }

          }

        }

        container car-action {
          if-feature car-action-mode ;

          description 'Policy map based on car-action.' ;
          container policy-maps {
            description 'Configure QoS policy map lists.' ;
            list policy-map {
              description 'Configure QoS policy maps.' ;
              key pmap-name ;
              leaf pmap-name {
                description 'Name of the policy map, support 1-31 characters.' ;
                type string {
                  length 1..31 {
                    description 'Name of the policy map, support 1-31 characters' ;
                  }

                }

              }

              container class-maps {
                description 'Configure QoS policy class.' ;
                list class-map {
                  description 'Configure QoS policy class.' ;
                  key cmap-name ;
                  leaf cmap-name {
                    description 'Name of the class map, support 1-31 characters.' ;
                    type string {
                      length 1..31 {
                        description 'Name of the class map, support 1-31 characters' ;
                      }

                    }

                  }

                  container police {
                    description 'Configure traffic policing.' ;
                    presence "Configure traffic policing" ;
                    leaf cir {
                      description 'Configure the CIR (Committed Information Rate) value, default: kilobits per second.' ;
                      type uint32 {
                        range 8..4294967295 {
                          description 'The CIR value (default: kilobits per second).' ;
                        }

                      }

                      mandatory true ;
                    }

                    leaf cir-unit {
                      description 'Set CIR unit, such as kbps, mbps, gbps.' ;
                      type qos-rate-unit-type ;

                    }

                    leaf cbs {
                      description 'Configure the CBS(Committed Burst Size) size in bytes.' ;
                      type uint32 {
                        range 1..4294967295 {
                          description 'The CBS(Committed Burst Size) size in bytes.' ;
                        }

                      }

                      units Byte ;
                    }

                    leaf pir {
                      description 'Configure the PIR(Peak Information Rate) value, default: kilobits per second.' ;
                      type uint32 {
                        range 8..4294967295 {
                          description 'The PIR(Peak Information Rate) value (default: kilobits per second).' ;
                        }

                      }

                      mandatory true ;
                    }

                    leaf pir-unit {
                      description 'Set PIR unit, such as kbps, mbps, gbps.' ;
                      type qos-rate-unit-type ;

                    }

                    leaf pbs {
                      description 'Configure the PBS(Peak Burst Size) size in bytes.' ;
                      type uint32 {
                        range 1..4294967295 {
                          description 'The PBS(Peak Burst Size) size in bytes.' ;
                        }

                      }

                      units Byte ;
                    }

                    container conform-action {
                      description 'Action to packets that conform to the rate limit.' ;
                      choice conform-action {
                        description 'Specify action to packets that conform to the rate limit.' ;
                        mandatory true ;
                        case ca-drop {
                          description 'Drop packet in conform-action.' ;
                          leaf drop {
                            description 'Specify action to drop packet.' ;
                            type empty ;

                            mandatory true ;
                          }

                        }

                        case ca-transmit {
                          description 'Transmit packet in conform-action.' ;
                          leaf transmit {
                            description 'Specify action to transmit packet.' ;
                            type empty ;

                            mandatory true ;
                          }

                        }

                        case ca-mpls-exp {
                          description 'Rewrite packet MPLS-EXP and transmit the packet.' ;
                          leaf set-exp-transmit {
                            description 'Specify action to rewrite packet MPLS-EXP and transmit it.' ;
                            type empty ;

                            mandatory true ;
                          }

                          container mpls-label-type {
                            description 'Set MPLS-EXP label type.' ;
                            presence "Set MPLS-EXP label type" ;
                            leaf label-type {
                              description 'Set MPLS-EXP label position.' ;
                              type enumeration {
                                enum topmost {
                                  value 1 ;
                                  description 'Set the MPLS-EXP value on topmost label' ;
                                }

                                enum imposition {
                                  value 2 ;
                                  description 'Set the MPLS-EXP value on imposition label' ;
                                }

                                enum inner {
                                  value 3 ;
                                  description 'Set the MPLS-EXP value on inner label' ;
                                }

                              }

                              mandatory true ;
                            }

                          }

                          leaf mpls-exp-value {
                            description 'Reset MPLS-EXP value in conform-action, support <0-7>.' ;
                            type uint8 {
                              range 0..7 {
                                description 'The MPLS-EXP value, support <0-7>' ;
                              }

                            }

                            mandatory true ;
                          }

                        }

                        case ca-precedence {
                          description 'Rewrite packet precedence and transmit the packet.' ;
                          leaf set-prec-transmit {
                            description 'Specify action to rewrite packet precedence and transmit it.' ;
                            type empty ;

                            mandatory true ;
                          }

                          leaf prec-value {
                            description 'Reset the IP-Precedence value in conform-action, support <0-7>.' ;
                            type uint8 {
                              range 0..7 {
                                description 'The IP-Precedence value, support <0-7>' ;
                              }

                            }

                            mandatory true ;
                          }

                        }

                        case ca-dscp {
                          description 'Rewrite packet DSCP and transmit the packet.' ;
                          leaf set-dscp-transmit {
                            description 'Specify action to rewrite packet DSCP and transmit it.' ;
                            type empty ;

                            mandatory true ;
                          }

                          leaf dscp-value {
                            description 'Reset DSCP in conform-action, support <0-63>.' ;
                            type uint8 {
                              range 0..63 {
                                description 'The DSCP value, support <0-63>' ;
                              }

                            }

                            mandatory true ;
                          }

                        }

                        case ca-8021p {
                          description 'Rewrite packet 802.1p and transmit the packet.' ;
                          leaf set-8021p-transmit {
                            description 'Specify action to rewrite packet 802.1p and transmit it.' ;
                            type empty ;

                            mandatory true ;
                          }

                          leaf value-8021p {
                            description 'Reset 802.1p in conform-action, support <0-7>.' ;
                            type uint8 {
                              range 0..7 {
                                description 'The 802.1p value, support <0-7>' ;
                              }

                            }

                            mandatory true ;
                          }

                        }

                        case ca-multi-exp-transmit {
                          description 'Rewrite packet multi-MPLS-EXP and transmit it.' ;
                          leaf set-multi-exp-transmit {
                            description 'Specify action to rewrite packet multi-MPLS-EXP and transmit it.' ;
                            type empty ;

                            mandatory true ;
                          }

                          leaf inner-value {
                            description 'Inner multi-MPLS-EXP value, support <0-7>.' ;
                            type uint8 {
                              range 0..7 {
                                description 'Inner multi-MPLS-EXP value, support <0-7>' ;
                              }

                            }

                            mandatory true ;
                          }

                          leaf outer-value {
                            description 'Outer multi-MPLS-EXP value, support <0-7>.' ;
                            type uint8 {
                              range 0..7 {
                                description 'Outer multi-MPLS-EXP value, support <0-7>' ;
                              }

                            }

                            mandatory true ;
                          }

                        }

                        case ca-service-class {
                          description 'Specify action to rewrite packet service-class and transmit it.' ;
                          leaf service-class-value {
                            description 'Reset service class in conform-action.' ;
                            type qos-service-class ;

                            mandatory true ;
                          }

                          ncd:revise-date 2020-06-23 ;
                        }

                      }

                    }

                    container exceed-action {
                      description 'Action to packets that exceed the rate limit.' ;
                      choice exceed-action {
                        description 'Specify action to packets that exceed the rate limit.' ;
                        mandatory true ;
                        case ea-drop {
                          description 'Drop packet in exceed-action.' ;
                          leaf drop {
                            description 'Specify action to drop packet.' ;
                            type empty ;

                            mandatory true ;
                          }

                        }

                        case ea-transmit {
                          description 'Transmit packet in exceed-action.' ;
                          leaf transmit {
                            description 'Specify action to transmit packet.' ;
                            type empty ;

                            mandatory true ;
                          }

                        }

                        case ea-mpls-exp {
                          description 'Rewrite packet MPLS-EXP and transmit the packet.' ;
                          leaf set-exp-transmit {
                            description 'Specify action to rewrite packet MPLS-EXP and transmit it.' ;
                            type empty ;

                            mandatory true ;
                          }

                          container mpls-label-type {
                            description 'Set MPLS-EXP label type.' ;
                            presence "Set MPLS-EXP label type" ;
                            leaf label-type {
                              description 'Set MPLS-EXP label position.' ;
                              type enumeration {
                                enum topmost {
                                  value 1 ;
                                  description 'Set the MPLS-EXP value on topmost label' ;
                                }

                                enum imposition {
                                  value 2 ;
                                  description 'Set the MPLS-EXP value on imposition label' ;
                                }

                                enum inner {
                                  value 3 ;
                                  description 'Set the MPLS-EXP value on inner label' ;
                                }

                              }

                              mandatory true ;
                            }

                          }

                          leaf mpls-exp-value {
                            description 'Reset MPLS-EXP value in exceed-action, support <0-7>.' ;
                            type uint8 {
                              range 0..7 {
                                description 'The MPLS-EXP value, support <0-7>' ;
                              }

                            }

                            mandatory true ;
                          }

                        }

                        case ea-precedence {
                          description 'Rewrite packet precedence and transmit the packet.' ;
                          leaf set-prec-transmit {
                            description 'Specify action to rewrite packet precedence and transmit it.' ;
                            type empty ;

                            mandatory true ;
                          }

                          leaf prec-value {
                            description 'Reset the IP-Precedence value in exceed-action, support <0-7>.' ;
                            type uint8 {
                              range 0..7 {
                                description 'The IP-Precedence value, support <0-7>' ;
                              }

                            }

                            mandatory true ;
                          }

                        }

                        case ea-dscp {
                          description 'Rewrite packet DSCP and transmit the packet.' ;
                          leaf set-dscp-transmit {
                            description 'Specify action to rewrite packet DSCP and transmit it.' ;
                            type empty ;

                            mandatory true ;
                          }

                          leaf dscp-value {
                            description 'Reset DSCP in exceed-action, support <0-63>.' ;
                            type uint8 {
                              range 0..63 {
                                description 'The DSCP value, support <0-63>' ;
                              }

                            }

                            mandatory true ;
                          }

                        }

                        case ea-8021p {
                          description 'Rewrite packet 802.1p and transmit the packet.' ;
                          leaf set-8021p-transmit {
                            description 'Specify action to rewrite packet 802.1p and transmit it.' ;
                            type empty ;

                            mandatory true ;
                          }

                          leaf value-8021p {
                            description 'Reset 802.1p in exceed-action, support <0-7>.' ;
                            type uint8 {
                              range 0..7 {
                                description 'The 802.1p value, support <0-7>' ;
                              }

                            }

                            mandatory true ;
                          }

                        }

                        case ea-multi-exp-transmit {
                          description 'Rewrite packet multi-MPLS-EXP and transmit it.' ;
                          leaf set-multi-exp-transmit {
                            description 'Specify action to rewrite packet multi-MPLS-EXP and transmit it.' ;
                            type empty ;

                            mandatory true ;
                          }

                          leaf inner-value {
                            description 'Inner multi-MPLS-EXP value, support <0-7>.' ;
                            type uint8 {
                              range 0..7 {
                                description 'Inner multi-MPLS-EXP value, support <0-7>' ;
                              }

                            }

                            mandatory true ;
                          }

                          leaf outer-value {
                            description 'Outer multi-MPLS-EXP value, support <0-7>.' ;
                            type uint8 {
                              range 0..7 {
                                description 'Outer multi-MPLS-EXP value, support <0-7>' ;
                              }

                            }

                            mandatory true ;
                          }

                        }

                        case ea-service-class {
                          description 'Specify action to rewrite packet service class and transmit it.' ;
                          leaf service-class-value {
                            description 'Reset service class in exceed-action.' ;
                            type qos-service-class ;

                            mandatory true ;
                          }

                          ncd:revise-date 2020-06-23 ;
                        }

                      }

                    }

                    container violate-action {
                      description 'Action to packets that violate the rate limit.' ;
                      choice violate-action {
                        description 'Specify action to packets that violate the rate limit.' ;
                        mandatory true ;
                        case va-drop {
                          description 'Drop packet in violate-action.' ;
                          leaf drop {
                            description 'Specify action to drop packet.' ;
                            type empty ;

                            mandatory true ;
                          }

                        }

                        case va-transmit {
                          description 'Transmit packet in violate-action.' ;
                          leaf transmit {
                            description 'Specify action to transmit packet.' ;
                            type empty ;

                            mandatory true ;
                          }

                        }

                        case va-mpls-exp {
                          description 'Rewrite packet MPLS-EXP and transmit the packet.' ;
                          leaf set-exp-transmit {
                            description 'Specify action to rewrite packet MPLS-EXP and transmit it.' ;
                            type empty ;

                            mandatory true ;
                          }

                          container mpls-label-type {
                            description 'Set MPLS-EXP label type.' ;
                            presence "Set MPLS-EXP label type" ;
                            leaf label-type {
                              description 'Set MPLS-EXP label position.' ;
                              type enumeration {
                                enum topmost {
                                  value 1 ;
                                  description 'Set the MPLS-EXP value on topmost label' ;
                                }

                                enum imposition {
                                  value 2 ;
                                  description 'Set the MPLS-EXP value on imposition label' ;
                                }

                                enum inner {
                                  value 3 ;
                                  description 'Set the MPLS-EXP value on inner label' ;
                                }

                              }

                              mandatory true ;
                            }

                          }

                          leaf mpls-exp-value {
                            description 'Reset MPLS-EXP value in violate-action, support <0-7>.' ;
                            type uint8 {
                              range 0..7 {
                                description 'The MPLS-EXP value, support <0-7>' ;
                              }

                            }

                            mandatory true ;
                          }

                        }

                        case va-precedence {
                          description 'Rewrite packet precedence and transmit the packet.' ;
                          leaf set-prec-transmit {
                            description 'Specify action to rewrite packet precedence and transmit it.' ;
                            type empty ;

                            mandatory true ;
                          }

                          leaf prec-value {
                            description 'Reset the IP-Precedence value in violate-action, support <0-7>.' ;
                            type uint8 {
                              range 0..7 {
                                description 'The IP-Precedence value, support <0-7>' ;
                              }

                            }

                            mandatory true ;
                          }

                        }

                        case va-dscp {
                          description 'Rewrite packet DSCP and transmit the packet.' ;
                          leaf set-dscp-transmit {
                            description 'Specify action to rewrite packet DSCP and transmit it.' ;
                            type empty ;

                            mandatory true ;
                          }

                          leaf dscp-value {
                            description 'Reset DSCP in violate-action, support <0-63>.' ;
                            type uint8 {
                              range 0..63 {
                                description 'The DSCP value, support <0-63>' ;
                              }

                            }

                            mandatory true ;
                          }

                        }

                        case va-8021p {
                          description 'Rewrite packet 802.1p and transmit the packet.' ;
                          leaf set-8021p-transmit {
                            description 'Specify action to rewrite packet 802.1p and transmit it.' ;
                            type empty ;

                            mandatory true ;
                          }

                          leaf value-8021p {
                            description 'Reset 802.1p in violate-action, support <0-7>.' ;
                            type uint8 {
                              range 0..7 {
                                description 'The 802.1p value, support <0-7>' ;
                              }

                            }

                            mandatory true ;
                          }

                        }

                        case va-multi-exp-transmit {
                          description 'Rewrite packet multi-MPLS-EXP and transmit it.' ;
                          leaf set-multi-exp-transmit {
                            description 'Specify action to rewrite packet multi-MPLS-EXP and transmit it.' ;
                            type empty ;

                            mandatory true ;
                          }

                          leaf inner-value {
                            description 'Inner multi-MPLS-EXP value, support <0-7>.' ;
                            type uint8 {
                              range 0..7 {
                                description 'Inner multi-MPLS-EXP value, support <0-7>' ;
                              }

                            }

                            mandatory true ;
                          }

                          leaf outer-value {
                            description 'Outer multi-MPLS-EXP value, support <0-7>.' ;
                            type uint8 {
                              range 0..7 {
                                description 'Outer multi-MPLS-EXP value, support <0-7>' ;
                              }

                            }

                            mandatory true ;
                          }

                        }

                        case va-service-class {
                          description 'Specify action to rewrite packet service class and transmit it.' ;
                          leaf service-class-value {
                            description 'Reset service class in violate-action.' ;
                            type qos-service-class ;

                            mandatory true ;
                          }

                          ncd:revise-date 2020-06-23 ;
                        }

                      }

                    }

                  }

                  container priority-level {
                    description 'Configure PQ(Priority Queuing) priority level.' ;
                    presence "Configure PQ priority level" ;
                    leaf priority-value {
                      description 'Set the priority level of PQ.' ;
                      type uint16 {
                        range 1..4 {
                          description 'The priority level of PQ, support <1-4>.' ;
                        }

                      }

                      mandatory true ;
                    }

                    ncd:revise-date 2017-06-12 ;
                  }

                  container priority-llq {
                    description 'Configure LLQ(Low Latency Queuing) priority.' ;
                    presence "Configure LLQ priority" ;
                    leaf priority-llq {
                      description 'Specify LLQ.' ;
                      type empty ;

                      mandatory true ;
                    }

                    ncd:revise-date 2017-06-12 ;
                  }

                  container set {
                    description 'Mark a packet.' ;
                    container dscp {
                      description 'Select DSCP as mark type.' ;
                      presence "Select DSCP as mark type" ;
                      container inherit {
                        description 'Set the DSCP value by inheriting.' ;
                        leaf inherit-type {
                          description 'Specify the source inherit type, such as precedence, mpls-exp, 8021p, dscp, pay-load 8021p.' ;
                          type enumeration {
                            enum precedence {
                              value 1 ;
                              description 'Select precedence as source inherit' ;
                            }

                            enum mpls-exp {
                              value 2 ;
                              description 'Select MPLS-EXP as source inherit' ;
                            }

                            enum 8021p {
                              value 3 ;
                              description 'Select 802.1p as source inherit' ;
                            }

                            enum dscp {
                              value 4 ;
                              description 'Select dscp as source inherit' ;
                            }

                            enum pay-load-8021p {
                              value 6 ;
                              description 'Select inner 802.1p as source inherit' ;
                            }

                          }

                          mandatory true ;
                        }

                      }

                    }

                    container precedence {
                      description 'Select precedence as mark type.' ;
                      presence "Select precedence as mark type" ;
                      container inherit {
                        description 'Set the IP Precedence value by inheriting.' ;
                        leaf inherit-type {
                          description 'Specify the source inherit type, such as precedence, mpls-exp, 8021p, dscp.' ;
                          type enumeration {
                            enum precedence {
                              value 1 ;
                              description 'Select precedence as source inherit' ;
                            }

                            enum mpls-exp {
                              value 2 ;
                              description 'Select MPLS-EXP as source inherit' ;
                            }

                            enum 8021p {
                              value 3 ;
                              description 'Select 802.1p as source inherit' ;
                            }

                            enum dscp {
                              value 4 ;
                              description 'Select dscp as source inherit' ;
                            }

                          }

                          mandatory true ;
                        }

                      }

                    }

                    container pri-8021p {
                      description 'Select 802.1p as mark type.' ;
                      presence "Select 802.1p as mark type" ;
                      container inherit {
                        description 'Set the 802.1p value by inheriting.' ;
                        leaf inherit-type {
                          description 'Specify the source inherit type, such as precedence, mpls-exp, 8021p, dscp.' ;
                          type enumeration {
                            enum precedence {
                              value 1 ;
                              description 'Select precedence as source inherit' ;
                            }

                            enum mpls-exp {
                              value 2 ;
                              description 'Select MPLS-EXP as source inherit' ;
                            }

                            enum 8021p {
                              value 3 ;
                              description 'Select 802.1p as source inherit' ;
                            }

                            enum dscp {
                              value 4 ;
                              description 'Select dscp as source inherit' ;
                            }

                          }

                          mandatory true ;
                        }

                        leaf inner-outer {
                          description 'Set 8021p inner or outer flag.If vlaue is 0, it means outer flag. If value is 1,it means inner and outer flag.' ;
                          type uint8 {
                            range 0..1 {
                              description 'Inner or outer flag. 0 is outer. 1 is inner and outer' ;
                            }

                          }

                          default 0 ;
                        }

                      }

                    }

                    container mpls-exp {
                      description 'Select MPLS-EXP as mark type.' ;
                      presence "Select MPLS-EXP as mark type" ;
                      leaf label-type {
                        if-feature policy-action-set-label ;

                        description 'Select MPLS-EXP label position, such as default, topmost, imposition, inner.' ;
                        type enumeration {
                          enum topmost {
                            value 1 ;
                            description 'Set the MPLS-EXP value on topmost label' ;
                          }

                          enum imposition {
                            value 2 ;
                            description 'Set the MPLS-EXP value on all imposed labels' ;
                          }

                          enum default {
                            value 0 ;
                            description 'The default for topmost label' ;
                          }

                          enum inner {
                            value 3 ;
                            description 'Set the MPLS-EXP value on inner label' ;
                          }

                        }

                        mandatory true ;
                      }

                      container inherit {
                        description 'Set the MPLS-EXP value by inheriting.' ;
                        leaf inherit-type {
                          description 'Specify the source inherit type, such as precedence, mpls-exp, 8021p, dscp.' ;
                          type enumeration {
                            enum precedence {
                              value 1 ;
                              description 'Select precedence as source inherit' ;
                            }

                            enum mpls-exp {
                              value 2 ;
                              description 'Select MPLS-EXP as source inherit' ;
                            }

                            enum 8021p {
                              value 3 ;
                              description 'Select 802.1p as source inherit' ;
                            }

                            enum dscp {
                              value 4 ;
                              description 'Select dscp as source inherit' ;
                            }

                          }

                          mandatory true ;
                        }

                      }

                    }

                    container service-class {
                      description 'Configure service class.' ;
                      presence "Configure service function path" ;
                      leaf service-class {
                        description 'Select service class of PHB info.' ;
                        type qos-service-class ;

                        mandatory true ;
                      }

                      leaf color-type {
                        description 'Specify packets color, support <green,yellow,red>.' ;
                        type qos-color-type ;

                        ncd:revise-date 2021-01-18 ;
                      }

                    }

                    ncd:revise-date 2018-09-19 ;
                  }

                }

                container class-default {
                  description 'Select policy association default class.' ;
                  presence "Configure the default class" ;
                  leaf class-default {
                    description 'Specify the default class.' ;
                    type empty ;

                    mandatory true ;
                  }

                  container police {
                    description 'Configure traffic policing.' ;
                    presence "Configure traffic policing" ;
                    leaf cir {
                      description 'Configure the CIR (Committed Information Rate) value, default: kilobits per second.' ;
                      type uint32 {
                        range 8..4294967295 {
                          description 'The CIR value (default: kilobits per second).' ;
                        }

                      }

                      mandatory true ;
                    }

                    leaf cir-unit {
                      description 'Set CIR unit, such as kbps, mbps, gbps.' ;
                      type qos-rate-unit-type ;

                    }

                    leaf cbs {
                      description 'Configure the CBS(Committed Burst Size) size in bytes.' ;
                      type uint32 {
                        range 1..4294967295 {
                          description 'The CBS(Committed Burst Size) size in bytes.' ;
                        }

                      }

                      units Byte ;
                    }

                    leaf pir {
                      description 'Configure the PIR(Peak Information Rate) value, default: kilobits per second.' ;
                      type uint32 {
                        range 8..4294967295 {
                          description 'The PIR(Peak Information Rate) value (default: kilobits per second).' ;
                        }

                      }

                      mandatory true ;
                    }

                    leaf pir-unit {
                      description 'Set PIR unit, such as kbps, mbps, gbps.' ;
                      type qos-rate-unit-type ;

                    }

                    leaf pbs {
                      description 'Configure the PBS(Peak Burst Size) size in bytes.' ;
                      type uint32 {
                        range 1..4294967295 {
                          description 'The PBS(Peak Burst Size) size in bytes.' ;
                        }

                      }

                      units Byte ;
                    }

                    container conform-action {
                      description 'Action to packets that conform to the rate limit.' ;
                      choice conform-action {
                        description 'Specify action to packets that conform to the rate limit.' ;
                        mandatory true ;
                        case ca-drop {
                          description 'Drop packet in conform-action.' ;
                          leaf drop {
                            description 'Specify action to drop packet.' ;
                            type empty ;

                            mandatory true ;
                          }

                        }

                        case ca-transmit {
                          description 'Transmit packet in conform-action.' ;
                          leaf transmit {
                            description 'Specify action to transmit packet.' ;
                            type empty ;

                            mandatory true ;
                          }

                        }

                        case ca-mpls-exp {
                          description 'Rewrite packet MPLS-EXP and transmit the packet.' ;
                          leaf set-exp-transmit {
                            description 'Specify action to rewrite packet MPLS-EXP and transmit it.' ;
                            type empty ;

                            mandatory true ;
                          }

                          container mpls-label-type {
                            description 'Set MPLS-EXP label type.' ;
                            presence "Set MPLS-EXP label type" ;
                            leaf label-type {
                              description 'Set MPLS-EXP label position.' ;
                              type enumeration {
                                enum topmost {
                                  value 1 ;
                                  description 'Set the MPLS-EXP value on topmost label' ;
                                }

                                enum imposition {
                                  value 2 ;
                                  description 'Set the MPLS-EXP value on imposition label' ;
                                }

                                enum inner {
                                  value 3 ;
                                  description 'Set the MPLS-EXP value on inner label' ;
                                }

                              }

                              mandatory true ;
                            }

                          }

                          leaf mpls-exp-value {
                            description 'Reset MPLS-EXP value in conform-action, support <0-7>.' ;
                            type uint8 {
                              range 0..7 {
                                description 'The MPLS-EXP value, support <0-7>' ;
                              }

                            }

                            mandatory true ;
                          }

                        }

                        case ca-precedence {
                          description 'Rewrite packet precedence and transmit the packet.' ;
                          leaf set-prec-transmit {
                            description 'Specify action to rewrite packet precedence and transmit it.' ;
                            type empty ;

                            mandatory true ;
                          }

                          leaf prec-value {
                            description 'Reset the IP-Precedence value in conform-action, support <0-7>.' ;
                            type uint8 {
                              range 0..7 {
                                description 'The IP-Precedence value, support <0-7>' ;
                              }

                            }

                            mandatory true ;
                          }

                        }

                        case ca-dscp {
                          description 'Rewrite packet DSCP and transmit the packet.' ;
                          leaf set-dscp-transmit {
                            description 'Specify action to rewrite packet DSCP and transmit it.' ;
                            type empty ;

                            mandatory true ;
                          }

                          leaf dscp-value {
                            description 'Reset DSCP in conform-action, support <0-63>.' ;
                            type uint8 {
                              range 0..63 {
                                description 'The DSCP value, support <0-63>' ;
                              }

                            }

                            mandatory true ;
                          }

                        }

                        case ca-8021p {
                          description 'Rewrite packet 802.1p and transmit the packet.' ;
                          leaf set-8021p-transmit {
                            description 'Specify action to rewrite packet 802.1p and transmit it.' ;
                            type empty ;

                            mandatory true ;
                          }

                          leaf value-8021p {
                            description 'Reset 802.1p in conform-action, support <0-7>.' ;
                            type uint8 {
                              range 0..7 {
                                description 'The 802.1p value, support <0-7>' ;
                              }

                            }

                            mandatory true ;
                          }

                        }

                        case ca-multi-exp-transmit {
                          description 'Rewrite packet multi-MPLS-EXP and transmit it.' ;
                          leaf set-multi-exp-transmit {
                            description 'Specify action to rewrite packet multi-MPLS-EXP and transmit it.' ;
                            type empty ;

                            mandatory true ;
                          }

                          leaf inner-value {
                            description 'Inner multi-MPLS-EXP value, support <0-7>.' ;
                            type uint8 {
                              range 0..7 {
                                description 'Inner multi-MPLS-EXP value, support <0-7>' ;
                              }

                            }

                            mandatory true ;
                          }

                          leaf outer-value {
                            description 'Outer multi-MPLS-EXP value, support <0-7>.' ;
                            type uint8 {
                              range 0..7 {
                                description 'Outer multi-MPLS-EXP value, support <0-7>' ;
                              }

                            }

                            mandatory true ;
                          }

                        }

                        case ca-service-class {
                          description 'Specify action to rewrite packet service-class and transmit it.' ;
                          leaf service-class-value {
                            description 'Reset service class in conform-action.' ;
                            type qos-service-class ;

                            mandatory true ;
                          }

                          ncd:revise-date 2020-06-23 ;
                        }

                      }

                    }

                    container exceed-action {
                      description 'Action to packets that exceed the rate limit.' ;
                      choice exceed-action {
                        description 'Specify action to packets that exceed the rate limit.' ;
                        mandatory true ;
                        case ea-drop {
                          description 'Drop packet in exceed-action.' ;
                          leaf drop {
                            description 'Specify action to drop packet.' ;
                            type empty ;

                            mandatory true ;
                          }

                        }

                        case ea-transmit {
                          description 'Transmit packet in exceed-action.' ;
                          leaf transmit {
                            description 'Specify action to transmit packet.' ;
                            type empty ;

                            mandatory true ;
                          }

                        }

                        case ea-mpls-exp {
                          description 'Rewrite packet MPLS-EXP and transmit the packet.' ;
                          leaf set-exp-transmit {
                            description 'Specify action to rewrite packet MPLS-EXP and transmit it.' ;
                            type empty ;

                            mandatory true ;
                          }

                          container mpls-label-type {
                            description 'Set MPLS-EXP label type.' ;
                            presence "Set MPLS-EXP label type" ;
                            leaf label-type {
                              description 'Set MPLS-EXP label position.' ;
                              type enumeration {
                                enum topmost {
                                  value 1 ;
                                  description 'Set the MPLS-EXP value on topmost label' ;
                                }

                                enum imposition {
                                  value 2 ;
                                  description 'Set the MPLS-EXP value on imposition label' ;
                                }

                                enum inner {
                                  value 3 ;
                                  description 'Set the MPLS-EXP value on inner label' ;
                                }

                              }

                              mandatory true ;
                            }

                          }

                          leaf mpls-exp-value {
                            description 'Reset MPLS-EXP value in exceed-action, support <0-7>.' ;
                            type uint8 {
                              range 0..7 {
                                description 'The MPLS-EXP value, support <0-7>' ;
                              }

                            }

                            mandatory true ;
                          }

                        }

                        case ea-precedence {
                          description 'Rewrite packet precedence and transmit the packet.' ;
                          leaf set-prec-transmit {
                            description 'Specify action to rewrite packet precedence and transmit it.' ;
                            type empty ;

                            mandatory true ;
                          }

                          leaf prec-value {
                            description 'Reset the IP-Precedence value in exceed-action, support <0-7>.' ;
                            type uint8 {
                              range 0..7 {
                                description 'The IP-Precedence value, support <0-7>' ;
                              }

                            }

                            mandatory true ;
                          }

                        }

                        case ea-dscp {
                          description 'Rewrite packet DSCP and transmit the packet.' ;
                          leaf set-dscp-transmit {
                            description 'Specify action to rewrite packet DSCP and transmit it.' ;
                            type empty ;

                            mandatory true ;
                          }

                          leaf dscp-value {
                            description 'Reset DSCP in exceed-action, support <0-63>.' ;
                            type uint8 {
                              range 0..63 {
                                description 'The DSCP value, support <0-63>' ;
                              }

                            }

                            mandatory true ;
                          }

                        }

                        case ea-8021p {
                          description 'Rewrite packet 802.1p and transmit the packet.' ;
                          leaf set-8021p-transmit {
                            description 'Specify action to rewrite packet 802.1p and transmit it.' ;
                            type empty ;

                            mandatory true ;
                          }

                          leaf value-8021p {
                            description 'Reset 802.1p in exceed-action, support <0-7>.' ;
                            type uint8 {
                              range 0..7 {
                                description 'The 802.1p value, support <0-7>' ;
                              }

                            }

                            mandatory true ;
                          }

                        }

                        case ea-multi-exp-transmit {
                          description 'Rewrite packet multi-MPLS-EXP and transmit it.' ;
                          leaf set-multi-exp-transmit {
                            description 'Specify action to rewrite packet multi-MPLS-EXP and transmit it.' ;
                            type empty ;

                            mandatory true ;
                          }

                          leaf inner-value {
                            description 'Inner multi-MPLS-EXP value, support <0-7>.' ;
                            type uint8 {
                              range 0..7 {
                                description 'Inner multi-MPLS-EXP value, support <0-7>' ;
                              }

                            }

                            mandatory true ;
                          }

                          leaf outer-value {
                            description 'Outer multi-MPLS-EXP value, support <0-7>.' ;
                            type uint8 {
                              range 0..7 {
                                description 'Outer multi-MPLS-EXP value, support <0-7>' ;
                              }

                            }

                            mandatory true ;
                          }

                        }

                        case ea-service-class {
                          description 'Specify action to rewrite packet service class and transmit it.' ;
                          leaf service-class-value {
                            description 'Reset service class in exceed-action.' ;
                            type qos-service-class ;

                            mandatory true ;
                          }

                          ncd:revise-date 2020-06-23 ;
                        }

                      }

                    }

                    container violate-action {
                      description 'Action to packets that violate the rate limit.' ;
                      choice violate-action {
                        description 'Specify action to packets that violate the rate limit.' ;
                        mandatory true ;
                        case va-drop {
                          description 'Drop packet in violate-action.' ;
                          leaf drop {
                            description 'Specify action to drop packet.' ;
                            type empty ;

                            mandatory true ;
                          }

                        }

                        case va-transmit {
                          description 'Transmit packet in violate-action.' ;
                          leaf transmit {
                            description 'Specify action to transmit packet.' ;
                            type empty ;

                            mandatory true ;
                          }

                        }

                        case va-mpls-exp {
                          description 'Rewrite packet MPLS-EXP and transmit the packet.' ;
                          leaf set-exp-transmit {
                            description 'Specify action to rewrite packet MPLS-EXP and transmit it.' ;
                            type empty ;

                            mandatory true ;
                          }

                          container mpls-label-type {
                            description 'Set MPLS-EXP label type.' ;
                            presence "Set MPLS-EXP label type" ;
                            leaf label-type {
                              description 'Set MPLS-EXP label position.' ;
                              type enumeration {
                                enum topmost {
                                  value 1 ;
                                  description 'Set the MPLS-EXP value on topmost label' ;
                                }

                                enum imposition {
                                  value 2 ;
                                  description 'Set the MPLS-EXP value on imposition label' ;
                                }

                                enum inner {
                                  value 3 ;
                                  description 'Set the MPLS-EXP value on inner label' ;
                                }

                              }

                              mandatory true ;
                            }

                          }

                          leaf mpls-exp-value {
                            description 'Reset MPLS-EXP value in violate-action, support <0-7>.' ;
                            type uint8 {
                              range 0..7 {
                                description 'The MPLS-EXP value, support <0-7>' ;
                              }

                            }

                            mandatory true ;
                          }

                        }

                        case va-precedence {
                          description 'Rewrite packet precedence and transmit the packet.' ;
                          leaf set-prec-transmit {
                            description 'Specify action to rewrite packet precedence and transmit it.' ;
                            type empty ;

                            mandatory true ;
                          }

                          leaf prec-value {
                            description 'Reset the IP-Precedence value in violate-action, support <0-7>.' ;
                            type uint8 {
                              range 0..7 {
                                description 'The IP-Precedence value, support <0-7>' ;
                              }

                            }

                            mandatory true ;
                          }

                        }

                        case va-dscp {
                          description 'Rewrite packet DSCP and transmit the packet.' ;
                          leaf set-dscp-transmit {
                            description 'Specify action to rewrite packet DSCP and transmit it.' ;
                            type empty ;

                            mandatory true ;
                          }

                          leaf dscp-value {
                            description 'Reset DSCP in violate-action, support <0-63>.' ;
                            type uint8 {
                              range 0..63 {
                                description 'The DSCP value, support <0-63>' ;
                              }

                            }

                            mandatory true ;
                          }

                        }

                        case va-8021p {
                          description 'Rewrite packet 802.1p and transmit the packet.' ;
                          leaf set-8021p-transmit {
                            description 'Specify action to rewrite packet 802.1p and transmit it.' ;
                            type empty ;

                            mandatory true ;
                          }

                          leaf value-8021p {
                            description 'Reset 802.1p in violate-action, support <0-7>.' ;
                            type uint8 {
                              range 0..7 {
                                description 'The 802.1p value, support <0-7>' ;
                              }

                            }

                            mandatory true ;
                          }

                        }

                        case va-multi-exp-transmit {
                          description 'Rewrite packet multi-MPLS-EXP and transmit it.' ;
                          leaf set-multi-exp-transmit {
                            description 'Specify action to rewrite packet multi-MPLS-EXP and transmit it.' ;
                            type empty ;

                            mandatory true ;
                          }

                          leaf inner-value {
                            description 'Inner multi-MPLS-EXP value, support <0-7>.' ;
                            type uint8 {
                              range 0..7 {
                                description 'Inner multi-MPLS-EXP value, support <0-7>' ;
                              }

                            }

                            mandatory true ;
                          }

                          leaf outer-value {
                            description 'Outer multi-MPLS-EXP value, support <0-7>.' ;
                            type uint8 {
                              range 0..7 {
                                description 'Outer multi-MPLS-EXP value, support <0-7>' ;
                              }

                            }

                            mandatory true ;
                          }

                        }

                        case va-service-class {
                          description 'Specify action to rewrite packet service class and transmit it.' ;
                          leaf service-class-value {
                            description 'Reset service class in violate-action.' ;
                            type qos-service-class ;

                            mandatory true ;
                          }

                          ncd:revise-date 2020-06-23 ;
                        }

                      }

                    }

                  }

                  container priority-level {
                    description 'Configure PQ(Priority Queuing) priority level.' ;
                    presence "Configure PQ priority level" ;
                    leaf priority-value {
                      description 'Set the priority level of PQ, support <1-4>.' ;
                      type uint16 {
                        range 1..4 {
                          description 'The priority level of PQ, support <1-4>.' ;
                        }

                      }

                      mandatory true ;
                    }

                    ncd:revise-date 2017-06-12 ;
                  }

                  container priority-llq {
                    description 'Configure LLQ(Low Latency Queuing) priority.' ;
                    presence "Configure LLQ priority" ;
                    leaf priority-llq {
                      description 'Specify LLQ.' ;
                      type empty ;

                      mandatory true ;
                    }

                    ncd:revise-date 2017-06-12 ;
                  }

                  container set {
                    description 'Mark a packet.' ;
                    container dscp {
                      description 'Select DSCP as mark type.' ;
                      presence "Select DSCP as mark type" ;
                      container inherit {
                        description 'Set the DSCP value by inheriting.' ;
                        leaf inherit-type {
                          description 'Specify the source inherit type, such as precedence, mpls-exp, 8021p, dscp, pay-load 8021p.' ;
                          type enumeration {
                            enum precedence {
                              value 1 ;
                              description 'Select precedence as source inherit' ;
                            }

                            enum mpls-exp {
                              value 2 ;
                              description 'Select MPLS-EXP as source inherit' ;
                            }

                            enum 8021p {
                              value 3 ;
                              description 'Select 802.1p as source inherit' ;
                            }

                            enum dscp {
                              value 4 ;
                              description 'Select dscp as source inherit' ;
                            }

                            enum pay-load-8021p {
                              value 6 ;
                              description 'Select inner 802.1p as source inherit' ;
                            }

                          }

                          mandatory true ;
                        }

                      }

                    }

                    container precedence {
                      description 'Select precedence as mark type.' ;
                      presence "Select precedence as mark type" ;
                      container inherit {
                        description 'Set the IP Precedence value by inheriting.' ;
                        leaf inherit-type {
                          description 'Specify the source inherit type, such as precedence, mpls-exp, 8021p, dscp.' ;
                          type enumeration {
                            enum precedence {
                              value 1 ;
                              description 'Select precedence as source inherit' ;
                            }

                            enum mpls-exp {
                              value 2 ;
                              description 'Select MPLS-EXP as source inherit' ;
                            }

                            enum 8021p {
                              value 3 ;
                              description 'Select 802.1p as source inherit' ;
                            }

                            enum dscp {
                              value 4 ;
                              description 'Select dscp as source inherit' ;
                            }

                          }

                          mandatory true ;
                        }

                      }

                    }

                    container pri-8021p {
                      description 'Select 802.1p as mark type.' ;
                      presence "Select 802.1p as mark type" ;
                      container inherit {
                        description 'Set the 802.1p value by inheriting.' ;
                        leaf inherit-type {
                          description 'Specify the source inherit type, such as precedence, mpls-exp, 8021p, dscp.' ;
                          type enumeration {
                            enum precedence {
                              value 1 ;
                              description 'Select precedence as source inherit' ;
                            }

                            enum mpls-exp {
                              value 2 ;
                              description 'Select MPLS-EXP as source inherit' ;
                            }

                            enum 8021p {
                              value 3 ;
                              description 'Select 802.1p as source inherit' ;
                            }

                            enum dscp {
                              value 4 ;
                              description 'Select dscp as source inherit' ;
                            }

                          }

                          mandatory true ;
                        }

                        leaf inner-outer {
                          description 'Set 8021p inner or outer flag.If vlaue is 0, it means outer flag. If value is 1,it means inner and outer flag.' ;
                          type uint8 {
                            range 0..1 {
                              description 'Inner or outer flag. 0 is outer. 1 is inner and outer' ;
                            }

                          }

                          default 0 ;
                        }

                      }

                    }

                    container mpls-exp {
                      description 'Select MPLS-EXP as mark type.' ;
                      presence "Select MPLS-EXP as mark type" ;
                      leaf label-type {
                        if-feature policy-action-set-label ;

                        description 'Select MPLS-EXP label position, such as default, topmost, imposition, inner.' ;
                        type enumeration {
                          enum topmost {
                            value 1 ;
                            description 'Set the MPLS-EXP value on topmost label' ;
                          }

                          enum imposition {
                            value 2 ;
                            description 'Set the MPLS-EXP value on all imposed labels' ;
                          }

                          enum default {
                            value 0 ;
                            description 'The default for topmost label' ;
                          }

                          enum inner {
                            value 3 ;
                            description 'Set the MPLS-EXP value on inner label' ;
                          }

                        }

                        mandatory true ;
                      }

                      container inherit {
                        description 'Set the MPLS-EXP value by inheriting.' ;
                        leaf inherit-type {
                          description 'Specify the source inherit type, such as precedence, mpls-exp, 8021p, dscp.' ;
                          type enumeration {
                            enum precedence {
                              value 1 ;
                              description 'Select precedence as source inherit' ;
                            }

                            enum mpls-exp {
                              value 2 ;
                              description 'Select MPLS-EXP as source inherit' ;
                            }

                            enum 8021p {
                              value 3 ;
                              description 'Select 802.1p as source inherit' ;
                            }

                            enum dscp {
                              value 4 ;
                              description 'Select dscp as source inherit' ;
                            }

                          }

                          mandatory true ;
                        }

                      }

                    }

                    container service-class {
                      description 'Configure service class.' ;
                      presence "Configure service function path" ;
                      leaf service-class {
                        description 'Select service class of PHB info.' ;
                        type qos-service-class ;

                        mandatory true ;
                      }

                      leaf color-type {
                        description 'Specify packets color, support <green,yellow,red>.' ;
                        type qos-color-type ;

                        ncd:revise-date 2021-01-18 ;
                      }

                    }

                    ncd:revise-date 2018-09-19 ;
                  }

                }

              }

            }

          }

        }

        container phb-based {
          if-feature phb-mode ;

          description 'Policy map based on phb.' ;
          container policy-maps {
            description 'Configure QoS policy map lists.' ;
            list policy-map {
              description 'Configure QoS policy maps.' ;
              key pmap-name ;
              leaf pmap-name {
                description 'Name of the policy map, support 1-31 characters.' ;
                type string {
                  length 1..31 {
                    description 'Name of the policy map, support 1-31 characters' ;
                  }

                }

              }

              container class-maps {
                description 'Configure QoS policy class.' ;
                list class-map {
                  description 'Configure QoS policy class.' ;
                  key cmap-name ;
                  leaf cmap-name {
                    description 'Name of the class map, support 1-31 characters.' ;
                    type string {
                      length 1..31 ;

                    }

                  }

                  container bandwidth {
                    description 'Configure minimum guaranteed bandwidth.' ;
                    presence "Configure minimum guaranteed bandwidth" ;
                    leaf percentage {
                      description 'Set the exact bandwidth percentage, support <1-100>.' ;
                      type uint16 {
                        range 1..100 {
                          description 'The exact bandwidth percentage, support <1-100>' ;
                        }

                      }

                      mandatory true ;
                    }

                  }

                  container priority-level {
                    description 'Configure PQ(Priority Queuing) priority level.' ;
                    presence "Configure PQ priority level" ;
                    leaf priority-value {
                      description 'Set the priority level of PQ.' ;
                      type uint16 {
                        range 1..8 {
                          description 'The priority level of PQ.' ;
                        }

                      }

                      mandatory true ;
                    }

                  }

                  container priority-llq {
                    description 'Configure LLQ(Low Latency Queuing) priority.' ;
                    presence "Configure LLQ priority" ;
                    leaf priority-llq {
                      description 'Specify LLQ.' ;
                      type empty ;

                      mandatory true ;
                    }

                  }

                  container police {
                    description 'Configure traffic policing.' ;
                    presence "Configure traffic policing" ;
                    leaf cir {
                      description 'Configure the CIR (Committed Information Rate) value, default: kilobits per second.' ;
                      type uint32 {
                        range 8..4294967295 {
                          description 'The CIR value (default: kilobits per second), support <8-4294967295>' ;
                        }

                      }

                      mandatory true ;
                    }

                    leaf cir-unit {
                      description 'Set CIR unit, such as kbps, mbps, gbps.' ;
                      type qos-rate-unit-type ;

                    }

                    leaf cbs {
                      description 'Configure the CBS(Committed Burst Size) size, default: KB.' ;
                      type uint32 {
                        range 1..4294967295 {
                          description 'The CBS(Committed Burst Size) size (default: KB), support <1-4294967295>' ;
                        }

                      }

                    }

                    leaf cbs-unit {
                      description 'Set CBS unit, such as kb, mb, gb.' ;
                      type qos-bucket-unit-type ;

                    }

                    container pir-pbs {
                      description 'Configure PIR and PBS.' ;
                      presence "Configure pir and pbs" ;
                      leaf pir {
                        description 'Configure the PIR(Peak Information Rate) value, default: kilobits per second.' ;
                        type uint32 {
                          range 8..4294967295 {
                            description 'The PIR(Peak Information Rate) value (default: kilobits per second), support <8-4294967295>' ;
                          }

                        }

                        mandatory true ;
                      }

                      leaf pir-unit {
                        description 'Set PIR unit, such as kbps, mbps, gbps.' ;
                        type qos-rate-unit-type ;

                      }

                      leaf pbs {
                        description 'Configure the PBS(Peak Burst Size) size, default: KB.' ;
                        type uint32 {
                          range 1..4294967295 {
                            description 'The PBS(Peak Burst Size) size (default: KB), support <1-4294967295>' ;
                          }

                        }

                      }

                      leaf pbs-unit {
                        description 'Set PBS unit, such as kb, mb, gb.' ;
                        type qos-bucket-unit-type ;

                      }

                    }

                  }

                  container random-detect {
                    description 'Configure WRED(Weighted Random Early Detection) information.' ;
                    container enable {
                      description 'Enable/disable WRED function.' ;
                      presence "Configure WRED enable" ;
                      leaf enable {
                        description 'Enable WRED.' ;
                        type empty ;

                        mandatory true ;
                      }

                    }

                    container colors {
                      description 'Configure WRED thresholds based on color.' ;
                      list color {
                        description 'Configure WRED thresholds based on color.' ;
                        key color-type ;
                        leaf color-type {
                          description 'Set WRED color, such as green, yellow, red.' ;
                          type qos-color-type ;

                        }

                        leaf min-threshold {
                          status obsolete {
                            ncd:revise-date 2019-08-05 ;
                          }

                          description 'Set the minimum threshold, support <1-100>.' ;
                          type uint32 {
                            range 1..100 {
                              description 'The minimum threshold in percent, support <1-100>' ;
                            }

                          }

                          mandatory true ;
                        }

                        leaf max-threshold {
                          status obsolete {
                            ncd:revise-date 2019-08-05 ;
                          }

                          description 'Set the maximum threshold, support <1-100>.' ;
                          type uint32 {
                            range 1..100 {
                              description 'The maximum threshold in percent, support <1-100>' ;
                            }

                          }

                          mandatory true ;
                        }

                        choice threshold {
                          description 'Set the threshold.' ;
                          case threshold-value {
                            description 'Set the threshold value.' ;
                            leaf min-threshold-value {
                              description 'Set the minimum threshold, support <1-1024000>.' ;
                              type uint32 {
                                range 1..1024000 {
                                  description 'The minimum threshold in kilobytes, support <1-1024000>' ;
                                }

                              }

                              units KB ;
                              mandatory true ;
                            }

                            leaf max-threshold-value {
                              description 'Set the maximum threshold, support <1-1024000>.' ;
                              type uint32 {
                                range 1..1024000 {
                                  description 'The maximum threshold in kilobytes, support <1-1024000>' ;
                                }

                              }

                              units KB ;
                              mandatory true ;
                            }

                            ncd:revise-date 2021-01-18 ;
                          }

                          case threshold-percentage {
                            description 'Set the threshold percentage.' ;
                            container threshold-percentage {
                              description 'Set the threshold percentage.' ;
                              leaf min-threshold-percentage {
                                description 'Set the minimum threshold percentage, support <1-100>.' ;
                                type uint32 {
                                  range 1..100 {
                                    description 'The minimum threshold percentage, support <1-100>' ;
                                  }

                                }

                                mandatory true ;
                              }

                              leaf max-threshold-percentage {
                                description 'Set the maximum threshold percentage, support <1-100>.' ;
                                type uint32 {
                                  range 1..100 {
                                    description 'The maximum threshold percentage, support <1-100>' ;
                                  }

                                }

                                mandatory true ;
                              }

                            }

                          }

                          ncd:revise-date 2019-08-05 ;
                        }

                        leaf probability {
                          description 'Set mark probability denominator, support <1-100>.' ;
                          type uint8 {
                            range 1..100 {
                              description 'Set mark probability denominator, support <1-100>' ;
                            }

                          }

                          mandatory true ;
                        }

                      }

                    }

                    container precedences {
                      description 'Configure WRED thresholds based on precedence.' ;
                      list precedence {
                        description 'Configure WRED thresholds based on precedence.' ;
                        key prec-value ;
                        leaf prec-value {
                          description 'Set the precedence value, such as MPLS EXP, VLAN 802.1p, IP DSCP, IP Precedence, support <0-7>.' ;
                          type uint16 {
                            range 0..7 {
                              description 'The IP-Precedence value, support <0-7>' ;
                            }

                          }

                        }

                        choice threshold {
                          description 'Set the threshold.' ;
                          case threshold-value {
                            description 'Set the threshold value.' ;
                            leaf min-threshold {
                              description 'Set the minimum threshold (default: kilobytes).' ;
                              type uint32 {
                                range 1..4294967295 {
                                  description 'The minimum threshold (default: kilobytes), support <1-4294967295>' ;
                                }

                              }

                              mandatory true ;
                            }

                            leaf min-threshold-unit {
                              description 'set min-threshold unit, such as kbytes, mbytes, gbytes.' ;
                              type qos-threshold-unit-type ;

                            }

                            leaf max-threshold {
                              description 'Set the maximum threshold (default: kilobytes).' ;
                              type uint32 {
                                range 1..4294967295 {
                                  description 'The maximum threshold (default: kilobytes), support <1-4294967295>.' ;
                                }

                              }

                              mandatory true ;
                            }

                            leaf max-threshold-unit {
                              description 'set max-threshold unit, such as kbytes, mbytes, gbytes.' ;
                              type qos-threshold-unit-type ;

                            }

                          }

                          case threshold-percentage {
                            description 'Set the threshold percentage.' ;
                            container threshold-percentage {
                              description 'Set the threshold percentage.' ;
                              leaf min-threshold-percentage {
                                description 'Set the minimum threshold percentage, support <1-100>.' ;
                                type uint32 {
                                  range 1..100 {
                                    description 'The minimum threshold percentage, support <1-100>' ;
                                  }

                                }

                                mandatory true ;
                              }

                              leaf max-threshold-percentage {
                                description 'Set the maximum threshold percentage, support <1-100>.' ;
                                type uint32 {
                                  range 1..100 {
                                    description 'The maximum threshold percentage, support <1-100>' ;
                                  }

                                }

                                mandatory true ;
                              }

                            }

                          }

                          case threshold-cachetime {
                            if-feature policy-action-wred-precedence-cachetime ;

                            description 'Set the threshold cachetime.' ;
                            container threshold-cachetime {
                              description 'Set the threshold cachetime.' ;
                              leaf min-threshold-cachetime {
                                description 'Set the minimum threshold cachetime (default: ms).' ;
                                type uint32 {
                                  range 1..1000 {
                                    description 'The minimum threshold cachetime, support <1-1000>' ;
                                  }

                                }

                                mandatory true ;
                              }

                              leaf max-threshold-cachetime {
                                description 'Set the maximum threshold cachetime (default: ms).' ;
                                type uint32 {
                                  range 1..1000 {
                                    description 'The maximum threshold cachetime, support <1-1000>' ;
                                  }

                                }

                                mandatory true ;
                              }

                            }

                            ncd:revise-date 2021-11-19 ;
                          }

                        }

                        leaf probability {
                          description 'Set mark probability denominator, support <1-100>.' ;
                          type uint32 {
                            range 1..100 {
                              description 'Set mark probability denominator, support <1-100>' ;
                            }

                          }

                          mandatory true ;
                        }

                      }

                      ncd:revise-date 2021-01-18 ;
                    }

                    container weight {
                      description 'Configure WRED exponential weight factor.' ;
                      presence "Configure WRED exponential weight factor" ;
                      leaf weight-value {
                        description 'Specify exponent used in weighted average calculation, support <1-16>.' ;
                        type uint16 {
                          range 1..16 {
                            description 'Exponent used in weighted average calculation' ;
                          }

                        }

                        mandatory true ;
                      }

                      ncd:revise-date 2021-01-18 ;
                    }

                    ncd:revise-date 2018-08-18 ;
                  }

                  container service-policy {
                    description 'Configure hierarchical service policy.' ;
                    presence "Configure hierarchical service policy" ;
                    leaf hpolicy-name {
                      description 'Name of the hierarchical policy, support 1-31 characters.' ;
                      type string {
                        length 1..31 {
                          description 'Name of the hierarchical policy, support 1-31 characters' ;
                        }

                      }

                      mandatory true ;
                    }

                    ncd:revise-date 2021-01-11 ;
                  }

                  container queue-limit {
                    if-feature phb-pmap-action-queue-limit ;

                    description 'Configure queue depth.' ;
                    presence "Configure queue depth" ;
                    choice queue-limit {
                      description 'Configure queue depth' ;
                      case queue-value {
                        description 'Set queue depth value(default:KB).' ;
                        container queue-value {
                          description 'Set queue depth value(default:KB).' ;
                          leaf queue-value {
                            description 'Set queue depth value(default:KB).' ;
                            type uint32 {
                              range 7..8000000 {
                                description 'Set queue depth value(default:KB)' ;
                              }

                            }

                            mandatory true ;
                          }

                        }

                      }

                      case queue-cache-time {
                        description 'Configure cache time of the queue.' ;
                        container queue-cache-time {
                          description 'Configure cache time of the queue.' ;
                          leaf queue-cache-time {
                            description 'Set cache time(default:us).' ;
                            type uint32 {
                              range 1..100000 {
                                description 'Set cache time(default:us)' ;
                              }

                            }

                            mandatory true ;
                          }

                        }

                      }

                    }

                    ncd:revise-date 2023-04-03 ;
                  }

                }

                container class-default {
                  description 'Select policy association default class.' ;
                  presence "Specify the default class" ;
                  leaf class-default {
                    description 'Specify the default class.' ;
                    type empty ;

                    mandatory true ;
                  }

                  container bandwidth {
                    description 'Configure minimum guaranteed bandwidth.' ;
                    presence "Configure minimum guaranteed bandwidth" ;
                    leaf percentage {
                      description 'Set the exact bandwidth percentage, support <1-100>.' ;
                      type uint16 {
                        range 1..100 {
                          description 'The exact bandwidth percentage, support <1-100>' ;
                        }

                      }

                      mandatory true ;
                    }

                  }

                  container priority-level {
                    description 'Configure PQ(Priority Queuing) priority level.' ;
                    presence "Configure PQ priority level" ;
                    leaf priority-value {
                      description 'Set the priority level of PQ.' ;
                      type uint16 {
                        range 1..8 {
                          description 'The priority level of PQ.' ;
                        }

                      }

                      mandatory true ;
                    }

                  }

                  container priority-llq {
                    description 'Configure LLQ(Low Latency Queuing) priority.' ;
                    presence "Configure LLQ priority" ;
                    leaf priority-llq {
                      description 'Specify LLQ.' ;
                      type empty ;

                      mandatory true ;
                    }

                  }

                  container police {
                    description 'Configure traffic policing.' ;
                    presence "Configure traffic policing" ;
                    leaf cir {
                      description 'Configure the CIR (Committed Information Rate) value, default: kilobits per second.' ;
                      type uint32 {
                        range 8..4294967295 {
                          description 'The CIR value (default: kilobits per second), support <8-4294967295>' ;
                        }

                      }

                      mandatory true ;
                    }

                    leaf cir-unit {
                      description 'Set CIR unit, such as kbps, mbps, gbps.' ;
                      type qos-rate-unit-type ;

                    }

                    leaf cbs {
                      description 'Configure the CBS(Committed Burst Size) size, default: KB.' ;
                      type uint32 {
                        range 1..4294967295 {
                          description 'The CBS(Committed Burst Size) size (default: KB), support <1-4294967295>' ;
                        }

                      }

                    }

                    leaf cbs-unit {
                      description 'Set CBS unit, such as kb, mb, gb.' ;
                      type qos-bucket-unit-type ;

                    }

                    container pir-pbs {
                      description 'Configure PIR and PBS.' ;
                      presence "Configure pir and pbs" ;
                      leaf pir {
                        description 'Configure the PIR(Peak Information Rate) value, default: kilobits per second.' ;
                        type uint32 {
                          range 8..4294967295 {
                            description 'The PIR(Peak Information Rate) value (default: kilobits per second), support <8-4294967295>' ;
                          }

                        }

                        mandatory true ;
                      }

                      leaf pir-unit {
                        description 'Set PIR unit, such as kbps, mbps, gbps.' ;
                        type qos-rate-unit-type ;

                      }

                      leaf pbs {
                        description 'Configure the PBS(Peak Burst Size) size, default: KB.' ;
                        type uint32 {
                          range 1..4294967295 {
                            description 'The PBS(Peak Burst Size) size (default: KB), support <1-4294967295>' ;
                          }

                        }

                      }

                      leaf pbs-unit {
                        description 'Set PBS unit, such as kb, mb, gb.' ;
                        type qos-bucket-unit-type ;

                      }

                    }

                  }

                  container random-detect {
                    description 'Configure WRED(Weighted Random Early Detection) information.' ;
                    container enable {
                      description 'Enable/disable WRED function.' ;
                      presence "Configure WRED enable" ;
                      leaf enable {
                        description 'Enable WRED.' ;
                        type empty ;

                        mandatory true ;
                      }

                    }

                    container colors {
                      description 'Configure WRED thresholds based on color.' ;
                      list color {
                        description 'Configure WRED thresholds based on color.' ;
                        key color-type ;
                        leaf color-type {
                          description 'Set WRED color, such as green, yellow, red.' ;
                          type qos-color-type ;

                        }

                        leaf min-threshold {
                          status obsolete {
                            ncd:revise-date 2019-08-05 ;
                          }

                          description 'Set the minimum threshold, support <1-100>.' ;
                          type uint32 {
                            range 1..100 {
                              description 'The minimum threshold in percent, support <1-100>' ;
                            }

                          }

                          mandatory true ;
                        }

                        leaf max-threshold {
                          status obsolete {
                            ncd:revise-date 2019-08-05 ;
                          }

                          description 'Set the maximum threshold, support <1-100>.' ;
                          type uint32 {
                            range 1..100 {
                              description 'The maximum threshold in percent, support <1-100>' ;
                            }

                          }

                          mandatory true ;
                        }

                        choice threshold {
                          description 'Set the threshold.' ;
                          case threshold-value {
                            description 'Set the threshold value.' ;
                            leaf min-threshold-value {
                              description 'Set the minimum threshold, support <1-1024000>.' ;
                              type uint32 {
                                range 1..1024000 {
                                  description 'The minimum threshold in kilobytes, support <1-1024000>' ;
                                }

                              }

                              units KB ;
                              mandatory true ;
                            }

                            leaf max-threshold-value {
                              description 'Set the maximum threshold, support <1-1024000>.' ;
                              type uint32 {
                                range 1..1024000 {
                                  description 'The maximum threshold in kilobytes, support <1-1024000>' ;
                                }

                              }

                              units KB ;
                              mandatory true ;
                            }

                            ncd:revise-date 2021-01-18 ;
                          }

                          case threshold-percentage {
                            description 'Set the threshold percentage.' ;
                            container threshold-percentage {
                              description 'Set the threshold percentage.' ;
                              leaf min-threshold-percentage {
                                description 'Set the minimum threshold percentage, support <1-100>.' ;
                                type uint32 {
                                  range 1..100 {
                                    description 'The minimum threshold percentage, support <1-100>' ;
                                  }

                                }

                                mandatory true ;
                              }

                              leaf max-threshold-percentage {
                                description 'Set the maximum threshold percentage, support <1-100>.' ;
                                type uint32 {
                                  range 1..100 {
                                    description 'The maximum threshold percentage, support <1-100>' ;
                                  }

                                }

                                mandatory true ;
                              }

                            }

                          }

                          ncd:revise-date 2019-08-05 ;
                        }

                        leaf probability {
                          description 'Set mark probability denominator, support <1-100>.' ;
                          type uint8 {
                            range 1..100 {
                              description 'Set mark probability denominator, support <1-100>' ;
                            }

                          }

                          mandatory true ;
                        }

                      }

                    }

                    container precedences {
                      description 'Configure WRED thresholds based on precedence.' ;
                      list precedence {
                        description 'Configure WRED thresholds based on precedence.' ;
                        key prec-value ;
                        leaf prec-value {
                          description 'Set the precedence value, such as MPLS EXP, VLAN 802.1p, IP DSCP, IP Precedence, support <0-7>.' ;
                          type uint16 {
                            range 0..7 {
                              description 'The IP-Precedence value, support <0-7>' ;
                            }

                          }

                        }

                        choice threshold {
                          description 'Set the threshold.' ;
                          case threshold-value {
                            description 'Set the threshold value.' ;
                            leaf min-threshold {
                              description 'Set the minimum threshold (default: kilobytes).' ;
                              type uint32 {
                                range 1..4294967295 {
                                  description 'The minimum threshold (default: kilobytes), support <1-4294967295>' ;
                                }

                              }

                              mandatory true ;
                            }

                            leaf min-threshold-unit {
                              description 'set min-threshold unit, such as kbytes, mbytes, gbytes.' ;
                              type qos-threshold-unit-type ;

                            }

                            leaf max-threshold {
                              description 'Set the maximum threshold (default: kilobytes).' ;
                              type uint32 {
                                range 1..4294967295 {
                                  description 'The maximum threshold (default: kilobytes), support <1-4294967295>.' ;
                                }

                              }

                              mandatory true ;
                            }

                            leaf max-threshold-unit {
                              description 'set max-threshold unit, such as kbytes, mbytes, gbytes.' ;
                              type qos-threshold-unit-type ;

                            }

                          }

                          case threshold-percentage {
                            description 'Set the threshold percentage.' ;
                            container threshold-percentage {
                              description 'Set the threshold percentage.' ;
                              leaf min-threshold-percentage {
                                description 'Set the minimum threshold percentage, support <1-100>.' ;
                                type uint32 {
                                  range 1..100 {
                                    description 'The minimum threshold percentage, support <1-100>' ;
                                  }

                                }

                                mandatory true ;
                              }

                              leaf max-threshold-percentage {
                                description 'Set the maximum threshold percentage, support <1-100>.' ;
                                type uint32 {
                                  range 1..100 {
                                    description 'The maximum threshold percentage, support <1-100>' ;
                                  }

                                }

                                mandatory true ;
                              }

                            }

                          }

                          case threshold-cachetime {
                            if-feature policy-action-wred-precedence-cachetime ;

                            description 'Set the threshold cachetime.' ;
                            container threshold-cachetime {
                              description 'Set the threshold cachetime.' ;
                              leaf min-threshold-cachetime {
                                description 'Set the minimum threshold cachetime (default: ms).' ;
                                type uint32 {
                                  range 1..1000 {
                                    description 'The minimum threshold cachetime, support <1-1000>' ;
                                  }

                                }

                                mandatory true ;
                              }

                              leaf max-threshold-cachetime {
                                description 'Set the maximum threshold cachetime (default: ms).' ;
                                type uint32 {
                                  range 1..1000 {
                                    description 'The maximum threshold cachetime, support <1-1000>' ;
                                  }

                                }

                                mandatory true ;
                              }

                            }

                            ncd:revise-date 2021-11-19 ;
                          }

                        }

                        leaf probability {
                          description 'Set mark probability denominator, support <1-100>.' ;
                          type uint32 {
                            range 1..100 {
                              description 'Set mark probability denominator, support <1-100>' ;
                            }

                          }

                          mandatory true ;
                        }

                      }

                      ncd:revise-date 2021-01-18 ;
                    }

                    container weight {
                      description 'Configure WRED exponential weight factor.' ;
                      presence "Configure WRED exponential weight factor" ;
                      leaf weight-value {
                        description 'Specify exponent used in weighted average calculation, support <1-16>.' ;
                        type uint16 {
                          range 1..16 {
                            description 'Exponent used in weighted average calculation' ;
                          }

                        }

                        mandatory true ;
                      }

                      ncd:revise-date 2021-01-18 ;
                    }

                    ncd:revise-date 2018-08-18 ;
                  }

                  container service-policy {
                    description 'Configure hierarchical service policy.' ;
                    presence "Configure hierarchical service policy" ;
                    leaf hpolicy-name {
                      description 'Name of the hierarchical policy, support 1-31 characters.' ;
                      type string {
                        length 1..31 {
                          description 'Name of the hierarchical policy, support 1-31 characters' ;
                        }

                      }

                      mandatory true ;
                    }

                    ncd:revise-date 2021-01-11 ;
                  }

                  container queue-limit {
                    if-feature phb-pmap-action-queue-limit ;

                    description 'Configure queue depth.' ;
                    presence "Configure queue depth" ;
                    choice queue-limit {
                      description 'Configure queue depth.' ;
                      case queue-value {
                        description 'Set queue depth value(default:KB).' ;
                        container queue-value {
                          description 'Set queue depth value(default:KB).' ;
                          leaf queue-value {
                            description 'Set queue depth value(default:KB).' ;
                            type uint32 {
                              range 7..8000000 {
                                description 'Set queue depth value(default:KB)' ;
                              }

                            }

                            mandatory true ;
                          }

                        }

                      }

                      case queue-cache-time {
                        description 'Configure cache time of the queue.' ;
                        container queue-cache-time {
                          description 'Configure cache time of the queue.' ;
                          leaf queue-cache-time {
                            description 'Set cache time(default:us).' ;
                            type uint32 {
                              range 1..100000 {
                                description 'Set cache time(default:us)' ;
                              }

                            }

                            mandatory true ;
                          }

                        }

                      }

                    }

                    ncd:revise-date 2023-04-03 ;
                  }

                }

              }

              container pmap-description {
                description 'Description of a policy map, support 1-79 characters.' ;
                presence "Specify description of policy map" ;
                leaf pmap-description {
                  description 'Description of a policy map, support 1-79 characters.' ;
                  type ncd:string-with-blank {
                    length 1..79 {
                      description 'Description of a policy map, support 1-79 characters.' ;
                    }

                  }

                  mandatory true ;
                }

                ncd:revise-date 2020-06-18 ;
              }

            }

          }

        }

        container sub-interface-based {
          if-feature sub-interface-mode ;

          description 'Policy map based on sub-interface.' ;
          container policy-maps {
            description 'Configure QoS policy map lists.' ;
            list policy-map {
              description 'Configure QoS policy maps.' ;
              key pmap-name ;
              leaf pmap-name {
                description 'Name of the policy map, support 1-31 characters.' ;
                type string {
                  length 1..31 {
                    description 'Name of the policy map, support 1-31 characters' ;
                  }

                }

              }

              container class-maps {
                description 'Configure QoS policy class.' ;
                list class-map {
                  description 'Configure QoS policy class.' ;
                  key cmap-name ;
                  leaf cmap-name {
                    description 'Name of the class map, support 1-31 characters.' ;
                    type string {
                      length 1..31 {
                        description 'Name of the class map, support 1-31 characters' ;
                      }

                    }

                  }

                  container bandwidth {
                    description 'Configure minimum guaranteed bandwidth.' ;
                    presence "Configure minimum guaranteed bandwidth" ;
                    leaf percentage {
                      description 'Set the exact bandwidth percentage, support <1-100>.' ;
                      type uint16 {
                        range 1..100 {
                          description 'The exact bandwidth percentage, support <1-100>' ;
                        }

                      }

                      mandatory true ;
                    }

                  }

                  container priority-level {
                    description 'Configure PQ(Priority Queuing) priority level.' ;
                    presence "Configure PQ priority level" ;
                    leaf priority-value {
                      description 'Set the priority level of PQ.' ;
                      type uint16 {
                        range 1..4 {
                          description 'The priority level of PQ, support <1-4>' ;
                        }

                      }

                      mandatory true ;
                    }

                  }

                  container priority-llq {
                    description 'Configure LLQ(Low Latency Queuing) priority.' ;
                    presence "Configure LLQ priority" ;
                    leaf priority-llq {
                      description 'Specify LLQ.' ;
                      type empty ;

                      mandatory true ;
                    }

                  }

                  container police {
                    description 'Configure traffic policing.' ;
                    presence "Configure traffic policing" ;
                    leaf cir {
                      description 'Configure the CIR (Committed Information Rate) value, default: kilobits per second.' ;
                      type uint32 {
                        range 8..4294967295 {
                          description 'The CIR value (default: kilobits per second), support <8-4294967295>' ;
                        }

                      }

                      mandatory true ;
                    }

                    leaf cir-unit {
                      description 'Set CIR unit, such as kbps, mbps, gbps.' ;
                      type qos-rate-unit-type ;

                    }

                    leaf cbs {
                      description 'Configure the CBS(Committed Burst Size) size, default: KB.' ;
                      type uint32 {
                        range 1..4294967295 {
                          description 'The CBS(Committed Burst Size) size (default: KB), support <1-4294967295>' ;
                        }

                      }

                    }

                    leaf cbs-unit {
                      description 'Set CBS unit, such as kb, mb, gb.' ;
                      type qos-bucket-unit-type ;

                    }

                    container pir-pbs {
                      description 'Configure PIR and PBS.' ;
                      presence "Configure pir and pbs" ;
                      leaf pir {
                        description 'Configure the PIR(Peak Information Rate) value, default: kilobits per second.' ;
                        type uint32 {
                          range 8..4294967295 {
                            description 'The PIR(Peak Information Rate) value (default: kilobits per second), support <8-4294967295>' ;
                          }

                        }

                        mandatory true ;
                      }

                      leaf pir-unit {
                        description 'Set PIR unit, such as kbps, mbps, gbps.' ;
                        type qos-rate-unit-type ;

                      }

                      leaf pbs {
                        description 'Configure the PBS(Peak Burst Size) size, default: KB.' ;
                        type uint32 {
                          range 1..4294967295 {
                            description 'The PBS(Peak Burst Size) size (default: KB), support <1-4294967295>' ;
                          }

                        }

                      }

                      leaf pbs-unit {
                        description 'Set PBS unit, such as kb, mb, gb.' ;
                        type qos-bucket-unit-type ;

                      }

                    }

                  }

                }

                container class-default {
                  description 'Select policy association default class.' ;
                  presence "Specify the default class" ;
                  leaf class-default {
                    description 'Specify the default class.' ;
                    type empty ;

                    mandatory true ;
                  }

                  container bandwidth {
                    description 'Configure minimum guaranteed bandwidth.' ;
                    presence "Configure minimum guaranteed bandwidth" ;
                    leaf percentage {
                      description 'Set the exact bandwidth percentage, support <1-100>.' ;
                      type uint16 {
                        range 1..100 {
                          description 'The exact bandwidth percentage, support <1-100>' ;
                        }

                      }

                      mandatory true ;
                    }

                  }

                  container priority-level {
                    description 'Configure PQ(Priority Queuing) priority level.' ;
                    presence "Configure PQ priority level" ;
                    leaf priority-value {
                      description 'Set the priority level of PQ.' ;
                      type uint16 {
                        range 1..4 {
                          description 'The priority level of PQ, support <1-4>' ;
                        }

                      }

                      mandatory true ;
                    }

                  }

                  container priority-llq {
                    description 'Configure LLQ(Low Latency Queuing) priority.' ;
                    presence "Configure LLQ priority" ;
                    leaf priority-llq {
                      description 'Specify LLQ.' ;
                      type empty ;

                      mandatory true ;
                    }

                  }

                  container police {
                    description 'Configure traffic policing.' ;
                    presence "Configure traffic policing" ;
                    leaf cir {
                      description 'Configure the CIR (Committed Information Rate) value, default: kilobits per second.' ;
                      type uint32 {
                        range 8..4294967295 {
                          description 'The CIR value (default: kilobits per second), support <8-4294967295>' ;
                        }

                      }

                      mandatory true ;
                    }

                    leaf cir-unit {
                      description 'Set PIR unit, such as kbps, mbps, gbps.' ;
                      type qos-rate-unit-type ;

                    }

                    leaf cbs {
                      description 'Configure the PBS(Peak Burst Size) size, default: KB.' ;
                      type uint32 {
                        range 1..4294967295 {
                          description 'The PBS(Peak Burst Size) size (default: KB), support <1-4294967295>' ;
                        }

                      }

                    }

                    leaf cbs-unit {
                      description 'Set PBS unit, such as kb, mb, gb.' ;
                      type qos-bucket-unit-type ;

                    }

                    container pir-pbs {
                      description 'Configure PIR and PBS.' ;
                      presence "Configure pir and pbs" ;
                      leaf pir {
                        description 'Configure the PIR(Peak Information Rate) value, default: kilobits per second.' ;
                        type uint32 {
                          range 8..4294967295 {
                            description 'The PIR(Peak Information Rate) value (default: kilobits per second), support <8-4294967295>' ;
                          }

                        }

                        mandatory true ;
                      }

                      leaf pir-unit {
                        description 'Set PIR unit, such as kbps, mbps, gbps.' ;
                        type qos-rate-unit-type ;

                      }

                      leaf pbs {
                        description 'Configure the PBS(Peak Burst Size) size, default: KB.' ;
                        type uint32 {
                          range 1..4294967295 {
                            description 'The PBS(Peak Burst Size) size (default: KB), support <1-4294967295>' ;
                          }

                        }

                      }

                      leaf pbs-unit {
                        description 'Set PBS unit, such as kb, mb, gb.' ;
                        type qos-bucket-unit-type ;

                      }

                    }

                  }

                }

              }

              container pmap-description {
                description 'Description of a policy map, support 1-79 characters.' ;
                presence "Specify description of policy map" ;
                leaf pmap-description {
                  description 'Description of a policy map, support 1-79 characters.' ;
                  type ncd:string-with-blank {
                    length 1..79 {
                      description 'Description of a policy map, support 1-79 characters.' ;
                    }

                  }

                  mandatory true ;
                }

                ncd:revise-date 2020-06-18 ;
              }

            }

          }

        }

        container switch-fabric-based {
          if-feature switch-fabric-mode ;

          description 'Policy map based on switch-fabric.' ;
          container policy-maps {
            description 'Configure QoS policy map lists.' ;
            list policy-map {
              description 'Configure QoS policy maps.' ;
              key pmap-name ;
              leaf pmap-name {
                description 'Name of the policy map, support 1-31 characters.' ;
                type string {
                  length 1..31 {
                    description 'Name of the policy map, support 1-31 characters' ;
                  }

                }

              }

              container class-maps {
                description 'Configure QoS policy class.' ;
                list class-map {
                  description 'Configure QoS policy class.' ;
                  key cmap-name ;
                  leaf cmap-name {
                    description 'Name of the class map, support 1-31 characters.' ;
                    type string {
                      length 1..31 ;

                    }

                  }

                  container bandwidth {
                    description 'Configure minimum guaranteed bandwidth.' ;
                    presence "Configure minimum guaranteed bandwidth" ;
                    leaf percentage {
                      description 'Set the exact bandwidth percentage, support <1-100>.' ;
                      type uint16 {
                        range 1..100 {
                          description 'The exact bandwidth percentage, support <1-100>' ;
                        }

                      }

                      mandatory true ;
                    }

                  }

                  container priority-level {
                    description 'Configure PQ(Priority Queuing) priority level.' ;
                    presence "Configure PQ priority level" ;
                    leaf priority-value {
                      description 'Set the priority level of PQ.' ;
                      type uint16 {
                        range 1..4 {
                          description 'The priority level of PQ, support <1-4>' ;
                        }

                      }

                      mandatory true ;
                    }

                  }

                  container police {
                    description 'Configure traffic policing.' ;
                    presence "Configure traffic policing" ;
                    leaf cir {
                      description 'Configure the CIR (Committed Information Rate) value, default: kilobits per second.' ;
                      type uint32 {
                        range 8..4294967295 {
                          description 'The CIR value (default: kilobits per second), support <8-4294967295>' ;
                        }

                      }

                      mandatory true ;
                    }

                    leaf cir-unit {
                      description 'Set CIR unit, such as kbps, mbps, gbps.' ;
                      type qos-rate-unit-type ;

                    }

                    leaf cbs {
                      description 'Configure the CBS(Committed Burst Size) size, default: KB.' ;
                      type uint32 {
                        range 1..4294967295 {
                          description 'The CBS(Committed Burst Size) size (default: KB), support <1-4294967295>' ;
                        }

                      }

                      mandatory true ;
                    }

                    leaf cbs-unit {
                      description 'Set CBS unit, such as kb, mb, gb.' ;
                      type qos-bucket-unit-type ;

                    }

                  }

                  container random-detect {
                    description 'Configure WRED(Weighted Random Early Detection) information.' ;
                    container enable {
                      description 'Enable/disable WRED function.' ;
                      presence "Configure WRED enable" ;
                      leaf enable {
                        description 'Enable WRED.' ;
                        type empty ;

                        mandatory true ;
                      }

                    }

                    container colors {
                      description 'Configure WRED thresholds based on color.' ;
                      list color {
                        description 'Configure WRED thresholds based on color.' ;
                        key color-type ;
                        leaf color-type {
                          description 'Set WRED color, such as green, yellow, red.' ;
                          type qos-color-type ;

                        }

                        leaf min-threshold {
                          description 'Set the minimum threshold, support <1-1024000>.' ;
                          type uint32 {
                            range 1..1024000 {
                              description 'The minimum threshold in kilobytes, support <1-1024000>' ;
                            }

                          }

                          units KB ;
                          mandatory true ;
                        }

                        leaf max-threshold {
                          description 'Set the maximum threshold, support <1-1024000>.' ;
                          type uint32 {
                            range 1..1024000 {
                              description 'The maximum threshold in kilobytes, support <1-1024000>' ;
                            }

                          }

                          units KB ;
                          mandatory true ;
                        }

                        leaf probability {
                          description 'Set mark probability denominator, support <1-100>.' ;
                          type uint8 {
                            range 1..100 {
                              description 'Set mark probability denominator, support <1-100>' ;
                            }

                          }

                          mandatory true ;
                        }

                      }

                    }

                    container precedences {
                      description 'Configure WRED thresholds based on precedence.' ;
                      list precedence {
                        description 'Configure WRED thresholds based on precedence.' ;
                        key prec-value ;
                        leaf prec-value {
                          description 'Set the precedence value, such as MPLS EXP, VLAN 802.1p, IP DSCP, IP Precedence, support <0-7>.' ;
                          type uint16 {
                            range 0..7 {
                              description 'The precedence value, support <0-7>' ;
                            }

                          }

                        }

                        choice threshold {
                          description 'Set the threshold.' ;
                          case threshold-value {
                            description 'Set the threshold value.' ;
                            leaf min-threshold {
                              description 'Set the minimum threshold (default: kilobytes).' ;
                              type uint32 {
                                range 1..4294967295 {
                                  description 'The minimum threshold (default: kilobytes), support <1-4294967295>' ;
                                }

                              }

                              mandatory true ;
                            }

                            leaf min-threshold-unit {
                              description 'Set min-threshold unit, such as kbytes, mbytes, gbytes.' ;
                              type qos-threshold-unit-type ;

                            }

                            leaf max-threshold {
                              description 'Set the maximum threshold (default: kilobytes).' ;
                              type uint32 {
                                range 1..4294967295 {
                                  description 'The maximum threshold (default: kilobytes), support <1-4294967295>' ;
                                }

                              }

                              mandatory true ;
                            }

                            leaf max-threshold-unit {
                              description 'Set max-threshold unit, such as kbytes, mbytes, gbytes.' ;
                              type qos-threshold-unit-type ;

                            }

                          }

                          case threshold-cachetime {
                            if-feature policy-action-wred-precedence-cachetime ;

                            description 'Set the threshold cachetime.' ;
                            container threshold-cachetime {
                              description 'Set the threshold cachetime.' ;
                              leaf min-threshold-cachetime {
                                description 'Set the minimum threshold cachetime (default: ms).' ;
                                type uint32 {
                                  range 1..1000 {
                                    description 'The minimum threshold cachetime, support <1-1000>' ;
                                  }

                                }

                                mandatory true ;
                              }

                              leaf max-threshold-cachetime {
                                description 'Set the maximum threshold cachetime (default: ms).' ;
                                type uint32 {
                                  range 1..1000 {
                                    description 'The maximum threshold cachetime, support <1-1000>' ;
                                  }

                                }

                                mandatory true ;
                              }

                            }

                            ncd:revise-date 2021-11-19 ;
                          }

                        }

                        leaf probability {
                          description 'Set mark probability denominator, support <1-100>.' ;
                          type uint32 {
                            range 1..100 {
                              description 'Set mark probability denominator, support <1-100>' ;
                            }

                          }

                          mandatory true ;
                        }

                      }

                    }

                    container weight {
                      description 'Configure WRED exponential weight factor.' ;
                      presence "Configure WRED exponential weight factor" ;
                      leaf weight-value {
                        description 'Specify exponent used in weighted average calculation, support <1-16>.' ;
                        type uint16 {
                          range 1..16 {
                            description 'Exponent used in weighted average calculation' ;
                          }

                        }

                        mandatory true ;
                      }

                    }

                  }

                  container service-policy {
                    description 'Configure hierarchical service policy.' ;
                    presence "Configure hierarchical service policy" ;
                    leaf hpolicy-name {
                      description 'Name of the hierarchical policy, support 1-31 characters.' ;
                      type string {
                        length 1..31 {
                          description 'Name of the hierarchical policy, support 1-31 characters' ;
                        }

                      }

                      mandatory true ;
                    }

                  }

                  container map {
                    description 'Set the packet level.' ;
                    presence "Set the packet level" ;
                    leaf map-priority {
                      description 'Map the packet priority.' ;
                      type enumeration {
                        enum high {
                          value 1 ;
                          description 'High priority' ;
                        }

                        enum middle {
                          value 2 ;
                          description 'Middle priority' ;
                        }

                        enum normal {
                          value 3 ;
                          description 'Normal priority' ;
                        }

                        enum low {
                          value 4 ;
                          description 'Low priority' ;
                        }

                      }

                      mandatory true ;
                    }

                  }

                }

                container class-default {
                  description 'Select policy association default class.' ;
                  presence "Specify the default class" ;
                  leaf class-default {
                    description 'Specify the default class.' ;
                    type empty ;

                    mandatory true ;
                  }

                  container bandwidth {
                    description 'Configure minimum guaranteed bandwidth.' ;
                    presence "Configure minimum guaranteed bandwidth" ;
                    leaf percentage {
                      description 'Set the exact bandwidth percentage, support <1-100>.' ;
                      type uint16 {
                        range 1..100 {
                          description 'The exact bandwidth percentage, support <1-100>' ;
                        }

                      }

                      mandatory true ;
                    }

                  }

                  container priority-level {
                    description 'Configure PQ(Priority Queuing) priority level.' ;
                    presence "Configure PQ priority level" ;
                    leaf priority-value {
                      description 'Set the priority level of PQ.' ;
                      type uint16 {
                        range 1..4 {
                          description 'The priority level of PQ, support <1-4>' ;
                        }

                      }

                      mandatory true ;
                    }

                  }

                  container police {
                    description 'Configure traffic policing.' ;
                    presence "Configure traffic policing" ;
                    leaf cir {
                      description 'Configure the CIR (Committed Information Rate) value, default: kilobits per second.' ;
                      type uint32 {
                        range 8..4294967295 {
                          description 'The CIR value (default: kilobits per second), support <8-4294967295>' ;
                        }

                      }

                      mandatory true ;
                    }

                    leaf cir-unit {
                      description 'Set CIR unit, such as kbps, mbps, gbps.' ;
                      type qos-rate-unit-type ;

                    }

                    leaf cbs {
                      description 'Configure the CBS(Committed Burst Size) size, default: KB.' ;
                      type uint32 {
                        range 1..4294967295 {
                          description 'The CBS(Committed Burst Size) size (default: KB), support <1-4294967295>' ;
                        }

                      }

                      mandatory true ;
                    }

                    leaf cbs-unit {
                      description 'Set CBS unit, such as kb, mb, gb.' ;
                      type qos-bucket-unit-type ;

                    }

                  }

                  container random-detect {
                    description 'Configure WRED(Weighted Random Early Detection) information.' ;
                    container enable {
                      description 'Enable/disable WRED function.' ;
                      presence "Configure WRED enable" ;
                      leaf enable {
                        description 'Enable WRED.' ;
                        type empty ;

                        mandatory true ;
                      }

                    }

                    container colors {
                      description 'Configure WRED thresholds based on color.' ;
                      list color {
                        description 'Configure WRED thresholds based on color.' ;
                        key color-type ;
                        leaf color-type {
                          description 'Set WRED color, such as green, yellow, red.' ;
                          type qos-color-type ;

                        }

                        leaf min-threshold {
                          description 'Set the minimum threshold, support <1-1024000>.' ;
                          type uint32 {
                            range 1..1024000 {
                              description 'The minimum threshold in kilobytes, support <1-1024000>' ;
                            }

                          }

                          units KB ;
                          mandatory true ;
                        }

                        leaf max-threshold {
                          description 'Set the maximum threshold, support <1-1024000>.' ;
                          type uint32 {
                            range 1..1024000 {
                              description 'The maximum threshold in kilobytes, support <1-1024000>' ;
                            }

                          }

                          units KB ;
                          mandatory true ;
                        }

                        leaf probability {
                          description 'Set mark probability denominator, support <1-100>.' ;
                          type uint8 {
                            range 1..100 ;

                          }

                          mandatory true ;
                        }

                      }

                    }

                    container precedences {
                      description 'Configure WRED thresholds based on precedence.' ;
                      list precedence {
                        description 'Configure WRED thresholds based on precedence.' ;
                        key prec-value ;
                        leaf prec-value {
                          description 'Set the precedence value, such as MPLS EXP, VLAN 802.1p, IP DSCP, IP Precedence, support <0-7>.' ;
                          type uint16 {
                            range 0..7 {
                              description 'The precedence value, support <0-7>' ;
                            }

                          }

                        }

                        choice threshold {
                          description 'Set the threshold.' ;
                          case threshold-value {
                            description 'Set the threshold value.' ;
                            leaf min-threshold {
                              description 'Set the minimum threshold (default: kilobytes).' ;
                              type uint32 {
                                range 1..4294967295 {
                                  description 'The minimum threshold (default: kilobytes), support <1-4294967295>' ;
                                }

                              }

                              mandatory true ;
                            }

                            leaf min-threshold-unit {
                              description 'Set min-threshold unit, such as kbytes, mbytes, gbytes.' ;
                              type qos-threshold-unit-type ;

                            }

                            leaf max-threshold {
                              description 'Set the maximum threshold (default: kilobytes).' ;
                              type uint32 {
                                range 1..4294967295 {
                                  description 'The maximum threshold (default: kilobytes), support <1-4294967295>' ;
                                }

                              }

                              mandatory true ;
                            }

                            leaf max-threshold-unit {
                              description 'Set max-threshold unit, such as kbytes, mbytes, gbytes.' ;
                              type qos-threshold-unit-type ;

                            }

                          }

                          case threshold-cachetime {
                            if-feature policy-action-wred-precedence-cachetime ;

                            description 'Set the threshold cachetime.' ;
                            container threshold-cachetime {
                              description 'Set the threshold cachetime.' ;
                              leaf min-threshold-cachetime {
                                description 'Set the minimum threshold cachetime (default: ms).' ;
                                type uint32 {
                                  range 1..1000 {
                                    description 'The minimum threshold cachetime, support <1-1000>' ;
                                  }

                                }

                                mandatory true ;
                              }

                              leaf max-threshold-cachetime {
                                description 'Set the maximum threshold cachetime (default: ms).' ;
                                type uint32 {
                                  range 1..1000 {
                                    description 'The maximum threshold cachetime, support <1-1000>' ;
                                  }

                                }

                                mandatory true ;
                              }

                            }

                            ncd:revise-date 2021-11-19 ;
                          }

                        }

                        leaf probability {
                          description 'Set mark probability denominator, support <1-100>.' ;
                          type uint32 {
                            range 1..100 {
                              description 'Set mark probability denominator, support <1-100>' ;
                            }

                          }

                          mandatory true ;
                        }

                      }

                    }

                    container weight {
                      description 'Configure WRED exponential weight factor.' ;
                      presence "Configure WRED exponential weight factor" ;
                      leaf weight-value {
                        description 'Specify exponent used in weighted average calculation, support <1-16>.' ;
                        type uint16 {
                          range 1..16 {
                            description 'Exponent used in weighted average calculation' ;
                          }

                        }

                        mandatory true ;
                      }

                    }

                  }

                  container service-policy {
                    description 'Configure hierarchical service policy.' ;
                    presence "Configure hierarchical service policy" ;
                    leaf hpolicy-name {
                      description 'Name of the hierarchical policy, support 1-31 characters.' ;
                      type string {
                        length 1..31 {
                          description 'Name of the hierarchical policy, support 1-31 characters' ;
                        }

                      }

                      mandatory true ;
                    }

                  }

                  container map {
                    description 'Set the packet level.' ;
                    presence "Set the packet level" ;
                    leaf map-priority {
                      description 'Map the packet priority.' ;
                      type enumeration {
                        enum high {
                          value 1 ;
                          description 'High priority' ;
                        }

                        enum middle {
                          value 2 ;
                          description 'Middle priority' ;
                        }

                        enum normal {
                          value 3 ;
                          description 'Normal priority' ;
                        }

                        enum low {
                          value 4 ;
                          description 'Low priority' ;
                        }

                      }

                      mandatory true ;
                    }

                  }

                }

              }

            }

          }

        }

        container flowspec-based {
          description 'Policy map based on flowspec.' ;
          container policy-maps {
            description 'Configure QoS policy map lists.' ;
            list policy-map {
              description 'Configure QoS policy maps.' ;
              key pmap-name ;
              leaf pmap-name {
                description 'Name of the policy map, support 1-31 characters.' ;
                type string {
                  length 1..31 {
                    description 'Name of the policy map, support 1-31 characters.' ;
                  }

                }

              }

              container class-maps {
                description 'Configure QoS policy class.' ;
                list class-map {
                  description 'Configure QoS policy class.' ;
                  key cmap-name ;
                  leaf cmap-name {
                    description 'Name of the class map, support 1-31 characters.' ;
                    type string {
                      length 1..31 {
                        description 'Name of the class map, support 1-31 characters.' ;
                      }

                    }

                  }

                  container drop {
                    description 'Configure drop.' ;
                    presence "Configure drop" ;
                    leaf drop {
                      description 'Specify drop.' ;
                      type empty ;

                      mandatory true ;
                    }

                  }

                  container police {
                    description 'Configure traffic policing.' ;
                    presence "Configure traffic policing" ;
                    leaf rate {
                      description 'Set the rate value(default:kilobits per second).' ;
                      type uint32 {
                        range 8..4294967295 {
                          description 'Set the rate value(default:kilobits per second).' ;
                        }

                      }

                      mandatory true ;
                    }

                    leaf rate-unit {
                      description 'Set rate unit, such as kbps, mbps, gbps.' ;
                      type qos-rate-unit-type ;

                    }

                  }

                  container redirect-nexthop {
                    description 'Redirect a packet.' ;
                    presence "Redirect a packet" ;
                    choice next-hop {
                      description 'Set next hop.' ;
                      mandatory true ;
                      case ip-address {
                        description 'Configurate IPv4 address as next-hop.' ;
                        container ip-address {
                          description 'Configurate IPv4 address as next-hop.' ;
                          leaf ipv4-address {
                            description 'IPv4 address.' ;
                            type ncd:ipv4-address ;

                            mandatory true ;
                          }

                          choice ipaddr-nexthop {
                            description 'Set next hop based on IPv4 Address.' ;
                            case global {
                              description 'Global route.' ;
                              leaf global {
                                description 'Global route.' ;
                                type empty ;

                              }

                            }

                            case route-target {
                              description 'Configurate route-target as next-hop.' ;
                              container route-target {
                                description 'Configurate route-target as next-hop.' ;
                                presence "Configurate route-target as next-hop" ;
                                leaf route-target {
                                  description 'Configurate route-target as next-hop.' ;
                                  type empty ;

                                  mandatory true ;
                                }

                                choice rt-pattern {
                                  description 'Route-target pattern, such as <0-65535>:<0-4294967295>, A.B.C.D:<0-65535>, <1-65535>.<0-65535>:<0-65535>.' ;
                                  mandatory true ;
                                  case asn-nn {
                                    description 'Route target, <0-65535>:<0-4294967295>.' ;
                                    leaf asn-nn {
                                      description 'Route target, <0-65535>:<0-4294967295>.' ;
                                      type ncd:asn-nn ;

                                      mandatory true ;
                                    }

                                  }

                                  case ipadd-nn {
                                    description 'Route target, A.B.C.D:<0-65535>.' ;
                                    leaf ipadd-nn {
                                      description 'Route target, A.B.C.D:<0-65535>.' ;
                                      type ncd:ipadd-nn ;

                                      mandatory true ;
                                    }

                                  }

                                  case asnd-nn {
                                    description 'Route target, <1-65535>.<0-65535>:<0-65535>.' ;
                                    leaf asnd-nn {
                                      description 'Route target, <1-65535>.<0-65535>:<0-65535>.' ;
                                      type ncd:asnd-nn ;

                                      mandatory true ;
                                    }

                                  }

                                }

                              }

                            }

                            case vrf {
                              description 'Configurate virtual route forwarding as next-hop.' ;
                              container vrf {
                                description 'Configurate virtual route forwarding as next-hop.' ;
                                presence "Configurate virtual route forwarding as next-hop" ;
                                leaf vrf-name {
                                  description 'Virtual route forwarding name, support 1-32 characters.' ;
                                  type string {
                                    length 1..32 {
                                      description 'Virtual route forwarding name, support 1-32 characters.' ;
                                    }

                                  }

                                  mandatory true ;
                                }

                              }

                            }

                          }

                          leaf copy {
                            description 'Copy flag.' ;
                            type empty ;

                            ncd:revise-date 2020-07-17 ;
                          }

                        }

                      }

                      case route-target {
                        description 'Configurate route-target as next-hop.' ;
                        container route-target {
                          description 'Configurate route-target as next-hop.' ;
                          leaf route-target {
                            description 'Configurate route-target as next-hop.' ;
                            type empty ;

                            mandatory true ;
                          }

                          choice rt-pattern {
                            description 'Route-target pattern, such as <0-65535>:<0-4294967295>, A.B.C.D:<0-65535>, <1-65535>.<0-65535>:<0-65535>.' ;
                            mandatory true ;
                            case asn-nn {
                              description 'Route target, <0-65535>:<0-4294967295>.' ;
                              leaf asn-nn {
                                description 'Route target, <0-65535>:<0-4294967295>.' ;
                                type ncd:asn-nn ;

                                mandatory true ;
                              }

                            }

                            case ipadd-nn {
                              description 'Route target, A.B.C.D:<0-65535>.' ;
                              leaf ipadd-nn {
                                description 'Route target, A.B.C.D:<0-65535>.' ;
                                type ncd:ipadd-nn ;

                                mandatory true ;
                              }

                            }

                            case asnd-nn {
                              description 'Route target, <1-65535>.<0-65535>:<0-65535>.' ;
                              leaf asnd-nn {
                                description 'Route target, <1-65535>.<0-65535>:<0-65535>.' ;
                                type ncd:asnd-nn ;

                                mandatory true ;
                              }

                            }

                          }

                        }

                      }

                      case vrf {
                        description 'Configurate virtual route forwarding as next-hop.' ;
                        container vrf {
                          description 'Configurate virtual route forwarding as next-hop.' ;
                          leaf vrf-name {
                            description 'Virtual route forwarding name, support 1-32 characters.' ;
                            type string {
                              length 1..32 {
                                description 'Virtual route forwarding name, support 1-32 characters.' ;
                              }

                            }

                            mandatory true ;
                          }

                        }

                      }

                      case ipv6-address {
                        description 'Configurate IPv6 address as next-hop.' ;
                        container ipv6-address {
                          description 'Configurate IPv6 address as next-hop.' ;
                          leaf ipv6-address {
                            description 'IPv6 address.' ;
                            type ncd:ipv6-address ;

                            mandatory true ;
                          }

                          choice ipaddr-nexthop {
                            description 'Set next hop based on IPv6 Address.' ;
                            case global {
                              description 'Global route.' ;
                              leaf global {
                                description 'Global route.' ;
                                type empty ;

                              }

                            }

                            case route-target {
                              description 'Configurate route-target as next-hop.' ;
                              container route-target {
                                description 'Configurate route-target as next-hop.' ;
                                presence "Configurate route-target as next-hop" ;
                                leaf route-target {
                                  description 'Configurate route-target as next-hop.' ;
                                  type empty ;

                                  mandatory true ;
                                }

                                choice rt-pattern {
                                  description 'Route-target pattern, such as <0-65535>:<0-4294967295>, A.B.C.D:<0-65535>, <1-65535>.<0-65535>:<0-65535>.' ;
                                  mandatory true ;
                                  case asn-nn {
                                    description 'Route target, <0-65535>:<0-4294967295>.' ;
                                    leaf asn-nn {
                                      description 'Route target, <0-65535>:<0-4294967295>.' ;
                                      type ncd:asn-nn ;

                                      mandatory true ;
                                    }

                                  }

                                  case ipadd-nn {
                                    description 'Route target, A.B.C.D:<0-65535>.' ;
                                    leaf ipadd-nn {
                                      description 'Route target, A.B.C.D:<0-65535>.' ;
                                      type ncd:ipadd-nn ;

                                      mandatory true ;
                                    }

                                  }

                                  case asnd-nn {
                                    description 'Route target, <1-65535>.<0-65535>:<0-65535>.' ;
                                    leaf asnd-nn {
                                      description 'Route target, <1-65535>.<0-65535>:<0-65535>.' ;
                                      type ncd:asnd-nn ;

                                      mandatory true ;
                                    }

                                  }

                                }

                              }

                            }

                            case vrf {
                              description 'Configurate virtual route forwarding as next-hop.' ;
                              container vrf {
                                description 'Configurate virtual route forwarding as next-hop.' ;
                                presence "Configurate virtual route forwarding as next-hop" ;
                                leaf vrf-name {
                                  description 'Virtual route forwarding name, support 1-32 characters.' ;
                                  type string {
                                    length 1..32 {
                                      description 'Virtual route forwarding name, support 1-32 characters.' ;
                                    }

                                  }

                                  mandatory true ;
                                }

                              }

                            }

                            case color-sid {
                              description 'Configurate color and prefix-sid as next-hop.' ;
                              container color-sid {
                                description 'Configurate color and prefix-sid as next-hop.' ;
                                presence "Configurate color and prefix-sid as next-hop" ;
                                leaf color {
                                  description 'Color value, support 1-4294967295.' ;
                                  type uint32 {
                                    range 1..4294967295 ;

                                  }

                                  mandatory true ;
                                }

                                leaf prefix-sid {
                                  description 'Prefix SID value, <X:X:X:X:X:X:X:X>.' ;
                                  type ncd:ipv6-address ;

                                  mandatory true ;
                                }

                              }

                              ncd:revise-date 2020-10-20 ;
                            }

                          }

                          leaf copy {
                            description 'Copy flag.' ;
                            type empty ;

                          }

                        }

                        ncd:revise-date 2020-07-17 ;
                      }

                      case srv6-be {
                        description 'Configurate srv6-be.' ;
                        container srv6-be {
                          if-feature policy-action-rediret-nexthop-srv6be ;

                          description 'Configurate srv6-be.' ;
                          leaf srv6-be {
                            description 'Configurate srv6-be.' ;
                            type ncd:ipv6-address ;

                            mandatory true ;
                          }

                          leaf end-point {
                            description 'Configurate end-point.' ;
                            type ncd:ipv6-address ;

                            mandatory true ;
                          }

                          leaf copy {
                            description 'Copy flag.' ;
                            type empty ;

                          }

                        }

                        ncd:revise-date 2022-09-26 ;
                      }

                    }

                  }

                  container sampler {
                    description 'Configure sampler.' ;
                    presence "Configure sampler" ;
                    leaf sampler {
                      description 'Specify sampler.' ;
                      type empty ;

                      mandatory true ;
                    }

                  }

                  container set {
                    description 'Mark a packet.' ;
                    presence "Mark a packet" ;
                    container dscp {
                      description 'Select DSCP as mark type.' ;
                      presence "Select DSCP as mark type" ;
                      leaf dscp-value {
                        description 'DSCP value, support <0-63>.' ;
                        type uint16 {
                          range 0..63 {
                            description 'DSCP value, support <0-63>' ;
                          }

                        }

                        mandatory true ;
                      }

                    }

                  }

                  container redirect-rsvp-te {
                    status obsolete {
                      ncd:revise-date 2020-12-02 ;
                    }

                    description 'Redirect RSVP-TE.' ;
                    presence "Redirect RSVP-TE" ;
                    leaf tunnel-id {
                      description 'Tunnel ID.' ;
                      type uint32 {
                        range 1..65535 ;

                      }

                      mandatory true ;
                    }

                    choice address {
                      description 'Tunnel address.' ;
                      mandatory true ;
                      case ipv4 {
                        description 'Choose IPv4 address.' ;
                        leaf ipv4-sender-address {
                          description 'IPv4 sender address.' ;
                          type ncd:ipv4-address ;

                          mandatory true ;
                        }

                        leaf ipv4-end-address {
                          description 'IPv4 end point address.' ;
                          type ncd:ipv4-address ;

                          mandatory true ;
                        }

                      }

                      case ipv6 {
                        description 'Choose IPv6 address.' ;
                        leaf ipv6-sender-address {
                          description 'IPv6 sender address.' ;
                          type ncd:ipv6-address ;

                          mandatory true ;
                        }

                        leaf ipv6-end-address {
                          description 'IPv6 end point address.' ;
                          type ncd:ipv6-address ;

                          mandatory true ;
                        }

                      }

                    }

                    leaf copy {
                      description 'Copy flag.' ;
                      type empty ;

                    }

                    ncd:revise-date 2020-02-03 ;
                  }

                  container redirect-sr-te {
                    status obsolete {
                      ncd:revise-date 2020-12-02 ;
                    }

                    description 'Redirect SR-TE.' ;
                    presence "Redirect SR-TE" ;
                    leaf tunnel-id {
                      description 'Tunnel ID.' ;
                      type uint32 {
                        range 1..65535 ;

                      }

                      mandatory true ;
                    }

                    choice address {
                      description 'Tunnel address.' ;
                      mandatory true ;
                      case ipv4 {
                        description 'Choose IPv4 address.' ;
                        leaf ipv4-sender-address {
                          description 'IPv4 sender address.' ;
                          type ncd:ipv4-address ;

                          mandatory true ;
                        }

                        leaf ipv4-end-address {
                          description 'IPv4 end point address.' ;
                          type ncd:ipv4-address ;

                          mandatory true ;
                        }

                      }

                      case ipv6 {
                        description 'Choose IPv6 address.' ;
                        leaf ipv6-sender-address {
                          description 'IPv6 sender address.' ;
                          type ncd:ipv6-address ;

                          mandatory true ;
                        }

                        leaf ipv6-end-address {
                          description 'IPv6 end point address.' ;
                          type ncd:ipv6-address ;

                          mandatory true ;
                        }

                      }

                    }

                    leaf copy {
                      description 'Copy flag.' ;
                      type empty ;

                    }

                    ncd:revise-date 2020-02-03 ;
                  }

                  container redirect-tunnel-id {
                    description 'Redirect tunnel ID.' ;
                    presence "Redirect tunnel ID" ;
                    leaf indirection-id {
                      description 'Indirection ID.' ;
                      type uint32 {
                        range 1..4294967295 ;

                      }

                      mandatory true ;
                    }

                    leaf copy {
                      description 'Copy flag.' ;
                      type empty ;

                    }

                    ncd:revise-date 2020-12-02 ;
                  }

                  container if-group {
                    if-feature flowspec-if-group ;

                    description 'Configure interface group.' ;
                    presence "Configure interface group" ;
                    list if-group {
                      description 'Configure interface group.' ;
                      key if-group-id ;
                      leaf if-group-id {
                        description 'Set interface group ID.' ;
                        type uint16 {
                          range 0..16383 {
                            description 'Set interface group ID.' ;
                          }

                        }

                      }

                    }

                    ncd:revise-date 2022-10-10 ;
                  }

                }

              }

              container pmap-description {
                description 'Description of a policy map, support 1-79 characters.' ;
                presence "Specify description of policy map" ;
                leaf pmap-description {
                  description 'Description of a policy map, support 1-79 characters.' ;
                  type ncd:string-with-blank {
                    length 1..79 {
                      description 'Description of a policy map, support 1-79 characters.' ;
                    }

                  }

                  mandatory true ;
                }

                ncd:revise-date 2020-06-18 ;
              }

            }

          }

          ncd:revise-date 2017-06-12 ;
        }

        container policy-map-id {
          description 'QoS policy map lists id, only for the query.' ;
          container policy-maps {
            description 'QoS policy map lists.' ;
            list policy-map {
              description 'QoS policy map list.' ;
              key pmap-name ;
              leaf pmap-name {
                description 'Name of the policy map, support 1-31 characters.' ;
                type string {
                  length 1..31 {
                    description 'Name of the policy map, support 1-31 characters' ;
                  }

                }

              }

              leaf pmap-id {
                description 'QoS policy map list id.' ;
                type uint32 {
                  range 1..5000 {
                    description 'H-QoS policy map list id' ;
                  }

                }

              }

            }

          }

          ncd:revise-date 2015-03-31 ;
        }

        container flow-behavior {
          description 'Policy map based on flow-behavior.' ;
          container policy-maps {
            description 'Configure QoS policy map lists.' ;
            list policy-map {
              description 'Configure QoS policy maps.' ;
              key pmap-name ;
              leaf pmap-name {
                description 'Name of the policy map, support 1-31 characters.' ;
                type string {
                  length 1..31 {
                    description 'Name of the policy map, support 1-31 characters.' ;
                  }

                }

              }

              container class-maps {
                description 'Configure QoS policy class.' ;
                list class-map {
                  description 'Configure QoS policy class.' ;
                  key cmap-name ;
                  leaf cmap-name {
                    description 'Name of the class map, support 1-31 characters.' ;
                    type string {
                      length 1..31 {
                        description 'Name of the class map, support 1-31 characters.' ;
                      }

                    }

                  }

                  container set {
                    description 'Mark a packet.' ;
                    presence "Mark a packet" ;
                    container default-action {
                      description 'Configure default action.' ;
                      presence "Configure default action" ;
                      leaf default-action {
                        description 'Set default action.' ;
                        type empty ;

                        mandatory true ;
                      }

                    }

                    container next-hop {
                      description 'Set next hop.' ;
                      presence "Set next hop" ;
                      choice next-hop {
                        description 'Set next hop.' ;
                        mandatory true ;
                        case ip-address {
                          description 'Configurate IP address as next-hop.' ;
                          container ip-address {
                            description 'Configurate IP address as next-hop.' ;
                            choice v4-v6-address {
                              description 'Configurate IP address as next-hop.' ;
                              mandatory true ;
                              case v4-addr {
                                description 'Configurate IPv4 address as next-hop.' ;
                                container ipv4-address {
                                  description 'Configurate IPv4 address as next-hop.' ;
                                  leaf ipv4-address {
                                    description 'IPv4 address.' ;
                                    type ncd:ipv4-address ;

                                    mandatory true ;
                                  }

                                  choice ipaddr-nexthop {
                                    description 'Set next hop based on IPv4 Address.' ;
                                    case vrf {
                                      description 'Configurate virtual route forwarding as next-hop.' ;
                                      container vrf {
                                        description 'Configurate virtual route forwarding as next-hop.' ;
                                        presence "Configurate virtual route forwarding as next-hop" ;
                                        leaf vrf-name {
                                          description 'Virtual route forwarding name, support 1-32 characters.' ;
                                          type string {
                                            length 1..32 {
                                              description 'Virtual route forwarding name, support 1-32 characters.' ;
                                            }

                                          }

                                          mandatory true ;
                                        }

                                      }

                                    }

                                    case interface {
                                      description 'Configurate interface as next-hop.' ;
                                      container interface {
                                        description 'Configurate interface as next-hop.' ;
                                        presence "Configurate interface as next-hop" ;
                                        leaf if-name {
                                          description 'Set interface name.' ;
                                          type ncd:ifname ;

                                          mandatory true ;
                                        }

                                      }

                                    }

                                  }

                                }

                              }

                              case v6-addr {
                                description 'Configurate IPv6 address as next-hop.' ;
                                container ipv6-address {
                                  description 'Configurate IPv6 address as next-hop.' ;
                                  leaf ipv6-address {
                                    description 'IPv6 address.' ;
                                    type ncd:ipv6-address ;

                                    mandatory true ;
                                  }

                                  choice ipaddr-nexthop {
                                    description 'Set next hop based on IPv4 Address.' ;
                                    case vrf {
                                      description 'Configurate virtual route forwarding as next-hop.' ;
                                      container vrf {
                                        description 'Configurate virtual route forwarding as next-hop.' ;
                                        presence "Configurate virtual route forwarding as next-hop" ;
                                        leaf vrf-name {
                                          description 'Virtual route forwarding name, support 1-32 characters.' ;
                                          type string {
                                            length 1..32 {
                                              description 'Virtual route forwarding name, support 1-32 characters.' ;
                                            }

                                          }

                                          mandatory true ;
                                        }

                                      }

                                    }

                                    case interface {
                                      description 'Configurate interface as next-hop.' ;
                                      container interface {
                                        description 'Configurate interface as next-hop.' ;
                                        presence "Configurate interface as next-hop" ;
                                        leaf if-name {
                                          description 'Set interface name.' ;
                                          type ncd:ifname ;

                                          mandatory true ;
                                        }

                                      }

                                    }

                                  }

                                }

                              }

                              ncd:revise-date 2019-06-27 ;
                            }

                          }

                        }

                        case interface {
                          description 'Configurate interface as next-hop.' ;
                          container interface {
                            description 'Configurate interface as next-hop.' ;
                            leaf if-name {
                              description 'Set interface name.' ;
                              type ncd:ifname ;

                              mandatory true ;
                            }

                          }

                        }

                      }

                    }

                    container vxlan {
                      description 'Set VXLAN.' ;
                      presence "Set VXLAN" ;
                      choice v4-v6 {
                        description 'Select IPv4 or IPv6.' ;
                        mandatory true ;
                        case ipv4 {
                          description 'Specify IPv4.' ;
                          container ipv4 {
                            description 'Specify IPv4.' ;
                            leaf src-addr {
                              description 'Source address of VXLAN tunnel.' ;
                              type ncd:ipv4-address ;

                              mandatory true ;
                            }

                            leaf dst-addr {
                              description 'Destination address of VXLAN tunnel.' ;
                              type ncd:ipv4-address ;

                              mandatory true ;
                            }

                            leaf vni-id {
                              description 'VNI ID.' ;
                              type uint32 {
                                range 1..16777215 {
                                  description 'VNI ID' ;
                                }

                              }

                              mandatory true ;
                            }

                          }

                        }

                        case ipv6 {
                          description 'Specify IPv6.' ;
                          container ipv6 {
                            description 'Specify IPv6.' ;
                            leaf src-addr {
                              description 'Source address of VXLAN tunnel.' ;
                              type ncd:ipv6-address ;

                              mandatory true ;
                            }

                            leaf dst-addr {
                              description 'Destination address of VXLAN tunnel.' ;
                              type ncd:ipv6-address ;

                              mandatory true ;
                            }

                            leaf vni-id {
                              description 'VNI ID.' ;
                              type uint32 {
                                range 1..16777215 {
                                  description 'VNI ID' ;
                                }

                              }

                              mandatory true ;
                            }

                          }

                        }

                        ncd:revise-date 2020-03-05 ;
                      }

                    }

                  }

                }

              }

              container pmap-description {
                description 'Description of a policy map, support 1-79 characters.' ;
                presence "Specify description of policy map" ;
                leaf pmap-description {
                  description 'Description of a policy map, support 1-79 characters.' ;
                  type ncd:string-with-blank {
                    length 1..79 {
                      description 'Description of a policy map, support 1-79 characters.' ;
                    }

                  }

                  mandatory true ;
                }

                ncd:revise-date 2020-06-18 ;
              }

            }

          }

          ncd:revise-date 2019-04-15 ;
        }

        container traffic-based {
          description 'Policy map based on traffic.' ;
          container policy-maps {
            description 'Configure QoS policy map lists.' ;
            list policy-map {
              description 'Configure QoS policy maps.' ;
              key pmap-name ;
              leaf pmap-name {
                description 'Name of the policy map, support 1-31 characters.' ;
                type string {
                  length 1..31 {
                    description 'Name of the policy map, support 1-31 characters' ;
                  }

                }

              }

              container share-mode {
                description 'Set policy-map on shared or unshared mode.' ;
                presence "Set policy-map on shared or unshared mode." ;
                leaf share-mode {
                  description 'Set policy-map on shared or unshared mode.' ;
                  type enumeration {
                    enum shared {
                      value 1 ;
                      description 'Set policy-map on shared mode' ;
                    }

                    enum unshared {
                      value 2 ;
                      description 'Set policy-map on unshared mode' ;
                    }

                  }

                  mandatory true ;
                }

                ncd:revise-date 2021-11-22 ;
              }

              container class-maps {
                description 'Configure QoS policy class.' ;
                list class-map {
                  description 'Configure QoS policy class.' ;
                  key cmap-name ;
                  leaf cmap-name {
                    description 'Name of the class map, support 1-31 characters.' ;
                    type string {
                      length 1..31 {
                        description 'Name of the class map, support 1-31 characters' ;
                      }

                    }

                  }

                  container police {
                    description 'Configure traffic policing.' ;
                    presence "Configure traffic policing" ;
                    container mode {
                      description 'Set color mode.' ;
                      presence "Configure mode information" ;
                      leaf mode-type {
                        description 'Color mode type.' ;
                        type enumeration {
                          enum blind {
                            value 1 ;
                            description 'Color-Blind mode' ;
                          }

                          enum aware {
                            value 2 ;
                            description 'Color-Aware mode' ;
                          }

                        }

                        mandatory true ;
                      }

                    }

                    choice buket-value-percent {
                      description 'Configure CIR CBS PIR and PBS.' ;
                      mandatory true ;
                      case buket-value {
                        description 'Configure CIR CBS PIR and PBS in numerical form.' ;
                        container c-buket {
                          description 'Configure C-buket related parameters.' ;
                          container cir-value {
                            description 'Configure the CIR.' ;
                            leaf cir {
                              description 'Configure the CIR (Committed Information Rate) value, default: kilobits per second.' ;
                              type uint32 {
                                range 8..4294967295 {
                                  description 'The CIR value (default: kilobits per second),support <8-4294967295>' ;
                                }

                              }

                              mandatory true ;
                            }

                            leaf cir-unit {
                              description 'Set CIR unit, such as kbps, mbps, gbps, pps.' ;
                              type qos-rate-unit-type-ex ;

                            }

                          }

                          container cbs-value {
                            description 'Configure the CBS.' ;
                            presence cbs ;
                            leaf cbs {
                              description 'Configure the CBS(Committed Burst Size) size, default: KB.' ;
                              type uint32 {
                                range 1..4294967295 {
                                  description 'The CBS(Committed Burst Size) size in bytes, support <1-4294967295>' ;
                                }

                              }

                              mandatory true ;
                            }

                            leaf cbs-unit {
                              description 'Set CBS unit, such as kb, mb, gb.' ;
                              type qos-bucket-unit-type ;

                            }

                          }

                        }

                        container p-buket {
                          description 'Configure P-buket related parameters.' ;
                          presence p-buket ;
                          container pir-value {
                            description 'Configure the PIR.' ;
                            leaf pir {
                              description 'Configure the PIR(Peak Information Rate) value, default: kilobits per second.' ;
                              type uint32 {
                                range 8..4294967295 {
                                  description 'The PIR(Peak Information Rate) value (default: kilobits per second), support <8-4294967295>' ;
                                }

                              }

                              mandatory true ;
                            }

                            leaf pir-unit {
                              description 'Set PIR unit, such as kbps, mbps, gbps, pps.' ;
                              type qos-rate-unit-type-ex ;

                            }

                          }

                          container pbs-value {
                            description 'Configure the PBS.' ;
                            presence pbs ;
                            leaf pbs {
                              description 'Configure the PBS(Peak Burst Size) size, default: KB.' ;
                              type uint32 {
                                range 1..4294967295 {
                                  description 'The PBS(Peak Burst Size) size in bytes, support <1-4294967295>' ;
                                }

                              }

                              mandatory true ;
                            }

                            leaf pbs-unit {
                              description 'Set PBS unit, such as kb, mb, gb.' ;
                              type qos-bucket-unit-type ;

                            }

                          }

                        }

                      }

                      case buket-percent {
                        description 'Configure CIR and PIR with percentage form.' ;
                        container cir {
                          description 'Configure CIR with percentage form.' ;
                          leaf cir-percent {
                            description 'Configure CIR with percentage form.' ;
                            type uint8 {
                              range 1..100 {
                                description 'Configure CIR with percentage form' ;
                              }

                            }

                            mandatory true ;
                          }

                        }

                        container pir {
                          description 'Configure PIR with percentage form.' ;
                          presence pir ;
                          leaf pir-percent {
                            description 'Configure PIR with percentage form.' ;
                            type uint8 {
                              range 1..100 {
                                description 'Configure PIR with percentage form' ;
                              }

                            }

                            mandatory true ;
                          }

                        }

                      }

                    }

                    container action {
                      description 'Set monitoring action  for each measurement evaluation packet.' ;
                      container conform-action {
                        description 'Action to packets that conform to the rate limit.' ;
                        choice conform-action {
                          description 'Specify action to packets that conform to the rate limit.' ;
                          mandatory true ;
                          case ca-drop {
                            description 'Drop packet in conform-action.' ;
                            leaf drop {
                              description 'Specify action to drop packet.' ;
                              type empty ;

                              mandatory true ;
                            }

                          }

                          case ca-transmit {
                            description 'Transmit packet in conform-action.' ;
                            leaf transmit {
                              description 'Specify action to transmit packet.' ;
                              type empty ;

                              mandatory true ;
                            }

                          }

                          case ca-mpls-exp {
                            description 'Rewrite packet MPLS-EXP and transmit the packet.' ;
                            leaf set-exp-transmit {
                              description 'Specify action to rewrite packet MPLS-EXP and transmit it.' ;
                              type empty ;

                              mandatory true ;
                            }

                            leaf mpls-exp-value {
                              description 'Reset MPLS-EXP value in conform-action, support <0-7>.' ;
                              type uint8 {
                                range 0..7 {
                                  description 'The MPLS-EXP value, support <0-7>' ;
                                }

                              }

                              mandatory true ;
                            }

                          }

                          case ca-precedence {
                            description 'Rewrite packet precedence and transmit the packet.' ;
                            leaf set-prec-transmit {
                              description 'Specify action to rewrite packet precedence and transmit it.' ;
                              type empty ;

                              mandatory true ;
                            }

                            leaf prec-value {
                              description 'Reset the IP-Precedence value in conform-action, support <0-7>.' ;
                              type uint8 {
                                range 0..7 {
                                  description 'The IP-Precedence value, support <0-7>' ;
                                }

                              }

                              mandatory true ;
                            }

                          }

                          case ca-dscp {
                            description 'Rewrite packet DSCP and transmit the packet.' ;
                            leaf set-dscp-transmit {
                              description 'Specify action to rewrite packet DSCP and transmit it.' ;
                              type empty ;

                              mandatory true ;
                            }

                            leaf dscp-value {
                              description 'Reset DSCP in conform-action, support <0-63>.' ;
                              type uint8 {
                                range 0..63 {
                                  description 'The DSCP value, support <0-63>' ;
                                }

                              }

                              mandatory true ;
                            }

                          }

                          case ca-8021p {
                            description 'Rewrite packet 802.1p and transmit the packet.' ;
                            leaf set-8021p-transmit {
                              description 'Specify action to rewrite packet 802.1p and transmit it.' ;
                              type empty ;

                              mandatory true ;
                            }

                            leaf value-8021p {
                              description 'Reset 802.1p in conform-action, support <0-7>.' ;
                              type uint8 {
                                range 0..7 {
                                  description 'The 802.1p value, support <0-7>' ;
                                }

                              }

                              mandatory true ;
                            }

                          }

                          case ca-service-class {
                            description 'Rewrite packet service-class and transmit it.' ;
                            leaf service-class-value {
                              description 'Reset service class in conform-action.' ;
                              type qos-service-class ;

                              mandatory true ;
                            }

                          }

                        }

                      }

                      container exceed-action {
                        description 'Action to packets that exceed the rate limit.' ;
                        choice exceed-action {
                          description 'Specify action to packets that exceed the rate limit.' ;
                          mandatory true ;
                          case ea-drop {
                            description 'Drop packet in exceed-action.' ;
                            leaf drop {
                              description 'Specify action to drop packet.' ;
                              type empty ;

                              mandatory true ;
                            }

                          }

                          case ea-transmit {
                            description 'Transmit packet in exceed-action.' ;
                            leaf transmit {
                              description 'Specify action to transmit packet.' ;
                              type empty ;

                              mandatory true ;
                            }

                          }

                          case ea-mpls-exp {
                            description 'Rewrite packet MPLS-EXP and transmit the packet.' ;
                            leaf set-exp-transmit {
                              description 'Specify action to rewrite packet MPLS-EXP and transmit it.' ;
                              type empty ;

                              mandatory true ;
                            }

                            leaf mpls-exp-value {
                              description 'Reset MPLS-EXP value in exceed-action, support <0-7>.' ;
                              type uint8 {
                                range 0..7 {
                                  description 'The MPLS-EXP value, support <0-7>' ;
                                }

                              }

                              mandatory true ;
                            }

                          }

                          case ea-precedence {
                            description 'Rewrite packet precedence and transmit the packet.' ;
                            leaf set-prec-transmit {
                              description 'Specify action to rewrite packet precedence and transmit it.' ;
                              type empty ;

                              mandatory true ;
                            }

                            leaf prec-value {
                              description 'Reset the IP-Precedence value in exceed-action, support <0-7>.' ;
                              type uint8 {
                                range 0..7 {
                                  description 'The IP-Precedence value, support <0-7>' ;
                                }

                              }

                              mandatory true ;
                            }

                          }

                          case ea-dscp {
                            description 'Rewrite packet DSCP and transmit the packet.' ;
                            leaf set-dscp-transmit {
                              description 'Specify action to rewrite packet DSCP and transmit it.' ;
                              type empty ;

                              mandatory true ;
                            }

                            leaf dscp-value {
                              description 'Reset DSCP in exceed-action, support <0-63>.' ;
                              type uint8 {
                                range 0..63 {
                                  description 'The DSCP value, support <0-63>' ;
                                }

                              }

                              mandatory true ;
                            }

                          }

                          case ea-8021p {
                            description 'Rewrite packet 802.1p and transmit the packet.' ;
                            leaf set-8021p-transmit {
                              description 'Specify action to rewrite packet 802.1p and transmit it.' ;
                              type empty ;

                              mandatory true ;
                            }

                            leaf value-8021p {
                              description 'Reset 802.1p in exceed-action, support <0-7>.' ;
                              type uint8 {
                                range 0..7 {
                                  description 'The 802.1p value, support <0-7>' ;
                                }

                              }

                              mandatory true ;
                            }

                          }

                          case ea-service-class {
                            description 'Rewrite packet service-class and transmit it.' ;
                            leaf service-class-value {
                              description 'Reset service class in exceed-action.' ;
                              type qos-service-class ;

                              mandatory true ;
                            }

                          }

                        }

                      }

                      container violate-action {
                        description 'Action to packets that violate the rate limit.' ;
                        choice violate-action {
                          description 'Specify action to packets that violate the rate limit.' ;
                          mandatory true ;
                          case va-drop {
                            description 'Drop packet in violate-action.' ;
                            leaf drop {
                              description 'Specify action to drop packet.' ;
                              type empty ;

                              mandatory true ;
                            }

                          }

                          case va-transmit {
                            description 'Transmit packet in violate-action.' ;
                            leaf transmit {
                              description 'Specify action to transmit packet.' ;
                              type empty ;

                              mandatory true ;
                            }

                          }

                          case va-mpls-exp {
                            description 'Rewrite packet MPLS-EXP and transmit the packet.' ;
                            leaf set-exp-transmit {
                              description 'Specify action to rewrite packet MPLS-EXP and transmit it.' ;
                              type empty ;

                              mandatory true ;
                            }

                            leaf mpls-exp-value {
                              description 'Reset MPLS-EXP value in violate-action, support <0-7>.' ;
                              type uint8 {
                                range 0..7 {
                                  description 'The MPLS-EXP value, support <0-7>' ;
                                }

                              }

                              mandatory true ;
                            }

                          }

                          case va-precedence {
                            description 'Rewrite packet precedence and transmit the packet.' ;
                            leaf set-prec-transmit {
                              description 'Specify action to rewrite packet precedence and transmit it.' ;
                              type empty ;

                              mandatory true ;
                            }

                            leaf prec-value {
                              description 'Reset the IP-Precedence value in violate-action, support <0-7>.' ;
                              type uint8 {
                                range 0..7 {
                                  description 'The IP-Precedence value, support <0-7>' ;
                                }

                              }

                              mandatory true ;
                            }

                          }

                          case va-dscp {
                            description 'Rewrite packet DSCP and transmit the packet.' ;
                            leaf set-dscp-transmit {
                              description 'Specify action to rewrite packet DSCP and transmit it.' ;
                              type empty ;

                              mandatory true ;
                            }

                            leaf dscp-value {
                              description 'Reset DSCP in violate-action, support <0-63>.' ;
                              type uint8 {
                                range 0..63 {
                                  description 'The DSCP value, support <0-63>' ;
                                }

                              }

                              mandatory true ;
                            }

                          }

                          case va-8021p {
                            description 'Rewrite packet 802.1p and transmit the packet.' ;
                            leaf set-8021p-transmit {
                              description 'Specify action to rewrite packet 802.1p and transmit it.' ;
                              type empty ;

                              mandatory true ;
                            }

                            leaf value-8021p {
                              description 'Reset 802.1p in violate-action, support <0-7>.' ;
                              type uint8 {
                                range 0..7 {
                                  description 'The 802.1p value, support <0-7>' ;
                                }

                              }

                              mandatory true ;
                            }

                          }

                          case va-service-class {
                            description 'Rewrite packet service-class and transmit it.' ;
                            leaf service-class-value {
                              description 'Reset service class in violate-action.' ;
                              type qos-service-class ;

                              mandatory true ;
                            }

                          }

                        }

                      }

                    }

                  }

                  container mirror {
                    description 'Configure mirror.' ;
                    presence "Configure mirror" ;
                    leaf session-id {
                      description 'Set the session id.' ;
                      type uint32 {
                        range 1..4294967295 {
                          description 'Set the session id.' ;
                        }

                      }

                      mandatory true ;
                    }

                  }

                  container set {
                    description 'Mark a packet.' ;
                    container service-class {
                      description 'Configure service class.' ;
                      presence "Configure service function path" ;
                      leaf service-class {
                        description 'Select service class of PHB info.' ;
                        type qos-service-class ;

                        mandatory true ;
                      }

                      leaf color-type {
                        description 'Specify packets color, support <green,yellow,red>.' ;
                        type qos-color-type ;

                      }

                    }

                    container dscp {
                      description 'Select DSCP as mark type.' ;
                      presence "Select DSCP as mark typ" ;
                      choice method {
                        description 'Specify the method to set DSCP.' ;
                        mandatory true ;
                        case set-value {
                          description 'Set the DSCP value directly.' ;
                          container set-value {
                            description 'Set the DSCP value directly.' ;
                            leaf dscp-value {
                              description 'DSCP value, support <0-63>.' ;
                              type uint16 {
                                range 0..63 {
                                  description 'DSCP value, support <0-63>' ;
                                }

                              }

                              mandatory true ;
                            }

                          }

                        }

                        case inherit {
                          status obsolete {
                            ncd:revise-date 2021-06-04 ;
                          }

                          description 'Set the DSCP value by inheriting.' ;
                          container inherit {
                            description 'Set the DSCP value by inheriting.' ;
                            leaf inherit-type {
                              description 'Specify the source inherit type, such as precedence, mpls-exp, 8021p, dscp, pay-load 8021p.' ;
                              type enumeration {
                                enum precedence {
                                  value 1 ;
                                  description 'Select precedence as source inherit' ;
                                }

                                enum mpls-exp {
                                  value 2 ;
                                  description 'Select MPLS-EXP as source inherit' ;
                                }

                                enum 8021p {
                                  value 3 ;
                                  description 'Select 802.1p as source inherit' ;
                                }

                                enum dscp {
                                  value 4 ;
                                  description 'Select dscp as source inherit' ;
                                }

                                enum pay-load-8021p {
                                  value 6 ;
                                  description 'Select inner 802.1p as source inherit' ;
                                }

                              }

                              mandatory true ;
                            }

                          }

                        }

                      }

                      ncd:revise-date 2021-01-25 ;
                    }

                    container precedence {
                      description 'Select precedence as mark type.' ;
                      presence "Select precedence as mark type" ;
                      choice method {
                        description 'Specify the method to set IP Precedence.' ;
                        mandatory true ;
                        case set-value {
                          description 'Set the IP Precedence value directly.' ;
                          container set-value {
                            description 'Set the IP Precedence value directly.' ;
                            leaf prec-value {
                              description 'IP Precedence value, support <0-7>.' ;
                              type uint16 {
                                range 0..7 {
                                  description 'IP Precedence value, support <0-7>' ;
                                }

                              }

                              mandatory true ;
                            }

                          }

                        }

                        case inherit {
                          status obsolete {
                            ncd:revise-date 2021-06-04 ;
                          }

                          description 'Set the IP Precedence value by inheriting.' ;
                          container inherit {
                            description 'Set the IP Precedence value by inheriting.' ;
                            leaf inherit-type {
                              description 'Specify the source inherit type, such as precedence, mpls-exp, 8021p, dscp.' ;
                              type enumeration {
                                enum precedence {
                                  value 1 ;
                                  description 'Select precedence as source inherit' ;
                                }

                                enum mpls-exp {
                                  value 2 ;
                                  description 'Select MPLS-EXP as source inherit' ;
                                }

                                enum 8021p {
                                  value 3 ;
                                  description 'Select 802.1p as source inherit' ;
                                }

                                enum dscp {
                                  value 4 ;
                                  description 'Select dscp as source inherit' ;
                                }

                              }

                              mandatory true ;
                            }

                          }

                        }

                      }

                      ncd:revise-date 2021-01-25 ;
                    }

                    container pri-8021p {
                      description 'Select 802.1p as mark type.' ;
                      presence "Select 802.1p as mark type" ;
                      choice method {
                        description 'Specify the method to set 802.1p.' ;
                        mandatory true ;
                        case set-value {
                          description 'Set the 802.1p value directly.' ;
                          container set-value {
                            description 'Set the 802.1p value directly.' ;
                            leaf value-8021p {
                              description '802.1p value, support <0-7>.' ;
                              type uint16 {
                                range 0..7 {
                                  description '802.1p value, support <0-7>' ;
                                }

                              }

                              mandatory true ;
                            }

                            leaf inner-outer {
                              description 'Set 8021p inner or outer flag.If vlaue is 0, it means outer flag. If value is 1,it means inner and outer flag.' ;
                              type uint8 {
                                range 0..1 {
                                  description 'Inner or outer flag. 0 is outer. 1 is inner and outer' ;
                                }

                              }

                              default 0 ;
                            }

                          }

                        }

                        case inherit {
                          status obsolete {
                            ncd:revise-date 2021-06-04 ;
                          }

                          description 'Set the 802.1p value by inheriting.' ;
                          container inherit {
                            description 'Set the 802.1p value by inheriting.' ;
                            leaf inherit-type {
                              description 'Specify the source inherit type, such as precedence, mpls-exp, 8021p, dscp.' ;
                              type enumeration {
                                enum precedence {
                                  value 1 ;
                                  description 'Select precedence as source inherit' ;
                                }

                                enum mpls-exp {
                                  value 2 ;
                                  description 'Select MPLS-EXP as source inherit' ;
                                }

                                enum 8021p {
                                  value 3 ;
                                  description 'Select 802.1p as source inherit' ;
                                }

                                enum dscp {
                                  value 4 ;
                                  description 'Select dscp as source inherit' ;
                                }

                              }

                              mandatory true ;
                            }

                            leaf inner-outer {
                              description 'Set 8021p inner or outer flag.If vlaue is 0, it means outer flag. If value is 1,it means inner and outer flag.' ;
                              type uint8 {
                                range 0..1 {
                                  description 'Inner or outer flag. 0 is outer. 1 is inner and outer' ;
                                }

                              }

                              default 0 ;
                            }

                          }

                        }

                      }

                      ncd:revise-date 2021-01-25 ;
                    }

                    container mpls-exp {
                      description 'Select MPLS-EXP as mark type.' ;
                      presence "Select MPLS-EXP as mark type" ;
                      leaf label-type {
                        if-feature policy-action-set-label ;

                        description 'Select MPLS-EXP label position, such as default, topmost, imposition, inner.' ;
                        type enumeration {
                          enum topmost {
                            value 1 ;
                            description 'Set the MPLS-EXP value on topmost label' ;
                          }

                          enum imposition {
                            value 2 ;
                            description 'Set the MPLS-EXP value on all imposed labels' ;
                          }

                          enum default {
                            value 0 ;
                            description 'The default for topmost label' ;
                          }

                          enum inner {
                            value 3 ;
                            description 'Set the MPLS-EXP value on inner label' ;
                          }

                        }

                      }

                      choice method {
                        description 'Specify the method to set MPLS-EXP.' ;
                        mandatory true ;
                        case set-value {
                          description 'Set the MPLS-EXP value directly.' ;
                          container set-value {
                            description 'Set the MPLS-EXP value directly.' ;
                            leaf mpls-exp-value {
                              description 'MPLS-EXP value, support <0-7>.' ;
                              type uint16 {
                                range 0..7 {
                                  description 'MPLS-EXP value, support <0-7>' ;
                                }

                              }

                              mandatory true ;
                            }

                          }

                        }

                        case inherit {
                          status obsolete {
                            ncd:revise-date 2021-06-04 ;
                          }

                          description 'Set the MPLS-EXP value by inheriting.' ;
                          container inherit {
                            description 'Set the MPLS-EXP value by inheriting.' ;
                            leaf inherit-type {
                              description 'Specify the source inherit type, such as precedence, mpls-exp, 8021p, dscp.' ;
                              type enumeration {
                                enum precedence {
                                  value 1 ;
                                  description 'Select precedence as source inherit' ;
                                }

                                enum mpls-exp {
                                  value 2 ;
                                  description 'Select MPLS-EXP as source inherit' ;
                                }

                                enum 8021p {
                                  value 3 ;
                                  description 'Select 802.1p as source inherit' ;
                                }

                                enum dscp {
                                  value 4 ;
                                  description 'Select dscp as source inherit' ;
                                }

                              }

                              mandatory true ;
                            }

                          }

                        }

                      }

                      ncd:revise-date 2021-01-25 ;
                    }

                    container vlan-id {
                      description 'Configure VLAN ID.' ;
                      presence "Configure VLAN ID" ;
                      leaf vlan-value {
                        description 'Set VLAN ID, support <1-4094>.' ;
                        type uint16 {
                          range 1..4094 ;

                        }

                        mandatory true ;
                      }

                      ncd:revise-date 2021-01-25 ;
                    }

                    container interface {
                      description 'Specify interface name.' ;
                      presence "Specify interface name" ;
                      leaf if-name {
                        description 'Specify interface name.' ;
                        type ncd:ifname {
                          length 1..31 {
                            description 'Name of the interface, support 1-31 characters' ;
                          }

                        }

                        mandatory true ;
                      }

                      ncd:revise-date 2021-08-03 ;
                    }

                  }

                  container urpf-type {
                    description 'Configure URPF(Unicast Reverse Path Forwarding) type:IPv4 urpf or IPv6 urpf.' ;
                    presence "Configure URPF type" ;
                    choice ip-type {
                      description 'Configure the IP protocol type of URPF(Unicast Reverse Path Forwarding):IPv4 or IPv6.' ;
                      mandatory true ;
                      case ipv4 {
                        description 'Configure IPv4 URPF(Unicast Reverse Path Forwarding) type.' ;
                        leaf ipv4 {
                          description 'IPv4 URPF type.' ;
                          type empty ;

                          mandatory true ;
                        }

                      }

                      case ipv6 {
                        description 'Configure IPv6 URPF(Unicast Reverse Path Forwarding) type.' ;
                        leaf ipv6 {
                          description 'IPv6 URPF type.' ;
                          type empty ;

                          mandatory true ;
                        }

                      }

                    }

                  }

                  container statistics {
                    description 'Configure the statistics function of class.' ;
                    presence "Configure statistics function" ;
                    leaf statis-enable {
                      description 'Enable the statistics function.' ;
                      type empty ;

                      mandatory true ;
                    }

                  }

                  container drop {
                    description 'Configure drop.' ;
                    presence "Configure drop" ;
                    leaf drop {
                      description 'Specify drop.' ;
                      type empty ;

                      mandatory true ;
                    }

                    ncd:revise-date 2021-01-11 ;
                  }

                  container redirect {
                    description 'Configure redirect.' ;
                    choice sfc {
                      case pbr {
                        container route-map {
                          description 'Configure redirect route-map of PBR.' ;
                          presence "Configure redirect route-map" ;
                          leaf route-map-name {
                            description 'The name of route-map.' ;
                            type string {
                              length 1..200 ;

                            }

                            mandatory true ;
                          }

                          leaf route-map-type {
                            description 'The type of route-map,IPv4 or IPv6.' ;
                            type enumeration {
                              enum ipv4 {
                                value 1 ;
                              }

                              enum ipv6 {
                                value 2 ;
                              }

                            }

                            mandatory true ;
                          }

                          leaf vrf-name {
                            description 'VRF name.' ;
                            type string {
                              length 1..32 ;

                            }

                          }

                          if-feature policy-action-rediret-route-map ;

                        }

                        description 'Configure Policy-based Routing.' ;
                      }

                      case nsh {
                        container nsh {
                          leaf service-path {
                            type uint32 {
                              range 1..16777215 ;

                            }

                            description 'Value of service-path ID.' ;
                            mandatory true ;
                          }

                          leaf service-index {
                            type uint8 {
                              range 1..255 ;

                            }

                            description 'Value of service-index ID.' ;
                            mandatory true ;
                          }

                          if-feature policy-action-redirect-nsh ;

                          presence "Configure redirect nsh" ;
                          description 'Configure redirect NSH of SFC.' ;
                          ncd:revise-date 2024-09-02 ;
                        }

                        description 'Configure Network Service Header.' ;
                      }

                      description 'Configure Service Function Chain.' ;
                    }

                    ncd:revise-date 2021-01-25 ;
                  }

                  container vlan-stacking {
                    if-feature policy-action-vlan-stacking ;

                    description 'Configure vlan-stacking.' ;
                    presence "Configure vlan-stacking" ;
                    leaf value {
                      description 'Set the value of vlan-stack.' ;
                      type uint16 {
                        range 1..4094 ;

                      }

                      mandatory true ;
                    }

                    leaf priority {
                      description 'Set the priority of vlan-stack.' ;
                      type uint8 {
                        range 0..7 ;

                      }

                      mandatory true ;
                    }

                    ncd:revise-date 2021-01-25 ;
                  }

                  container load-sharing {
                    description 'Configure load-sharing.' ;
                    if-feature policy-ecmp-hash ;

                    container ecmp-hash {
                      leaf ecmp-mode {
                        type enumeration {
                          enum per-stream {
                            value 1 ;
                            description 'Configure per-stream ecmp mode.' ;
                          }

                          enum per-packet {
                            value 2 ;
                            description 'Configure per-packet ecmp mode.' ;
                          }

                          enum spray {
                            value 3 ;
                            description 'Configure spray ecmp mode.' ;
                          }

                        }

                        description 'Configure ecmp mode.' ;
                        mandatory true ;
                      }

                      description 'Configure ecmp-hash.' ;
                      presence ecmp-hash ;
                    }

                    ncd:revise-date 2025-03-10 ;
                  }

                }

                container class-default {
                  description 'Select policy association default class.' ;
                  presence "Specify the default class" ;
                  leaf class-default {
                    description 'Specify the default class.' ;
                    type empty ;

                    mandatory true ;
                  }

                  container police {
                    description 'Configure traffic policing.' ;
                    presence "Configure traffic policing" ;
                    container mode {
                      description 'Set color mode.' ;
                      presence "Configure mode information" ;
                      leaf mode-type {
                        description 'Color mode type.' ;
                        type enumeration {
                          enum blind {
                            value 1 ;
                            description 'Color-Blind mode' ;
                          }

                          enum aware {
                            value 2 ;
                            description 'Color-Aware mode' ;
                          }

                        }

                        mandatory true ;
                      }

                    }

                    choice buket-value-percent {
                      description 'Configure CIR CBS PIR and PBS.' ;
                      mandatory true ;
                      case buket-value {
                        description 'Configure CIR CBS PIR and PBS in numerical form.' ;
                        container c-buket {
                          description 'Configure C-buket related parameters.' ;
                          container cir-value {
                            description 'Configure the CIR.' ;
                            leaf cir {
                              description 'Configure the CIR (Committed Information Rate) value, default: kilobits per second.' ;
                              type uint32 {
                                range 8..4294967295 {
                                  description 'The CIR value (default: kilobits per second),support <8-4294967295>' ;
                                }

                              }

                              mandatory true ;
                            }

                            leaf cir-unit {
                              description 'Set CIR unit, such as kbps, mbps, gbps, pps.' ;
                              type qos-rate-unit-type-ex ;

                            }

                          }

                          container cbs-value {
                            description 'Configure the CBS.' ;
                            presence cbs ;
                            leaf cbs {
                              description 'Configure the CBS(Committed Burst Size) size, default: KB.' ;
                              type uint32 {
                                range 1..4294967295 {
                                  description 'The CBS(Committed Burst Size) size in bytes, support <1-4294967295>' ;
                                }

                              }

                              mandatory true ;
                            }

                            leaf cbs-unit {
                              description 'Set CBS unit, such as kb, mb, gb.' ;
                              type qos-bucket-unit-type ;

                            }

                          }

                        }

                        container p-buket {
                          description 'Configure P-buket related parameters.' ;
                          presence p-buket ;
                          container pir-value {
                            description 'Configure the PIR.' ;
                            leaf pir {
                              description 'Configure the PIR(Peak Information Rate) value, default: kilobits per second.' ;
                              type uint32 {
                                range 8..4294967295 {
                                  description 'The PIR(Peak Information Rate) value (default: kilobits per second), support <8-4294967295>' ;
                                }

                              }

                              mandatory true ;
                            }

                            leaf pir-unit {
                              description 'Set PIR unit, such as kbps, mbps, gbps, pps.' ;
                              type qos-rate-unit-type-ex ;

                            }

                          }

                          container pbs-value {
                            description 'Configure the PBS.' ;
                            presence pbs ;
                            leaf pbs {
                              description 'Configure the PBS(Peak Burst Size) size, default: KB.' ;
                              type uint32 {
                                range 1..4294967295 {
                                  description 'The PBS(Peak Burst Size) size in bytes, support <1-4294967295>' ;
                                }

                              }

                              mandatory true ;
                            }

                            leaf pbs-unit {
                              description 'Set PBS unit, such as kb, mb, gb.' ;
                              type qos-bucket-unit-type ;

                            }

                          }

                        }

                      }

                      case buket-percent {
                        description 'Configure CIR and PIR with percentage form.' ;
                        container cir {
                          description 'Configure CIR with percentage form.' ;
                          leaf cir-percent {
                            description 'Configure CIR with percentage form.' ;
                            type uint8 {
                              range 1..100 {
                                description 'Configure CIR with percentage form' ;
                              }

                            }

                            mandatory true ;
                          }

                        }

                        container pir {
                          description 'Configure PIR with percentage form.' ;
                          presence pir ;
                          leaf pir-percent {
                            description 'Configure PIR with percentage form.' ;
                            type uint8 {
                              range 1..100 {
                                description 'Configure PIR with percentage form' ;
                              }

                            }

                            mandatory true ;
                          }

                        }

                      }

                    }

                    container action {
                      description 'Set monitoring action  for each measurement evaluation packet.' ;
                      container conform-action {
                        description 'Action to packets that conform to the rate limit.' ;
                        choice conform-action {
                          description 'Specify action to packets that conform to the rate limit.' ;
                          mandatory true ;
                          case ca-drop {
                            description 'Drop packet in conform-action.' ;
                            leaf drop {
                              description 'Specify action to drop packet.' ;
                              type empty ;

                              mandatory true ;
                            }

                          }

                          case ca-transmit {
                            description 'Transmit packet in conform-action.' ;
                            leaf transmit {
                              description 'Specify action to transmit packet.' ;
                              type empty ;

                              mandatory true ;
                            }

                          }

                          case ca-mpls-exp {
                            description 'Rewrite packet MPLS-EXP and transmit the packet.' ;
                            leaf set-exp-transmit {
                              description 'Specify action to rewrite packet MPLS-EXP and transmit it.' ;
                              type empty ;

                              mandatory true ;
                            }

                            leaf mpls-exp-value {
                              description 'Reset MPLS-EXP value in conform-action, support <0-7>.' ;
                              type uint8 {
                                range 0..7 {
                                  description 'The MPLS-EXP value, support <0-7>' ;
                                }

                              }

                              mandatory true ;
                            }

                          }

                          case ca-precedence {
                            description 'Rewrite packet precedence and transmit the packet.' ;
                            leaf set-prec-transmit {
                              description 'Specify action to rewrite packet precedence and transmit it.' ;
                              type empty ;

                              mandatory true ;
                            }

                            leaf prec-value {
                              description 'Reset the IP-Precedence value in conform-action, support <0-7>.' ;
                              type uint8 {
                                range 0..7 {
                                  description 'The IP-Precedence value, support <0-7>' ;
                                }

                              }

                              mandatory true ;
                            }

                          }

                          case ca-dscp {
                            description 'Rewrite packet DSCP and transmit the packet.' ;
                            leaf set-dscp-transmit {
                              description 'Specify action to rewrite packet DSCP and transmit it' ;
                              type empty ;

                              mandatory true ;
                            }

                            leaf dscp-value {
                              description 'Reset DSCP in conform-action, support <0-63>' ;
                              type uint8 {
                                range 0..63 {
                                  description 'The DSCP value, support <0-63>' ;
                                }

                              }

                              mandatory true ;
                            }

                          }

                          case ca-8021p {
                            description 'Rewrite packet 802.1p and transmit the packet' ;
                            leaf set-8021p-transmit {
                              description 'Specify action to rewrite packet 802.1p and transmit it.' ;
                              type empty ;

                              mandatory true ;
                            }

                            leaf value-8021p {
                              description 'Reset 802.1p in conform-action, support <0-7>.' ;
                              type uint8 {
                                range 0..7 {
                                  description 'The 802.1p value, support <0-7>' ;
                                }

                              }

                              mandatory true ;
                            }

                          }

                          case ca-service-class {
                            description 'Rewrite packet service-class and transmit it.' ;
                            leaf service-class-value {
                              description 'Reset service class in conform-action.' ;
                              type qos-service-class ;

                              mandatory true ;
                            }

                          }

                        }

                      }

                      container exceed-action {
                        description 'Action to packets that exceed the rate limit.' ;
                        choice exceed-action {
                          description 'Specify action to packets that exceed the rate limit.' ;
                          mandatory true ;
                          case ea-drop {
                            description 'Drop packet in exceed-action.' ;
                            leaf drop {
                              description 'Specify action to drop packet.' ;
                              type empty ;

                              mandatory true ;
                            }

                          }

                          case ea-transmit {
                            description 'Transmit packet in exceed-action.' ;
                            leaf transmit {
                              description 'Specify action to transmit packet.' ;
                              type empty ;

                              mandatory true ;
                            }

                          }

                          case ea-mpls-exp {
                            description 'Rewrite packet MPLS-EXP and transmit the packet.' ;
                            leaf set-exp-transmit {
                              description 'Specify action to rewrite packet MPLS-EXP and transmit it.' ;
                              type empty ;

                              mandatory true ;
                            }

                            leaf mpls-exp-value {
                              description 'Reset MPLS-EXP value in exceed-action, support <0-7>.' ;
                              type uint8 {
                                range 0..7 {
                                  description 'The MPLS-EXP value, support <0-7>' ;
                                }

                              }

                              mandatory true ;
                            }

                          }

                          case ea-precedence {
                            description 'Rewrite packet precedence and transmit the packet.' ;
                            leaf set-prec-transmit {
                              description 'Specify action to rewrite packet precedence and transmit it.' ;
                              type empty ;

                              mandatory true ;
                            }

                            leaf prec-value {
                              description 'Reset the IP-Precedence value in exceed-action, support <0-7>.' ;
                              type uint8 {
                                range 0..7 {
                                  description 'The IP-Precedence value, support <0-7>' ;
                                }

                              }

                              mandatory true ;
                            }

                          }

                          case ea-dscp {
                            description 'Rewrite packet DSCP and transmit the packet.' ;
                            leaf set-dscp-transmit {
                              description 'Specify action to rewrite packet DSCP and transmit it.' ;
                              type empty ;

                              mandatory true ;
                            }

                            leaf dscp-value {
                              description 'Reset DSCP in exceed-action, support <0-63>.' ;
                              type uint8 {
                                range 0..63 {
                                  description 'The DSCP value, support <0-63>' ;
                                }

                              }

                              mandatory true ;
                            }

                          }

                          case ea-8021p {
                            description 'Rewrite packet 802.1p and transmit the packet.' ;
                            leaf set-8021p-transmit {
                              description 'Specify action to rewrite packet 802.1p and transmit it.' ;
                              type empty ;

                              mandatory true ;
                            }

                            leaf value-8021p {
                              description 'Reset 802.1p in exceed-action, support <0-7>.' ;
                              type uint8 {
                                range 0..7 {
                                  description 'The 802.1p value, support <0-7>' ;
                                }

                              }

                              mandatory true ;
                            }

                          }

                          case ea-service-class {
                            description 'Rewrite packet service-class and transmit it.' ;
                            leaf service-class-value {
                              description 'Reset service class in exceed-action.' ;
                              type qos-service-class ;

                              mandatory true ;
                            }

                          }

                        }

                      }

                      container violate-action {
                        description 'Action to packets that violate the rate limit.' ;
                        choice violate-action {
                          description 'Specify action to packets that violate the rate limit.' ;
                          mandatory true ;
                          case va-drop {
                            description 'Drop packet in violate-action.' ;
                            leaf drop {
                              description 'Specify action to drop packet.' ;
                              type empty ;

                              mandatory true ;
                            }

                          }

                          case va-transmit {
                            description 'Transmit packet in violate-action.' ;
                            leaf transmit {
                              description 'Specify action to transmit packet.' ;
                              type empty ;

                              mandatory true ;
                            }

                          }

                          case va-mpls-exp {
                            description 'Rewrite packet MPLS-EXP and transmit the packet.' ;
                            leaf set-exp-transmit {
                              description 'Specify action to rewrite packet MPLS-EXP and transmit it.' ;
                              type empty ;

                              mandatory true ;
                            }

                            leaf mpls-exp-value {
                              description 'Reset MPLS-EXP value in violate-action, support <0-7>.' ;
                              type uint8 {
                                range 0..7 {
                                  description 'The MPLS-EXP value, support <0-7>' ;
                                }

                              }

                              mandatory true ;
                            }

                          }

                          case va-precedence {
                            description 'Rewrite packet precedence and transmit the packet.' ;
                            leaf set-prec-transmit {
                              description 'Specify action to rewrite packet precedence and transmit it.' ;
                              type empty ;

                              mandatory true ;
                            }

                            leaf prec-value {
                              description 'Reset the IP-Precedence value in violate-action, support <0-7>.' ;
                              type uint8 {
                                range 0..7 {
                                  description 'The IP-Precedence value, support <0-7>' ;
                                }

                              }

                              mandatory true ;
                            }

                          }

                          case va-dscp {
                            description 'Rewrite packet DSCP and transmit the packet.' ;
                            leaf set-dscp-transmit {
                              description 'Specify action to rewrite packet DSCP and transmit it.' ;
                              type empty ;

                              mandatory true ;
                            }

                            leaf dscp-value {
                              description 'Reset DSCP in violate-action, support <0-63>.' ;
                              type uint8 {
                                range 0..63 {
                                  description 'The DSCP value, support <0-63>' ;
                                }

                              }

                              mandatory true ;
                            }

                          }

                          case va-8021p {
                            description 'Rewrite packet 802.1p and transmit the packet.' ;
                            leaf set-8021p-transmit {
                              description 'Specify action to rewrite packet 802.1p and transmit it.' ;
                              type empty ;

                              mandatory true ;
                            }

                            leaf value-8021p {
                              description 'Reset 802.1p in violate-action, support <0-7>.' ;
                              type uint8 {
                                range 0..7 {
                                  description 'The 802.1p value, support <0-7>' ;
                                }

                              }

                              mandatory true ;
                            }

                          }

                          case va-service-class {
                            description 'Rewrite packet service-class and transmit it.' ;
                            leaf service-class-value {
                              description 'Reset service class in violate-action.' ;
                              type qos-service-class ;

                              mandatory true ;
                            }

                          }

                        }

                      }

                    }

                  }

                  container mirror {
                    description 'Configure mirror.' ;
                    presence "Configure mirror" ;
                    leaf session-id {
                      description 'Set the session id.' ;
                      type uint32 {
                        range 1..4294967295 {
                          description 'Set the session id.' ;
                        }

                      }

                      mandatory true ;
                    }

                  }

                  container set {
                    description 'Mark a packet.' ;
                    container service-class {
                      description 'Configure service class.' ;
                      presence "Configure service function path" ;
                      leaf service-class {
                        description 'Select service class of PHB info.' ;
                        type qos-service-class ;

                        mandatory true ;
                      }

                      leaf color-type {
                        description 'Specify packets color, support <green,yellow,red>.' ;
                        type qos-color-type ;

                      }

                    }

                    container dscp {
                      description 'Select DSCP as mark type.' ;
                      presence "Select DSCP as mark typ" ;
                      choice method {
                        description 'Specify the method to set DSCP.' ;
                        mandatory true ;
                        case set-value {
                          description 'Set the DSCP value directly.' ;
                          container set-value {
                            description 'Set the DSCP value directly.' ;
                            leaf dscp-value {
                              description 'DSCP value, support <0-63>.' ;
                              type uint16 {
                                range 0..63 {
                                  description 'DSCP value, support <0-63>' ;
                                }

                              }

                              mandatory true ;
                            }

                          }

                        }

                        case inherit {
                          status obsolete {
                            ncd:revise-date 2021-06-04 ;
                          }

                          description 'Set the DSCP value by inheriting.' ;
                          container inherit {
                            description 'Set the DSCP value by inheriting.' ;
                            leaf inherit-type {
                              description 'Specify the source inherit type, such as precedence, mpls-exp, 8021p, dscp, pay-load 8021p.' ;
                              type enumeration {
                                enum precedence {
                                  value 1 ;
                                  description 'Select precedence as source inherit' ;
                                }

                                enum mpls-exp {
                                  value 2 ;
                                  description 'Select MPLS-EXP as source inherit' ;
                                }

                                enum 8021p {
                                  value 3 ;
                                  description 'Select 802.1p as source inherit' ;
                                }

                                enum dscp {
                                  value 4 ;
                                  description 'Select dscp as source inherit' ;
                                }

                                enum pay-load-8021p {
                                  value 6 ;
                                  description 'Select inner 802.1p as source inherit' ;
                                }

                              }

                              mandatory true ;
                            }

                          }

                        }

                      }

                      ncd:revise-date 2021-01-25 ;
                    }

                    container precedence {
                      description 'Select precedence as mark type.' ;
                      presence "Select precedence as mark type" ;
                      choice method {
                        description 'Specify the method to set IP Precedence.' ;
                        mandatory true ;
                        case set-value {
                          description 'Set the IP Precedence value directly.' ;
                          container set-value {
                            description 'Set the IP Precedence value directly.' ;
                            leaf prec-value {
                              description 'IP Precedence value, support <0-7>.' ;
                              type uint16 {
                                range 0..7 {
                                  description 'IP Precedence value, support <0-7>' ;
                                }

                              }

                              mandatory true ;
                            }

                          }

                        }

                        case inherit {
                          status obsolete {
                            ncd:revise-date 2021-06-04 ;
                          }

                          description 'Set the IP Precedence value by inheriting.' ;
                          container inherit {
                            description 'Set the IP Precedence value by inheriting.' ;
                            leaf inherit-type {
                              description 'Specify the source inherit type, such as precedence, mpls-exp, 8021p, dscp.' ;
                              type enumeration {
                                enum precedence {
                                  value 1 ;
                                  description 'Select precedence as source inherit' ;
                                }

                                enum mpls-exp {
                                  value 2 ;
                                  description 'Select MPLS-EXP as source inherit' ;
                                }

                                enum 8021p {
                                  value 3 ;
                                  description 'Select 802.1p as source inherit' ;
                                }

                                enum dscp {
                                  value 4 ;
                                  description 'Select dscp as source inherit' ;
                                }

                              }

                              mandatory true ;
                            }

                          }

                        }

                      }

                      ncd:revise-date 2021-01-25 ;
                    }

                    container pri-8021p {
                      description 'Select 802.1p as mark type.' ;
                      presence "Select 802.1p as mark type" ;
                      choice method {
                        description 'Specify the method to set 802.1p.' ;
                        mandatory true ;
                        case set-value {
                          description 'Set the 802.1p value directly.' ;
                          container set-value {
                            description 'Set the 802.1p value directly.' ;
                            leaf value-8021p {
                              description '802.1p value, support <0-7>.' ;
                              type uint16 {
                                range 0..7 {
                                  description '802.1p value, support <0-7>' ;
                                }

                              }

                              mandatory true ;
                            }

                            leaf inner-outer {
                              description 'Set 8021p inner or outer flag.If vlaue is 0, it means outer flag. If value is 1,it means inner and outer flag.' ;
                              type uint8 {
                                range 0..1 {
                                  description 'Inner or outer flag. 0 is outer. 1 is inner and outer' ;
                                }

                              }

                              default 0 ;
                            }

                          }

                        }

                        case inherit {
                          status obsolete {
                            ncd:revise-date 2021-06-04 ;
                          }

                          description 'Set the 802.1p value by inheriting.' ;
                          container inherit {
                            description 'Set the 802.1p value by inheriting.' ;
                            leaf inherit-type {
                              description 'Specify the source inherit type, such as precedence, mpls-exp, 8021p, dscp.' ;
                              type enumeration {
                                enum precedence {
                                  value 1 ;
                                  description 'Select precedence as source inherit' ;
                                }

                                enum mpls-exp {
                                  value 2 ;
                                  description 'Select MPLS-EXP as source inherit' ;
                                }

                                enum 8021p {
                                  value 3 ;
                                  description 'Select 802.1p as source inherit' ;
                                }

                                enum dscp {
                                  value 4 ;
                                  description 'Select dscp as source inherit' ;
                                }

                              }

                              mandatory true ;
                            }

                            leaf inner-outer {
                              description 'Set 8021p inner or outer flag.If vlaue is 0, it means outer flag. If value is 1,it means inner and outer flag.' ;
                              type uint8 {
                                range 0..1 {
                                  description 'Inner or outer flag. 0 is outer. 1 is inner and outer' ;
                                }

                              }

                              default 0 ;
                            }

                          }

                        }

                      }

                      ncd:revise-date 2021-01-25 ;
                    }

                    container mpls-exp {
                      description 'Select MPLS-EXP as mark type.' ;
                      presence "Select MPLS-EXP as mark type" ;
                      leaf label-type {
                        if-feature policy-action-set-label ;

                        description 'Select MPLS-EXP label position, such as default, topmost, imposition, inner.' ;
                        type enumeration {
                          enum topmost {
                            value 1 ;
                            description 'Set the MPLS-EXP value on topmost label' ;
                          }

                          enum imposition {
                            value 2 ;
                            description 'Set the MPLS-EXP value on all imposed labels' ;
                          }

                          enum default {
                            value 0 ;
                            description 'The default for topmost label' ;
                          }

                          enum inner {
                            value 3 ;
                            description 'Set the MPLS-EXP value on inner label' ;
                          }

                        }

                      }

                      choice method {
                        description 'Specify the method to set MPLS-EXP.' ;
                        mandatory true ;
                        case set-value {
                          description 'Set the MPLS-EXP value directly.' ;
                          container set-value {
                            description 'Set the MPLS-EXP value directly.' ;
                            leaf mpls-exp-value {
                              description 'MPLS-EXP value, support <0-7>.' ;
                              type uint16 {
                                range 0..7 {
                                  description 'MPLS-EXP value, support <0-7>' ;
                                }

                              }

                              mandatory true ;
                            }

                          }

                        }

                        case inherit {
                          status obsolete {
                            ncd:revise-date 2021-06-04 ;
                          }

                          description 'Set the MPLS-EXP value by inheriting.' ;
                          container inherit {
                            description 'Set the MPLS-EXP value by inheriting.' ;
                            leaf inherit-type {
                              description 'Specify the source inherit type, such as precedence, mpls-exp, 8021p, dscp.' ;
                              type enumeration {
                                enum precedence {
                                  value 1 ;
                                  description 'Select precedence as source inherit' ;
                                }

                                enum mpls-exp {
                                  value 2 ;
                                  description 'Select MPLS-EXP as source inherit' ;
                                }

                                enum 8021p {
                                  value 3 ;
                                  description 'Select 802.1p as source inherit' ;
                                }

                                enum dscp {
                                  value 4 ;
                                  description 'Select dscp as source inherit' ;
                                }

                              }

                              mandatory true ;
                            }

                          }

                        }

                      }

                      ncd:revise-date 2021-01-25 ;
                    }

                    container vlan-id {
                      description 'Configure VLAN ID.' ;
                      presence "Configure VLAN ID" ;
                      leaf vlan-value {
                        description 'Set VLAN ID, support <1-4094>.' ;
                        type uint16 {
                          range 1..4094 ;

                        }

                        mandatory true ;
                      }

                      ncd:revise-date 2021-01-25 ;
                    }

                    container interface {
                      description 'Specify interface name.' ;
                      presence "Specify interface name" ;
                      leaf if-name {
                        description 'Specify interface name.' ;
                        type ncd:ifname {
                          length 1..31 {
                            description 'Name of the interface, support 1-31 characters' ;
                          }

                        }

                        mandatory true ;
                      }

                      ncd:revise-date 2021-08-03 ;
                    }

                  }

                  container urpf-type {
                    description 'Configure URPF(Unicast Reverse Path Forwarding) type:IPv4 urpf or IPv6 urpf.' ;
                    presence "Configure URPF type" ;
                    choice ip-type {
                      description 'Configure the IP protocol type of URPF(Unicast Reverse Path Forwarding):IPv4 or IPv6.' ;
                      mandatory true ;
                      case ipv4 {
                        description 'Configure IPv4 URPF(Unicast Reverse Path Forwarding) type.' ;
                        leaf ipv4 {
                          description 'IPv4 URPF type.' ;
                          type empty ;

                          mandatory true ;
                        }

                      }

                      case ipv6 {
                        description 'Configure IPv6 URPF(Unicast Reverse Path Forwarding) type.' ;
                        leaf ipv6 {
                          description 'IPv6 URPF type.' ;
                          type empty ;

                          mandatory true ;
                        }

                      }

                    }

                  }

                  container statistics {
                    description 'Configure the statistics function of class.' ;
                    presence "Configure statistics function" ;
                    leaf statis-enable {
                      description 'Enable the statistics function.' ;
                      type empty ;

                      mandatory true ;
                    }

                  }

                  container drop {
                    description 'Configure drop.' ;
                    presence "Configure drop" ;
                    leaf drop {
                      description 'Specify drop.' ;
                      type empty ;

                      mandatory true ;
                    }

                    ncd:revise-date 2021-01-11 ;
                  }

                  container redirect {
                    description 'Configure redirect.' ;
                    choice sfc {
                      description 'Configure Service Function Chain.' ;
                      case pbr {
                        container route-map {
                          description 'Configure redirect route-map of PBR.' ;
                          presence "Configure redirect route-map" ;
                          leaf route-map-name {
                            description 'The name of route-map.' ;
                            type string {
                              length 1..200 ;

                            }

                          }

                          leaf route-map-type {
                            description 'The type of route-map,IPv4 or IPv6.' ;
                            type enumeration {
                              enum ipv4 {
                                value 1 ;
                              }

                              enum ipv6 {
                                value 2 ;
                              }

                            }

                          }

                          leaf vrf-name {
                            description 'VRF name.' ;
                            type string {
                              length 1..32 ;

                            }

                          }

                          if-feature policy-action-rediret-route-map ;

                        }

                        description 'Configure Policy-based Routing.' ;
                      }

                      case nsh {
                        container nsh {
                          leaf service-path {
                            type uint32 {
                              range 1..16777215 ;

                            }

                            description 'Value of service-path ID.' ;
                            mandatory true ;
                          }

                          leaf service-index {
                            type uint8 {
                              range 1..255 ;

                            }

                            description 'Value of service-index ID.' ;
                            mandatory true ;
                          }

                          if-feature policy-action-redirect-nsh ;

                          description 'Configure redirect NSH of SFC.' ;
                          presence "Configure redirect nsh" ;
                          ncd:revise-date 2024-09-02 ;
                        }

                        description 'Configure Network Service Header.' ;
                      }

                    }

                    ncd:revise-date 2021-01-25 ;
                  }

                  container vlan-stacking {
                    if-feature policy-action-vlan-stacking ;

                    description 'Configure vlan-stacking.' ;
                    presence "Configure vlan-stacking" ;
                    leaf value {
                      description 'Set the value of vlan-stack.' ;
                      type uint16 {
                        range 1..4094 ;

                      }

                    }

                    leaf priority {
                      description 'Set the priority of vlan-stack.' ;
                      type uint8 {
                        range 0..7 ;

                      }

                    }

                    ncd:revise-date 2021-01-25 ;
                  }

                  container load-sharing {
                    description 'Configure load-sharing.' ;
                    if-feature policy-ecmp-hash ;

                    container ecmp-hash {
                      leaf ecmp-mode {
                        type enumeration {
                          enum per-stream {
                            value 1 ;
                            description 'Configure per-stream ecmp mode.' ;
                          }

                          enum per-packet {
                            description 'Configure per-packet ecmp mode.' ;
                            value 2 ;
                          }

                          enum spray {
                            description 'Configure spray ecmp mode.' ;
                            value 3 ;
                          }

                        }

                        description 'Configure ecmp mode.' ;
                        mandatory true ;
                      }

                      description 'Configure ecmp-hash.' ;
                      presence ecmp-hash ;
                    }

                    ncd:revise-date 2025-03-10 ;
                  }

                }

              }

              container pmap-description {
                description 'Description of a policy map, support 1-79 characters.' ;
                presence "Specify description of policy map" ;
                leaf pmap-description {
                  description 'Description of a policy map, support 1-79 characters.' ;
                  type ncd:string-with-blank {
                    length 1..79 {
                      description 'Description of a policy map, support 1-79 characters.' ;
                    }

                  }

                  mandatory true ;
                }

                ncd:revise-date 2021-01-18 ;
              }

            }

          }

          ncd:revise-date 2020-12-23 ;
        }

        container cps-based {
          description 'Policy map based on control-plane-security.' ;
          container policy-maps {
            description 'Configure QoS policy map lists.' ;
            list policy-map {
              description 'Configure QoS policy maps.' ;
              key pmap-name ;
              leaf pmap-name {
                description 'Name of the policy map, support 1-31 characters.' ;
                type string {
                  length 1..31 {
                    description 'Name of the policy map, support 1-31 characters' ;
                  }

                }

              }

              container class-maps {
                description 'Configure QoS policy class.' ;
                list class-map {
                  description 'Configure QoS policy class.' ;
                  key cmap-name ;
                  leaf cmap-name {
                    description 'Name of the class map, support 1-31 characters.' ;
                    type string {
                      length 1..31 {
                        description 'Name of the class map, support 1-31 characters' ;
                      }

                    }

                  }

                  container police {
                    description 'Configure traffic policing.' ;
                    presence "Configure traffic policing" ;
                    container c-bucket {
                      description 'Configure C-bucket related parameters.' ;
                      container cir-value {
                        description 'Configure the CIR.' ;
                        leaf cir {
                          description 'Configure the CIR (Committed Information Rate) value, unit: packets per second.' ;
                          type uint32 {
                            range 1..4294967295 {
                              description 'The CIR value (Unit: packets per second)' ;
                            }

                          }

                          mandatory true ;
                        }

                      }

                    }

                  }

                  container drop {
                    description 'Configure drop.' ;
                    presence "Configure drop" ;
                    leaf drop {
                      description 'Specify drop.' ;
                      type empty ;

                      mandatory true ;
                    }

                  }

                  container priority-level {
                    description 'Configure PQ(Priority Queuing) priority level.' ;
                    presence "Configure PQ priority level" ;
                    leaf priority-value {
                      description 'Set the priority level of PQ.' ;
                      type uint16 {
                        range 1..65535 {
                          description 'The priority level of PQ' ;
                        }

                      }

                      mandatory true ;
                    }

                  }

                }

                container class-default {
                  description 'Select policy association default class.' ;
                  presence "Specify the default class" ;
                  leaf class-default {
                    description 'Specify the default class.' ;
                    type empty ;

                    mandatory true ;
                  }

                  container police {
                    description 'Configure traffic policing.' ;
                    presence "Configure traffic policing" ;
                    container c-bucket {
                      description 'Configure C-bucket related parameters.' ;
                      container cir-value {
                        description 'Configure the CIR.' ;
                        leaf cir {
                          description 'Configure the CIR (Committed Information Rate) value, unit: packets per second.' ;
                          type uint32 {
                            range 1..4294967295 {
                              description 'The CIR value (Unit: packets per second)' ;
                            }

                          }

                          mandatory true ;
                        }

                      }

                    }

                  }

                  container drop {
                    description 'Configure drop.' ;
                    presence "Configure drop" ;
                    leaf drop {
                      description 'Specify drop.' ;
                      type empty ;

                      mandatory true ;
                    }

                  }

                  container priority-level {
                    description 'Configure PQ(Priority Queuing) priority level.' ;
                    presence "Configure PQ priority level" ;
                    leaf priority-value {
                      description 'Set the priority level of PQ.' ;
                      type uint16 {
                        range 1..65535 {
                          description 'The priority level of PQ' ;
                        }

                      }

                      mandatory true ;
                    }

                  }

                }

              }

              container pmap-description {
                description 'Description of a policy map, support 1-79 characters.' ;
                presence "Specify description of policy map" ;
                leaf pmap-description {
                  description 'Description of a policy map, support 1-79 characters.' ;
                  type ncd:string-with-blank {
                    length 1..79 {
                      description 'Description of a policy map, support 1-79 characters.' ;
                    }

                  }

                  mandatory true ;
                }

              }

            }

          }

          ncd:revise-date 2021-04-18 ;
        }

      }

      container service-policys {
        if-feature service-policy ;

        description 'Bind H-QoS policys to the interface.' ;
        list service-policy {
          description 'Bind H-QoS policys to the interface.' ;
          key 'if-name if-direction bound-type' ;
          leaf if-name {
            description 'Configure the name of the attaching interface.' ;
            type ncd:ifname {
              length 1..31 {
                description 'Name of the attaching interface, support 1-31 characters' ;
              }

            }

          }

          leaf if-direction {
            description 'Configure the interface direction.' ;
            type enumeration {
              enum input {
                value 1 ;
                description 'Attaches to the input interface' ;
              }

              enum output {
                value 2 ;
                description 'Attaches to the output interface' ;
              }

            }

          }

          leaf bound-type {
            description 'Specify the bind mode.' ;
            type enumeration {
              enum normal {
                value 1 ;
                description 'Set policies bound on link-ports with normal' ;
              }

              enum overwrite {
                value 2 ;
                description 'Set policies bound on link-ports with overwrite' ;
              }

              enum multiple-level-qos {
                value 4 ;
                description 'Set multiple level qos mode' ;
              }

            }

          }

          leaf pmap-name {
            description 'Name of the policy map bound on the interface, support 1-31 characters.' ;
            type string {
              length 1..31 {
                description 'Name of the policy map, support 1-31 characters' ;
              }

            }

            mandatory true ;
          }

          leaf statistical-share {
            description 'Set statistical share.' ;
            type boolean ;

            default false ;
          }

          leaf share-group {
            description 'Specify share group ID.' ;
            type uint32 {
              range 1..5000 ;

            }

            ncd:revise-date 2021-01-18 ;
          }

          leaf switch-fabric {
            description 'Set switch-fabric.' ;
            type boolean ;

            default false ;
            ncd:revise-date 2021-08-10 ;
          }

          container shape {
            description 'Configure shape.' ;
            presence "Configure shape" ;
            leaf rate {
              description 'Configure rate.' ;
              type uint32 {
                range 8..4294967295 {
                  description 'Rate in kilobits per second' ;
                }

              }

              units kbps ;
              mandatory true ;
            }

            container burst {
              description 'Configure burst and exburst size.' ;
              presence "Configure burst and exburst size in KB" ;
              leaf burst-size {
                description 'Burst size.' ;
                type uint32 {
                  range 2..250000000 {
                    description 'Burst size in KB, support <2-250000000>' ;
                  }

                }

                units KB ;
                mandatory true ;
              }

            }

            ncd:revise-date 2021-03-22 ;
          }

        }

      }

      container traffic-policy-interfaces {
        if-feature traffic-policy ;

        description 'Bind QoS policys to the interface.' ;
        list traffic-policy-interface {
          description 'Bind QoS policys to the interface.' ;
          key 'if-name if-direction' ;
          leaf if-name {
            description 'Configure the name of the attaching interface.' ;
            type ncd:ifname {
              length 1..31 {
                description 'Name of the attaching interface, support 1-31 characters' ;
              }

            }

          }

          leaf if-direction {
            description 'Configure the interface direction.' ;
            type enumeration {
              enum input {
                value 1 ;
                description 'Attaches to the input interface' ;
              }

              enum output {
                value 2 ;
                description 'Attaches to the output interface' ;
              }

            }

          }

          leaf bound-type {
            description 'Specify the bind mode.' ;
            type enumeration {
              enum overwrite {
                value 2 ;
                description 'Set policies bound on link-ports with overwrite' ;
              }

              enum normal {
                value 1 ;
                description 'Set policies bound on link-ports with normal' ;
              }

            }

            default normal ;
          }

          leaf pmap-name {
            description 'Name of the policy map bound on the interface, support 1-31 characters.' ;
            type string {
              length 1..31 {
                description 'Name of the policy map, support 1-31 characters' ;
              }

            }

            mandatory true ;
          }

          leaf statistical-share {
            description 'Set statistical share.' ;
            type boolean ;

            default false ;
          }

          leaf description {
            description 'Description of the QoS policys bind to the interface, support 1-79 characters.' ;
            type ncd:string-with-blank {
              length 1..79 {
                description 'Description of the QoS policys bind to the interface, support 1-79 characters.' ;
              }

            }

            ncd:revise-date 2021-08-10 ;
          }

        }

        ncd:revise-date 2021-01-25 ;
      }

      container rate-limit {
        description 'Configure interface rate limit parameters.' ;
        container unicasts {
          description 'Match unicast.' ;
          list unicast {
            description 'Configure interface rate limit based on matching unicast.' ;
            key 'if-name if-direct' ;
            leaf if-name {
              description 'Configure the name of the attaching interface.' ;
              type ncd:ifname {
                length 1..31 {
                  description 'Name of the attaching interface, support 1-31 characters' ;
                }

              }

            }

            leaf if-direct {
              description 'Specify the direction of interface.' ;
              type enumeration {
                enum input {
                  value 1 ;
                  description 'Rate limit on input' ;
                }

                enum output {
                  value 2 ;
                  description 'Rate limit on output' ;
                }

              }

            }

            leaf rate-limit-desc {
              description 'Description of rate limit, support 1-79 characters.' ;
              type ncd:string-with-blank {
                length 1..79 {
                  description 'Description of rate limit, support 1-79 characters.' ;
                }

              }

              ncd:revise-date 2020-06-18 ;
            }

            choice unit-style {
              description "Specify unit's style." ;
              mandatory true ;
              case unit-value {
                description 'Configure the value style.' ;
                leaf cir {
                  description 'Configure the CIR(Committed Information Rate) value (default: kilobits per second).' ;
                  type uint32 {
                    range 0..4294967295 {
                      description 'The CIR value (default: kilobits per second).' ;
                    }

                  }

                  mandatory true ;
                }

                leaf cir-unit {
                  description 'Set cir unit, such as kbps, mbps, gbps.' ;
                  type qos-rate-unit-type ;

                }

                leaf cbs {
                  description 'Configure the CBS(Committed Burst Size) size in bytes.' ;
                  type uint32 {
                    range 0..4294967294 {
                      description 'The CBS(Committed Burst Size) size in bytes.' ;
                    }

                  }

                  units byte ;
                }

                leaf pir {
                  description 'Configure the PIR(Peak Information Rate) value (default: kilobits per second).' ;
                  type uint32 {
                    range 0..4294967295 {
                      description 'The PIR(Peak Information Rate) value (default: kilobits per second).' ;
                    }

                  }

                  mandatory true ;
                }

                leaf pir-unit {
                  description 'Set pir unit, such as kbps, mbps, gbps.' ;
                  type qos-rate-unit-type ;

                }

                leaf pbs {
                  description 'Configure the PBS(Peak Burst Size) size in bytes.' ;
                  type uint32 {
                    range 0..4294967294 {
                      description 'The PBS(Peak Burst Size) size in KB.' ;
                    }

                  }

                  units byte ;
                }

              }

              case unit-percentage {
                description 'Configure the percentage style.' ;
                leaf cir-percentage {
                  description 'Configure the CIR(Committed Information Rate) percentage (Set the accuracy rate per hundred (1%)).' ;
                  type uint32 {
                    range 1..100 {
                      description 'The CIR percentage, support <1-100>' ;
                    }

                  }

                  mandatory true ;
                }

                leaf pir-percentage {
                  description 'Configure the PIR(Peak Information Rate) percentage (Set the accuracy rate per hundred (1%)).' ;
                  type uint32 {
                    range 1..100 {
                      description 'The PIR percentage, support <1-100>' ;
                    }

                  }

                  mandatory true ;
                }

                ncd:revise-date 2020-12-23 ;
              }

            }

            choice buket-value-percent {
              if-feature car-buket-value-percent ;

              description 'Configure CIR, CBS, PIR and PBS.' ;
              mandatory true ;
              case buket-value {
                description 'Configure CIR, CBS, PIR and PBS in numerical form.' ;
                container c-buket {
                  description 'Configure C-buket related parameters.' ;
                  container cir-value {
                    description 'Configure the CIR(Committed Information Rate).' ;
                    leaf cir {
                      description 'Configure the CIR(Committed Information Rate) value (default: kilobits per second).' ;
                      type uint32 {
                        range "0|8..4294967295" {
                          description 'The CIR value (default: kilobits per second).' ;
                        }

                      }

                      mandatory true ;
                    }

                    leaf cir-unit {
                      description 'Set cir unit, such as kbps, mbps, gbps, pps.' ;
                      type qos-rate-unit-type-ex ;

                    }

                  }

                  container cbs-value {
                    description 'Configure the CBS(Committed Burst Size).' ;
                    presence cbs ;
                    leaf cbs {
                      description 'Configure the CBS(Committed Burst Size) value in bytes.' ;
                      type uint32 {
                        range 1..4294967295 {
                          description 'The CBS(Committed Burst Size) size in bytes, support <1-4294967295>' ;
                        }

                      }

                      units byte ;
                      mandatory true ;
                    }

                  }

                }

                container p-buket {
                  description 'Configure P-buket related parameters.' ;
                  presence p-buket ;
                  container pir-value {
                    description 'Configure the PIR(Peak Information Rate).' ;
                    leaf pir {
                      description 'Configure the PIR(Peak Information Rate) value (default: kilobits per second).' ;
                      type uint32 {
                        range 8..4294967295 {
                          description 'The PIR(Peak Information Rate) value (default: kilobits per second), support <8-4294967295>' ;
                        }

                      }

                      mandatory true ;
                    }

                    leaf pir-unit {
                      description 'Set pir unit, such as kbps, mbps, gbps, pps.' ;
                      type qos-rate-unit-type-ex ;

                    }

                  }

                  container pbs-value {
                    description 'Configure the PBS(Peak Burst Size).' ;
                    presence pbs ;
                    leaf pbs {
                      description 'Configure the PBS(Peak Burst Size) value in bytes.' ;
                      type uint32 {
                        range 1..4294967295 {
                          description 'The PBS(Peak Burst Size) size in bytes, support <1-4294967295>' ;
                        }

                      }

                      units byte ;
                      mandatory true ;
                    }

                  }

                }

              }

              case buket-percent {
                description 'Configure CIR and PIR in percentage.' ;
                container cir-percent {
                  description 'Configure CIR in percentage.' ;
                  leaf cir-percent {
                    description 'Configure CIR in percentage.' ;
                    type uint32 {
                      range 1..100 ;

                    }

                    mandatory true ;
                  }

                }

                container pir-percent {
                  description 'Configure PIR in percentage.' ;
                  presence pir ;
                  leaf pir-percent {
                    description 'Configure PIR in percentage.' ;
                    type uint32 {
                      range 1..100 ;

                    }

                    mandatory true ;
                  }

                }

              }

              ncd:revise-date 2021-01-25 ;
            }

            leaf statistical-share {
              description 'The flag of statistical-share.' ;
              type boolean ;

              default false ;
            }

            leaf token-bucket-id {
              description 'Set token bucket id.' ;
              type uint32 {
                range 1..4294967295 {
                  description 'Token bucket id' ;
                }

              }

              ncd:revise-date 2019-10-28 ;
            }

            container mode {
              if-feature qos-car-mode ;

              description 'Set color mode.' ;
              presence "Configure mode information" ;
              leaf mode-type {
                description 'Set color mode type.' ;
                type enumeration {
                  enum blind {
                    value 1 ;
                    description 'Color-Blind mode' ;
                  }

                  enum aware {
                    value 2 ;
                    description 'Color-Aware mode' ;
                  }

                }

                mandatory true ;
              }

            }

            container conform-action {
              description 'Action to packets that conform to the rate limit.' ;
              choice action {
                description 'Specify action to packets that conform to the rate limit.' ;
                mandatory true ;
                case ca-drop {
                  description 'Drop packet.' ;
                  leaf drop {
                    description 'Drop packet.' ;
                    type empty ;

                    mandatory true ;
                  }

                }

                case ca-transmit {
                  description 'Transmit packet.' ;
                  leaf transmit {
                    description 'Transmit packet.' ;
                    type empty ;

                    mandatory true ;
                  }

                }

                case ca-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case ca-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 {
                          description 'The IP-Precedence value, support <0-7>' ;
                        }

                      }

                      mandatory true ;
                    }

                  }

                }

                case ca-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case ca-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case ca-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case ca-service-class {
                  description 'Rewrite packet service class and transmit the packet.' ;
                  container set-service-class-transmit {
                    description 'Rewrite packet service-class and transmit it.' ;
                    leaf service-class-value {
                      description 'Reset service class.' ;
                      type qos-service-class ;

                      mandatory true ;
                    }

                  }

                  ncd:revise-date 2020-05-18 ;
                }

              }

            }

            container exceed-action {
              description 'Action to packets that exceed the rate limit.' ;
              choice action {
                description 'Specify action to packets that exceed the rate limit.' ;
                mandatory true ;
                case ea-drop {
                  description 'Drop packet.' ;
                  leaf drop {
                    description 'Drop packet.' ;
                    type empty ;

                    mandatory true ;
                  }

                }

                case ea-transmit {
                  description 'Transmit packet.' ;
                  leaf transmit {
                    description 'Transmit packet.' ;
                    type empty ;

                    mandatory true ;
                  }

                }

                case ea-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position,.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case ea-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 {
                          description 'The IP-Precedence value, support <0-7>' ;
                        }

                      }

                      mandatory true ;
                    }

                  }

                }

                case ea-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case ea-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case ea-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case ea-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container violate-action {
              description 'Action to packets that violate the rate limit.' ;
              choice action {
                description 'Specify action to packets that violate the rate limit.' ;
                mandatory true ;
                case va-drop {
                  description 'Drop packet.' ;
                  leaf drop {
                    description 'Drop packet.' ;
                    type empty ;

                    mandatory true ;
                  }

                }

                case va-transmit {
                  description 'Transmit packet.' ;
                  leaf transmit {
                    description 'Transmit packet.' ;
                    type empty ;

                    mandatory true ;
                  }

                }

                case va-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case va-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 ;

                      }

                      mandatory true ;
                    }

                  }

                }

                case va-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case va-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case va-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case va-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container coupling-flag {
              description 'The Coupling Flag indicates whether tokens that would overflow the C-bucket should be added to the E-bucket.' ;
              presence "Configure coupling flag information" ;
              leaf cf-value {
                description 'Configure coupling-flag value.' ;
                type uint8 {
                  range 0..1 ;

                }

              }

              if-feature qos-car-cf ;

              ncd:revise-date 2023-09-12 ;
            }

            container adjust {
              description 'Configure QoS accuracy adjustment values.' ;
              presence "Configure adjust information" ;
              leaf adjust-value {
                description 'Configure QoS accuracy adjustment values.' ;
                type int32 {
                  range -32..31 ;

                }

              }

              if-feature qos-car-adjust ;

              ncd:revise-date 2023-09-12 ;
            }

          }

        }

        container unknown-unicasts {
          description 'Match unknown unicast.' ;
          list unknown-unicast {
            description 'Configure interface rate limit based on matching unknown unicast.' ;
            key 'if-name if-direct' ;
            leaf if-name {
              description 'Configure the name of the attaching interface.' ;
              type ncd:ifname {
                length 1..31 {
                  description 'Name of the attaching interface, support 1-31 characters' ;
                }

              }

            }

            leaf if-direct {
              description 'Specify the direction of interface.' ;
              type enumeration {
                enum input {
                  value 1 ;
                  description 'Rate limit on input' ;
                }

                enum output {
                  value 2 ;
                  description 'Rate limit on output' ;
                }

              }

            }

            leaf rate-limit-desc {
              description 'Description of rate limit, support 1-79 characters.' ;
              type ncd:string-with-blank {
                length 1..79 {
                  description 'Description of rate limit, support 1-79 characters.' ;
                }

              }

              ncd:revise-date 2020-06-18 ;
            }

            choice unit-style {
              description "Specify unit's style." ;
              mandatory true ;
              case unit-value {
                description 'Configure the value style.' ;
                leaf cir {
                  description 'Configure the CIR(Committed Information Rate) value (default: kilobits per second).' ;
                  type uint32 {
                    range 0..4294967295 {
                      description 'The CIR value (default: kilobits per second).' ;
                    }

                  }

                  mandatory true ;
                }

                leaf cir-unit {
                  description 'Set cir unit, such as kbps, mbps, gbps.' ;
                  type qos-rate-unit-type ;

                }

                leaf cbs {
                  description 'Configure the CBS(Committed Burst Size) size in bytes.' ;
                  type uint32 {
                    range 0..4294967294 {
                      description 'The CBS(Committed Burst Size) size in bytes.' ;
                    }

                  }

                  units byte ;
                }

                leaf pir {
                  description 'Configure the PIR(Peak Information Rate) value (default: kilobits per second).' ;
                  type uint32 {
                    range 0..4294967295 {
                      description 'The PIR(Peak Information Rate) value (default: kilobits per second).' ;
                    }

                  }

                  mandatory true ;
                }

                leaf pir-unit {
                  description 'Set pir unit, such as kbps, mbps, gbps.' ;
                  type qos-rate-unit-type ;

                }

                leaf pbs {
                  description 'Configure the PBS(Peak Burst Size) size in bytes.' ;
                  type uint32 {
                    range 0..4294967294 {
                      description 'The PBS(Peak Burst Size) size in KB.' ;
                    }

                  }

                  units byte ;
                }

              }

              case unit-percentage {
                description 'Configure the percentage style.' ;
                leaf cir-percentage {
                  description 'Configure the CIR(Committed Information Rate) percentage (Set the accuracy rate per hundred (1%)).' ;
                  type uint32 {
                    range 1..100 {
                      description 'The CIR percentage, support <1-100>' ;
                    }

                  }

                  mandatory true ;
                }

                leaf pir-percentage {
                  description 'Configure the PIR(Peak Information Rate) percentage (Set the accuracy rate per hundred (1%)).' ;
                  type uint32 {
                    range 1..100 {
                      description 'The PIR percentage, support <1-100>' ;
                    }

                  }

                  mandatory true ;
                }

                ncd:revise-date 2020-12-23 ;
              }

            }

            choice buket-value-percent {
              if-feature car-buket-value-percent ;

              description 'Configure CIR, CBS, PIR and PBS.' ;
              mandatory true ;
              case buket-value {
                description 'Configure CIR, CBS, PIR and PBS in numerical form.' ;
                container c-buket {
                  description 'Configure C-buket related parameters.' ;
                  container cir-value {
                    description 'Configure the CIR(Committed Information Rate).' ;
                    leaf cir {
                      description 'Configure the CIR(Committed Information Rate) value (default: kilobits per second).' ;
                      type uint32 {
                        range "0|8..4294967295" {
                          description 'The CIR value (default: kilobits per second).' ;
                        }

                      }

                      mandatory true ;
                    }

                    leaf cir-unit {
                      description 'Set cir unit, such as kbps, mbps, gbps, pps.' ;
                      type qos-rate-unit-type-ex ;

                    }

                  }

                  container cbs-value {
                    description 'Configure the CBS(Committed Burst Size).' ;
                    presence cbs ;
                    leaf cbs {
                      description 'Configure the CBS(Committed Burst Size) value in bytes.' ;
                      type uint32 {
                        range 1..4294967295 {
                          description 'The CBS(Committed Burst Size) size in bytes, support <1-4294967295>' ;
                        }

                      }

                      units byte ;
                      mandatory true ;
                    }

                  }

                }

                container p-buket {
                  description 'Configure P-buket related parameters.' ;
                  presence p-buket ;
                  container pir-value {
                    description 'Configure the PIR(Peak Information Rate).' ;
                    leaf pir {
                      description 'Configure the PIR(Peak Information Rate) value (default: kilobits per second).' ;
                      type uint32 {
                        range 8..4294967295 {
                          description 'The PIR(Peak Information Rate) value (default: kilobits per second), support <8-4294967295>' ;
                        }

                      }

                      mandatory true ;
                    }

                    leaf pir-unit {
                      description 'Set pir unit, such as kbps, mbps, gbps, pps.' ;
                      type qos-rate-unit-type-ex ;

                    }

                  }

                  container pbs-value {
                    description 'Configure the PBS(Peak Burst Size).' ;
                    presence pbs ;
                    leaf pbs {
                      description 'Configure the PBS(Peak Burst Size) value in bytes.' ;
                      type uint32 {
                        range 1..4294967295 {
                          description 'The PBS(Peak Burst Size) size in bytes, support <1-4294967295>' ;
                        }

                      }

                      units byte ;
                      mandatory true ;
                    }

                  }

                }

              }

              case buket-percent {
                description 'Configure CIR and PIR in percentage.' ;
                container cir-percent {
                  description 'Configure CIR in percentage.' ;
                  leaf cir-percent {
                    description 'Configure CIR in percentage.' ;
                    type uint32 {
                      range 1..100 ;

                    }

                    mandatory true ;
                  }

                }

                container pir-percent {
                  description 'Configure PIR in percentage.' ;
                  presence pir ;
                  leaf pir-percent {
                    description 'Configure PIR in percentage.' ;
                    type uint32 {
                      range 1..100 ;

                    }

                    mandatory true ;
                  }

                }

              }

              ncd:revise-date 2021-01-25 ;
            }

            leaf statistical-share {
              description 'The flag of statistical-share.' ;
              type boolean ;

              default false ;
            }

            leaf token-bucket-id {
              description 'Set token bucket id.' ;
              type uint32 {
                range 1..4294967295 {
                  description 'Token bucket id' ;
                }

              }

              ncd:revise-date 2019-10-28 ;
            }

            container mode {
              if-feature qos-car-mode ;

              description 'Set color mode.' ;
              presence "Configure mode information" ;
              leaf mode-type {
                description 'Set color mode type.' ;
                type enumeration {
                  enum blind {
                    value 1 ;
                    description 'Color-Blind mode' ;
                  }

                  enum aware {
                    value 2 ;
                    description 'Color-Aware mode' ;
                  }

                }

                mandatory true ;
              }

            }

            container conform-action {
              description 'Action to packets that conform to the rate limit.' ;
              choice action {
                description 'Specify action to packets that conform to the rate limit.' ;
                mandatory true ;
                case ca-drop {
                  description 'Drop packet.' ;
                  leaf drop {
                    description 'Drop packet.' ;
                    type empty ;

                    mandatory true ;
                  }

                }

                case ca-transmit {
                  description 'Transmit packet.' ;
                  leaf transmit {
                    description 'Transmit packet.' ;
                    type empty ;

                    mandatory true ;
                  }

                }

                case ca-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case ca-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 {
                          description 'The IP-Precedence value, support <0-7>' ;
                        }

                      }

                      mandatory true ;
                    }

                  }

                }

                case ca-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case ca-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case ca-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case ca-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container exceed-action {
              description 'Action to packets that exceed the rate limit.' ;
              choice action {
                description 'Specify action to packets that exceed the rate limit.' ;
                mandatory true ;
                case ea-drop {
                  description 'Drop packet.' ;
                  leaf drop {
                    description 'Drop packet.' ;
                    type empty ;

                    mandatory true ;
                  }

                }

                case ea-transmit {
                  description 'Transmit packet.' ;
                  leaf transmit {
                    description 'Transmit packet.' ;
                    type empty ;

                    mandatory true ;
                  }

                }

                case ea-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case ea-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 {
                          description 'The IP-Precedence value, support <0-7>' ;
                        }

                      }

                      mandatory true ;
                    }

                  }

                }

                case ea-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case ea-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case ea-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case ea-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container violate-action {
              description 'Action to packets that violate the rate limit.' ;
              choice action {
                description 'Specify action to packets that violate the rate limit.' ;
                mandatory true ;
                case va-drop {
                  description 'Drop packet.' ;
                  leaf drop {
                    description 'Drop packet.' ;
                    type empty ;

                    mandatory true ;
                  }

                }

                case va-transmit {
                  description 'Transmit packet.' ;
                  leaf transmit {
                    description 'Transmit packet.' ;
                    type empty ;

                    mandatory true ;
                  }

                }

                case va-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case va-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 ;

                      }

                      mandatory true ;
                    }

                  }

                }

                case va-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case va-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case va-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case va-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container coupling-flag {
              description 'The Coupling Flag indicates whether tokens that would overflow the C-bucket should be added to the E-bucket.' ;
              presence "Configure coupling flag information" ;
              leaf cf-value {
                description 'Configure coupling-flag value.' ;
                type uint8 {
                  range 0..1 ;

                }

              }

              if-feature qos-car-cf ;

              ncd:revise-date 2023-09-12 ;
            }

            container adjust {
              description 'Configure QoS accuracy adjustment values.' ;
              presence "Configure adjust information" ;
              leaf adjust-value {
                description 'Configure QoS accuracy adjustment values.' ;
                type int32 {
                  range -32..31 ;

                }

              }

              if-feature qos-car-adjust ;

              ncd:revise-date 2023-09-12 ;
            }

          }

          ncd:revise-date 2015-10-28 ;
        }

        container multicasts {
          description 'Match multicast.' ;
          list multicast {
            description 'Configure interface rate limit based on matching multicast.' ;
            key 'if-name if-direct' ;
            leaf if-name {
              description 'Configure the name of the attaching interface.' ;
              type ncd:ifname {
                length 1..31 {
                  description 'Name of the attaching interface, support 1-31 characters' ;
                }

              }

            }

            leaf if-direct {
              description 'Specify the direction of interface.' ;
              type enumeration {
                enum input {
                  value 1 ;
                  description 'Rate limit on input' ;
                }

                enum output {
                  value 2 ;
                  description 'Rate limit on output' ;
                }

              }

            }

            leaf rate-limit-desc {
              description 'Description of rate limit, support 1-79 characters.' ;
              type ncd:string-with-blank {
                length 1..79 {
                  description 'Description of rate limit, support 1-79 characters.' ;
                }

              }

              ncd:revise-date 2020-06-18 ;
            }

            choice unit-style {
              description "Specify unit's style." ;
              mandatory true ;
              case unit-value {
                description 'Configure the value style.' ;
                leaf cir {
                  description 'Configure the CIR(Committed Information Rate) value (default: kilobits per second).' ;
                  type uint32 {
                    range 0..4294967295 {
                      description 'The CIR value (default: kilobits per second).' ;
                    }

                  }

                  mandatory true ;
                }

                leaf cir-unit {
                  description 'Set cir unit, such as kbps, mbps, gbps.' ;
                  type qos-rate-unit-type ;

                }

                leaf cbs {
                  description 'Configure the CBS(Committed Burst Size) size in bytes.' ;
                  type uint32 {
                    range 0..4294967294 {
                      description 'The CBS(Committed Burst Size) size in bytes.' ;
                    }

                  }

                  units byte ;
                }

                leaf pir {
                  description 'Configure the PIR(Peak Information Rate) value (default: kilobits per second).' ;
                  type uint32 {
                    range 0..4294967295 {
                      description 'The PIR(Peak Information Rate) value (default: kilobits per second).' ;
                    }

                  }

                  mandatory true ;
                }

                leaf pir-unit {
                  description 'Set pir unit, such as kbps, mbps, gbps.' ;
                  type qos-rate-unit-type ;

                }

                leaf pbs {
                  description 'Configure the PBS(Peak Burst Size) size in bytes.' ;
                  type uint32 {
                    range 0..4294967294 {
                      description 'The PBS(Peak Burst Size) size in KB.' ;
                    }

                  }

                  units byte ;
                }

              }

              case unit-percentage {
                description 'Configure the percentage style.' ;
                leaf cir-percentage {
                  description 'Configure the CIR(Committed Information Rate) percentage (Set the accuracy rate per hundred (1%)).' ;
                  type uint32 {
                    range 1..100 {
                      description 'The CIR percentage, support <1-100>' ;
                    }

                  }

                  mandatory true ;
                }

                leaf pir-percentage {
                  description 'Configure the PIR(Peak Information Rate) percentage (Set the accuracy rate per hundred (1%)).' ;
                  type uint32 {
                    range 1..100 {
                      description 'The PIR percentage, support <1-100>' ;
                    }

                  }

                  mandatory true ;
                }

                ncd:revise-date 2020-12-23 ;
              }

            }

            choice buket-value-percent {
              if-feature car-buket-value-percent ;

              description 'Configure CIR, CBS, PIR and PBS.' ;
              mandatory true ;
              case buket-value {
                description 'Configure CIR, CBS, PIR and PBS in numerical form.' ;
                container c-buket {
                  description 'Configure C-buket related parameters.' ;
                  container cir-value {
                    description 'Configure the CIR(Committed Information Rate).' ;
                    leaf cir {
                      description 'Configure the CIR(Committed Information Rate) value (default: kilobits per second).' ;
                      type uint32 {
                        range "0|8..4294967295" {
                          description 'The CIR value (default: kilobits per second).' ;
                        }

                      }

                      mandatory true ;
                    }

                    leaf cir-unit {
                      description 'Set cir unit, such as kbps, mbps, gbps, pps.' ;
                      type qos-rate-unit-type-ex ;

                    }

                  }

                  container cbs-value {
                    description 'Configure the CBS(Committed Burst Size).' ;
                    presence cbs ;
                    leaf cbs {
                      description 'Configure the CBS(Committed Burst Size) value in bytes.' ;
                      type uint32 {
                        range 1..4294967295 {
                          description 'The CBS(Committed Burst Size) size in bytes, support <1-4294967295>' ;
                        }

                      }

                      units byte ;
                      mandatory true ;
                    }

                  }

                }

                container p-buket {
                  description 'Configure P-buket related parameters.' ;
                  presence p-buket ;
                  container pir-value {
                    description 'Configure the PIR(Peak Information Rate).' ;
                    leaf pir {
                      description 'Configure the PIR(Peak Information Rate) value (default: kilobits per second).' ;
                      type uint32 {
                        range 8..4294967295 {
                          description 'The PIR(Peak Information Rate) value (default: kilobits per second), support <8-4294967295>' ;
                        }

                      }

                      mandatory true ;
                    }

                    leaf pir-unit {
                      description 'Set pir unit, such as kbps, mbps, gbps, pps.' ;
                      type qos-rate-unit-type-ex ;

                    }

                  }

                  container pbs-value {
                    description 'Configure the PBS(Peak Burst Size).' ;
                    presence pbs ;
                    leaf pbs {
                      description 'Configure the PBS(Peak Burst Size) value in bytes.' ;
                      type uint32 {
                        range 1..4294967295 {
                          description 'The PBS(Peak Burst Size) size in bytes, support <1-4294967295>' ;
                        }

                      }

                      units byte ;
                      mandatory true ;
                    }

                  }

                }

              }

              case buket-percent {
                description 'Configure CIR and PIR in percentage.' ;
                container cir-percent {
                  description 'Configure CIR in percentage.' ;
                  leaf cir-percent {
                    description 'Configure CIR in percentage.' ;
                    type uint32 {
                      range 1..100 ;

                    }

                    mandatory true ;
                  }

                }

                container pir-percent {
                  description 'Configure PIR in percentage.' ;
                  presence pir ;
                  leaf pir-percent {
                    description 'Configure PIR in percentage.' ;
                    type uint32 {
                      range 1..100 ;

                    }

                    mandatory true ;
                  }

                }

              }

              ncd:revise-date 2021-01-25 ;
            }

            leaf statistical-share {
              description 'The flag of statistical-share.' ;
              type boolean ;

              default false ;
            }

            leaf token-bucket-id {
              description 'Set token bucket id.' ;
              type uint32 {
                range 1..4294967295 {
                  description 'Token bucket id' ;
                }

              }

              ncd:revise-date 2019-10-28 ;
            }

            container mode {
              if-feature qos-car-mode ;

              description 'Set color mode.' ;
              presence "Configure mode information" ;
              leaf mode-type {
                description 'Set color mode type.' ;
                type enumeration {
                  enum blind {
                    value 1 ;
                    description 'Color-Blind mode' ;
                  }

                  enum aware {
                    value 2 ;
                    description 'Color-Aware mode' ;
                  }

                }

                mandatory true ;
              }

            }

            container conform-action {
              description 'Action to packets that conform to the rate limit.' ;
              choice action {
                description 'Specify action to packets that conform to the rate limit.' ;
                mandatory true ;
                case ca-drop {
                  description 'Drop packet.' ;
                  leaf drop {
                    description 'Drop packet.' ;
                    type empty ;

                    mandatory true ;
                  }

                }

                case ca-transmit {
                  description 'Transmit packet.' ;
                  leaf transmit {
                    description 'Transmit packet.' ;
                    type empty ;

                    mandatory true ;
                  }

                }

                case ca-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case ca-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 {
                          description 'The IP-Precedence value, support <0-7>' ;
                        }

                      }

                      mandatory true ;
                    }

                  }

                }

                case ca-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case ca-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case ca-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case ca-service-class {
                  description 'Rewrite packet service class and transmit the packet.' ;
                  container set-service-class-transmit {
                    description 'Rewrite packet service class and transmit it.' ;
                    leaf service-class-value {
                      description 'Reset service-class.' ;
                      type qos-service-class ;

                      mandatory true ;
                    }

                  }

                  ncd:revise-date 2020-05-18 ;
                }

              }

            }

            container exceed-action {
              description 'Action to packets that exceed the rate limit.' ;
              choice action {
                description 'Specify action to packets that exceed the rate limit.' ;
                mandatory true ;
                case ea-drop {
                  description 'Drop packet.' ;
                  leaf drop {
                    description 'Drop packet.' ;
                    type empty ;

                    mandatory true ;
                  }

                }

                case ea-transmit {
                  description 'Transmit packet.' ;
                  leaf transmit {
                    description 'Transmit packet.' ;
                    type empty ;

                    mandatory true ;
                  }

                }

                case ea-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case ea-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 {
                          description 'The IP-Precedence value, support <0-7>' ;
                        }

                      }

                      mandatory true ;
                    }

                  }

                }

                case ea-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case ea-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case ea-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case ea-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container violate-action {
              description 'Action to packets that violate the rate limit.' ;
              choice action {
                description 'Specify action to packets that violate the rate limit.' ;
                mandatory true ;
                case va-drop {
                  description 'Drop packet.' ;
                  leaf drop {
                    description 'Drop packet.' ;
                    type empty ;

                    mandatory true ;
                  }

                }

                case va-transmit {
                  description 'Transmit packet.' ;
                  leaf transmit {
                    description 'Transmit packet.' ;
                    type empty ;

                    mandatory true ;
                  }

                }

                case va-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case va-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 ;

                      }

                      mandatory true ;
                    }

                  }

                }

                case va-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case va-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case va-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case va-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container coupling-flag {
              description 'The Coupling Flag indicates whether tokens that would overflow the C-bucket should be added to the E-bucket.' ;
              presence "Configure coupling flag information" ;
              leaf cf-value {
                description 'Configure coupling-flag value.' ;
                type uint8 {
                  range 0..1 ;

                }

              }

              if-feature qos-car-cf ;

              ncd:revise-date 2023-09-12 ;
            }

            container adjust {
              description 'Configure QoS accuracy adjustment values.' ;
              presence "Configure adjust information" ;
              leaf adjust-value {
                description 'Configure QoS accuracy adjustment values.' ;
                type int32 {
                  range -32..31 ;

                }

              }

              if-feature qos-car-adjust ;

              ncd:revise-date 2023-09-12 ;
            }

          }

        }

        container unknown-multicasts {
          description 'Match unknown multicast.' ;
          list unknown-multicast {
            description 'Configure interface rate limit based on matching unknown multicast.' ;
            key 'if-name if-direct' ;
            leaf if-name {
              description 'Configure the name of the attaching interface.' ;
              type ncd:ifname {
                length 1..31 {
                  description 'Name of the attaching interface, support 1-31 characters' ;
                }

              }

            }

            leaf if-direct {
              description 'Specify the direction of interface.' ;
              type enumeration {
                enum input {
                  value 1 ;
                  description 'Rate limit on input' ;
                }

                enum output {
                  value 2 ;
                  description 'Rate limit on output' ;
                }

              }

            }

            leaf rate-limit-desc {
              description 'Description of rate limit, support 1-79 characters.' ;
              type ncd:string-with-blank {
                length 1..79 {
                  description 'Description of rate limit, support 1-79 characters.' ;
                }

              }

              ncd:revise-date 2020-06-18 ;
            }

            choice unit-style {
              description "Specify unit's style." ;
              mandatory true ;
              case unit-value {
                description 'Configure the value style.' ;
                leaf cir {
                  description 'Configure the CIR(Committed Information Rate) value (default: kilobits per second).' ;
                  type uint32 {
                    range 0..4294967295 {
                      description 'The CIR value (default: kilobits per second).' ;
                    }

                  }

                  mandatory true ;
                }

                leaf cir-unit {
                  description 'Set cir unit, such as kbps, mbps, gbps.' ;
                  type qos-rate-unit-type ;

                }

                leaf cbs {
                  description 'Configure the CBS(Committed Burst Size) size in bytes.' ;
                  type uint32 {
                    range 0..4294967294 {
                      description 'The CBS(Committed Burst Size) size in bytes.' ;
                    }

                  }

                  units byte ;
                }

                leaf pir {
                  description 'Configure the PIR(Peak Information Rate) value (default: kilobits per second).' ;
                  type uint32 {
                    range 0..4294967295 {
                      description 'The PIR(Peak Information Rate) value (default: kilobits per second).' ;
                    }

                  }

                  mandatory true ;
                }

                leaf pir-unit {
                  description 'Set pir unit, such as kbps, mbps, gbps.' ;
                  type qos-rate-unit-type ;

                }

                leaf pbs {
                  description 'Configure the PBS(Peak Burst Size) size in bytes.' ;
                  type uint32 {
                    range 0..4294967294 {
                      description 'The PBS(Peak Burst Size) size in KB.' ;
                    }

                  }

                  units byte ;
                }

              }

              case unit-percentage {
                description 'Configure the percentage style.' ;
                leaf cir-percentage {
                  description 'Configure the CIR(Committed Information Rate) percentage (Set the accuracy rate per hundred (1%)).' ;
                  type uint32 {
                    range 1..100 {
                      description 'The CIR percentage, support <1-100>' ;
                    }

                  }

                  mandatory true ;
                }

                leaf pir-percentage {
                  description 'Configure the PIR(Peak Information Rate) percentage (Set the accuracy rate per hundred (1%)).' ;
                  type uint32 {
                    range 1..100 {
                      description 'The PIR percentage, support <1-100>' ;
                    }

                  }

                  mandatory true ;
                }

                ncd:revise-date 2020-12-23 ;
              }

            }

            choice buket-value-percent {
              if-feature car-buket-value-percent ;

              description 'Configure CIR, CBS, PIR and PBS.' ;
              mandatory true ;
              case buket-value {
                description 'Configure CIR, CBS, PIR and PBS in numerical form.' ;
                container c-buket {
                  description 'Configure C-buket related parameters.' ;
                  container cir-value {
                    description 'Configure the CIR(Committed Information Rate).' ;
                    leaf cir {
                      description 'Configure the CIR(Committed Information Rate) value (default: kilobits per second).' ;
                      type uint32 {
                        range "0|8..4294967295" {
                          description 'The CIR value (default: kilobits per second).' ;
                        }

                      }

                      mandatory true ;
                    }

                    leaf cir-unit {
                      description 'Set cir unit, such as kbps, mbps, gbps, pps.' ;
                      type qos-rate-unit-type-ex ;

                    }

                  }

                  container cbs-value {
                    description 'Configure the CBS(Committed Burst Size).' ;
                    presence cbs ;
                    leaf cbs {
                      description 'Configure the CBS(Committed Burst Size) value in bytes.' ;
                      type uint32 {
                        range 1..4294967295 {
                          description 'The CBS(Committed Burst Size) size in bytes, support <1-4294967295>' ;
                        }

                      }

                      units byte ;
                      mandatory true ;
                    }

                  }

                }

                container p-buket {
                  description 'Configure P-buket related parameters.' ;
                  presence p-buket ;
                  container pir-value {
                    description 'Configure the PIR(Peak Information Rate).' ;
                    leaf pir {
                      description 'Configure the PIR(Peak Information Rate) value (default: kilobits per second).' ;
                      type uint32 {
                        range 8..4294967295 {
                          description 'The PIR(Peak Information Rate) value (default: kilobits per second), support <8-4294967295>' ;
                        }

                      }

                      mandatory true ;
                    }

                    leaf pir-unit {
                      description 'Set pir unit, such as kbps, mbps, gbps, pps.' ;
                      type qos-rate-unit-type-ex ;

                    }

                  }

                  container pbs-value {
                    description 'Configure the PBS(Peak Burst Size).' ;
                    presence pbs ;
                    leaf pbs {
                      description 'Configure the PBS(Peak Burst Size) value in bytes.' ;
                      type uint32 {
                        range 1..4294967295 {
                          description 'The PBS(Peak Burst Size) size in bytes, support <1-4294967295>' ;
                        }

                      }

                      units byte ;
                      mandatory true ;
                    }

                  }

                }

              }

              case buket-percent {
                description 'Configure CIR and PIR in percentage.' ;
                container cir-percent {
                  description 'Configure CIR in percentage.' ;
                  leaf cir-percent {
                    description 'Configure CIR in percentage.' ;
                    type uint32 {
                      range 1..100 ;

                    }

                    mandatory true ;
                  }

                }

                container pir-percent {
                  description 'Configure PIR in percentage.' ;
                  presence pir ;
                  leaf pir-percent {
                    description 'Configure PIR in percentage.' ;
                    type uint32 {
                      range 1..100 ;

                    }

                    mandatory true ;
                  }

                }

              }

              ncd:revise-date 2021-01-25 ;
            }

            leaf statistical-share {
              description 'The flag of statistical-share.' ;
              type boolean ;

              default false ;
            }

            leaf token-bucket-id {
              description 'Set token bucket id.' ;
              type uint32 {
                range 1..4294967295 {
                  description 'Token bucket id' ;
                }

              }

              ncd:revise-date 2019-10-28 ;
            }

            container mode {
              if-feature qos-car-mode ;

              description 'Set color mode.' ;
              presence "Configure mode information" ;
              leaf mode-type {
                description 'Set color mode type.' ;
                type enumeration {
                  enum blind {
                    value 1 ;
                    description 'Color-Blind mode' ;
                  }

                  enum aware {
                    value 2 ;
                    description 'Color-Aware mode' ;
                  }

                }

                mandatory true ;
              }

            }

            container conform-action {
              description 'Action to packets that conform to the rate limit.' ;
              choice action {
                description 'Specify action to packets that conform to the rate limit.' ;
                mandatory true ;
                case ca-drop {
                  description 'Drop packet.' ;
                  leaf drop {
                    description 'Drop packet.' ;
                    type empty ;

                    mandatory true ;
                  }

                }

                case ca-transmit {
                  description 'Transmit packet.' ;
                  leaf transmit {
                    description 'Transmit packet.' ;
                    type empty ;

                    mandatory true ;
                  }

                }

                case ca-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case ca-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 {
                          description 'The IP-Precedence value, support <0-7>' ;
                        }

                      }

                      mandatory true ;
                    }

                  }

                }

                case ca-dscpCopy {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                  ncd:revise-date 2020-05-18 ;
                }

                case ca-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case ca-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case ca-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container exceed-action {
              description 'Action to packets that exceed the rate limit.' ;
              choice action {
                description 'Specify action to packets that exceed the rate limit.' ;
                mandatory true ;
                case ea-drop {
                  description 'Drop packet.' ;
                  leaf drop {
                    description 'Drop packet.' ;
                    type empty ;

                    mandatory true ;
                  }

                }

                case ea-transmit {
                  description 'Transmit packet.' ;
                  leaf transmit {
                    description 'Transmit packet.' ;
                    type empty ;

                    mandatory true ;
                  }

                }

                case ea-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case ea-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 {
                          description 'The IP-Precedence value, support <0-7>' ;
                        }

                      }

                      mandatory true ;
                    }

                  }

                }

                case ea-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case ea-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case ea-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case ea-service-class {
                  description 'Rewrite packet DSCP and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container violate-action {
              description 'Action to packets that violate the rate limit.' ;
              choice action {
                description 'Specify action to packets that violate the rate limit.' ;
                mandatory true ;
                case va-drop {
                  description 'Drop packet.' ;
                  leaf drop {
                    description 'Drop packet.' ;
                    type empty ;

                    mandatory true ;
                  }

                }

                case va-transmit {
                  description 'Transmit packet.' ;
                  leaf transmit {
                    description 'Transmit packet.' ;
                    type empty ;

                    mandatory true ;
                  }

                }

                case va-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case va-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 ;

                      }

                      mandatory true ;
                    }

                  }

                }

                case va-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case va-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case va-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case va-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container coupling-flag {
              description 'The Coupling Flag indicates whether tokens that would overflow the C-bucket should be added to the E-bucket.' ;
              presence "Configure coupling flag information" ;
              leaf cf-value {
                description 'Configure coupling-flag value.' ;
                type uint8 {
                  range 0..1 ;

                }

              }

              if-feature qos-car-cf ;

              ncd:revise-date 2023-09-12 ;
            }

            container adjust {
              description 'Configure QoS accuracy adjustment values.' ;
              presence "Configure adjust information" ;
              leaf adjust-value {
                description 'Configure QoS accuracy adjustment values.' ;
                type int32 {
                  range -32..31 ;

                }

              }

              if-feature qos-car-adjust ;

              ncd:revise-date 2023-09-12 ;
            }

          }

          ncd:revise-date 2015-10-28 ;
        }

        container broadcasts {
          description 'Match broadcast.' ;
          list broadcast {
            description 'Configure interface rate limit based on matching broadcast.' ;
            key 'if-name if-direct' ;
            leaf if-name {
              description 'Configure the name of the attaching interface.' ;
              type ncd:ifname {
                length 1..31 {
                  description 'Name of the attaching interface, support 1-31 characters' ;
                }

              }

            }

            leaf if-direct {
              description 'Specify the direction of interface.' ;
              type enumeration {
                enum input {
                  value 1 ;
                  description 'Rate limit on input' ;
                }

                enum output {
                  value 2 ;
                  description 'Rate limit on output' ;
                }

              }

            }

            leaf rate-limit-desc {
              description 'Description of rate limit, support 1-79 characters.' ;
              type ncd:string-with-blank {
                length 1..79 {
                  description 'Description of rate limit, support 1-79 characters.' ;
                }

              }

              ncd:revise-date 2020-06-18 ;
            }

            choice unit-style {
              description "Specify unit's style." ;
              mandatory true ;
              case unit-value {
                description 'Configure the value style.' ;
                leaf cir {
                  description 'Configure the CIR(Committed Information Rate) value (default: kilobits per second).' ;
                  type uint32 {
                    range 0..4294967295 {
                      description 'The CIR value (default: kilobits per second).' ;
                    }

                  }

                  mandatory true ;
                }

                leaf cir-unit {
                  description 'Set cir unit, such as kbps, mbps, gbps.' ;
                  type qos-rate-unit-type ;

                }

                leaf cbs {
                  description 'Configure the CBS(Committed Burst Size) size in bytes.' ;
                  type uint32 {
                    range 0..4294967294 {
                      description 'The CBS(Committed Burst Size) size in bytes.' ;
                    }

                  }

                  units byte ;
                }

                leaf pir {
                  description 'Configure the PIR(Peak Information Rate) value (default: kilobits per second).' ;
                  type uint32 {
                    range 0..4294967295 {
                      description 'The PIR(Peak Information Rate) value (default: kilobits per second).' ;
                    }

                  }

                  mandatory true ;
                }

                leaf pir-unit {
                  description 'Set pir unit, such as kbps, mbps, gbps.' ;
                  type qos-rate-unit-type ;

                }

                leaf pbs {
                  description 'Configure the PBS(Peak Burst Size) size in bytes.' ;
                  type uint32 {
                    range 0..4294967294 {
                      description 'The PBS(Peak Burst Size) size in KB.' ;
                    }

                  }

                  units byte ;
                }

              }

              case unit-percentage {
                description 'Configure the percentage style.' ;
                leaf cir-percentage {
                  description 'Configure the CIR(Committed Information Rate) percentage (Set the accuracy rate per hundred (1%)).' ;
                  type uint32 {
                    range 1..100 {
                      description 'The CIR percentage, support <1-100>' ;
                    }

                  }

                  mandatory true ;
                }

                leaf pir-percentage {
                  description 'Configure the PIR(Peak Information Rate) percentage (Set the accuracy rate per hundred (1%)).' ;
                  type uint32 {
                    range 1..100 {
                      description 'The PIR percentage, support <1-100>' ;
                    }

                  }

                  mandatory true ;
                }

                ncd:revise-date 2020-12-23 ;
              }

            }

            choice buket-value-percent {
              if-feature car-buket-value-percent ;

              description 'Configure CIR, CBS, PIR and PBS.' ;
              mandatory true ;
              case buket-value {
                description 'Configure CIR, CBS, PIR and PBS in numerical form.' ;
                container c-buket {
                  description 'Configure C-buket related parameters.' ;
                  container cir-value {
                    description 'Configure the CIR(Committed Information Rate).' ;
                    leaf cir {
                      description 'Configure the CIR(Committed Information Rate) value (default: kilobits per second).' ;
                      type uint32 {
                        range "0|8..4294967295" {
                          description 'The CIR value (default: kilobits per second).' ;
                        }

                      }

                      mandatory true ;
                    }

                    leaf cir-unit {
                      description 'Set cir unit, such as kbps, mbps, gbps, pps.' ;
                      type qos-rate-unit-type-ex ;

                    }

                  }

                  container cbs-value {
                    description 'Configure the CBS(Committed Burst Size).' ;
                    presence cbs ;
                    leaf cbs {
                      description 'Configure the CBS(Committed Burst Size) value in bytes.' ;
                      type uint32 {
                        range 1..4294967295 {
                          description 'The CBS(Committed Burst Size) size in bytes, support <1-4294967295>' ;
                        }

                      }

                      units byte ;
                      mandatory true ;
                    }

                  }

                }

                container p-buket {
                  description 'Configure P-buket related parameters.' ;
                  presence p-buket ;
                  container pir-value {
                    description 'Configure the PIR(Peak Information Rate).' ;
                    leaf pir {
                      description 'Configure the PIR(Peak Information Rate) value (default: kilobits per second).' ;
                      type uint32 {
                        range 8..4294967295 {
                          description 'The PIR(Peak Information Rate) value (default: kilobits per second), support <8-4294967295>' ;
                        }

                      }

                      mandatory true ;
                    }

                    leaf pir-unit {
                      description 'Set pir unit, such as kbps, mbps, gbps, pps.' ;
                      type qos-rate-unit-type-ex ;

                    }

                  }

                  container pbs-value {
                    description 'Configure the PBS(Peak Burst Size).' ;
                    presence pbs ;
                    leaf pbs {
                      description 'Configure the PBS(Peak Burst Size) value in bytes.' ;
                      type uint32 {
                        range 1..4294967295 {
                          description 'The PBS(Peak Burst Size) size in bytes, support <1-4294967295>' ;
                        }

                      }

                      units byte ;
                      mandatory true ;
                    }

                  }

                }

              }

              case buket-percent {
                description 'Configure CIR and PIR in percentage.' ;
                container cir-percent {
                  description 'Configure CIR in percentage.' ;
                  leaf cir-percent {
                    description 'Configure CIR in percentage.' ;
                    type uint32 {
                      range 1..100 ;

                    }

                    mandatory true ;
                  }

                }

                container pir-percent {
                  description 'Configure PIR in percentage.' ;
                  presence pir ;
                  leaf pir-percent {
                    description 'Configure PIR in percentage.' ;
                    type uint32 {
                      range 1..100 ;

                    }

                    mandatory true ;
                  }

                }

              }

              ncd:revise-date 2021-01-25 ;
            }

            leaf statistical-share {
              description 'The flag of statistical-share.' ;
              type boolean ;

              default false ;
            }

            leaf token-bucket-id {
              description 'Set token bucket id.' ;
              type uint32 {
                range 1..4294967295 {
                  description 'Token bucket id' ;
                }

              }

              ncd:revise-date 2019-10-28 ;
            }

            container mode {
              if-feature qos-car-mode ;

              description 'Set color mode.' ;
              presence "Configure mode information" ;
              leaf mode-type {
                description 'Set color mode type.' ;
                type enumeration {
                  enum blind {
                    value 1 ;
                    description 'Color-Blind mode' ;
                  }

                  enum aware {
                    value 2 ;
                    description 'Color-Aware mode' ;
                  }

                }

                mandatory true ;
              }

            }

            container conform-action {
              description 'Action to packets that conform to the rate limit.' ;
              choice action {
                description 'Specify action to packets that conform to the rate limit.' ;
                mandatory true ;
                case ca-drop {
                  description 'Drop packet.' ;
                  leaf drop {
                    description 'Drop packet.' ;
                    type empty ;

                    mandatory true ;
                  }

                }

                case ca-transmit {
                  description 'Transmit packet.' ;
                  leaf transmit {
                    description 'Transmit packet.' ;
                    type empty ;

                    mandatory true ;
                  }

                }

                case ca-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case ca-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 {
                          description 'The IP-Precedence value, support <0-7>' ;
                        }

                      }

                      mandatory true ;
                    }

                  }

                }

                case ca-dscp {
                  description 'Rewrite packet DSCP and transmit the packet.' ;
                  container set-dscp-transmit {
                    description 'Rewrite packet DSCP and transmit it.' ;
                    leaf dscp-value {
                      description 'Reset DSCP in conform-action, support <0-63>.' ;
                      type uint8 {
                        range 0..63 {
                          description 'The DSCP value, support <0-63>' ;
                        }

                      }

                      mandatory true ;
                    }

                  }

                }

                case ca-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case ca-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case ca-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container exceed-action {
              description 'Action to packets that exceed the rate limit.' ;
              choice action {
                description 'Specify action to packets that exceed the rate limit.' ;
                mandatory true ;
                case ea-drop {
                  description 'Drop packet.' ;
                  leaf drop {
                    description 'Drop packet.' ;
                    type empty ;

                    mandatory true ;
                  }

                }

                case ea-transmit {
                  description 'Transmit packet.' ;
                  leaf transmit {
                    description 'Transmit packet.' ;
                    type empty ;

                    mandatory true ;
                  }

                }

                case ea-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case ea-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 {
                          description 'The IP-Precedence value, support <0-7>' ;
                        }

                      }

                      mandatory true ;
                    }

                  }

                }

                case ea-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case ea-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case ea-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case ea-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container violate-action {
              description 'Action to packets that violate the rate limit.' ;
              choice action {
                description 'Specify action to packets that violate the rate limit.' ;
                mandatory true ;
                case va-drop {
                  description 'Drop packet.' ;
                  leaf drop {
                    description 'Drop packet.' ;
                    type empty ;

                    mandatory true ;
                  }

                }

                case va-transmit {
                  description 'Transmit packet.' ;
                  leaf transmit {
                    description 'Transmit packet.' ;
                    type empty ;

                    mandatory true ;
                  }

                }

                case va-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case va-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 ;

                      }

                      mandatory true ;
                    }

                  }

                }

                case va-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case va-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case va-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case va-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container coupling-flag {
              description 'The Coupling Flag indicates whether tokens that would overflow the C-bucket should be added to the E-bucket.' ;
              presence "Configure coupling flag information" ;
              leaf cf-value {
                description 'Configure coupling-flag value.' ;
                type uint8 {
                  range 0..1 ;

                }

              }

              if-feature qos-car-cf ;

              ncd:revise-date 2023-09-12 ;
            }

            container adjust {
              description 'Configure QoS accuracy adjustment values.' ;
              presence "Configure adjust information" ;
              leaf adjust-value {
                description 'Configure QoS accuracy adjustment values.' ;
                type int32 {
                  range -32..31 ;

                }

              }

              if-feature qos-car-adjust ;

              ncd:revise-date 2023-09-12 ;
            }

          }

        }

        container unknowns {
          description 'Match unknown, only for VPLS.' ;
          list unknown {
            description 'Configure interface rate limit based on matching unknown.' ;
            key 'if-name if-direct' ;
            leaf if-name {
              description 'Configure the name of the attaching interface.' ;
              type ncd:ifname {
                length 1..31 {
                  description 'Name of the attaching interface, support 1-31 characters' ;
                }

              }

            }

            leaf if-direct {
              description 'Specify the direction of interface.' ;
              type enumeration {
                enum input {
                  value 1 ;
                  description 'Rate limit on input' ;
                }

                enum output {
                  value 2 ;
                  description 'Rate limit on output' ;
                }

              }

            }

            leaf rate-limit-desc {
              description 'Description of rate limit, support 1-79 characters.' ;
              type ncd:string-with-blank {
                length 1..79 {
                  description 'Description of rate limit, support 1-79 characters.' ;
                }

              }

              ncd:revise-date 2020-06-18 ;
            }

            choice unit-style {
              description "Specify unit's style." ;
              mandatory true ;
              case unit-value {
                description 'Configure the value style.' ;
                leaf cir {
                  description 'Configure the CIR(Committed Information Rate) value (default: kilobits per second).' ;
                  type uint32 {
                    range 0..4294967295 {
                      description 'The CIR value (default: kilobits per second).' ;
                    }

                  }

                  mandatory true ;
                }

                leaf cir-unit {
                  description 'Set cir unit, such as kbps, mbps, gbps.' ;
                  type qos-rate-unit-type ;

                }

                leaf cbs {
                  description 'Configure the CBS(Committed Burst Size) size in bytes.' ;
                  type uint32 {
                    range 0..4294967294 {
                      description 'The CBS(Committed Burst Size) size in bytes.' ;
                    }

                  }

                  units byte ;
                }

                leaf pir {
                  description 'Configure the PIR(Peak Information Rate) value (default: kilobits per second).' ;
                  type uint32 {
                    range 0..4294967295 {
                      description 'The PIR(Peak Information Rate) value (default: kilobits per second).' ;
                    }

                  }

                  mandatory true ;
                }

                leaf pir-unit {
                  description 'Set pir unit, such as kbps, mbps, gbps.' ;
                  type qos-rate-unit-type ;

                }

                leaf pbs {
                  description 'Configure the PBS(Peak Burst Size) size in bytes.' ;
                  type uint32 {
                    range 0..4294967294 {
                      description 'The PBS(Peak Burst Size) size in KB.' ;
                    }

                  }

                  units byte ;
                }

              }

              case unit-percentage {
                description 'Configure the percentage style.' ;
                leaf cir-percentage {
                  description 'Configure the CIR(Committed Information Rate) percentage (Set the accuracy rate per hundred (1%)).' ;
                  type uint32 {
                    range 1..100 {
                      description 'The CIR percentage, support <1-100>' ;
                    }

                  }

                  mandatory true ;
                }

                leaf pir-percentage {
                  description 'Configure the PIR(Peak Information Rate) percentage (Set the accuracy rate per hundred (1%)).' ;
                  type uint32 {
                    range 1..100 {
                      description 'The PIR percentage, support <1-100>' ;
                    }

                  }

                  mandatory true ;
                }

                ncd:revise-date 2020-12-23 ;
              }

            }

            leaf statistical-share {
              description 'The flag of statistical-share.' ;
              type boolean ;

              default false ;
            }

            leaf token-bucket-id {
              description 'Set token bucket id.' ;
              type uint32 {
                range 1..4294967295 {
                  description 'Token bucket id' ;
                }

              }

              ncd:revise-date 2019-10-28 ;
            }

            container mode {
              if-feature qos-car-mode ;

              description 'Set color mode.' ;
              presence "Configure mode information" ;
              leaf mode-type {
                description 'Set color mode type.' ;
                type enumeration {
                  enum blind {
                    value 1 ;
                    description 'Color-Blind mode' ;
                  }

                  enum aware {
                    value 2 ;
                    description 'Color-Aware mode' ;
                  }

                }

                mandatory true ;
              }

            }

            container conform-action {
              description 'Action to packets that conform to the rate limit.' ;
              choice action {
                description 'Specify action to packets that conform to the rate limit.' ;
                mandatory true ;
                case ca-drop {
                  description 'Drop packet.' ;
                  leaf drop {
                    description 'Drop packet.' ;
                    type empty ;

                    mandatory true ;
                  }

                }

                case ca-transmit {
                  description 'Transmit packet.' ;
                  leaf transmit {
                    description 'Transmit packet.' ;
                    type empty ;

                    mandatory true ;
                  }

                }

                case ca-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case ca-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 {
                          description 'The IP-Precedence value, support <0-7>' ;
                        }

                      }

                      mandatory true ;
                    }

                  }

                }

                case ca-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case ca-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case ca-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case ca-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container exceed-action {
              description 'Action to packets that exceed the rate limit.' ;
              choice action {
                description 'Specify action to packets that exceed the rate limit.' ;
                mandatory true ;
                case ea-drop {
                  description 'Drop packet.' ;
                  leaf drop {
                    description 'Drop packet.' ;
                    type empty ;

                    mandatory true ;
                  }

                }

                case ea-transmit {
                  description 'Transmit packet.' ;
                  leaf transmit {
                    description 'Transmit packet.' ;
                    type empty ;

                    mandatory true ;
                  }

                }

                case ea-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case ea-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 {
                          description 'The IP-Precedence value, support <0-7>' ;
                        }

                      }

                      mandatory true ;
                    }

                  }

                }

                case ea-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case ea-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case ea-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case ea-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container violate-action {
              description 'Action to packets that violate the rate limit.' ;
              choice action {
                description 'Specify action to packets that violate the rate limit.' ;
                mandatory true ;
                case va-drop {
                  description 'Drop packet.' ;
                  leaf drop {
                    description 'Drop packet.' ;
                    type empty ;

                    mandatory true ;
                  }

                }

                case va-transmit {
                  description 'Transmit packet.' ;
                  leaf transmit {
                    description 'Transmit packet.' ;
                    type empty ;

                    mandatory true ;
                  }

                }

                case va-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case va-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 ;

                      }

                      mandatory true ;
                    }

                  }

                }

                case va-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case va-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case va-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case va-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container coupling-flag {
              description 'The Coupling Flag indicates whether tokens that would overflow the C-bucket should be added to the E-bucket.' ;
              presence "Configure coupling flag information" ;
              leaf cf-value {
                description 'Configure coupling-flag value.' ;
                type uint8 {
                  range 0..1 ;

                }

              }

              if-feature qos-car-cf ;

              ncd:revise-date 2023-09-12 ;
            }

            container adjust {
              description 'Configure QoS accuracy adjustment values.' ;
              presence "Configure adjust information" ;
              leaf adjust-value {
                description 'Configure QoS accuracy adjustment values.' ;
                type int32 {
                  range -32..31 ;

                }

              }

              if-feature qos-car-adjust ;

              ncd:revise-date 2023-09-12 ;
            }

          }

        }

        container localports {
          description 'Match local port.' ;
          list localport {
            description 'Configure interface rate limit based on matching localport.' ;
            key 'if-name if-direct' ;
            leaf if-name {
              description 'Configure the name of the attaching interface.' ;
              type ncd:ifname {
                length 1..31 {
                  description 'Name of the attaching interface, support 1-31 characters' ;
                }

              }

            }

            leaf if-direct {
              description 'Specify the direction of interface.' ;
              type enumeration {
                enum input {
                  value 1 ;
                  description 'Rate limit on input' ;
                }

                enum output {
                  value 2 ;
                  description 'Rate limit on output' ;
                }

              }

            }

            leaf rate-limit-desc {
              description 'Description of rate limit, support 1-79 characters.' ;
              type ncd:string-with-blank {
                length 1..79 {
                  description 'Description of rate limit, support 1-79 characters.' ;
                }

              }

              ncd:revise-date 2020-06-18 ;
            }

            choice unit-style {
              description "Specify unit's style." ;
              mandatory true ;
              case unit-value {
                description 'Configure the value style.' ;
                leaf cir {
                  description 'Configure the CIR(Committed Information Rate) value (default: kilobits per second).' ;
                  type uint32 {
                    range 0..4294967295 {
                      description 'The CIR value (default: kilobits per second).' ;
                    }

                  }

                  mandatory true ;
                }

                leaf cir-unit {
                  description 'Set cir unit, such as kbps, mbps, gbps.' ;
                  type qos-rate-unit-type ;

                }

                leaf cbs {
                  description 'Configure the CBS(Committed Burst Size) size in bytes.' ;
                  type uint32 {
                    range 0..4294967294 {
                      description 'The CBS(Committed Burst Size) size in bytes.' ;
                    }

                  }

                  units byte ;
                }

                leaf pir {
                  description 'Configure the PIR(Peak Information Rate) value (default: kilobits per second).' ;
                  type uint32 {
                    range 0..4294967295 {
                      description 'The PIR(Peak Information Rate) value (default: kilobits per second).' ;
                    }

                  }

                  mandatory true ;
                }

                leaf pir-unit {
                  description 'Set pir unit, such as kbps, mbps, gbps.' ;
                  type qos-rate-unit-type ;

                }

                leaf pbs {
                  description 'Configure the PBS(Peak Burst Size) size in bytes.' ;
                  type uint32 {
                    range 0..4294967294 {
                      description 'The PBS(Peak Burst Size) size in KB.' ;
                    }

                  }

                  units byte ;
                }

              }

              case unit-percentage {
                description 'Configure the percentage style.' ;
                leaf cir-percentage {
                  description 'Configure the CIR(Committed Information Rate) percentage (Set the accuracy rate per hundred (1%)).' ;
                  type uint32 {
                    range 1..100 {
                      description 'The CIR percentage, support <1-100>' ;
                    }

                  }

                  mandatory true ;
                }

                leaf pir-percentage {
                  description 'Configure the PIR(Peak Information Rate) percentage (Set the accuracy rate per hundred (1%)).' ;
                  type uint32 {
                    range 1..100 {
                      description 'The PIR percentage, support <1-100>' ;
                    }

                  }

                  mandatory true ;
                }

                ncd:revise-date 2020-12-23 ;
              }

            }

            choice buket-value-percent {
              if-feature car-buket-value-percent ;

              description 'Configure CIR, CBS, PIR and PBS.' ;
              mandatory true ;
              case buket-value {
                description 'Configure CIR, CBS, PIR and PBS in numerical form.' ;
                container c-buket {
                  description 'Configure C-buket related parameters.' ;
                  container cir-value {
                    description 'Configure the CIR(Committed Information Rate).' ;
                    leaf cir {
                      description 'Configure the CIR(Committed Information Rate) value (default: kilobits per second).' ;
                      type uint32 {
                        range "0|8..4294967295" {
                          description 'The CIR value (default: kilobits per second).' ;
                        }

                      }

                      mandatory true ;
                    }

                    leaf cir-unit {
                      description 'Set cir unit, such as kbps, mbps, gbps, pps.' ;
                      type qos-rate-unit-type-ex ;

                    }

                  }

                  container cbs-value {
                    description 'Configure the CBS(Committed Burst Size).' ;
                    presence cbs ;
                    leaf cbs {
                      description 'Configure the CBS(Committed Burst Size) value in bytes.' ;
                      type uint32 {
                        range 1..4294967295 {
                          description 'The CBS(Committed Burst Size) size in bytes, support <1-4294967295>' ;
                        }

                      }

                      units byte ;
                      mandatory true ;
                    }

                  }

                }

                container p-buket {
                  description 'Configure P-buket related parameters.' ;
                  presence p-buket ;
                  container pir-value {
                    description 'Configure the PIR(Peak Information Rate).' ;
                    leaf pir {
                      description 'Configure the PIR(Peak Information Rate) value (default: kilobits per second).' ;
                      type uint32 {
                        range 8..4294967295 {
                          description 'The PIR(Peak Information Rate) value (default: kilobits per second), support <8-4294967295>' ;
                        }

                      }

                      mandatory true ;
                    }

                    leaf pir-unit {
                      description 'Set pir unit, such as kbps, mbps, gbps, pps.' ;
                      type qos-rate-unit-type-ex ;

                    }

                  }

                  container pbs-value {
                    description 'Configure the PBS(Peak Burst Size).' ;
                    presence pbs ;
                    leaf pbs {
                      description 'Configure the PBS(Peak Burst Size) value in bytes.' ;
                      type uint32 {
                        range 1..4294967295 {
                          description 'The PBS(Peak Burst Size) size in bytes, support <1-4294967295>' ;
                        }

                      }

                      units byte ;
                      mandatory true ;
                    }

                  }

                }

              }

              case buket-percent {
                description 'Configure CIR and PIR in percentage.' ;
                container cir-percent {
                  description 'Configure CIR in percentage.' ;
                  leaf cir-percent {
                    description 'Configure CIR in percentage.' ;
                    type uint32 {
                      range 1..100 ;

                    }

                    mandatory true ;
                  }

                }

                container pir-percent {
                  description 'Configure PIR in percentage.' ;
                  presence pir ;
                  leaf pir-percent {
                    description 'Configure PIR in percentage.' ;
                    type uint32 {
                      range 1..100 ;

                    }

                    mandatory true ;
                  }

                }

              }

              ncd:revise-date 2021-01-25 ;
            }

            leaf statistical-share {
              description 'The flag of statistical-share.' ;
              type boolean ;

              default false ;
            }

            leaf token-bucket-id {
              description 'Set token bucket id.' ;
              type uint32 {
                range 1..4294967295 {
                  description 'Token bucket id' ;
                }

              }

              ncd:revise-date 2019-10-28 ;
            }

            container mode {
              if-feature qos-car-mode ;

              description 'Set color mode.' ;
              presence "Configure mode information" ;
              leaf mode-type {
                description 'Set color mode type.' ;
                type enumeration {
                  enum blind {
                    value 1 ;
                    description 'Color-Blind mode' ;
                  }

                  enum aware {
                    value 2 ;
                    description 'Color-Aware mode' ;
                  }

                }

                mandatory true ;
              }

            }

            container conform-action {
              description 'Action to packets that conform to the rate limit.' ;
              choice action {
                description 'Specify action to packets that conform to the rate limit.' ;
                mandatory true ;
                case ca-drop {
                  description 'Drop packet.' ;
                  leaf drop {
                    description 'Drop packet.' ;
                    type empty ;

                    mandatory true ;
                  }

                }

                case ca-transmit {
                  description 'Transmit packet.' ;
                  leaf transmit {
                    description 'Transmit packet.' ;
                    type empty ;

                    mandatory true ;
                  }

                }

                case ca-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case ca-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 {
                          description 'The IP-Precedence value, support <0-7>' ;
                        }

                      }

                      mandatory true ;
                    }

                  }

                }

                case ca-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case ca-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case ca-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case ca-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container exceed-action {
              description 'Action to packets that exceed the rate limit.' ;
              choice action {
                description 'Specify action to packets that exceed the rate limit.' ;
                mandatory true ;
                case ea-drop {
                  description 'Drop packet.' ;
                  leaf drop {
                    description 'Drop packet.' ;
                    type empty ;

                    mandatory true ;
                  }

                }

                case ea-transmit {
                  description 'Transmit packet.' ;
                  leaf transmit {
                    description 'Transmit packet.' ;
                    type empty ;

                    mandatory true ;
                  }

                }

                case ea-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case ea-precedence {
                  description 'Rewrite packet precedence and transmit the packet.' ;
                  container set-prec-transmit {
                    description 'Rwrite packet precedence and transmit it.' ;
                    leaf prec-value {
                      description 'Reset the IP-Precedence value, support <0-7>.' ;
                      type uint8 {
                        range 0..7 {
                          description 'The IP-Precedence value, support <0-7>' ;
                        }

                      }

                      mandatory true ;
                    }

                  }

                }

                case ea-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case ea-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case ea-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case ea-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container violate-action {
              description 'Action to packets that violate the rate limit.' ;
              choice action {
                description 'Specify action to packets that violate the rate limit.' ;
                mandatory true ;
                case va-drop {
                  description 'Drop packet.' ;
                  leaf drop {
                    description 'Drop packet.' ;
                    type empty ;

                    mandatory true ;
                  }

                }

                case va-transmit {
                  description 'Transmit packet.' ;
                  leaf transmit {
                    description 'Transmit packet.' ;
                    type empty ;

                    mandatory true ;
                  }

                }

                case va-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case va-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 ;

                      }

                      mandatory true ;
                    }

                  }

                }

                case va-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case va-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case va-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case va-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container coupling-flag {
              description 'The Coupling Flag indicates whether tokens that would overflow the C-bucket should be added to the E-bucket.' ;
              presence "Configure coupling flag information" ;
              leaf cf-value {
                description 'Configure coupling-flag value.' ;
                type uint8 {
                  range 0..1 ;

                }

              }

              if-feature qos-car-cf ;

              ncd:revise-date 2023-09-12 ;
            }

            container adjust {
              description 'Configure QoS accuracy adjustment values.' ;
              presence "Configure adjust information" ;
              leaf adjust-value {
                description 'Configure QoS accuracy adjustment values.' ;
                type int32 {
                  range -32..31 ;

                }

              }

              if-feature qos-car-adjust ;

              ncd:revise-date 2023-09-12 ;
            }

          }

        }

        container dscps {
          description 'Match DSCP.' ;
          list dscp {
            description 'Configure interface rate limit based on matching dscp.' ;
            key 'if-name if-direct ip-protocol dscp-value' ;
            leaf if-name {
              description 'Configure the name of the attaching interface.' ;
              type ncd:ifname {
                length 1..31 {
                  description 'Name of the attaching interface, support 1-31 characters' ;
                }

              }

            }

            leaf if-direct {
              description 'Specify the direction of interface.' ;
              type enumeration {
                enum input {
                  value 1 ;
                  description 'Rate limit on input' ;
                }

                enum output {
                  value 2 ;
                  description 'Rate limit on output' ;
                }

              }

            }

            leaf ip-protocol {
              description 'Rate limit based on protocol.' ;
              type enumeration {
                enum any {
                  value 1 ;
                  description 'Rate limit based on any protocol' ;
                }

                enum ipv4 {
                  value 2 ;
                  description 'Rate limit based on IPv4' ;
                }

                enum ipv6 {
                  value 3 ;
                  description 'Rate limit based on IPv6' ;
                }

              }

            }

            leaf dscp-value {
              description 'DSCP value, support <0-63>.' ;
              type uint32 {
                range 0..63 {
                  description 'DSCP value, support <0-63>' ;
                }

              }

            }

            leaf rate-limit-desc {
              description 'Description of rate limit, support 1-79 characters.' ;
              type ncd:string-with-blank {
                length 1..79 {
                  description 'Description of rate limit, support 1-79 characters.' ;
                }

              }

              ncd:revise-date 2020-06-18 ;
            }

            choice unit-style {
              description "Specify unit's style." ;
              mandatory true ;
              case unit-value {
                description 'Configure the value style.' ;
                leaf cir {
                  description 'Configure the CIR(Committed Information Rate) value (default: kilobits per second).' ;
                  type uint32 {
                    range 0..4294967295 {
                      description 'The CIR value (default: kilobits per second).' ;
                    }

                  }

                  mandatory true ;
                }

                leaf cir-unit {
                  description 'Set cir unit, such as kbps, mbps, gbps.' ;
                  type qos-rate-unit-type ;

                }

                leaf cbs {
                  description 'Configure the CBS(Committed Burst Size) size in bytes.' ;
                  type uint32 {
                    range 0..4294967294 {
                      description 'The CBS(Committed Burst Size) size in bytes.' ;
                    }

                  }

                  units byte ;
                }

                leaf pir {
                  description 'Configure the PIR(Peak Information Rate) value (default: kilobits per second).' ;
                  type uint32 {
                    range 0..4294967295 {
                      description 'The PIR(Peak Information Rate) value (default: kilobits per second).' ;
                    }

                  }

                  mandatory true ;
                }

                leaf pir-unit {
                  description 'Set pir unit, such as kbps, mbps, gbps.' ;
                  type qos-rate-unit-type ;

                }

                leaf pbs {
                  description 'Configure the PBS(Peak Burst Size) size in bytes.' ;
                  type uint32 {
                    range 0..4294967294 {
                      description 'The PBS(Peak Burst Size) size in KB.' ;
                    }

                  }

                  units byte ;
                }

              }

              case unit-percentage {
                description 'Configure the percentage style.' ;
                leaf cir-percentage {
                  description 'Configure the CIR(Committed Information Rate) percentage (Set the accuracy rate per hundred (1%)).' ;
                  type uint32 {
                    range 1..100 {
                      description 'The CIR percentage, support <1-100>' ;
                    }

                  }

                  mandatory true ;
                }

                leaf pir-percentage {
                  description 'Configure the PIR(Peak Information Rate) percentage (Set the accuracy rate per hundred (1%)).' ;
                  type uint32 {
                    range 1..100 {
                      description 'The PIR percentage, support <1-100>' ;
                    }

                  }

                  mandatory true ;
                }

                ncd:revise-date 2020-12-23 ;
              }

            }

            leaf statistical-share {
              description 'The flag of statistical-share.' ;
              type boolean ;

              default false ;
            }

            leaf token-bucket-id {
              description 'Set token bucket id.' ;
              type uint32 {
                range 1..4294967295 {
                  description 'Token bucket id' ;
                }

              }

              ncd:revise-date 2019-10-28 ;
            }

            container mode {
              if-feature qos-car-mode ;

              description 'Set color mode.' ;
              presence "Configure mode information" ;
              leaf mode-type {
                description 'Set color mode type.' ;
                type enumeration {
                  enum blind {
                    value 1 ;
                    description 'Color-Blind mode' ;
                  }

                  enum aware {
                    value 2 ;
                    description 'Color-Aware mode' ;
                  }

                }

                mandatory true ;
              }

            }

            container conform-action {
              description 'Action to packets that conform to the rate limit.' ;
              choice action {
                description 'Specify action to packets that conform to the rate limit.' ;
                mandatory true ;
                case ca-drop {
                  description 'Drop packet.' ;
                  leaf drop {
                    description 'Drop packet.' ;
                    type empty ;

                    mandatory true ;
                  }

                }

                case ca-transmit {
                  description 'Transmit packet.' ;
                  leaf transmit {
                    description 'Transmit packet.' ;
                    type empty ;

                    mandatory true ;
                  }

                }

                case ca-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case ca-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 {
                          description 'The IP-Precedence value, support <0-7>' ;
                        }

                      }

                      mandatory true ;
                    }

                  }

                }

                case ca-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case ca-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case ca-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case ca-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container exceed-action {
              description 'Action to packets that exceed the rate limit.' ;
              choice action {
                description 'Specify action to packets that exceed the rate limit.' ;
                mandatory true ;
                case ea-drop {
                  description 'Drop packet.' ;
                  leaf drop {
                    description 'Drop packet.' ;
                    type empty ;

                    mandatory true ;
                  }

                }

                case ea-transmit {
                  description 'Transmit packet.' ;
                  leaf transmit {
                    description 'Transmit packet.' ;
                    type empty ;

                    mandatory true ;
                  }

                }

                case ea-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case ea-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 {
                          description 'The IP-Precedence value, support <0-7>' ;
                        }

                      }

                      mandatory true ;
                    }

                  }

                }

                case ea-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case ea-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case ea-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case ea-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container violate-action {
              description 'Action to packets that violate the rate limit.' ;
              choice action {
                description 'Specify action to packets that violate the rate limit.' ;
                mandatory true ;
                case va-drop {
                  description 'Drop packet.' ;
                  leaf drop {
                    description 'Drop packet.' ;
                    type empty ;

                    mandatory true ;
                  }

                }

                case va-transmit {
                  description 'Transmit packet.' ;
                  leaf transmit {
                    description 'Transmit packet.' ;
                    type empty ;

                    mandatory true ;
                  }

                }

                case va-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case va-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 ;

                      }

                      mandatory true ;
                    }

                  }

                }

                case va-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case va-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case va-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case va-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container coupling-flag {
              description 'The Coupling Flag indicates whether tokens that would overflow the C-bucket should be added to the E-bucket.' ;
              presence "Configure coupling flag information" ;
              leaf cf-value {
                description 'Configure coupling-flag value.' ;
                type uint8 {
                  range 0..1 ;

                }

              }

              if-feature qos-car-cf ;

              ncd:revise-date 2023-09-12 ;
            }

            container adjust {
              description 'Configure QoS accuracy adjustment values.' ;
              presence "Configure adjust information" ;
              leaf adjust-value {
                description 'Configure QoS accuracy adjustment values.' ;
                type int32 {
                  range -32..31 ;

                }

              }

              if-feature qos-car-adjust ;

              ncd:revise-date 2023-09-12 ;
            }

          }

        }

        container precedences {
          description 'Match IP precedence.' ;
          list precedence {
            description 'Configure interface rate limit based on matching precedence.' ;
            key 'if-name if-direct ip-protocol prec-value' ;
            leaf if-name {
              description 'Configure the name of the attaching interface.' ;
              type ncd:ifname {
                length 1..31 {
                  description 'Name of the attaching interface, support 1-31 characters' ;
                }

              }

            }

            leaf if-direct {
              description 'Specify the direction of interface.' ;
              type enumeration {
                enum input {
                  value 1 ;
                  description 'Rate limit on input' ;
                }

                enum output {
                  value 2 ;
                  description 'Rate limit on output' ;
                }

              }

            }

            leaf ip-protocol {
              description 'Rate limit based on protocol.' ;
              type enumeration {
                enum any {
                  value 1 ;
                  description 'Rate limit based on any protocol' ;
                }

                enum ipv4 {
                  value 2 ;
                  description 'Rate limit based on IPv4' ;
                }

                enum ipv6 {
                  value 3 ;
                  description 'Rate limit based on IPv6' ;
                }

              }

            }

            leaf prec-value {
              description 'IP precedence value, support <0-7>.' ;
              type uint32 {
                range 0..7 {
                  description 'IP precedence value, support <0-7>' ;
                }

              }

            }

            leaf rate-limit-desc {
              description 'Description of rate limit, support 1-79 characters.' ;
              type ncd:string-with-blank {
                length 1..79 {
                  description 'Description of rate limit, support 1-79 characters.' ;
                }

              }

              ncd:revise-date 2020-06-18 ;
            }

            choice unit-style {
              description "Specify unit's style." ;
              mandatory true ;
              case unit-value {
                description 'Configure the value style.' ;
                leaf cir {
                  description 'Configure the CIR(Committed Information Rate) value (default: kilobits per second).' ;
                  type uint32 {
                    range 0..4294967295 {
                      description 'The CIR value (default: kilobits per second).' ;
                    }

                  }

                  mandatory true ;
                }

                leaf cir-unit {
                  description 'Set cir unit, such as kbps, mbps, gbps.' ;
                  type qos-rate-unit-type ;

                }

                leaf cbs {
                  description 'Configure the CBS(Committed Burst Size) size in bytes.' ;
                  type uint32 {
                    range 0..4294967294 {
                      description 'The CBS(Committed Burst Size) size in bytes.' ;
                    }

                  }

                  units byte ;
                }

                leaf pir {
                  description 'Configure the PIR(Peak Information Rate) value (default: kilobits per second).' ;
                  type uint32 {
                    range 0..4294967295 {
                      description 'The PIR(Peak Information Rate) value (default: kilobits per second).' ;
                    }

                  }

                  mandatory true ;
                }

                leaf pir-unit {
                  description 'Set pir unit, such as kbps, mbps, gbps.' ;
                  type qos-rate-unit-type ;

                }

                leaf pbs {
                  description 'Configure the PBS(Peak Burst Size) size in bytes.' ;
                  type uint32 {
                    range 0..4294967294 {
                      description 'The PBS(Peak Burst Size) size in KB.' ;
                    }

                  }

                  units byte ;
                }

              }

              case unit-percentage {
                description 'Configure the percentage style.' ;
                leaf cir-percentage {
                  description 'Configure the CIR(Committed Information Rate) percentage (Set the accuracy rate per hundred (1%)).' ;
                  type uint32 {
                    range 1..100 {
                      description 'The CIR percentage, support <1-100>' ;
                    }

                  }

                  mandatory true ;
                }

                leaf pir-percentage {
                  description 'Configure the PIR(Peak Information Rate) percentage (Set the accuracy rate per hundred (1%)).' ;
                  type uint32 {
                    range 1..100 {
                      description 'The PIR percentage, support <1-100>' ;
                    }

                  }

                  mandatory true ;
                }

                ncd:revise-date 2020-12-23 ;
              }

            }

            leaf statistical-share {
              description 'The flag of statistical-share.' ;
              type boolean ;

              default false ;
            }

            leaf token-bucket-id {
              description 'Set token bucket id.' ;
              type uint32 {
                range 1..4294967295 {
                  description 'Token bucket id' ;
                }

              }

              ncd:revise-date 2019-10-28 ;
            }

            container mode {
              if-feature qos-car-mode ;

              description 'Set color mode.' ;
              presence "Configure mode information" ;
              leaf mode-type {
                description 'Set color mode type.' ;
                type enumeration {
                  enum blind {
                    value 1 ;
                    description 'Color-Blind mode' ;
                  }

                  enum aware {
                    value 2 ;
                    description 'Color-Aware mode' ;
                  }

                }

                mandatory true ;
              }

            }

            container conform-action {
              description 'Action to packets that conform to the rate limit.' ;
              choice action {
                description 'Specify action to packets that conform to the rate limit.' ;
                mandatory true ;
                case ca-drop {
                  description 'Drop packet.' ;
                  leaf drop {
                    description 'Drop packet.' ;
                    type empty ;

                    mandatory true ;
                  }

                }

                case ca-transmit {
                  description 'Transmit packet.' ;
                  leaf transmit {
                    description 'Transmit packet.' ;
                    type empty ;

                    mandatory true ;
                  }

                }

                case ca-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case ca-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 {
                          description 'The IP-Precedence value, support <0-7>' ;
                        }

                      }

                      mandatory true ;
                    }

                  }

                }

                case ca-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case ca-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case ca-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case ca-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container exceed-action {
              description 'Action to packets that exceed the rate limit.' ;
              choice action {
                description 'Specify action to packets that exceed the rate limit.' ;
                mandatory true ;
                case ea-drop {
                  description 'Drop packet.' ;
                  leaf drop {
                    description 'Drop packet.' ;
                    type empty ;

                    mandatory true ;
                  }

                }

                case ea-transmit {
                  description 'Transmit packet.' ;
                  leaf transmit {
                    description 'Transmit packet.' ;
                    type empty ;

                    mandatory true ;
                  }

                }

                case ea-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case ea-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 {
                          description 'The IP-Precedence value, support <0-7>' ;
                        }

                      }

                      mandatory true ;
                    }

                  }

                }

                case ea-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case ea-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case ea-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case ea-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container violate-action {
              description 'Action to packets that violate the rate limit.' ;
              choice action {
                description 'Specify action to packets that violate the rate limit.' ;
                mandatory true ;
                case va-drop {
                  description 'Drop packet.' ;
                  leaf drop {
                    description 'Drop packet.' ;
                    type empty ;

                    mandatory true ;
                  }

                }

                case va-transmit {
                  description 'Transmit packet.' ;
                  leaf transmit {
                    description 'Transmit packet.' ;
                    type empty ;

                    mandatory true ;
                  }

                }

                case va-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case va-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 ;

                      }

                      mandatory true ;
                    }

                  }

                }

                case va-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case va-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case va-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case va-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container coupling-flag {
              description 'The Coupling Flag indicates whether tokens that would overflow the C-bucket should be added to the E-bucket.' ;
              presence "Configure coupling flag information" ;
              leaf cf-value {
                description 'Configure coupling-flag value.' ;
                type uint8 {
                  range 0..1 ;

                }

              }

              if-feature qos-car-cf ;

              ncd:revise-date 2023-09-12 ;
            }

            container adjust {
              description 'Configure QoS accuracy adjustment values.' ;
              presence "Configure adjust information" ;
              leaf adjust-value {
                description 'Configure QoS accuracy adjustment values.' ;
                type int32 {
                  range -32..31 ;

                }

              }

              if-feature qos-car-adjust ;

              ncd:revise-date 2023-09-12 ;
            }

          }

        }

        container mpls-exps {
          description 'Match MPLS-EXP.' ;
          list mpls-exp {
            description 'Configure interface rate limit based on matching mpls-exp.' ;
            key 'if-name if-direct mpls-exp-value' ;
            leaf if-name {
              description 'Configure the name of the attaching interface.' ;
              type ncd:ifname {
                length 1..31 {
                  description 'Name of the attaching interface, support 1-31 characters' ;
                }

              }

            }

            leaf if-direct {
              description 'Specify the direction of interface.' ;
              type enumeration {
                enum input {
                  value 1 ;
                  description 'Rate limit on input' ;
                }

                enum output {
                  value 2 ;
                  description 'Rate limit on output' ;
                }

              }

            }

            leaf mpls-exp-value {
              description 'MPLS-EXP value, support <0-7>.' ;
              type uint32 {
                range 0..7 {
                  description 'MPLS-EXP value, support <0-7>' ;
                }

              }

            }

            leaf rate-limit-desc {
              description 'Description of rate limit, support 1-79 characters.' ;
              type ncd:string-with-blank {
                length 1..79 {
                  description 'Description of rate limit, support 1-79 characters.' ;
                }

              }

              ncd:revise-date 2020-06-18 ;
            }

            choice unit-style {
              description "Specify unit's style." ;
              mandatory true ;
              case unit-value {
                description 'Configure the value style.' ;
                leaf cir {
                  description 'Configure the CIR(Committed Information Rate) value (default: kilobits per second).' ;
                  type uint32 {
                    range 0..4294967295 {
                      description 'The CIR value (default: kilobits per second).' ;
                    }

                  }

                  mandatory true ;
                }

                leaf cir-unit {
                  description 'Set cir unit, such as kbps, mbps, gbps.' ;
                  type qos-rate-unit-type ;

                }

                leaf cbs {
                  description 'Configure the CBS(Committed Burst Size) size in bytes.' ;
                  type uint32 {
                    range 0..4294967294 {
                      description 'The CBS(Committed Burst Size) size in bytes.' ;
                    }

                  }

                  units byte ;
                }

                leaf pir {
                  description 'Configure the PIR(Peak Information Rate) value (default: kilobits per second).' ;
                  type uint32 {
                    range 0..4294967295 {
                      description 'The PIR(Peak Information Rate) value (default: kilobits per second).' ;
                    }

                  }

                  mandatory true ;
                }

                leaf pir-unit {
                  description 'Set pir unit, such as kbps, mbps, gbps.' ;
                  type qos-rate-unit-type ;

                }

                leaf pbs {
                  description 'Configure the PBS(Peak Burst Size) size in bytes.' ;
                  type uint32 {
                    range 0..4294967294 {
                      description 'The PBS(Peak Burst Size) size in KB.' ;
                    }

                  }

                  units byte ;
                }

              }

              case unit-percentage {
                description 'Configure the percentage style.' ;
                leaf cir-percentage {
                  description 'Configure the CIR(Committed Information Rate) percentage (Set the accuracy rate per hundred (1%)).' ;
                  type uint32 {
                    range 1..100 {
                      description 'The CIR percentage, support <1-100>' ;
                    }

                  }

                  mandatory true ;
                }

                leaf pir-percentage {
                  description 'Configure the PIR(Peak Information Rate) percentage (Set the accuracy rate per hundred (1%)).' ;
                  type uint32 {
                    range 1..100 {
                      description 'The PIR percentage, support <1-100>' ;
                    }

                  }

                  mandatory true ;
                }

                ncd:revise-date 2020-12-23 ;
              }

            }

            leaf statistical-share {
              description 'The flag of statistical-share.' ;
              type boolean ;

              default false ;
            }

            leaf token-bucket-id {
              description 'Set token bucket id.' ;
              type uint32 {
                range 1..4294967295 {
                  description 'Token bucket id' ;
                }

              }

              ncd:revise-date 2019-10-28 ;
            }

            container mode {
              if-feature qos-car-mode ;

              description 'Set color mode.' ;
              presence "Configure mode information" ;
              leaf mode-type {
                description 'Set color mode type.' ;
                type enumeration {
                  enum blind {
                    value 1 ;
                    description 'Color-Blind mode' ;
                  }

                  enum aware {
                    value 2 ;
                    description 'Color-Aware mode' ;
                  }

                }

                mandatory true ;
              }

            }

            container conform-action {
              description 'Action to packets that conform to the rate limit.' ;
              choice action {
                description 'Specify action to packets that conform to the rate limit.' ;
                mandatory true ;
                case ca-drop {
                  description 'Drop packet.' ;
                  leaf drop {
                    description 'Drop packet.' ;
                    type empty ;

                    mandatory true ;
                  }

                }

                case ca-transmit {
                  description 'Transmit packet.' ;
                  leaf transmit {
                    description 'Transmit packet.' ;
                    type empty ;

                    mandatory true ;
                  }

                }

                case ca-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case ca-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 {
                          description 'The IP-Precedence value, support <0-7>' ;
                        }

                      }

                      mandatory true ;
                    }

                  }

                }

                case ca-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case ca-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case ca-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case ca-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container exceed-action {
              description 'Action to packets that exceed the rate limit.' ;
              choice action {
                description 'Specify action to packets that exceed the rate limit.' ;
                mandatory true ;
                case ea-drop {
                  description 'Drop packet.' ;
                  leaf drop {
                    description 'Drop packet.' ;
                    type empty ;

                    mandatory true ;
                  }

                }

                case ea-transmit {
                  description 'Transmit packet.' ;
                  leaf transmit {
                    description 'Transmit packet.' ;
                    type empty ;

                    mandatory true ;
                  }

                }

                case ea-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case ea-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 {
                          description 'The IP-Precedence value, support <0-7>' ;
                        }

                      }

                      mandatory true ;
                    }

                  }

                }

                case ea-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case ea-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case ea-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case ea-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container violate-action {
              description 'Action to packets that violate the rate limit.' ;
              choice action {
                description 'Specify action to packets that violate the rate limit.' ;
                mandatory true ;
                case va-drop {
                  description 'Drop packet.' ;
                  leaf drop {
                    description 'Drop packet.' ;
                    type empty ;

                    mandatory true ;
                  }

                }

                case va-transmit {
                  description 'Transmit packet.' ;
                  leaf transmit {
                    description 'Transmit packet.' ;
                    type empty ;

                    mandatory true ;
                  }

                }

                case va-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case va-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 ;

                      }

                      mandatory true ;
                    }

                  }

                }

                case va-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case va-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case va-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case va-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container coupling-flag {
              description 'The Coupling Flag indicates whether tokens that would overflow the C-bucket should be added to the E-bucket.' ;
              presence "Configure coupling flag information" ;
              leaf cf-value {
                description 'Configure coupling-flag value.' ;
                type uint8 {
                  range 0..1 ;

                }

              }

              if-feature qos-car-cf ;

              ncd:revise-date 2023-09-12 ;
            }

            container adjust {
              description 'Configure QoS accuracy adjustment values.' ;
              presence "Configure adjust information" ;
              leaf adjust-value {
                description 'Configure QoS accuracy adjustment values.' ;
                type int32 {
                  range -32..31 ;

                }

              }

              if-feature qos-car-adjust ;

              ncd:revise-date 2023-09-12 ;
            }

          }

        }

        container inner-vlans {
          description 'Match inner VLAN ID.' ;
          list inner-vlan {
            description 'Configure interface rate limit based on matching inner-vlan.' ;
            key 'if-name if-direct inner-vlan' ;
            leaf if-name {
              description 'Configure the name of the attaching interface.' ;
              type ncd:ifname {
                length 1..31 {
                  description 'Name of the attaching interface, support 1-31 characters' ;
                }

              }

            }

            leaf if-direct {
              description 'Specify the direction of interface.' ;
              type enumeration {
                enum input {
                  value 1 ;
                  description 'Rate limit on input' ;
                }

                enum output {
                  value 2 ;
                  description 'Rate limit on output' ;
                }

              }

            }

            leaf inner-vlan {
              description 'Configure inner-VLAN value in range mode, support single inner-VLAN value or range(max num:4;spacing mark:,) in <1-4094>. For example,"1,300-400,1000,2000-4000",etc.' ;
              type qos-vlan-range ;

            }

            leaf rate-limit-desc {
              description 'Description of rate limit, support 1-79 characters.' ;
              type ncd:string-with-blank {
                length 1..79 {
                  description 'Description of rate limit, support 1-79 characters.' ;
                }

              }

              ncd:revise-date 2020-06-18 ;
            }

            choice unit-style {
              description "Specify unit's style." ;
              mandatory true ;
              case unit-value {
                description 'Configure the value style.' ;
                leaf cir {
                  description 'Configure the CIR(Committed Information Rate) value (default: kilobits per second).' ;
                  type uint32 {
                    range 0..4294967295 {
                      description 'The CIR value (default: kilobits per second).' ;
                    }

                  }

                  mandatory true ;
                }

                leaf cir-unit {
                  description 'Set cir unit, such as kbps, mbps, gbps.' ;
                  type qos-rate-unit-type ;

                }

                leaf cbs {
                  description 'Configure the CBS(Committed Burst Size) size in bytes.' ;
                  type uint32 {
                    range 0..4294967294 {
                      description 'The CBS(Committed Burst Size) size in bytes.' ;
                    }

                  }

                  units byte ;
                }

                leaf pir {
                  description 'Configure the PIR(Peak Information Rate) value (default: kilobits per second).' ;
                  type uint32 {
                    range 0..4294967295 {
                      description 'The PIR(Peak Information Rate) value (default: kilobits per second).' ;
                    }

                  }

                  mandatory true ;
                }

                leaf pir-unit {
                  description 'Set pir unit, such as kbps, mbps, gbps.' ;
                  type qos-rate-unit-type ;

                }

                leaf pbs {
                  description 'Configure the PBS(Peak Burst Size) size in bytes.' ;
                  type uint32 {
                    range 0..4294967294 {
                      description 'The PBS(Peak Burst Size) size in KB.' ;
                    }

                  }

                  units byte ;
                }

              }

              case unit-percentage {
                description 'Configure the percentage style.' ;
                leaf cir-percentage {
                  description 'Configure the CIR(Committed Information Rate) percentage (Set the accuracy rate per hundred (1%)).' ;
                  type uint32 {
                    range 1..100 {
                      description 'The CIR percentage, support <1-100>' ;
                    }

                  }

                  mandatory true ;
                }

                leaf pir-percentage {
                  description 'Configure the PIR(Peak Information Rate) percentage (Set the accuracy rate per hundred (1%)).' ;
                  type uint32 {
                    range 1..100 {
                      description 'The PIR percentage, support <1-100>' ;
                    }

                  }

                  mandatory true ;
                }

                ncd:revise-date 2020-12-23 ;
              }

            }

            leaf statistical-share {
              description 'The flag of statistical-share.' ;
              type boolean ;

              default false ;
            }

            leaf token-bucket-id {
              description 'Set token bucket id.' ;
              type uint32 {
                range 1..4294967295 {
                  description 'Token bucket id' ;
                }

              }

              ncd:revise-date 2019-10-28 ;
            }

            container mode {
              if-feature qos-car-mode ;

              description 'Set color mode.' ;
              presence "Configure mode information" ;
              leaf mode-type {
                description 'Set color mode type.' ;
                type enumeration {
                  enum blind {
                    value 1 ;
                    description 'Color-Blind mode' ;
                  }

                  enum aware {
                    value 2 ;
                    description 'Color-Aware mode' ;
                  }

                }

                mandatory true ;
              }

            }

            container conform-action {
              description 'Action to packets that conform to the rate limit.' ;
              choice action {
                description 'Specify action to packets that conform to the rate limit.' ;
                mandatory true ;
                case ca-drop {
                  description 'Drop packet.' ;
                  leaf drop {
                    description 'Drop packet.' ;
                    type empty ;

                    mandatory true ;
                  }

                }

                case ca-transmit {
                  description 'Transmit packet.' ;
                  leaf transmit {
                    description 'Transmit packet.' ;
                    type empty ;

                    mandatory true ;
                  }

                }

                case ca-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case ca-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 {
                          description 'The IP-Precedence value, support <0-7>' ;
                        }

                      }

                      mandatory true ;
                    }

                  }

                }

                case ca-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case ca-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case ca-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case ca-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container exceed-action {
              description 'Action to packets that exceed the rate limit.' ;
              choice action {
                description 'Specify action to packets that exceed the rate limit.' ;
                mandatory true ;
                case ea-drop {
                  description 'Drop packet.' ;
                  leaf drop {
                    description 'Drop packet.' ;
                    type empty ;

                    mandatory true ;
                  }

                }

                case ea-transmit {
                  description 'Transmit packet.' ;
                  leaf transmit {
                    description 'Transmit packet.' ;
                    type empty ;

                    mandatory true ;
                  }

                }

                case ea-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case ea-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 {
                          description 'The IP-Precedence value, support <0-7>' ;
                        }

                      }

                      mandatory true ;
                    }

                  }

                }

                case ea-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case ea-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case ea-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case ea-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container violate-action {
              description 'Action to packets that violate the rate limit.' ;
              choice action {
                description 'Specify action to packets that violate the rate limit.' ;
                mandatory true ;
                case va-drop {
                  description 'Drop packet.' ;
                  leaf drop {
                    description 'Drop packet.' ;
                    type empty ;

                    mandatory true ;
                  }

                }

                case va-transmit {
                  description 'Transmit packet.' ;
                  leaf transmit {
                    description 'Transmit packet.' ;
                    type empty ;

                    mandatory true ;
                  }

                }

                case va-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case va-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 ;

                      }

                      mandatory true ;
                    }

                  }

                }

                case va-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case va-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case va-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case va-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container coupling-flag {
              description 'The Coupling Flag indicates whether tokens that would overflow the C-bucket should be added to the E-bucket.' ;
              presence "Configure coupling flag information" ;
              leaf cf-value {
                description 'Configure coupling-flag value.' ;
                type uint8 {
                  range 0..1 ;

                }

              }

              if-feature qos-car-cf ;

              ncd:revise-date 2023-09-12 ;
            }

            container adjust {
              description 'Configure QoS accuracy adjustment values.' ;
              presence "Configure adjust information" ;
              leaf adjust-value {
                description 'Configure QoS accuracy adjustment values.' ;
                type int32 {
                  range -32..31 ;

                }

              }

              if-feature qos-car-adjust ;

              ncd:revise-date 2023-09-12 ;
            }

          }

        }

        container outer-vlans {
          description 'Match outer VLAN ID.' ;
          list outer-vlan {
            description 'Configure interface rate limit based on matching outer-vlan.' ;
            key 'if-name if-direct outer-vlan' ;
            leaf if-name {
              description 'Configure the name of the attaching interface.' ;
              type ncd:ifname {
                length 1..31 {
                  description 'Name of the attaching interface, support 1-31 characters' ;
                }

              }

            }

            leaf if-direct {
              description 'Specify the direction of interface.' ;
              type enumeration {
                enum input {
                  value 1 ;
                  description 'Rate limit on input' ;
                }

                enum output {
                  value 2 ;
                  description 'Rate limit on output' ;
                }

              }

            }

            leaf outer-vlan {
              description 'Configure outer-VLAN value in range mode, support single outer-VLAN value or range(max num:4;spacing mark:,) in <1-4094>. For example,"1,300-400,1000,2000-4000",etc.' ;
              type qos-vlan-range ;

            }

            leaf rate-limit-desc {
              description 'Description of rate limit, support 1-79 characters.' ;
              type ncd:string-with-blank {
                length 1..79 {
                  description 'Description of rate limit, support 1-79 characters.' ;
                }

              }

              ncd:revise-date 2020-06-18 ;
            }

            choice unit-style {
              description "Specify unit's style." ;
              mandatory true ;
              case unit-value {
                description 'Configure the value style.' ;
                leaf cir {
                  description 'Configure the CIR(Committed Information Rate) value (default: kilobits per second).' ;
                  type uint32 {
                    range 0..4294967295 {
                      description 'The CIR value (default: kilobits per second).' ;
                    }

                  }

                  mandatory true ;
                }

                leaf cir-unit {
                  description 'Set cir unit, such as kbps, mbps, gbps.' ;
                  type qos-rate-unit-type ;

                }

                leaf cbs {
                  description 'Configure the CBS(Committed Burst Size) size in bytes.' ;
                  type uint32 {
                    range 0..4294967294 {
                      description 'The CBS(Committed Burst Size) size in bytes.' ;
                    }

                  }

                  units byte ;
                }

                leaf pir {
                  description 'Configure the PIR(Peak Information Rate) value (default: kilobits per second).' ;
                  type uint32 {
                    range 0..4294967295 {
                      description 'The PIR(Peak Information Rate) value (default: kilobits per second).' ;
                    }

                  }

                  mandatory true ;
                }

                leaf pir-unit {
                  description 'Set pir unit, such as kbps, mbps, gbps.' ;
                  type qos-rate-unit-type ;

                }

                leaf pbs {
                  description 'Configure the PBS(Peak Burst Size) size in bytes.' ;
                  type uint32 {
                    range 0..4294967294 {
                      description 'The PBS(Peak Burst Size) size in KB.' ;
                    }

                  }

                  units byte ;
                }

              }

              case unit-percentage {
                description 'Configure the percentage style.' ;
                leaf cir-percentage {
                  description 'Configure the CIR(Committed Information Rate) percentage (Set the accuracy rate per hundred (1%)).' ;
                  type uint32 {
                    range 1..100 {
                      description 'The CIR percentage, support <1-100>' ;
                    }

                  }

                  mandatory true ;
                }

                leaf pir-percentage {
                  description 'Configure the PIR(Peak Information Rate) percentage (Set the accuracy rate per hundred (1%)).' ;
                  type uint32 {
                    range 1..100 {
                      description 'The PIR percentage, support <1-100>' ;
                    }

                  }

                  mandatory true ;
                }

                ncd:revise-date 2020-12-23 ;
              }

            }

            leaf statistical-share {
              description 'The flag of statistical-share.' ;
              type boolean ;

              default false ;
            }

            leaf token-bucket-id {
              description 'Set token bucket id.' ;
              type uint32 {
                range 1..4294967295 {
                  description 'Token bucket id' ;
                }

              }

              ncd:revise-date 2019-10-28 ;
            }

            container mode {
              if-feature qos-car-mode ;

              description 'Set color mode.' ;
              presence "Configure mode information" ;
              leaf mode-type {
                description 'Set color mode type.' ;
                type enumeration {
                  enum blind {
                    value 1 ;
                    description 'Color-Blind mode' ;
                  }

                  enum aware {
                    value 2 ;
                    description 'Color-Aware mode' ;
                  }

                }

                mandatory true ;
              }

            }

            container conform-action {
              description 'Action to packets that conform to the rate limit.' ;
              choice action {
                description 'Specify action to packets that conform to the rate limit.' ;
                mandatory true ;
                case ca-drop {
                  description 'Drop packet.' ;
                  leaf drop {
                    description 'Drop packet.' ;
                    type empty ;

                    mandatory true ;
                  }

                }

                case ca-transmit {
                  description 'Transmit packet.' ;
                  leaf transmit {
                    description 'Transmit packet.' ;
                    type empty ;

                    mandatory true ;
                  }

                }

                case ca-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case ca-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 {
                          description 'The IP-Precedence value, support <0-7>' ;
                        }

                      }

                      mandatory true ;
                    }

                  }

                }

                case ca-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case ca-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case ca-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case ca-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container exceed-action {
              description 'Action to packets that exceed the rate limit.' ;
              choice action {
                description 'Specify action to packets that exceed the rate limit.' ;
                mandatory true ;
                case ea-drop {
                  description 'Drop packet.' ;
                  leaf drop {
                    description 'Drop packet.' ;
                    type empty ;

                    mandatory true ;
                  }

                }

                case ea-transmit {
                  description 'Transmit packet.' ;
                  leaf transmit {
                    description 'Transmit packet.' ;
                    type empty ;

                    mandatory true ;
                  }

                }

                case ea-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case ea-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 {
                          description 'The IP-Precedence value, support <0-7>' ;
                        }

                      }

                      mandatory true ;
                    }

                  }

                }

                case ea-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case ea-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case ea-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case ea-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container violate-action {
              description 'Action to packets that violate the rate limit.' ;
              choice action {
                description 'Specify action to packets that violate the rate limit.' ;
                mandatory true ;
                case va-drop {
                  description 'Drop packet.' ;
                  leaf drop {
                    description 'Drop packet.' ;
                    type empty ;

                    mandatory true ;
                  }

                }

                case va-transmit {
                  description 'Transmit packet.' ;
                  leaf transmit {
                    description 'Transmit packet.' ;
                    type empty ;

                    mandatory true ;
                  }

                }

                case va-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case va-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 ;

                      }

                      mandatory true ;
                    }

                  }

                }

                case va-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case va-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case va-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case va-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container coupling-flag {
              description 'The Coupling Flag indicates whether tokens that would overflow the C-bucket should be added to the E-bucket.' ;
              presence "Configure coupling flag information" ;
              leaf cf-value {
                description 'Configure coupling-flag value.' ;
                type uint8 {
                  range 0..1 ;

                }

              }

              if-feature qos-car-cf ;

              ncd:revise-date 2023-09-12 ;
            }

            container adjust {
              description 'Configure QoS accuracy adjustment values.' ;
              presence "Configure adjust information" ;
              leaf adjust-value {
                description 'Configure QoS accuracy adjustment values.' ;
                type int32 {
                  range -32..31 ;

                }

              }

              if-feature qos-car-adjust ;

              ncd:revise-date 2023-09-12 ;
            }

          }

        }

        container multi-vlans {
          description 'Match inner and outer VLAN ID.' ;
          list multi-vlan {
            description 'Configure interface rate limit based on matching inner and outer vlan.' ;
            key 'if-name if-direct inner-vlan outer-vlan' ;
            leaf if-name {
              description 'Configure the name of the attaching interface.' ;
              type ncd:ifname {
                length 1..31 {
                  description 'Name of the attaching interface, support 1-31 characters' ;
                }

              }

            }

            leaf if-direct {
              description 'Specify the direction of interface.' ;
              type enumeration {
                enum input {
                  value 1 ;
                  description 'Rate limit on input' ;
                }

                enum output {
                  value 2 ;
                  description 'Rate limit on output' ;
                }

              }

            }

            leaf inner-vlan {
              description 'Configure inner-VLAN value in range mode, support single inner-VLAN value or range(max num:4;spacing mark:,) in <1-4094>. For example,"1,300-400,1000,2000-4000",etc.' ;
              type qos-vlan-range ;

            }

            leaf outer-vlan {
              description 'Configure outer-VLAN value in range mode, support single outer-VLAN value or range(max num:4;spacing mark:,) in <1-4094>. For example,"1,300-400,1000,2000-4000",etc.' ;
              type qos-vlan-range ;

            }

            leaf rate-limit-desc {
              description 'Description of rate limit, support 1-79 characters.' ;
              type ncd:string-with-blank {
                length 1..79 {
                  description 'Description of rate limit, support 1-79 characters.' ;
                }

              }

              ncd:revise-date 2020-06-18 ;
            }

            choice unit-style {
              description "Specify unit's style." ;
              mandatory true ;
              case unit-value {
                description 'Configure the value style.' ;
                leaf cir {
                  description 'Configure the CIR(Committed Information Rate) value (default: kilobits per second).' ;
                  type uint32 {
                    range 0..4294967295 {
                      description 'The CIR value (default: kilobits per second).' ;
                    }

                  }

                  mandatory true ;
                }

                leaf cir-unit {
                  description 'Set cir unit, such as kbps, mbps, gbps.' ;
                  type qos-rate-unit-type ;

                }

                leaf cbs {
                  description 'Configure the CBS(Committed Burst Size) size in bytes.' ;
                  type uint32 {
                    range 0..4294967294 {
                      description 'The CBS(Committed Burst Size) size in bytes.' ;
                    }

                  }

                  units byte ;
                }

                leaf pir {
                  description 'Configure the PIR(Peak Information Rate) value (default: kilobits per second).' ;
                  type uint32 {
                    range 0..4294967295 {
                      description 'The PIR(Peak Information Rate) value (default: kilobits per second).' ;
                    }

                  }

                  mandatory true ;
                }

                leaf pir-unit {
                  description 'Set pir unit, such as kbps, mbps, gbps.' ;
                  type qos-rate-unit-type ;

                }

                leaf pbs {
                  description 'Configure the PBS(Peak Burst Size) size in bytes.' ;
                  type uint32 {
                    range 0..4294967294 {
                      description 'The PBS(Peak Burst Size) size in KB.' ;
                    }

                  }

                  units byte ;
                }

              }

              case unit-percentage {
                description 'Configure the percentage style.' ;
                leaf cir-percentage {
                  description 'Configure the CIR(Committed Information Rate) percentage (Set the accuracy rate per hundred (1%)).' ;
                  type uint32 {
                    range 1..100 {
                      description 'The CIR percentage, support <1-100>' ;
                    }

                  }

                  mandatory true ;
                }

                leaf pir-percentage {
                  description 'Configure the PIR(Peak Information Rate) percentage (Set the accuracy rate per hundred (1%)).' ;
                  type uint32 {
                    range 1..100 {
                      description 'The PIR percentage, support <1-100>' ;
                    }

                  }

                  mandatory true ;
                }

                ncd:revise-date 2020-12-23 ;
              }

            }

            leaf statistical-share {
              description 'The flag of statistical-share.' ;
              type boolean ;

              default false ;
            }

            leaf token-bucket-id {
              description 'Set token bucket id.' ;
              type uint32 {
                range 1..4294967295 {
                  description 'Token bucket id' ;
                }

              }

              ncd:revise-date 2019-10-28 ;
            }

            container mode {
              if-feature qos-car-mode ;

              description 'Set color mode.' ;
              presence "Configure mode information" ;
              leaf mode-type {
                description 'Set color mode type.' ;
                type enumeration {
                  enum blind {
                    value 1 ;
                    description 'Color-Blind mode' ;
                  }

                  enum aware {
                    value 2 ;
                    description 'Color-Aware mode' ;
                  }

                }

                mandatory true ;
              }

            }

            container conform-action {
              description 'Action to packets that conform to the rate limit.' ;
              choice action {
                description 'Specify action to packets that conform to the rate limit.' ;
                mandatory true ;
                case ca-drop {
                  description 'Drop packet.' ;
                  leaf drop {
                    description 'Drop packet.' ;
                    type empty ;

                    mandatory true ;
                  }

                }

                case ca-transmit {
                  description 'Transmit packet.' ;
                  leaf transmit {
                    description 'Transmit packet.' ;
                    type empty ;

                    mandatory true ;
                  }

                }

                case ca-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case ca-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 {
                          description 'The IP-Precedence value, support <0-7>' ;
                        }

                      }

                      mandatory true ;
                    }

                  }

                }

                case ca-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case ca-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case ca-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case ca-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container exceed-action {
              description 'Action to packets that exceed the rate limit.' ;
              choice action {
                description 'Specify action to packets that exceed the rate limit.' ;
                mandatory true ;
                case ea-drop {
                  description 'Drop packet.' ;
                  leaf drop {
                    description 'Drop packet.' ;
                    type empty ;

                    mandatory true ;
                  }

                }

                case ea-transmit {
                  description 'Transmit packet.' ;
                  leaf transmit {
                    description 'Transmit packet.' ;
                    type empty ;

                    mandatory true ;
                  }

                }

                case ea-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case ea-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 {
                          description 'The IP-Precedence value, support <0-7>' ;
                        }

                      }

                      mandatory true ;
                    }

                  }

                }

                case ea-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case ea-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case ea-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case ea-service-class {
                  description 'Rewrite packet DSCP and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container violate-action {
              description 'Action to packets that violate the rate limit.' ;
              choice action {
                description 'Specify action to packets that violate the rate limit.' ;
                mandatory true ;
                case va-drop {
                  description 'Drop packet.' ;
                  leaf drop {
                    description 'Drop packet.' ;
                    type empty ;

                    mandatory true ;
                  }

                }

                case va-transmit {
                  description 'Transmit packet.' ;
                  leaf transmit {
                    description 'Transmit packet.' ;
                    type empty ;

                    mandatory true ;
                  }

                }

                case va-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case va-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 ;

                      }

                      mandatory true ;
                    }

                  }

                }

                case va-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case va-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case va-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case va-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container coupling-flag {
              description 'The Coupling Flag indicates whether tokens that would overflow the C-bucket should be added to the E-bucket.' ;
              presence "Configure coupling flag information" ;
              leaf cf-value {
                description 'Configure coupling-flag value.' ;
                type uint8 {
                  range 0..1 ;

                }

              }

              if-feature qos-car-cf ;

              ncd:revise-date 2023-09-12 ;
            }

            container adjust {
              description 'Configure QoS accuracy adjustment values.' ;
              presence "Configure adjust information" ;
              leaf adjust-value {
                description 'Configure QoS accuracy adjustment values.' ;
                type int32 {
                  range -32..31 ;

                }

              }

              if-feature qos-car-adjust ;

              ncd:revise-date 2023-09-12 ;
            }

          }

        }

        container inner-8021ps {
          description 'Match inner 802.1p value.' ;
          list inner-8021p {
            description 'Configure interface rate limit based on matching inner 802.1p.' ;
            key 'if-name if-direct in-8021p-value' ;
            leaf if-name {
              description 'Configure the name of the attaching interface.' ;
              type ncd:ifname {
                length 1..31 {
                  description 'Name of the attaching interface, support 1-31 characters' ;
                }

              }

            }

            leaf if-direct {
              description 'Specify the direction of interface.' ;
              type enumeration {
                enum input {
                  value 1 ;
                  description 'Rate limit on input' ;
                }

                enum output {
                  value 2 ;
                  description 'Rate limit on output' ;
                }

              }

            }

            leaf in-8021p-value {
              description 'Inner 802.1p value, support <0-7>.' ;
              type uint32 {
                range 0..7 {
                  description '802.1p value, support <0-7>' ;
                }

              }

            }

            leaf rate-limit-desc {
              description 'Description of rate limit, support 1-79 characters.' ;
              type ncd:string-with-blank {
                length 1..79 {
                  description 'Description of rate limit, support 1-79 characters.' ;
                }

              }

              ncd:revise-date 2020-06-18 ;
            }

            choice unit-style {
              description "Specify unit's style." ;
              mandatory true ;
              case unit-value {
                description 'Configure the value style.' ;
                leaf cir {
                  description 'Configure the CIR(Committed Information Rate) value (default: kilobits per second).' ;
                  type uint32 {
                    range 0..4294967295 {
                      description 'The CIR value (default: kilobits per second).' ;
                    }

                  }

                  mandatory true ;
                }

                leaf cir-unit {
                  description 'Set cir unit, such as kbps, mbps, gbps.' ;
                  type qos-rate-unit-type ;

                }

                leaf cbs {
                  description 'Configure the CBS(Committed Burst Size) size in bytes.' ;
                  type uint32 {
                    range 0..4294967294 {
                      description 'The CBS(Committed Burst Size) size in bytes.' ;
                    }

                  }

                  units byte ;
                }

                leaf pir {
                  description 'Configure the PIR(Peak Information Rate) value (default: kilobits per second).' ;
                  type uint32 {
                    range 0..4294967295 {
                      description 'The PIR(Peak Information Rate) value (default: kilobits per second).' ;
                    }

                  }

                  mandatory true ;
                }

                leaf pir-unit {
                  description 'Set pir unit, such as kbps, mbps, gbps.' ;
                  type qos-rate-unit-type ;

                }

                leaf pbs {
                  description 'Configure the PBS(Peak Burst Size) size in bytes.' ;
                  type uint32 {
                    range 0..4294967294 {
                      description 'The PBS(Peak Burst Size) size in KB.' ;
                    }

                  }

                  units byte ;
                }

              }

              case unit-percentage {
                description 'Configure the percentage style.' ;
                leaf cir-percentage {
                  description 'Configure the CIR(Committed Information Rate) percentage (Set the accuracy rate per hundred (1%)).' ;
                  type uint32 {
                    range 1..100 {
                      description 'The CIR percentage, support <1-100>' ;
                    }

                  }

                  mandatory true ;
                }

                leaf pir-percentage {
                  description 'Configure the PIR(Peak Information Rate) percentage (Set the accuracy rate per hundred (1%)).' ;
                  type uint32 {
                    range 1..100 {
                      description 'The PIR percentage, support <1-100>' ;
                    }

                  }

                  mandatory true ;
                }

                ncd:revise-date 2020-12-23 ;
              }

            }

            leaf statistical-share {
              description 'The flag of statistical-share.' ;
              type boolean ;

              default false ;
            }

            leaf token-bucket-id {
              description 'Set token bucket id.' ;
              type uint32 {
                range 1..4294967295 {
                  description 'Token bucket id' ;
                }

              }

              ncd:revise-date 2019-10-28 ;
            }

            container mode {
              if-feature qos-car-mode ;

              description 'Set color mode.' ;
              presence "Configure mode information" ;
              leaf mode-type {
                description 'Set color mode type.' ;
                type enumeration {
                  enum blind {
                    value 1 ;
                    description 'Color-Blind mode' ;
                  }

                  enum aware {
                    value 2 ;
                    description 'Color-Aware mode' ;
                  }

                }

                mandatory true ;
              }

            }

            container conform-action {
              description 'Action to packets that conform to the rate limit.' ;
              choice action {
                description 'Specify action to packets that conform to the rate limit.' ;
                mandatory true ;
                case ca-drop {
                  description 'Drop packet.' ;
                  leaf drop {
                    description 'Drop packet.' ;
                    type empty ;

                    mandatory true ;
                  }

                }

                case ca-transmit {
                  description 'Transmit packet.' ;
                  leaf transmit {
                    description 'Transmit packet.' ;
                    type empty ;

                    mandatory true ;
                  }

                }

                case ca-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case ca-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 {
                          description 'The IP-Precedence value, support <0-7>' ;
                        }

                      }

                      mandatory true ;
                    }

                  }

                }

                case ca-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case ca-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case ca-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case ca-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container exceed-action {
              description 'Action to packets that exceed the rate limit.' ;
              choice action {
                description 'Specify action to packets that exceed the rate limit.' ;
                mandatory true ;
                case ea-drop {
                  description 'Drop packet.' ;
                  leaf drop {
                    description 'Drop packet.' ;
                    type empty ;

                    mandatory true ;
                  }

                }

                case ea-transmit {
                  description 'Transmit packet.' ;
                  leaf transmit {
                    description 'Transmit packet.' ;
                    type empty ;

                    mandatory true ;
                  }

                }

                case ea-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case ea-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 {
                          description 'The IP-Precedence value, support <0-7>' ;
                        }

                      }

                      mandatory true ;
                    }

                  }

                }

                case ea-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case ea-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case ea-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case ea-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container violate-action {
              description 'Action to packets that violate the rate limit.' ;
              choice action {
                description 'Specify action to packets that violate the rate limit.' ;
                mandatory true ;
                case va-drop {
                  description 'Drop packet.' ;
                  leaf drop {
                    description 'Drop packet.' ;
                    type empty ;

                    mandatory true ;
                  }

                }

                case va-transmit {
                  description 'Transmit packet.' ;
                  leaf transmit {
                    description 'Transmit packet.' ;
                    type empty ;

                    mandatory true ;
                  }

                }

                case va-mpls-exp {
                  description 'Rewrite packet MPLS-EXP and transmit the packet .' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case va-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 ;

                      }

                      mandatory true ;
                    }

                  }

                }

                case va-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case va-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case va-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case va-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container coupling-flag {
              description 'The Coupling Flag indicates whether tokens that would overflow the C-bucket should be added to the E-bucket.' ;
              presence "Configure coupling flag information" ;
              leaf cf-value {
                description 'Configure coupling-flag value.' ;
                type uint8 {
                  range 0..1 ;

                }

              }

              if-feature qos-car-cf ;

              ncd:revise-date 2023-09-12 ;
            }

            container adjust {
              description 'Configure QoS accuracy adjustment values.' ;
              presence "Configure adjust information" ;
              leaf adjust-value {
                description 'Configure QoS accuracy adjustment values.' ;
                type int32 {
                  range -32..31 ;

                }

              }

              if-feature qos-car-adjust ;

              ncd:revise-date 2023-09-12 ;
            }

          }

        }

        container outer-8021ps {
          description 'Match outer 802.1p value.' ;
          list outer-8021p {
            description 'Configure interface rate limit based on matching outer 802.1p.' ;
            key 'if-name if-direct out-8021p-value' ;
            leaf if-name {
              description 'Configure the name of the attaching interface.' ;
              type ncd:ifname {
                length 1..31 {
                  description 'Name of the attaching interface, support 1-31 characters' ;
                }

              }

            }

            leaf if-direct {
              description 'Specify the direction of interface.' ;
              type enumeration {
                enum input {
                  value 1 ;
                  description 'Rate limit on input' ;
                }

                enum output {
                  value 2 ;
                  description 'Rate limit on output' ;
                }

              }

            }

            leaf out-8021p-value {
              description 'Outer 802.1p value, support <0-7>.' ;
              type uint32 {
                range 0..7 {
                  description '802.1p value, support <0-7>' ;
                }

              }

            }

            leaf rate-limit-desc {
              description 'Description of rate limit, support 1-79 characters.' ;
              type ncd:string-with-blank {
                length 1..79 {
                  description 'Description of rate limit, support 1-79 characters.' ;
                }

              }

              ncd:revise-date 2020-06-18 ;
            }

            choice unit-style {
              description "Specify unit's style." ;
              mandatory true ;
              case unit-value {
                description 'Configure the value style.' ;
                leaf cir {
                  description 'Configure the CIR(Committed Information Rate) value (default: kilobits per second).' ;
                  type uint32 {
                    range 0..4294967295 {
                      description 'The CIR value (default: kilobits per second).' ;
                    }

                  }

                  mandatory true ;
                }

                leaf cir-unit {
                  description 'Set cir unit, such as kbps, mbps, gbps.' ;
                  type qos-rate-unit-type ;

                }

                leaf cbs {
                  description 'Configure the CBS(Committed Burst Size) size in bytes.' ;
                  type uint32 {
                    range 0..4294967294 {
                      description 'The CBS(Committed Burst Size) size in bytes.' ;
                    }

                  }

                  units byte ;
                }

                leaf pir {
                  description 'Configure the PIR(Peak Information Rate) value (default: kilobits per second).' ;
                  type uint32 {
                    range 0..4294967295 {
                      description 'The PIR(Peak Information Rate) value (default: kilobits per second).' ;
                    }

                  }

                  mandatory true ;
                }

                leaf pir-unit {
                  description 'Set pir unit, such as kbps, mbps, gbps.' ;
                  type qos-rate-unit-type ;

                }

                leaf pbs {
                  description 'Configure the PBS(Peak Burst Size) size in bytes.' ;
                  type uint32 {
                    range 0..4294967294 {
                      description 'The PBS(Peak Burst Size) size in KB.' ;
                    }

                  }

                  units byte ;
                }

              }

              case unit-percentage {
                description 'Configure the percentage style.' ;
                leaf cir-percentage {
                  description 'Configure the CIR(Committed Information Rate) percentage (Set the accuracy rate per hundred (1%)).' ;
                  type uint32 {
                    range 1..100 {
                      description 'The CIR percentage, support <1-100>' ;
                    }

                  }

                  mandatory true ;
                }

                leaf pir-percentage {
                  description 'Configure the PIR(Peak Information Rate) percentage (Set the accuracy rate per hundred (1%)).' ;
                  type uint32 {
                    range 1..100 {
                      description 'The PIR percentage, support <1-100>' ;
                    }

                  }

                  mandatory true ;
                }

                ncd:revise-date 2020-12-23 ;
              }

            }

            leaf statistical-share {
              description 'The flag of statistical-share.' ;
              type boolean ;

              default false ;
            }

            leaf token-bucket-id {
              description 'Set token bucket id.' ;
              type uint32 {
                range 1..4294967295 {
                  description 'Token bucket id' ;
                }

              }

              ncd:revise-date 2019-10-28 ;
            }

            container mode {
              if-feature qos-car-mode ;

              description 'Set color mode.' ;
              presence "Configure mode information" ;
              leaf mode-type {
                description 'Set color mode type.' ;
                type enumeration {
                  enum blind {
                    value 1 ;
                    description 'Color-Blind mode' ;
                  }

                  enum aware {
                    value 2 ;
                    description 'Color-Aware mode' ;
                  }

                }

                mandatory true ;
              }

            }

            container conform-action {
              description 'Action to packets that conform to the rate limit.' ;
              choice action {
                description 'Specify action to packets that conform to the rate limit.' ;
                mandatory true ;
                case ca-drop {
                  description 'Drop packet.' ;
                  leaf drop {
                    description 'Drop packet.' ;
                    type empty ;

                    mandatory true ;
                  }

                }

                case ca-transmit {
                  description 'Transmit packet.' ;
                  leaf transmit {
                    description 'Transmit packet.' ;
                    type empty ;

                    mandatory true ;
                  }

                }

                case ca-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case ca-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 {
                          description 'The IP-Precedence value, support <0-7>' ;
                        }

                      }

                      mandatory true ;
                    }

                  }

                }

                case ca-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case ca-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case ca-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case ca-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container exceed-action {
              description 'Action to packets that exceed the rate limit.' ;
              choice action {
                description 'Specify action to packets that exceed the rate limit.' ;
                mandatory true ;
                case ea-drop {
                  description 'Drop packet.' ;
                  leaf drop {
                    description 'Drop packet.' ;
                    type empty ;

                    mandatory true ;
                  }

                }

                case ea-transmit {
                  description 'Transmit packet.' ;
                  leaf transmit {
                    description 'Transmit packet.' ;
                    type empty ;

                    mandatory true ;
                  }

                }

                case ea-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case ea-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 {
                          description 'The IP-Precedence value, support <0-7>' ;
                        }

                      }

                      mandatory true ;
                    }

                  }

                }

                case ea-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case ea-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case ea-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case ea-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container violate-action {
              description 'Action to packets that violate the rate limit.' ;
              choice action {
                description 'Specify action to packets that violate the rate limit.' ;
                mandatory true ;
                case va-drop {
                  description 'Drop packet.' ;
                  leaf drop {
                    description 'Drop packet.' ;
                    type empty ;

                    mandatory true ;
                  }

                }

                case va-transmit {
                  description 'Transmit packet.' ;
                  leaf transmit {
                    description 'Transmit packet.' ;
                    type empty ;

                    mandatory true ;
                  }

                }

                case va-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case va-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 ;

                      }

                      mandatory true ;
                    }

                  }

                }

                case va-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case va-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case va-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case va-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container coupling-flag {
              description 'The Coupling Flag indicates whether tokens that would overflow the C-bucket should be added to the E-bucket.' ;
              presence "Configure coupling flag information" ;
              leaf cf-value {
                description 'Configure coupling-flag value.' ;
                type uint8 {
                  range 0..1 ;

                }

              }

              if-feature qos-car-cf ;

              ncd:revise-date 2023-09-12 ;
            }

            container adjust {
              description 'Configure QoS accuracy adjustment values.' ;
              presence "Configure adjust information" ;
              leaf adjust-value {
                description 'Configure QoS accuracy adjustment values.' ;
                type int32 {
                  range -32..31 ;

                }

              }

              if-feature qos-car-adjust ;

              ncd:revise-date 2023-09-12 ;
            }

          }

        }

        container multi-8021ps {
          description 'Match inner and outer 802.1p value.' ;
          list multi-8021p {
            description 'Configure interface rate limit based on matching inner and outer 802.1p.' ;
            key 'if-name if-direct in-8021p-value out-8021p-value' ;
            leaf if-name {
              description 'Configure the name of the attaching interface.' ;
              type ncd:ifname {
                length 1..31 {
                  description 'Name of the attaching interface, support 1-31 characters' ;
                }

              }

            }

            leaf if-direct {
              description 'Specify the direction of interface.' ;
              type enumeration {
                enum input {
                  value 1 ;
                  description 'Rate limit on input' ;
                }

                enum output {
                  value 2 ;
                  description 'Rate limit on output' ;
                }

              }

            }

            leaf in-8021p-value {
              description 'Inner 802.1p value, support <0-7>.' ;
              type uint32 {
                range 0..7 {
                  description '802.1p value, support <0-7>' ;
                }

              }

            }

            leaf out-8021p-value {
              description 'Outer 802.1p value, support <0-7>.' ;
              type uint32 {
                range 0..7 {
                  description '802.1p value, support <0-7>' ;
                }

              }

            }

            leaf rate-limit-desc {
              description 'Description of rate limit, support 1-79 characters.' ;
              type ncd:string-with-blank {
                length 1..79 {
                  description 'Description of rate limit, support 1-79 characters.' ;
                }

              }

              ncd:revise-date 2020-06-18 ;
            }

            choice unit-style {
              description "Specify unit's style." ;
              mandatory true ;
              case unit-value {
                description 'Configure the value style.' ;
                leaf cir {
                  description 'Configure the CIR(Committed Information Rate) value (default: kilobits per second).' ;
                  type uint32 {
                    range 0..4294967295 {
                      description 'The CIR value (default: kilobits per second).' ;
                    }

                  }

                  mandatory true ;
                }

                leaf cir-unit {
                  description 'Set cir unit, such as kbps, mbps, gbps.' ;
                  type qos-rate-unit-type ;

                }

                leaf cbs {
                  description 'Configure the CBS(Committed Burst Size) size in bytes.' ;
                  type uint32 {
                    range 0..4294967294 {
                      description 'The CBS(Committed Burst Size) size in bytes.' ;
                    }

                  }

                  units byte ;
                }

                leaf pir {
                  description 'Configure the PIR(Peak Information Rate) value (default: kilobits per second).' ;
                  type uint32 {
                    range 0..4294967295 {
                      description 'The PIR(Peak Information Rate) value (default: kilobits per second).' ;
                    }

                  }

                  mandatory true ;
                }

                leaf pir-unit {
                  description 'Set pir unit, such as kbps, mbps, gbps.' ;
                  type qos-rate-unit-type ;

                }

                leaf pbs {
                  description 'Configure the PBS(Peak Burst Size) size in bytes.' ;
                  type uint32 {
                    range 0..4294967294 {
                      description 'The PBS(Peak Burst Size) size in KB.' ;
                    }

                  }

                  units byte ;
                }

              }

              case unit-percentage {
                description 'Configure the percentage style.' ;
                leaf cir-percentage {
                  description 'Configure the CIR(Committed Information Rate) percentage (Set the accuracy rate per hundred (1%)).' ;
                  type uint32 {
                    range 1..100 {
                      description 'The CIR percentage, support <1-100>' ;
                    }

                  }

                  mandatory true ;
                }

                leaf pir-percentage {
                  description 'Configure the PIR(Peak Information Rate) percentage (Set the accuracy rate per hundred (1%)).' ;
                  type uint32 {
                    range 1..100 {
                      description 'The PIR percentage, support <1-100>' ;
                    }

                  }

                  mandatory true ;
                }

                ncd:revise-date 2020-12-23 ;
              }

            }

            leaf statistical-share {
              description 'The flag of statistical-share.' ;
              type boolean ;

              default false ;
            }

            leaf token-bucket-id {
              description 'Set token bucket id.' ;
              type uint32 {
                range 1..4294967295 {
                  description 'Token bucket id' ;
                }

              }

              ncd:revise-date 2019-10-28 ;
            }

            container mode {
              if-feature qos-car-mode ;

              description 'Set color mode.' ;
              presence "Configure mode information" ;
              leaf mode-type {
                description 'Set color mode type.' ;
                type enumeration {
                  enum blind {
                    value 1 ;
                    description 'Color-Blind mode' ;
                  }

                  enum aware {
                    value 2 ;
                    description 'Color-Aware mode' ;
                  }

                }

                mandatory true ;
              }

            }

            container conform-action {
              description 'Action to packets that conform to the rate limit.' ;
              choice action {
                description 'Specify action to packets that conform to the rate limit.' ;
                mandatory true ;
                case ca-drop {
                  description 'Drop packet.' ;
                  leaf drop {
                    description 'Drop packet.' ;
                    type empty ;

                    mandatory true ;
                  }

                }

                case ca-transmit {
                  description 'Transmit packet.' ;
                  leaf transmit {
                    description 'Transmit packet.' ;
                    type empty ;

                    mandatory true ;
                  }

                }

                case ca-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case ca-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 {
                          description 'The IP-Precedence value, support <0-7>' ;
                        }

                      }

                      mandatory true ;
                    }

                  }

                }

                case ca-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case ca-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case ca-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case ca-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container exceed-action {
              description 'Action to packets that exceed the rate limit.' ;
              choice action {
                description 'Specify action to packets that exceed the rate limit.' ;
                mandatory true ;
                case ea-drop {
                  description 'Drop packet.' ;
                  leaf drop {
                    description 'Drop packet.' ;
                    type empty ;

                    mandatory true ;
                  }

                }

                case ea-transmit {
                  description 'Transmit packet.' ;
                  leaf transmit {
                    description 'Transmit packet.' ;
                    type empty ;

                    mandatory true ;
                  }

                }

                case ea-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case ea-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 {
                          description 'The IP-Precedence value, support <0-7>' ;
                        }

                      }

                      mandatory true ;
                    }

                  }

                }

                case ea-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case ea-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case ea-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case ea-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container violate-action {
              description 'Action to packets that violate the rate limit.' ;
              choice action {
                description 'Specify action to packets that violate the rate limit.' ;
                mandatory true ;
                case va-drop {
                  description 'Drop packet.' ;
                  leaf drop {
                    description 'Drop packet.' ;
                    type empty ;

                    mandatory true ;
                  }

                }

                case va-transmit {
                  description 'Transmit packet.' ;
                  leaf transmit {
                    description 'Transmit packet.' ;
                    type empty ;

                    mandatory true ;
                  }

                }

                case va-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case va-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 ;

                      }

                      mandatory true ;
                    }

                  }

                }

                case va-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case va-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case va-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case va-service-class {
                  description 'Rewrite packet service class and transmit the packet.' ;
                  container set-service-class-transmit {
                    description 'Rewrite packet service class and transmit it.' ;
                    leaf service-class-value {
                      description 'Reset service-class.' ;
                      type qos-service-class ;

                      mandatory true ;
                    }

                  }

                  ncd:revise-date 2020-05-18 ;
                }

              }

            }

            container coupling-flag {
              description 'The Coupling Flag indicates whether tokens that would overflow the C-bucket should be added to the E-bucket.' ;
              presence "Configure coupling flag information" ;
              leaf cf-value {
                description 'Configure coupling-flag value.' ;
                type uint8 {
                  range 0..1 ;

                }

              }

              if-feature qos-car-cf ;

              ncd:revise-date 2023-09-12 ;
            }

            container adjust {
              description 'Configure QoS accuracy adjustment values.' ;
              presence "Configure adjust information" ;
              leaf adjust-value {
                description 'Configure QoS accuracy adjustment values.' ;
                type int32 {
                  range -32..31 ;

                }

              }

              if-feature qos-car-adjust ;

              ncd:revise-date 2023-09-12 ;
            }

          }

        }

        container qos-groups {
          description 'Match qos-group number.' ;
          list qos-group {
            description 'Configure interface rate limit based on matching qos group.' ;
            key 'if-name if-direct qos-id' ;
            leaf if-name {
              description 'Configure the name of the attaching interface.' ;
              type ncd:ifname {
                length 1..31 {
                  description 'Name of the attaching interface, support 1-31 characters' ;
                }

              }

            }

            leaf if-direct {
              description 'Specify the direction of interface.' ;
              type enumeration {
                enum input {
                  value 1 ;
                  description 'Rate limit on input' ;
                }

                enum output {
                  value 2 ;
                  description 'Rate limit on output' ;
                }

              }

            }

            leaf qos-id {
              description 'Qos group number, support <1-16000>.' ;
              type uint32 {
                range 1..16000 {
                  description 'Qos group number,support <1-16000>' ;
                }

              }

            }

            leaf rate-limit-desc {
              description 'Description of rate limit, support 1-79 characters.' ;
              type ncd:string-with-blank {
                length 1..79 {
                  description 'Description of rate limit, support 1-79 characters.' ;
                }

              }

              ncd:revise-date 2020-06-18 ;
            }

            choice unit-style {
              description "Specify unit's style." ;
              mandatory true ;
              case unit-value {
                description 'Configure the value style.' ;
                leaf cir {
                  description 'Configure the CIR(Committed Information Rate) value (default: kilobits per second).' ;
                  type uint32 {
                    range 0..4294967295 {
                      description 'The CIR value (default: kilobits per second).' ;
                    }

                  }

                  mandatory true ;
                }

                leaf cir-unit {
                  description 'Set cir unit, such as kbps, mbps, gbps.' ;
                  type qos-rate-unit-type ;

                }

                leaf cbs {
                  description 'Configure the CBS(Committed Burst Size) size in bytes.' ;
                  type uint32 {
                    range 0..4294967294 {
                      description 'The CBS(Committed Burst Size) size in bytes.' ;
                    }

                  }

                  units byte ;
                }

                leaf pir {
                  description 'Configure the PIR(Peak Information Rate) value (default: kilobits per second).' ;
                  type uint32 {
                    range 0..4294967295 {
                      description 'The PIR(Peak Information Rate) value (default: kilobits per second).' ;
                    }

                  }

                  mandatory true ;
                }

                leaf pir-unit {
                  description 'Set pir unit, such as kbps, mbps, gbps.' ;
                  type qos-rate-unit-type ;

                }

                leaf pbs {
                  description 'Configure the PBS(Peak Burst Size) size in bytes.' ;
                  type uint32 {
                    range 0..4294967294 {
                      description 'The PBS(Peak Burst Size) size in KB.' ;
                    }

                  }

                  units byte ;
                }

              }

              case unit-percentage {
                description 'Configure the percentage style.' ;
                leaf cir-percentage {
                  description 'Configure the CIR(Committed Information Rate) percentage (Set the accuracy rate per hundred (1%)).' ;
                  type uint32 {
                    range 1..100 {
                      description 'The CIR percentage, support <1-100>' ;
                    }

                  }

                  mandatory true ;
                }

                leaf pir-percentage {
                  description 'Configure the PIR(Peak Information Rate) percentage (Set the accuracy rate per hundred (1%)).' ;
                  type uint32 {
                    range 1..100 {
                      description 'The PIR percentage, support <1-100>' ;
                    }

                  }

                  mandatory true ;
                }

                ncd:revise-date 2020-12-23 ;
              }

            }

            leaf statistical-share {
              description 'The flag of statistical-share.' ;
              type boolean ;

              default false ;
            }

            leaf token-bucket-id {
              description 'Set token bucket id.' ;
              type uint32 {
                range 1..4294967295 {
                  description 'Token bucket id' ;
                }

              }

              ncd:revise-date 2019-10-28 ;
            }

            container mode {
              if-feature qos-car-mode ;

              description 'Set color mode.' ;
              presence "Configure mode information" ;
              leaf mode-type {
                description 'Set color mode type.' ;
                type enumeration {
                  enum blind {
                    value 1 ;
                    description 'Color-Blind mode' ;
                  }

                  enum aware {
                    value 2 ;
                    description 'Color-Aware mode' ;
                  }

                }

                mandatory true ;
              }

            }

            container conform-action {
              description 'Action to packets that conform to the rate limit.' ;
              choice action {
                description 'Specify action to packets that conform to the rate limit.' ;
                mandatory true ;
                case ca-drop {
                  description 'Drop packet.' ;
                  leaf drop {
                    description 'Drop packet.' ;
                    type empty ;

                    mandatory true ;
                  }

                }

                case ca-transmit {
                  description 'Transmit packet.' ;
                  leaf transmit {
                    description 'Transmit packet.' ;
                    type empty ;

                    mandatory true ;
                  }

                }

                case ca-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case ca-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 {
                          description 'The IP-Precedence value, support <0-7>' ;
                        }

                      }

                      mandatory true ;
                    }

                  }

                }

                case ca-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case ca-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case ca-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case ca-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container exceed-action {
              description 'Action to packets that exceed the rate limit.' ;
              choice action {
                description 'Specify action to packets that exceed the rate limit.' ;
                mandatory true ;
                case ea-drop {
                  description 'Drop packet.' ;
                  leaf drop {
                    description 'Drop packet.' ;
                    type empty ;

                    mandatory true ;
                  }

                }

                case ea-transmit {
                  description 'Transmit packet.' ;
                  leaf transmit {
                    description 'Transmit packet.' ;
                    type empty ;

                    mandatory true ;
                  }

                }

                case ea-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case ea-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 {
                          description 'The IP-Precedence value, support <0-7>' ;
                        }

                      }

                      mandatory true ;
                    }

                  }

                }

                case ea-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case ea-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case ea-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case ea-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container violate-action {
              description 'Action to packets that violate the rate limit.' ;
              choice action {
                description 'Specify action to packets that violate the rate limit.' ;
                mandatory true ;
                case va-drop {
                  description 'Drop packet.' ;
                  leaf drop {
                    description 'Drop packet.' ;
                    type empty ;

                    mandatory true ;
                  }

                }

                case va-transmit {
                  description 'Transmit packet.' ;
                  leaf transmit {
                    description 'Transmit packet.' ;
                    type empty ;

                    mandatory true ;
                  }

                }

                case va-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case va-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 ;

                      }

                      mandatory true ;
                    }

                  }

                }

                case va-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case va-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case va-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case va-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container coupling-flag {
              description 'The Coupling Flag indicates whether tokens that would overflow the C-bucket should be added to the E-bucket.' ;
              presence "Configure coupling flag information" ;
              leaf cf-value {
                description 'Configure coupling-flag value.' ;
                type uint8 {
                  range 0..1 ;

                }

              }

              if-feature qos-car-cf ;

              ncd:revise-date 2023-09-12 ;
            }

            container adjust {
              description 'Configure QoS accuracy adjustment values.' ;
              presence "Configure adjust information" ;
              leaf adjust-value {
                description 'Configure QoS accuracy adjustment values.' ;
                type int32 {
                  range -32..31 ;

                }

              }

              if-feature qos-car-adjust ;

              ncd:revise-date 2023-09-12 ;
            }

          }

        }

        container access-lists {
          description 'Match access list.' ;
          list access-list {
            description 'Configure interface rate limit based on matching ACL.' ;
            key 'if-name if-direct acl-type acl-name' ;
            leaf if-name {
              description 'Configure the name of the attaching interface.' ;
              type ncd:ifname {
                length 1..31 {
                  description 'Name of the attaching interface, support 1-31 characters' ;
                }

              }

            }

            leaf if-direct {
              description 'Specify the direction of interface.' ;
              type enumeration {
                enum input {
                  value 1 ;
                  description 'Rate limit on input' ;
                }

                enum output {
                  value 2 ;
                  description 'Rate limit on output' ;
                }

              }

            }

            leaf acl-type {
              description 'Specify the type of access list.' ;
              type enumeration {
                enum ipv4-acl {
                  value 5 ;
                  description 'Match IPv4 access list' ;
                }

                enum ipv6-acl {
                  value 6 ;
                  description 'Match IPv6 access list' ;
                }

                enum link-acl {
                  value 15 ;
                  description 'Match link access list' ;
                }

                enum ipv4-mixed-acl {
                  value 19 ;
                  description 'Match ipv4 mixed access list' ;
                }

                enum ipv6-mixed-acl {
                  value 20 ;
                  description 'Match ipv6 mixed access list' ;
                }

              }

            }

            leaf acl-name {
              description 'Name of access list, support 1-31 characters.' ;
              type string {
                length 1..31 {
                  description 'Name of IPv4 access list, support 1-31 characters' ;
                }

              }

            }

            leaf rate-limit-desc {
              description 'Description of rate limit, support 1-79 characters.' ;
              type ncd:string-with-blank {
                length 1..79 {
                  description 'Description of rate limit, support 1-79 characters.' ;
                }

              }

              ncd:revise-date 2020-06-18 ;
            }

            choice unit-style {
              description "Specify unit's style." ;
              mandatory true ;
              case unit-value {
                description 'Configure the value style.' ;
                leaf cir {
                  description 'Configure the CIR(Committed Information Rate) value (default: kilobits per second).' ;
                  type uint32 {
                    range 0..4294967295 {
                      description 'The CIR value (default: kilobits per second).' ;
                    }

                  }

                  mandatory true ;
                }

                leaf cir-unit {
                  description 'Set cir unit, such as kbps, mbps, gbps.' ;
                  type qos-rate-unit-type ;

                }

                leaf cbs {
                  description 'Configure the CBS(Committed Burst Size) size in bytes.' ;
                  type uint32 {
                    range 0..4294967294 {
                      description 'The CBS(Committed Burst Size) size in bytes.' ;
                    }

                  }

                  units byte ;
                }

                leaf pir {
                  description 'Configure the PIR(Peak Information Rate) value (default: kilobits per second).' ;
                  type uint32 {
                    range 0..4294967295 {
                      description 'The PIR(Peak Information Rate) value (default: kilobits per second).' ;
                    }

                  }

                  mandatory true ;
                }

                leaf pir-unit {
                  description 'Set pir unit, such as kbps, mbps, gbps.' ;
                  type qos-rate-unit-type ;

                }

                leaf pbs {
                  description 'Configure the PBS(Peak Burst Size) size in bytes.' ;
                  type uint32 {
                    range 0..4294967294 {
                      description 'The PBS(Peak Burst Size) size in KB.' ;
                    }

                  }

                  units byte ;
                }

              }

              case unit-percentage {
                description 'Configure the percentage style.' ;
                leaf cir-percentage {
                  description 'Configure the CIR(Committed Information Rate) percentage (Set the accuracy rate per hundred (1%)).' ;
                  type uint32 {
                    range 1..100 {
                      description 'The CIR percentage, support <1-100>' ;
                    }

                  }

                  mandatory true ;
                }

                leaf pir-percentage {
                  description 'Configure the PIR(Peak Information Rate) percentage (Set the accuracy rate per hundred (1%)).' ;
                  type uint32 {
                    range 1..100 {
                      description 'The PIR percentage, support <1-100>' ;
                    }

                  }

                  mandatory true ;
                }

                ncd:revise-date 2020-12-23 ;
              }

            }

            leaf statistical-share {
              description 'The flag of statistical-share.' ;
              type boolean ;

              default false ;
            }

            leaf token-bucket-id {
              description 'Set token bucket id.' ;
              type uint32 {
                range 1..4294967295 {
                  description 'Token bucket id' ;
                }

              }

              ncd:revise-date 2019-10-28 ;
            }

            container mode {
              if-feature qos-car-mode ;

              description 'Set color mode.' ;
              presence "Configure mode information" ;
              leaf mode-type {
                description 'Set color mode type.' ;
                type enumeration {
                  enum blind {
                    value 1 ;
                    description 'Color-Blind mode' ;
                  }

                  enum aware {
                    value 2 ;
                    description 'Color-Aware mode' ;
                  }

                }

                mandatory true ;
              }

            }

            container conform-action {
              description 'Action to packets that conform to the rate limit.' ;
              choice action {
                description 'Specify action to packets that conform to the rate limit.' ;
                mandatory true ;
                case ca-drop {
                  description 'Drop packet.' ;
                  leaf drop {
                    description 'Drop packet.' ;
                    type empty ;

                    mandatory true ;
                  }

                }

                case ca-transmit {
                  description 'Transmit packet.' ;
                  leaf transmit {
                    description 'Transmit packet.' ;
                    type empty ;

                    mandatory true ;
                  }

                }

                case ca-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case ca-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 {
                          description 'The IP-Precedence value, support <0-7>' ;
                        }

                      }

                      mandatory true ;
                    }

                  }

                }

                case ca-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case ca-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case ca-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case ca-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container exceed-action {
              description 'Action to packets that exceed the rate limit.' ;
              choice action {
                description 'Specify action to packets that exceed the rate limit.' ;
                mandatory true ;
                case ea-drop {
                  description 'Drop packet.' ;
                  leaf drop {
                    description 'Drop packet.' ;
                    type empty ;

                    mandatory true ;
                  }

                }

                case ea-transmit {
                  description 'Transmit packet.' ;
                  leaf transmit {
                    description 'Transmit packet.' ;
                    type empty ;

                    mandatory true ;
                  }

                }

                case ea-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case ea-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 {
                          description 'The IP-Precedence value, support <0-7>' ;
                        }

                      }

                      mandatory true ;
                    }

                  }

                }

                case ea-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case ea-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case ea-multi-exp {
                  description 'Rewrite packet multi-MPLS-EXP and transmit it' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case ea-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container violate-action {
              description 'Action to packets that violate the rate limit.' ;
              choice action {
                description 'Specify action to packets that violate the rate limit.' ;
                mandatory true ;
                case va-drop {
                  description 'Drop packet.' ;
                  leaf drop {
                    description 'Drop packet.' ;
                    type empty ;

                    mandatory true ;
                  }

                }

                case va-transmit {
                  description 'Transmit packet.' ;
                  leaf transmit {
                    description 'Transmit packet.' ;
                    type empty ;

                    mandatory true ;
                  }

                }

                case va-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case va-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 ;

                      }

                      mandatory true ;
                    }

                  }

                }

                case va-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case va-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                      ncd:revise-date 2017-01-10 ;
                    }

                  }

                }

                case va-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case va-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                  ncd:revise-date 2020-05-18 ;
                }

              }

            }

            container coupling-flag {
              description 'The Coupling Flag indicates whether tokens that would overflow the C-bucket should be added to the E-bucket.' ;
              presence "Configure coupling flag information" ;
              leaf cf-value {
                description 'Configure coupling-flag value.' ;
                type uint8 {
                  range 0..1 ;

                }

              }

              if-feature qos-car-cf ;

              ncd:revise-date 2023-09-12 ;
            }

            container adjust {
              description 'Configure QoS accuracy adjustment values.' ;
              presence "Configure adjust information" ;
              leaf adjust-value {
                description 'Configure QoS accuracy adjustment values.' ;
                type int32 {
                  range -32..31 ;

                }

              }

              if-feature qos-car-adjust ;

              ncd:revise-date 2023-09-12 ;
            }

          }

        }

        container bums {
          description 'Match broadcast, unknown unicast and unknown multicast.' ;
          list bum {
            description 'Configure interface rate limit based on matching broadcast, unknown unicast and unknown multicast.' ;
            key 'if-name if-direct' ;
            leaf if-name {
              description 'Configure the name of the attaching interface.' ;
              type ncd:ifname {
                length 1..31 {
                  description 'Name of the attaching interface, support 1-31 characters' ;
                }

              }

            }

            leaf if-direct {
              description 'Specify the direction of interface.' ;
              type enumeration {
                enum input {
                  value 1 ;
                  description 'Rate limit on input' ;
                }

                enum output {
                  value 2 ;
                  description 'Rate limit on output' ;
                }

              }

            }

            leaf rate-limit-desc {
              description 'Description of rate limit, support 1-79 characters.' ;
              type ncd:string-with-blank {
                length 1..79 {
                  description 'Description of rate limit, support 1-79 characters.' ;
                }

              }

            }

            choice unit-style {
              description "Specify unit's style." ;
              mandatory true ;
              case unit-value {
                description 'Configure the value style.' ;
                leaf cir {
                  description 'Configure the CIR(Committed Information Rate) value (default: kilobits per second).' ;
                  type uint32 {
                    range 0..4294967295 {
                      description 'The CIR value (default: kilobits per second).' ;
                    }

                  }

                  mandatory true ;
                }

                leaf cir-unit {
                  description 'Set cir unit, such as kbps, mbps, gbps.' ;
                  type qos-rate-unit-type ;

                }

                leaf cbs {
                  description 'Configure the CBS(Committed Burst Size) size in bytes.' ;
                  type uint32 {
                    range 0..4294967294 {
                      description 'The CBS(Committed Burst Size) size in bytes.' ;
                    }

                  }

                  units byte ;
                }

                leaf pir {
                  description 'Configure the PIR(Peak Information Rate) value (default: kilobits per second).' ;
                  type uint32 {
                    range 0..4294967295 {
                      description 'The PIR(Peak Information Rate) value (default: kilobits per second).' ;
                    }

                  }

                  mandatory true ;
                }

                leaf pir-unit {
                  description 'Set pir unit, such as kbps, mbps, gbps.' ;
                  type qos-rate-unit-type ;

                }

                leaf pbs {
                  description 'Configure the PBS(Peak Burst Size) size in bytes.' ;
                  type uint32 {
                    range 0..4294967294 {
                      description 'The PBS(Peak Burst Size) size in KB.' ;
                    }

                  }

                  units byte ;
                }

              }

              case unit-percentage {
                description 'Configure the percentage style.' ;
                leaf cir-percentage {
                  description 'Configure the CIR(Committed Information Rate) percentage (Set the accuracy rate per hundred (1%)).' ;
                  type uint32 {
                    range 1..100 {
                      description 'The CIR percentage, support <1-100>' ;
                    }

                  }

                  mandatory true ;
                }

                leaf pir-percentage {
                  description 'Configure the PIR(Peak Information Rate) percentage (Set the accuracy rate per hundred (1%)).' ;
                  type uint32 {
                    range 1..100 {
                      description 'The PIR percentage, support <1-100>' ;
                    }

                  }

                  mandatory true ;
                }

              }

            }

            leaf statistical-share {
              description 'The flag of statistical-share.' ;
              type boolean ;

              default false ;
            }

            leaf token-bucket-id {
              description 'Set token bucket id.' ;
              type uint32 {
                range 1..4294967295 {
                  description 'Token bucket id' ;
                }

              }

            }

            container mode {
              if-feature qos-car-mode ;

              description 'Set color mode.' ;
              presence "Configure mode information" ;
              leaf mode-type {
                description 'Set color mode type.' ;
                type enumeration {
                  enum blind {
                    value 1 ;
                    description 'Color-Blind mode' ;
                  }

                  enum aware {
                    value 2 ;
                    description 'Color-Aware mode' ;
                  }

                }

                mandatory true ;
              }

            }

            container conform-action {
              description 'Action to packets that conform to the rate limit.' ;
              choice action {
                description 'Specify action to packets that conform to the rate limit.' ;
                mandatory true ;
                case ca-drop {
                  description 'Drop packet.' ;
                  leaf drop {
                    description 'Drop packet.' ;
                    type empty ;

                    mandatory true ;
                  }

                }

                case ca-transmit {
                  description 'Transmit packet.' ;
                  leaf transmit {
                    description 'Transmit packet.' ;
                    type empty ;

                    mandatory true ;
                  }

                }

                case ca-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case ca-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 {
                          description 'The IP-Precedence value, support <0-7>' ;
                        }

                      }

                      mandatory true ;
                    }

                  }

                }

                case ca-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case ca-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                    }

                  }

                }

                case ca-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case ca-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                }

              }

            }

            container exceed-action {
              description 'Action to packets that exceed the rate limit.' ;
              choice action {
                description 'Specify action to packets that exceed the rate limit.' ;
                mandatory true ;
                case ea-drop {
                  description 'Drop packet.' ;
                  leaf drop {
                    description 'Drop packet.' ;
                    type empty ;

                    mandatory true ;
                  }

                }

                case ea-transmit {
                  description 'Transmit packet.' ;
                  leaf transmit {
                    description 'Transmit packet.' ;
                    type empty ;

                    mandatory true ;
                  }

                }

                case ea-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case ea-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 {
                          description 'The IP-Precedence value, support <0-7>' ;
                        }

                      }

                      mandatory true ;
                    }

                  }

                }

                case ea-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case ea-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                    }

                  }

                }

                case ea-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case ea-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                }

              }

            }

            container violate-action {
              description 'Action to packets that violate the rate limit.' ;
              choice action {
                description 'Specify action to packets that violate the rate limit.' ;
                mandatory true ;
                case va-drop {
                  description 'Drop packet.' ;
                  leaf drop {
                    description 'Drop packet.' ;
                    type empty ;

                    mandatory true ;
                  }

                }

                case va-transmit {
                  description 'Transmit packet.' ;
                  leaf transmit {
                    description 'Transmit packet.' ;
                    type empty ;

                    mandatory true ;
                  }

                }

                case va-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case va-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 ;

                      }

                      mandatory true ;
                    }

                  }

                }

                case va-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case va-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                    }

                  }

                }

                case va-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case va-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                }

              }

            }

            container coupling-flag {
              description 'The Coupling Flag indicates whether tokens that would overflow the C-bucket should be added to the E-bucket.' ;
              presence "Configure coupling flag information" ;
              leaf cf-value {
                description 'Configure coupling-flag value.' ;
                type uint8 {
                  range 0..1 ;

                }

              }

              if-feature qos-car-cf ;

              ncd:revise-date 2023-09-12 ;
            }

            container adjust {
              description 'Configure QoS accuracy adjustment values.' ;
              presence "Configure adjust information" ;
              leaf adjust-value {
                description 'Configure QoS accuracy adjustment values.' ;
                type int32 {
                  range -32..31 ;

                }

              }

              if-feature qos-car-adjust ;

              ncd:revise-date 2023-09-12 ;
            }

          }

          ncd:revise-date 2022-06-13 ;
        }

        container bus {
          description 'Match broadcast and unknown unicast.' ;
          list bu {
            description 'Configure interface rate limit based on matching broadcast and unknown unicast.' ;
            key 'if-name if-direct' ;
            leaf if-name {
              description 'Configure the name of the attaching interface.' ;
              type ncd:ifname {
                length 1..31 {
                  description 'Name of the attaching interface, support 1-31 characters' ;
                }

              }

            }

            leaf if-direct {
              description 'Specify the direction of interface.' ;
              type enumeration {
                enum input {
                  value 1 ;
                  description 'Rate limit on input' ;
                }

                enum output {
                  value 2 ;
                  description 'Rate limit on output' ;
                }

              }

            }

            leaf rate-limit-desc {
              description 'Description of rate limit, support 1-79 characters.' ;
              type ncd:string-with-blank {
                length 1..79 {
                  description 'Description of rate limit, support 1-79 characters.' ;
                }

              }

            }

            choice unit-style {
              description "Specify unit's style." ;
              mandatory true ;
              case unit-value {
                description 'Configure the value style.' ;
                leaf cir {
                  description 'Configure the CIR(Committed Information Rate) value (default: kilobits per second).' ;
                  type uint32 {
                    range 0..4294967295 {
                      description 'The CIR value (default: kilobits per second).' ;
                    }

                  }

                  mandatory true ;
                }

                leaf cir-unit {
                  description 'Set cir unit, such as kbps, mbps, gbps.' ;
                  type qos-rate-unit-type ;

                }

                leaf cbs {
                  description 'Configure the CBS(Committed Burst Size) size in bytes.' ;
                  type uint32 {
                    range 0..4294967294 {
                      description 'The CBS(Committed Burst Size) size in bytes.' ;
                    }

                  }

                  units byte ;
                }

                leaf pir {
                  description 'Configure the PIR(Peak Information Rate) value (default: kilobits per second).' ;
                  type uint32 {
                    range 0..4294967295 {
                      description 'The PIR(Peak Information Rate) value (default: kilobits per second).' ;
                    }

                  }

                  mandatory true ;
                }

                leaf pir-unit {
                  description 'Set pir unit, such as kbps, mbps, gbps.' ;
                  type qos-rate-unit-type ;

                }

                leaf pbs {
                  description 'Configure the PBS(Peak Burst Size) size in bytes.' ;
                  type uint32 {
                    range 0..4294967294 {
                      description 'The PBS(Peak Burst Size) size in KB.' ;
                    }

                  }

                  units byte ;
                }

              }

              case unit-percentage {
                description 'Configure the percentage style.' ;
                leaf cir-percentage {
                  description 'Configure the CIR(Committed Information Rate) percentage (Set the accuracy rate per hundred (1%)).' ;
                  type uint32 {
                    range 1..100 {
                      description 'The CIR percentage, support <1-100>' ;
                    }

                  }

                  mandatory true ;
                }

                leaf pir-percentage {
                  description 'Configure the PIR(Peak Information Rate) percentage (Set the accuracy rate per hundred (1%)).' ;
                  type uint32 {
                    range 1..100 {
                      description 'The PIR percentage, support <1-100>' ;
                    }

                  }

                  mandatory true ;
                }

              }

            }

            leaf statistical-share {
              description 'The flag of statistical-share.' ;
              type boolean ;

              default false ;
            }

            leaf token-bucket-id {
              description 'Set token bucket id.' ;
              type uint32 {
                range 1..4294967295 {
                  description 'Token bucket id' ;
                }

              }

            }

            container mode {
              if-feature qos-car-mode ;

              description 'Set color mode.' ;
              presence "Configure mode information" ;
              leaf mode-type {
                description 'Set color mode type.' ;
                type enumeration {
                  enum blind {
                    value 1 ;
                    description 'Color-Blind mode' ;
                  }

                  enum aware {
                    value 2 ;
                    description 'Color-Aware mode' ;
                  }

                }

                mandatory true ;
              }

            }

            container conform-action {
              description 'Action to packets that conform to the rate limit.' ;
              choice action {
                description 'Specify action to packets that conform to the rate limit.' ;
                mandatory true ;
                case ca-drop {
                  description 'Drop packet.' ;
                  leaf drop {
                    description 'Drop packet.' ;
                    type empty ;

                    mandatory true ;
                  }

                }

                case ca-transmit {
                  description 'Transmit packet.' ;
                  leaf transmit {
                    description 'Transmit packet.' ;
                    type empty ;

                    mandatory true ;
                  }

                }

                case ca-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case ca-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 {
                          description 'The IP-Precedence value, support <0-7>' ;
                        }

                      }

                      mandatory true ;
                    }

                  }

                }

                case ca-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case ca-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                    }

                  }

                }

                case ca-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case ca-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                }

              }

            }

            container exceed-action {
              description 'Action to packets that exceed the rate limit.' ;
              choice action {
                description 'Specify action to packets that exceed the rate limit.' ;
                mandatory true ;
                case ea-drop {
                  description 'Drop packet.' ;
                  leaf drop {
                    description 'Drop packet.' ;
                    type empty ;

                    mandatory true ;
                  }

                }

                case ea-transmit {
                  description 'Transmit packet.' ;
                  leaf transmit {
                    description 'Transmit packet.' ;
                    type empty ;

                    mandatory true ;
                  }

                }

                case ea-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case ea-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 {
                          description 'The IP-Precedence value, support <0-7>' ;
                        }

                      }

                      mandatory true ;
                    }

                  }

                }

                case ea-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case ea-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                    }

                  }

                }

                case ea-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case ea-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                }

              }

            }

            container violate-action {
              description 'Action to packets that violate the rate limit.' ;
              choice action {
                description 'Specify action to packets that violate the rate limit.' ;
                mandatory true ;
                case va-drop {
                  description 'Drop packet.' ;
                  leaf drop {
                    description 'Drop packet.' ;
                    type empty ;

                    mandatory true ;
                  }

                }

                case va-transmit {
                  description 'Transmit packet.' ;
                  leaf transmit {
                    description 'Transmit packet.' ;
                    type empty ;

                    mandatory true ;
                  }

                }

                case va-mpls-exp {
                  description 'Rewrite packet MPLS-EXP and transmit the packet.' ;
                  container set-exp-transmit {
                    description 'Rewrite packet MPLS-EXP and transmit it.' ;
                    container mpls-label-type {
                      description 'Set MPLS-EXP label type.' ;
                      presence "Set MPLS-EXP label type" ;
                      leaf label-type {
                        description 'Set MPLS-EXP label position.' ;
                        type enumeration {
                          enum topmost {
                            value 1 ;
                            description 'Set the MPLS-EXP value on topmost label' ;
                          }

                          enum imposition {
                            value 2 ;
                            description 'Set the MPLS-EXP value on imposition label' ;
                          }

                          enum inner {
                            value 3 ;
                            description 'Set the MPLS-EXP value on inner label' ;
                          }

                        }

                        mandatory true ;
                      }

                    }

                    leaf mpls-exp-value {
                      description 'Reset MPLS-EXP value, support <0-7>.' ;
                      type uint8 {
                        range 0..7 {
                          description 'The MPLS-EXP value, support <0-7>' ;
                        }

                      }

                      mandatory true ;
                    }

                  }

                }

                case va-precedence {
                  description 'Rewrite packet precedence and transmit the packet.' ;
                  container set-prec-transmit {
                    description 'Rewrite packet precedence and transmit it.' ;
                    leaf prec-value {
                      description 'Reset the IP-Precedence value, support <0-7>.' ;
                      type uint8 {
                        range 0..7 ;

                      }

                      mandatory true ;
                    }

                  }

                }

                case va-dscp {
                  description 'Rewrite packet DSCP and transmit the packet.' ;
                  container set-dscp-transmit {
                    description 'Rewrite packet DSCP and transmit it.' ;
                    leaf dscp-value {
                      description 'Reset DSCP, support <0-63>.' ;
                      type uint8 {
                        range 0..63 {
                          description 'The DSCP value, support <0-63>' ;
                        }

                      }

                      mandatory true ;
                    }

                  }

                }

                case va-8021p {
                  description 'Rewrite packet 802.1p and transmit the packet.' ;
                  container set-8021p-transmit {
                    description 'Rewrite packet 802.1p and transmit it.' ;
                    leaf value-8021p {
                      description 'Reset 802.1p, support <0-7>.' ;
                      type uint8 {
                        range 0..7 {
                          description 'The 802.1p value, support <0-7>' ;
                        }

                      }

                      mandatory true ;
                    }

                    leaf inner-outer {
                      description 'Set 8021p inner or outer flag.If vlaue is 0, it means outer flag. If value is 1,it means inner and outer flag.' ;
                      type uint8 {
                        range 0..1 {
                          description 'Inner or outer flag. 0 is outer. 1 is inner and outer' ;
                        }

                      }

                      default 0 ;
                    }

                  }

                }

                case va-multi-exp {
                  description 'Rewrite packet multi-MPLS-EXP and transmit it.' ;
                  container set-multi-exp-transmit {
                    description 'Rewrite packet multi-MPLS-EXP and transmit it.' ;
                    leaf inner-value {
                      description 'Inner multi-MPLS-EXP value, support <0-7>.' ;
                      type uint8 {
                        range 0..7 {
                          description 'Inner multi-MPLS-EXP value, support <0-7>' ;
                        }

                      }

                      mandatory true ;
                    }

                    leaf outer-value {
                      description 'Outer multi-MPLS-EXP value, support <0-7>.' ;
                      type uint8 {
                        range 0..7 {
                          description 'Outer multi-MPLS-EXP value, support <0-7>' ;
                        }

                      }

                      mandatory true ;
                    }

                  }

                }

                case va-service-class {
                  description 'Rewrite packet service class and transmit the packet.' ;
                  container set-service-class-transmit {
                    description 'Rewrite packet service class and transmit it.' ;
                    leaf service-class-value {
                      description 'Reset service class.' ;
                      type qos-service-class ;

                      mandatory true ;
                    }

                  }

                }

              }

            }

            container coupling-flag {
              description 'The Coupling Flag indicates whether tokens that would overflow the C-bucket should be added to the E-bucket.' ;
              presence "Configure coupling flag information" ;
              leaf cf-value {
                description 'Configure coupling-flag value.' ;
                type uint8 {
                  range 0..1 ;

                }

              }

              if-feature qos-car-cf ;

              ncd:revise-date 2023-09-12 ;
            }

            container adjust {
              description 'Configure QoS accuracy adjustment values.' ;
              presence "Configure adjust information" ;
              leaf adjust-value {
                description 'Configure QoS accuracy adjustment values.' ;
                type int32 {
                  range -32..31 ;

                }

              }

              if-feature qos-car-adjust ;

              ncd:revise-date 2023-09-12 ;
            }

          }

          ncd:revise-date 2022-06-13 ;
        }

      }

      container diffserv {
        if-feature diffserv ;

        description 'Differentiated Services.' ;
        container ds-domains {
          description 'Configure the template of diffserv domain.' ;
          list ds-domain {
            description 'Configure the template of diffserv domain, the max number of template is 8.' ;
            key domain-name ;
            leaf domain-name {
              description 'Name of the diffserv domain, support 1-31 characters.' ;
              type string {
                length 1..31 {
                  description 'Name of the diffserv domain, support 1-31 characters' ;
                }

              }

            }

            container map {
              description 'Configure the mapping between some protocol and PHB.' ;
              container pri-8021ps {
                status obsolete {
                  ncd:revise-date 2016-12-20 ;
                }

                description 'Configure the mapping based on 802.1p.' ;
                list pri-8021p {
                  status obsolete {
                    ncd:revise-date 2016-12-20 ;
                  }

                  description 'Map 802.1p to PHB, PHB include server class and color.' ;
                  key value-8021p ;
                  leaf value-8021p {
                    status obsolete {
                      ncd:revise-date 2016-12-20 ;
                    }

                    description '802.1p value, support <0-7>.' ;
                    type uint32 {
                      range 0..7 {
                        description '802.1p value, support <0-7>' ;
                      }

                    }

                  }

                  leaf server-class {
                    status obsolete {
                      ncd:revise-date 2016-12-20 ;
                    }

                    description 'Specify server class of PHB info, support <af1,af2,af3,af4,be,cs6,cs7,ef>.' ;
                    type qos-service-class ;

                    mandatory true ;
                  }

                  leaf color-type {
                    status obsolete {
                      ncd:revise-date 2016-12-20 ;
                    }

                    description 'Specify packets color, support <green,yellow,red>.' ;
                    type qos-color-type ;

                    mandatory true ;
                  }

                }

              }

              container pri-8021p-singles {
                description 'Configure the mapping based on 802.1p.' ;
                list pri-8021p-single {
                  description 'Map 802.1p to PHB.' ;
                  key value-8021p ;
                  leaf value-8021p {
                    description '802.1p value, support <0-7>.' ;
                    type uint32 {
                      range 0..7 {
                        description '802.1p value, support <0-7>' ;
                      }

                    }

                  }

                  leaf server-class {
                    description 'Specify server class of PHB info, support <af1,af2,af3,af4,be,cs6,cs7,ef>.' ;
                    type qos-service-class ;

                    mandatory true ;
                  }

                  leaf color-type {
                    description 'Specify packets color, support <green,yellow,red>.' ;
                    type qos-color-type ;

                    mandatory true ;
                  }

                }

                ncd:revise-date 2016-12-20 ;
              }

              container pri-8021p-ranges {
                description 'Configure the mapping based on 802.1p.' ;
                list pri-8021p-range {
                  description 'Map 802.1p to PHB, PHB include server class and color.' ;
                  key value-8021p ;
                  leaf value-8021p {
                    description '802.1p value, support single 802.1p value or range(max num:4;spacing mark:,) in <0-7>. For example,"0,3-5,7",etc.' ;
                    type qos-8021p-bitmap ;

                  }

                  leaf server-class {
                    description 'Specify server class of PHB info, support <af1,af2,af3,af4,be,cs6,cs7,ef>.' ;
                    type qos-service-class ;

                    mandatory true ;
                  }

                  leaf color-type {
                    description 'Specify packets color, support <green,yellow,red>.' ;
                    type qos-color-type ;

                    mandatory true ;
                  }

                }

                ncd:revise-date 2016-12-20 ;
              }

              container mpls-exps {
                status obsolete {
                  ncd:revise-date 2016-12-20 ;
                }

                description 'Configure the mapping based on MPLS-EXP.' ;
                list mpls-exp {
                  status obsolete {
                    ncd:revise-date 2016-12-20 ;
                  }

                  description 'Map MPLS-EXP to PHB, PHB include server class and color.' ;
                  key mpls-exp-value ;
                  leaf mpls-exp-value {
                    status obsolete {
                      ncd:revise-date 2016-12-20 ;
                    }

                    description 'MPLS-EXP value, support <0-7>.' ;
                    type uint32 {
                      range 0..7 {
                        description 'MPLS-EXP value, support <0-7>' ;
                      }

                    }

                  }

                  leaf server-class {
                    status obsolete {
                      ncd:revise-date 2016-12-20 ;
                    }

                    description 'Specify server class of PHB info, support <af1,af2,af3,af4,be,cs6,cs7,ef>.' ;
                    type qos-service-class ;

                    mandatory true ;
                  }

                  leaf color-type {
                    status obsolete {
                      ncd:revise-date 2016-12-20 ;
                    }

                    description 'Specify packets color, support <green,yellow,red>.' ;
                    type qos-color-type ;

                    mandatory true ;
                  }

                }

              }

              container mpls-exp-singles {
                description 'Configure the mapping based on MPLS-EXP.' ;
                list mpls-exp-single {
                  description 'Map MPLS-EXP to PHB, PHB include server class and color.' ;
                  key mpls-exp-value ;
                  leaf mpls-exp-value {
                    description 'MPLS-EXP value, support <0-7>.' ;
                    type uint32 {
                      range 0..7 {
                        description 'MPLS-EXP value, support <0-7>' ;
                      }

                    }

                  }

                  leaf server-class {
                    description 'Specify server class of PHB info, support <af1,af2,af3,af4,be,cs6,cs7,ef>.' ;
                    type qos-service-class ;

                    mandatory true ;
                  }

                  leaf color-type {
                    description 'Specify packets color, support <green,yellow,red>.' ;
                    type qos-color-type ;

                    mandatory true ;
                  }

                }

                ncd:revise-date 2016-12-20 ;
              }

              container mpls-exp-ranges {
                description 'Configure the mapping based on MPLS-EXP.' ;
                list mpls-exp-range {
                  description 'Map MPLS-EXP to PHB, PHB include server class and color.' ;
                  key mpls-exp-value ;
                  leaf mpls-exp-value {
                    description 'MPLS-EXP value, support single MPLS-EXP value or range(max num:4;spacing mark:,) in <0-7>. For example,"0,3-5,7",etc.' ;
                    type qos-mpls-bitmap ;

                  }

                  leaf server-class {
                    description 'Specify server class of PHB info, support <af1,af2,af3,af4,be,cs6,cs7,ef>.' ;
                    type qos-service-class ;

                    mandatory true ;
                  }

                  leaf color-type {
                    description 'Specify packets color, support <green,yellow,red>.' ;
                    type qos-color-type ;

                    mandatory true ;
                  }

                }

                ncd:revise-date 2016-12-20 ;
              }

              container phbs {
                description 'Configure PHB (Per Hop Behavior).' ;
                container pri-8021ps {
                  description 'PHB be mapped to 802.1p.' ;
                  list pri-8021p {
                    description 'PHB be mapped to 802.1p.' ;
                    key 'server-class color-type' ;
                    leaf server-class {
                      description 'Specify server class of PHB info, support <af1,af2,af3,af4,be,cs6,cs7,ef>.' ;
                      type qos-service-class ;

                    }

                    leaf color-type {
                      description 'Specify packets color, support <green,yellow,red>.' ;
                      type qos-color-type ;

                    }

                    leaf value-8021p {
                      description '802.1p value, support <0-7>.' ;
                      type uint32 {
                        range 0..7 {
                          description '802.1p value, support <0-7>' ;
                        }

                      }

                      mandatory true ;
                    }

                  }

                }

                container mpls-exps {
                  description 'PHB be mapped to MPLS-EXP.' ;
                  list mpls-exp {
                    description 'PHB be mapped to MPLS-EXP.' ;
                    key 'server-class color-type' ;
                    leaf server-class {
                      description 'Specify server class of PHB info, support <af1,af2,af3,af4,be,cs6,cs7,ef>.' ;
                      type qos-service-class ;

                    }

                    leaf color-type {
                      description 'Specify packets color, support <green,yellow,red>.' ;
                      type qos-color-type ;

                    }

                    leaf mpls-exp-value {
                      description 'MPLS-EXP value, support <0-7>.' ;
                      type uint32 {
                        range 0..7 {
                          description 'MPLS-EXP value, support <0-7>' ;
                        }

                      }

                      mandatory true ;
                    }

                  }

                }

                container ipv4-dscps {
                  description 'PHB be mapped to IPv4 DSCP.' ;
                  list ipv4-dscp {
                    description 'PHB be mapped to IPv4 DSCP.' ;
                    key 'server-class color-type' ;
                    leaf server-class {
                      description 'Specify server class of PHB info, support <af1,af2,af3,af4,be,cs6,cs7,ef>.' ;
                      type qos-service-class ;

                    }

                    leaf color-type {
                      description 'Specify packets color, support <green,yellow,red>.' ;
                      type qos-color-type ;

                    }

                    leaf dscp-value {
                      description 'IPv4 DSCP value, support <0-63>.' ;
                      type uint32 {
                        range 0..63 {
                          description 'IPv4 DSCP value, support <0-63>' ;
                        }

                      }

                      mandatory true ;
                    }

                  }

                }

                container ipv6-dscps {
                  description 'PHB be mapped to IPv6 DSCP.' ;
                  list ipv6-dscp {
                    description 'PHB be mapped to IPv6 DSCP.' ;
                    key 'server-class color-type' ;
                    leaf server-class {
                      description 'Specify server class of PHB info, support <af1,af2,af3,af4,be,cs6,cs7,ef>.' ;
                      type qos-service-class ;

                    }

                    leaf color-type {
                      description 'Specify packets color, support <green,yellow,red>.' ;
                      type qos-color-type ;

                    }

                    leaf dscp-value {
                      description 'IPv6 DSCP value, support <0-63>.' ;
                      type uint32 {
                        range 0..63 {
                          description 'IPv6 DSCP value, support <0-63>' ;
                        }

                      }

                      mandatory true ;
                    }

                  }

                }

              }

              container link-acls {
                description 'Configure the mapping based on link access list.' ;
                list link-acl {
                  description 'Map link access list to PHB, PHB include server class and color.' ;
                  key acl-name ;
                  leaf acl-name {
                    description 'Set link-access-list name, support 1-31 characters.' ;
                    type string {
                      length 1..31 {
                        description 'Name of ACL, support 1-31 characters' ;
                      }

                    }

                  }

                  leaf server-class {
                    description 'Specify server class of PHB info, support <af1,af2,af3,af4,be,cs6,cs7,ef>.' ;
                    type qos-service-class ;

                    mandatory true ;
                  }

                  leaf color-type {
                    description 'Specify packets color, support <green,yellow,red>.' ;
                    type qos-color-type ;

                    mandatory true ;
                  }

                }

              }

              container ipv4-dscps {
                status obsolete {
                  ncd:revise-date 2016-12-20 ;
                }

                description 'Configure the mapping based on IPv4 DSCP.' ;
                list ipv4-dscp {
                  status obsolete {
                    ncd:revise-date 2016-12-20 ;
                  }

                  description 'Map IPv4 DSCP to PHB, PHB include server class and color.' ;
                  key dscp-value ;
                  leaf dscp-value {
                    status obsolete {
                      ncd:revise-date 2016-12-20 ;
                    }

                    description 'IPv4 DSCP value, support <0-63>.' ;
                    type uint32 {
                      range 0..63 {
                        description 'IPv4 DSCP value, support <0-63>' ;
                      }

                    }

                  }

                  leaf server-class {
                    status obsolete {
                      ncd:revise-date 2016-12-20 ;
                    }

                    description 'Specify server class of PHB info, support <af1,af2,af3,af4,be,cs6,cs7,ef>.' ;
                    type qos-service-class ;

                    mandatory true ;
                  }

                  leaf color-type {
                    status obsolete {
                      ncd:revise-date 2016-12-20 ;
                    }

                    description 'Specify packets color, support <green,yellow,red>.' ;
                    type qos-color-type ;

                    mandatory true ;
                  }

                }

              }

              container ipv4-dscp-singles {
                description 'Configure the mapping based on IPv4 DSCP.' ;
                list ipv4-dscp-single {
                  description 'Map IPv4 DSCP to PHB, PHB include server class and color.' ;
                  key dscp-value ;
                  leaf dscp-value {
                    description 'IPv4 DSCP value, support <0-63>.' ;
                    type uint32 {
                      range 0..63 {
                        description 'IPv4 DSCP value, support <0-63>' ;
                      }

                    }

                  }

                  leaf server-class {
                    description 'Specify server class of PHB info, support <af1,af2,af3,af4,be,cs6,cs7,ef>.' ;
                    type qos-service-class ;

                    mandatory true ;
                  }

                  leaf color-type {
                    description 'Specify packets color, support <green,yellow,red>.' ;
                    type qos-color-type ;

                    mandatory true ;
                  }

                }

                ncd:revise-date 2016-12-20 ;
              }

              container ipv4-dscp-ranges {
                description 'Configure the mapping based on IPv4 DSCP.' ;
                list ipv4-dscp-range {
                  description 'Map IPv4 DSCP to PHB, PHB include server class and color.' ;
                  key dscp-value ;
                  leaf dscp-value {
                    description 'IPv4 DSCP value, support single DSCP value or range(max num:4;spacing mark:,) in <0-63>. For example,"6,10-30,40,50-60",etc.' ;
                    type qos-dscp-bitmap ;

                  }

                  leaf server-class {
                    description 'Specify server class of PHB info, support <af1,af2,af3,af4,be,cs6,cs7,ef>.' ;
                    type qos-service-class ;

                    mandatory true ;
                  }

                  leaf color-type {
                    description 'Specify packets color, support <green,yellow,red>.' ;
                    type qos-color-type ;

                    mandatory true ;
                  }

                }

                ncd:revise-date 2016-12-20 ;
              }

              container ipv4-acls {
                description 'Configure the mapping based on IPv4 access list.' ;
                list ipv4-acl {
                  description 'Map IPv4 access list to PHB, PHB include server class and color.' ;
                  key acl-name ;
                  leaf acl-name {
                    description 'Set ipv4-access-list name, support 1-31 characters.' ;
                    type string {
                      length 1..31 {
                        description 'Name of ACL, support 1-31 characters' ;
                      }

                    }

                  }

                  leaf server-class {
                    description 'Specify server class of PHB info, support <af1,af2,af3,af4,be,cs6,cs7,ef>.' ;
                    type qos-service-class ;

                    mandatory true ;
                  }

                  leaf color-type {
                    description 'Specify packets color, support <green,yellow,red>.' ;
                    type qos-color-type ;

                    mandatory true ;
                  }

                }

              }

              container ipv4-mixed-acls {
                description 'Configure the mapping based on IPv4 mixed access list.' ;
                list ipv4-mixed-acl {
                  description 'Map IPv4 mixed access list to PHB, PHB include server class and color.' ;
                  key acl-name ;
                  leaf acl-name {
                    description 'Set ipv4-mixed-access-list name, support 1-31 characters.' ;
                    type string {
                      length 1..31 {
                        description 'Name of ACL, support 1-31 characters' ;
                      }

                    }

                  }

                  leaf server-class {
                    description 'Specify server class of PHB info, support <af1,af2,af3,af4,be,cs6,cs7,ef>.' ;
                    type qos-service-class ;

                    mandatory true ;
                  }

                  leaf color-type {
                    description 'Specify packets color, support <green,yellow,red>.' ;
                    type qos-color-type ;

                    mandatory true ;
                  }

                }

              }

              container ipv6-dscps {
                status obsolete {
                  ncd:revise-date 2016-12-20 ;
                }

                description 'Configure the mapping based on IPv6 DSCP.' ;
                list ipv6-dscp {
                  status obsolete {
                    ncd:revise-date 2016-12-20 ;
                  }

                  description 'Map IPv6 DSCP to PHB, PHB include server class and color.' ;
                  key dscp-value ;
                  leaf dscp-value {
                    status obsolete {
                      ncd:revise-date 2016-12-20 ;
                    }

                    description 'IPv6 DSCP value, support <0-63>.' ;
                    type uint32 {
                      range 0..63 {
                        description 'IPv6 DSCP value, support <0-63>' ;
                      }

                    }

                  }

                  leaf server-class {
                    status obsolete {
                      ncd:revise-date 2016-12-20 ;
                    }

                    description 'Specify server class of PHB info, support <af1,af2,af3,af4,be,cs6,cs7,ef>.' ;
                    type qos-service-class ;

                    mandatory true ;
                  }

                  leaf color-type {
                    status obsolete {
                      ncd:revise-date 2016-12-20 ;
                    }

                    description 'Specify packets color, support <green,yellow,red>.' ;
                    type qos-color-type ;

                    mandatory true ;
                  }

                }

              }

              container ipv6-dscp-singles {
                description 'Configure the mapping based on IPv6 DSCP.' ;
                list ipv6-dscp-single {
                  description 'Map IPv6 DSCP to PHB, PHB include server class and color.' ;
                  key dscp-value ;
                  leaf dscp-value {
                    description 'IPv6 DSCP value, support <0-63>.' ;
                    type uint32 {
                      range 0..63 {
                        description 'IPv6 DSCP value, support <0-63>' ;
                      }

                    }

                  }

                  leaf server-class {
                    description 'Specify server class of PHB info, support <af1,af2,af3,af4,be,cs6,cs7,ef>.' ;
                    type qos-service-class ;

                    mandatory true ;
                  }

                  leaf color-type {
                    description 'Specify packets color, support <green,yellow,red>.' ;
                    type qos-color-type ;

                    mandatory true ;
                  }

                }

                ncd:revise-date 2016-12-20 ;
              }

              container ipv6-dscp-ranges {
                description 'Configure the mapping based on IPv6 DSCP.' ;
                list ipv6-dscp-range {
                  description 'Map IPv6 DSCP to PHB, PHB include server class and color.' ;
                  key dscp-value ;
                  leaf dscp-value {
                    description 'IPv6 DSCP value, support single DSCP value or range(max num:4;spacing mark:,) in <0-63>. For example,"6,10-30,40,50-60",etc.' ;
                    type qos-dscp-bitmap ;

                  }

                  leaf server-class {
                    description 'Specify server class of PHB info, support <af1,af2,af3,af4,be,cs6,cs7,ef>.' ;
                    type qos-service-class ;

                    mandatory true ;
                  }

                  leaf color-type {
                    description 'Specify packets color, support <green,yellow,red>.' ;
                    type qos-color-type ;

                    mandatory true ;
                  }

                }

                ncd:revise-date 2016-12-20 ;
              }

              container ipv6-acls {
                description 'Configure the mapping based on IPv6 access list.' ;
                list ipv6-acl {
                  description 'Map IPv6 access list to PHB, PHB include server class and color.' ;
                  key acl-name ;
                  leaf acl-name {
                    description 'Set ipv6-access-list name, support 1-31 characters.' ;
                    type string {
                      length 1..31 {
                        description 'Name of ACL, support 1-31 characters' ;
                      }

                    }

                  }

                  leaf server-class {
                    description 'Specify server class of PHB info, support <af1,af2,af3,af4,be,cs6,cs7,ef>.' ;
                    type qos-service-class ;

                    mandatory true ;
                  }

                  leaf color-type {
                    description 'Specify packets color, support <green,yellow,red>.' ;
                    type qos-color-type ;

                    mandatory true ;
                  }

                }

              }

              container ipv6-mixed-acls {
                description 'Configure the mapping based on IPv6 mixed access list.' ;
                list ipv6-mixed-acl {
                  description 'Map IPv6 mixed access list to PHB, PHB include server class and color.' ;
                  key acl-name ;
                  leaf acl-name {
                    description 'Set ipv6-mixed-access-list name, support 1-31 characters.' ;
                    type string {
                      length 1..31 {
                        description 'Name of ACL, support 1-31 characters' ;
                      }

                    }

                  }

                  leaf server-class {
                    description 'Specify server class of PHB info, support <af1,af2,af3,af4,be,cs6,cs7,ef>.' ;
                    type qos-service-class ;

                    mandatory true ;
                  }

                  leaf color-type {
                    description 'Specify packets color, support <green,yellow,red>.' ;
                    type qos-color-type ;

                    mandatory true ;
                  }

                }

              }

            }

          }

        }

      }

      container qos-ds-domains {
        if-feature qos-ds-domains ;

        description 'Configure the used diffserv domain template.' ;
        list qos-ds-domain {
          description 'Configure interface binding DS domain.' ;
          key if-name ;
          leaf if-name {
            description 'Specify the name of interface binding DS domain, support 1-31 characters.' ;
            type ncd:ifname {
              length 1..31 {
                description 'Name of the interface, support 1-31 characters' ;
              }

            }

          }

          leaf ds-domain-name {
            description 'Name of the diffserv domain, support 1-31 characters.' ;
            type string {
              length 1..31 {
                description 'Name of the diffserv domain, support 1-31 characters' ;
              }

            }

            mandatory true ;
          }

          leaf bound-type {
            description 'Specify the bind mode.' ;
            type enumeration {
              enum overwrite {
                value 2 ;
                description 'Set DS-domain bound on link-ports with overwrite' ;
              }

            }

            ncd:revise-date 2018-09-19 ;
          }

        }

      }

      container qos-prioritys {
        if-feature qos-prioritys ;

        description 'Configure the type of priority trusted by QoS.' ;
        list qos-priority {
          description 'Configure the type of priority trusted by QoS.' ;
          key if-name ;
          leaf if-name {
            description 'Specify the name of interface applied, support 1-31 characters.' ;
            type ncd:ifname {
              length 1..31 {
                description 'Name of the interface, support 1-31 characters' ;
              }

            }

          }

          leaf priority-type {
            description 'Set the priority type trusted by interface.' ;
            type enumeration {
              enum 8021p {
                value 1 ;
                description 'Based on 802.1p' ;
              }

              enum ip-dscp {
                value 2 ;
                description 'Based on IP DSCP' ;
              }

              enum mpls-exp {
                value 3 ;
                description 'Based on MPLS-EXP' ;
              }

            }

            mandatory true ;
          }

        }

      }

      container qos-schedule {
        if-feature qos-schedule ;

        description 'Set scheduling policy for a certain transmitting entity.' ;
        container interfaces {
          description 'Set scheduling policy for a certain interface.' ;
          list interface {
            description 'Set scheduling policy for a certain interface.' ;
            key if-name ;
            leaf if-name {
              description 'Name of the attaching tunnel.' ;
              type ncd:ifname {
                length 1..31 {
                  description 'Name of the attaching tunnel' ;
                }

              }

            }

            choice schedule {
              description 'Configure schedule policy.' ;
              mandatory true ;
              case sche-group {
                description 'Configure schedule based on the combination of schedule policy.' ;
                container queue-schedule {
                  description 'Configure queue schedule.' ;
                  presence "Configure queue schedule" ;
                  choice queue-schedule {
                    description 'Select the type of queue schedule.' ;
                    mandatory true ;
                    case pq {
                      description 'Set PQ(Priority Queuing) scheduling between transmitting entities.' ;
                      leaf priority-level {
                        description 'Set the priority level of PQ, support <1-4>.' ;
                        type uint8 {
                          range 1..4 {
                            description 'The priority level of PQ, support<1-4>' ;
                          }

                        }

                      }

                    }

                    case wfq {
                      description 'Set WFQ(Weighted Fair Queuing) scheduling between transmitting entities.' ;
                      leaf wfq-weight {
                        description 'Set the weight of WFQ, support <1-100>.' ;
                        type uint8 {
                          range 1..100 {
                            description 'The weight of WFQ, support <1-100>' ;
                          }

                        }

                      }

                    }

                  }

                }

                leaf pmap-name {
                  description 'Name of scheduling policy based on PHB, support 1-31 characters.' ;
                  type string {
                    length 1..31 {
                      description 'Name of the policy map, support 1-31 characters' ;
                    }

                  }

                }

              }

            }

          }

        }

        container pws {
          description 'Set scheduling policy for a certain PW.' ;
          list pw {
            description 'Set scheduling policy for a certain PW.' ;
            key pw-name ;
            leaf pw-name {
              description 'Name of the PW, support 1-31 characters.' ;
              type string {
                length 1..31 {
                  description 'The name of PW, support 1-31 characters' ;
                }

              }

            }

            choice schedule {
              description 'Configure schedule policy.' ;
              mandatory true ;
              case sche-group {
                description 'Configure schedule based on the combination of schedule policy.' ;
                container queue-schedule {
                  description 'Configure queue schedule.' ;
                  presence "Configure queue schedule" ;
                  choice queue-schedule {
                    description 'Select the type of queue schedule.' ;
                    mandatory true ;
                    case pq {
                      description 'Set PQ(Priority Queuing) scheduling between transmitting entities.' ;
                      leaf priority-level {
                        description 'Set the priority level of PQ, support <1-4>.' ;
                        type uint8 {
                          range 1..4 {
                            description 'The priority level of PQ, support<1-4>' ;
                          }

                        }

                      }

                    }

                    case wfq {
                      description 'Set WFQ(Weighted Fair Queuing) scheduling between transmitting entities.' ;
                      leaf wfq-weight {
                        description 'Set the weight of WFQ, support <1-100>.' ;
                        type uint8 {
                          range 1..100 {
                            description 'The weight of WFQ, support <1-100>' ;
                          }

                        }

                      }

                    }

                  }

                }

                leaf pmap-name {
                  description 'Name of scheduling policy based on PHB, support 1-31 characters.' ;
                  type string {
                    length 1..31 {
                      description 'Name of the policy map, support 1-31 characters' ;
                    }

                  }

                }

                leaf statistical-share {
                  description 'Set statistical share.' ;
                  type boolean ;

                  default false ;
                  ncd:revise-date 2021-03-04 ;
                }

              }

            }

          }

        }

        container pw-ins {
          description 'Set ingress scheduling policy for a certain PW.' ;
          list pw-in {
            description 'Set ingress scheduling policy for a certain PW.' ;
            key pw-name ;
            leaf pw-name {
              description 'Name of the PW, support 1-31 characters.' ;
              type string {
                length 1..31 {
                  description 'The name of PW, support 1-31 characters' ;
                }

              }

            }

            choice schedule {
              description 'Configure schedule policy.' ;
              mandatory true ;
              case sche-group {
                description 'Configure schedule based on the combination of schedule policy.' ;
                container queue-schedule {
                  description 'Configure queue schedule.' ;
                  presence "Configure queue schedule" ;
                  choice queue-schedule {
                    description 'Select the type of queue schedule.' ;
                    mandatory true ;
                    case pq {
                      description 'Set PQ(Priority Queuing) scheduling between transmitting entities.' ;
                      leaf priority-level {
                        description 'Set the priority level of PQ, support <1-4>.' ;
                        type uint8 {
                          range 1..4 {
                            description 'The priority level of PQ, support<1-4>' ;
                          }

                        }

                      }

                    }

                    case wfq {
                      description 'Set WFQ(Weighted Fair Queuing) scheduling between transmitting entities.' ;
                      leaf wfq-weight {
                        description 'Set the weight of WFQ, support <1-100>.' ;
                        type uint8 {
                          range 1..100 {
                            description 'The weight of WFQ, support <1-100>' ;
                          }

                        }

                      }

                    }

                  }

                }

                leaf pmap-name {
                  description 'Name of scheduling policy based on PHB, support 1-31 characters.' ;
                  type string {
                    length 1..31 {
                      description 'Name of the policy map, support 1-31 characters' ;
                    }

                  }

                }

                leaf statistical-share {
                  description 'Set statistical share.' ;
                  type boolean ;

                  default false ;
                  ncd:revise-date 2021-03-04 ;
                }

              }

            }

          }

          ncd:revise-date 2021-01-18 ;
        }

        container tes {
          description 'Set scheduling policy for a certain TE.' ;
          list te {
            description 'Set scheduling policy for a certain TE.' ;
            key te-tunnel ;
            leaf te-tunnel {
              description 'Name of the attaching tunnel.' ;
              type ncd:ifname ;

            }

            choice schedule {
              description 'Configure schedule policy.' ;
              mandatory true ;
              case sche-group {
                description 'Configure schedule based on the combination of schedule policy.' ;
                container queue-schedule {
                  description 'Configure queue schedule.' ;
                  presence "Configure queue schedule" ;
                  choice queue-schedule {
                    description 'Select the type of queue schedule.' ;
                    mandatory true ;
                    case pq {
                      description 'Set PQ(Priority Queuing) scheduling between transmitting entities.' ;
                      leaf priority-level {
                        description 'Set the priority level of PQ, support <1-4>.' ;
                        type uint8 {
                          range 1..4 {
                            description 'The priority level of PQ, support<1-4>' ;
                          }

                        }

                      }

                    }

                    case wfq {
                      description 'Set WFQ(Weighted Fair Queuing) scheduling between transmitting entities.' ;
                      leaf wfq-weight {
                        description 'Set the weight of WFQ, support <1-100>.' ;
                        type uint8 {
                          range 1..100 {
                            description 'The weight of WFQ, support <1-100>' ;
                          }

                        }

                      }

                    }

                  }

                }

                leaf pmap-name {
                  description 'Name of scheduling policy based on PHB, support 1-31 characters.' ;
                  type string {
                    length 1..31 {
                      description 'Name of the policy map, support 1-31 characters' ;
                    }

                  }

                }

              }

            }

          }

          ncd:revise-date 2021-03-24 ;
        }

        container te-reverses {
          if-feature schedule-te-reverse ;

          description 'Set scheduling policy for a certain reverse TE.' ;
          list te-reverse {
            description 'Set scheduling policy for a certain reverse TE.' ;
            key te-tunnel ;
            leaf te-tunnel {
              description 'Name of the attaching tunnel.' ;
              type ncd:ifname ;

            }

            choice schedule {
              description 'Configure schedule policy.' ;
              mandatory true ;
              case sche-group {
                description 'Configure schedule based on the combination of schedule policy.' ;
                container queue-schedule {
                  description 'Configure queue schedule.' ;
                  presence "Configure queue schedule" ;
                  choice queue-schedule {
                    description 'Select the type of queue schedule.' ;
                    mandatory true ;
                    case pq {
                      description 'Set PQ(Priority Queuing) scheduling between transmitting entities.' ;
                      leaf priority-level {
                        description 'Set the priority level of PQ, support <1-4>.' ;
                        type uint8 {
                          range 1..4 {
                            description 'The priority level of PQ, support<1-4>' ;
                          }

                        }

                      }

                    }

                    case wfq {
                      description 'Set WFQ(Weighted Fair Queuing) scheduling between transmitting entities.' ;
                      leaf wfq-weight {
                        description 'Set the weight of WFQ, support <1-100>.' ;
                        type uint8 {
                          range 1..100 {
                            description 'The weight of WFQ, support <1-100>' ;
                          }

                        }

                      }

                    }

                  }

                }

                leaf pmap-name {
                  description 'Name of scheduling policy based on PHB, support 1-31 characters.' ;
                  type string {
                    length 1..31 {
                      description 'Name of the policy map, support 1-31 characters' ;
                    }

                  }

                }

              }

            }

          }

          ncd:revise-date 2022-09-08 ;
        }

        container bgp-ads {
          description 'Set scheduling policy for a certain BGP-AD.' ;
          list bgp-ad {
            description 'Set scheduling policy for a certain BGP-AD.' ;
            key 'vpls-name peer-router-id' ;
            leaf vpls-name {
              description 'Set VPLS instance name, support 1-32 characters.' ;
              type string {
                length 1..32 ;

              }

            }

            leaf peer-router-id {
              description 'Set peer router id.' ;
              type ncd:ipv4-address ;

            }

            choice schedule {
              description 'Configure schedule policy.' ;
              mandatory true ;
              case sche-group {
                description 'Configure schedule based on the combination of schedule policy.' ;
                container queue-schedule {
                  description 'Configure queue schedule.' ;
                  presence "Configure queue schedule" ;
                  choice queue-schedule {
                    description 'Select the type of queue schedule.' ;
                    mandatory true ;
                    case pq {
                      description 'Set PQ(Priority Queuing) scheduling between transmitting entities.' ;
                      leaf priority-level {
                        description 'Set the priority level of PQ, support <1-4>.' ;
                        type uint8 {
                          range 1..4 {
                            description 'The priority level of PQ, support<1-4>' ;
                          }

                        }

                      }

                    }

                    case wfq {
                      description 'Set WFQ(Weighted Fair Queuing) scheduling between transmitting entities.' ;
                      leaf wfq-weight {
                        description 'Set the weight of WFQ, support <1-100>.' ;
                        type uint8 {
                          range 1..100 {
                            description 'The weight of WFQ, support <1-100>' ;
                          }

                        }

                      }

                    }

                  }

                }

                leaf pmap-name {
                  description 'Name of scheduling policy based on PHB, support 1-31 characters.' ;
                  type string {
                    length 1..31 {
                      description 'Name of the policy map, support 1-31 characters' ;
                    }

                  }

                }

              }

            }

          }

          ncd:revise-date 2021-01-11 ;
        }

      }

      container switch-fabrics {
        if-feature switch-fabric ;

        description 'Configure H-QoS switch fabric policy bind.' ;
        container normals {
          description 'Configure H-QoS switch fabric policy bind based on shelf and slot.' ;
          list normal {
            description 'Configure H-QoS switch fabric policy bind based on shelf and slot.' ;
            key 'shelf slot mode' ;
            leaf shelf {
              description 'Specify the shelf number, support <0-7>.' ;
              type uint8 {
                range 0..7 {
                  description 'The shelf number, support <0-7>' ;
                }

              }

            }

            leaf slot {
              description 'Specify the slot number, support <0-17>.' ;
              type uint8 {
                range 0..17 {
                  description 'The slot number, support <0-17>' ;
                }

              }

            }

            leaf mode {
              description 'Set switch fabric mode.' ;
              type enumeration {
                enum unicast {
                  value 1 ;
                  description 'Specify unicast mode' ;
                }

                enum multicast {
                  value 2 ;
                  description 'Specify multicast mode' ;
                }

              }

            }

            leaf pmap-name {
              description 'Name of the policy based on switch-fabric, support 1-31 characters.' ;
              type string {
                length 1..31 {
                  description 'Name of the policy map, support 1-31 characters' ;
                }

              }

              mandatory true ;
            }

          }

        }

        container subslots {
          description 'Configure H-QoS switch fabric policy bind, support subslot.' ;
          list subslot {
            description 'Configure H-QoS switch fabric policy bind, support subslot.' ;
            key 'shelf slot mode subslot' ;
            leaf shelf {
              description 'Specify the shelf number, support <0-7>.' ;
              type uint8 {
                range 0..7 {
                  description 'The shelf number, support <0-7>' ;
                }

              }

            }

            leaf slot {
              description 'Specify the slot number, support <0-17>.' ;
              type uint8 {
                range 0..17 {
                  description 'The slot number, support <0-17>' ;
                }

              }

            }

            leaf mode {
              description 'Set switch fabric mode, only unicast in the case of supporting subslot.' ;
              type enumeration {
                enum unicast {
                  value 1 ;
                  description 'Specify unicast mode' ;
                }

              }

            }

            leaf subslot {
              description 'Specify the subslot number, support <0-3>.' ;
              type uint8 {
                range 0..3 {
                  description 'The subslot number, support <0-3>' ;
                }

              }

            }

            leaf pmap-name {
              description 'Name of the policy based on switch-fabric, support 1-31 characters.' ;
              type string {
                length 1..31 {
                  description 'Name of the policy map, support 1-31 characters' ;
                }

              }

              mandatory true ;
            }

          }

          container group1s {
            description 'Configure H-QoS switch fabric policy bind, support parameter template for subslot 0 and 1.' ;
            list group1 {
              description 'Configure H-QoS switch fabric policy bind, support parameter template for subslot 0 and 1.' ;
              key 'shelf slot mode' ;
              leaf shelf {
                description 'Specify the shelf number, support <0-7>.' ;
                type uint8 {
                  range 0..7 {
                    description 'The shelf number, support <0-7>' ;
                  }

                }

              }

              leaf slot {
                description 'Specify the slot number, support <0-17>.' ;
                type uint8 {
                  range 0..17 {
                    description 'The slot number, support <0-17>' ;
                  }

                }

              }

              leaf mode {
                description 'Set switch fabric mode, only multicast in the case of supporting parameter template for subslot 0 and 1.' ;
                type enumeration {
                  enum multicast {
                    value 2 ;
                    description 'Specify multicast mode' ;
                  }

                }

              }

              leaf pmap-name {
                description 'Name of the policy based on switch-fabric, support 1-31 characters.' ;
                type string {
                  length 1..31 {
                    description 'Name of the policy map, support 1-31 characters' ;
                  }

                }

                mandatory true ;
              }

            }

          }

          container group2s {
            description 'Configure H-QoS switch fabric policy bind, support parameter template for subslot 2 and 3.' ;
            list group2 {
              description 'Configure H-QoS switch fabric policy bind, support parameter template for subslot 2 and 3.' ;
              key 'shelf slot mode' ;
              leaf shelf {
                description 'Specify the shelf number, support <0-7>.' ;
                type uint8 {
                  range 0..7 {
                    description 'The shelf number, support <0-7>' ;
                  }

                }

              }

              leaf slot {
                description 'Specify the slot number, support <0-17>.' ;
                type uint8 {
                  range 0..17 {
                    description 'The slot number, support <0-17>' ;
                  }

                }

              }

              leaf mode {
                description 'Set switch fabric mode, only multicast in the case of supporting parameter template for subslot 2 and 3.' ;
                type enumeration {
                  enum multicast {
                    value 2 ;
                    description 'Specify multicast mode' ;
                  }

                }

              }

              leaf pmap-name {
                description 'Name of the policy based on switch-fabric, support 1-31 characters.' ;
                type string {
                  length 1..31 {
                    description 'Name of the policy map, support 1-31 characters' ;
                  }

                }

                mandatory true ;
              }

            }

          }

          container ports {
            description 'Configure H-QoS switch fabric policy bind, support port.' ;
            list port {
              description 'Configure H-QoS switch fabric policy bind, support port.' ;
              key 'shelf slot mode subslot port' ;
              leaf shelf {
                description 'Specify the shelf number, support <0-7>.' ;
                type uint8 {
                  range 0..7 {
                    description 'The shelf number, support <0-7>' ;
                  }

                }

              }

              leaf slot {
                description 'Specify the slot number, support <0-17>.' ;
                type uint8 {
                  range 0..17 {
                    description 'The slot number, support <0-17>' ;
                  }

                }

              }

              leaf mode {
                description 'Set switch fabric mode, only unicast and switch-port in the case of supporting parameter template for subslot.' ;
                type enumeration {
                  enum unicast {
                    value 1 ;
                    description 'Specify unicast mode' ;
                  }

                  enum switch-port {
                    value 3 ;
                    description 'Specify switch-port mode' ;
                  }

                }

              }

              leaf subslot {
                description 'Specify the subslot number, support <0-3>.' ;
                type uint8 {
                  range 0..3 {
                    description 'The subslot number, support <0-3>' ;
                  }

                }

              }

              leaf port {
                description 'Specify the port number, support <1-48>.' ;
                type uint8 {
                  range 1..48 {
                    description 'The port number, support <1-48>' ;
                  }

                }

              }

              leaf pmap-name {
                description 'Name of the policy based on switch-fabric, support 1-31 characters.' ;
                type string {
                  length 1..31 {
                    description 'Name of the policy map, support 1-31 characters' ;
                  }

                }

                mandatory true ;
              }

            }

          }

        }

        container interfaces {
          description 'Configure H-QoS switch fabric policy bind based on interface.' ;
          list interface {
            description 'Configure H-QoS switch fabric policy bind based on interface.' ;
            key 'interface mode' ;
            leaf interface {
              description 'Configure the name of the attaching interface.' ;
              type ncd:ifname ;

            }

            leaf mode {
              description 'Set switch fabric mode, such as unicast.' ;
              type enumeration {
                enum unicast {
                  value 1 ;
                  description 'Specify unicast mode' ;
                }

              }

            }

            leaf pmap-name {
              description 'Name of the policy based on switch-fabric, support 1-31 characters.' ;
              type string {
                length 1..31 ;

              }

              mandatory true ;
            }

          }

          ncd:revise-date 2020-08-25 ;
        }

      }

      container traffic-shapes {
        if-feature traffic-shape ;

        description 'Configure traffic shape.' ;
        list traffic-shape {
          description 'Configure traffic shape.' ;
          key if-name ;
          leaf if-name {
            description 'Name of the interface.' ;
            type ncd:ifname {
              length 1..31 {
                description 'Name of the interface, support 1-31 characters' ;
              }

            }

          }

          leaf rate {
            description 'Set the shaping rate.' ;
            type uint32 {
              range 8..4294967295 {
                description 'Rate in kilobits per second.' ;
              }

            }

            units kbps ;
            mandatory true ;
          }

          container burst {
            description 'Configure burst and exburst size.' ;
            presence "Configure burst and exburst size in KB" ;
            leaf burst-size {
              description 'Burst size.' ;
              type uint32 {
                range 2..250000000 {
                  description 'Burst size in KB, support <2-250000000>' ;
                }

              }

              units KB ;
              mandatory true ;
            }

            container excess-burst {
              description 'Configure exburst.' ;
              presence "Configure exburst" ;
              leaf exburst-size {
                description 'Excess burst size.' ;
                type uint32 {
                  range 2..250000000 {
                    description 'Excess burst size in KB, support <2-250000000>' ;
                  }

                }

                units KB ;
                mandatory true ;
              }

            }

          }

          container network-header-len {
            description 'Length of network header.' ;
            presence "Length of network header" ;
            leaf network-header-length {
              description 'Length of network header.' ;
              type int32 {
                range -63..63 {
                  description 'Length of network header' ;
                }

              }

              mandatory true ;
            }

            ncd:revise-date 2020-06-02 ;
          }

          leaf statistical-share {
            description 'Set statistical share.' ;
            type boolean ;

            default false ;
            ncd:revise-date 2021-01-18 ;
          }

        }

      }

      container traffic-shape-dirs {
        if-feature traffic-shape-dir ;

        description 'Configure traffic shape on the specific interface and direction.' ;
        list traffic-shape-dir {
          description 'Configure traffic shape on the specific interface and direction.' ;
          key 'if-name direction' ;
          leaf if-name {
            description 'Name of the interface.' ;
            type ncd:ifname {
              length 1..31 {
                description 'Name of the interface, support 1-31 characters' ;
              }

            }

          }

          leaf direction {
            description 'Configure the interface direction.' ;
            type enumeration {
              enum input {
                value 1 ;
                description 'Attaches to the input interface' ;
              }

            }

          }

          leaf rate {
            description 'Set the shaping rate.' ;
            type uint32 {
              range 8..4294967295 {
                description 'Rate in kilobits per second' ;
              }

            }

            units kbps ;
            mandatory true ;
          }

          container burst {
            description 'Configure burst and exburst size.' ;
            presence "Configure burst and exburst size in KB" ;
            leaf burst-size {
              description 'Burst size.' ;
              type uint32 {
                range 2..250000000 {
                  description 'Burst size in KB, support <2-250000000>' ;
                }

              }

              units KB ;
              mandatory true ;
            }

            container excess-burst {
              description 'Configure exburst.' ;
              presence "Configure exburst" ;
              leaf exburst-size {
                description 'Excess burst size.' ;
                type uint32 {
                  range 2..250000000 {
                    description 'Excess burst size in KB, support <2-250000000>' ;
                  }

                }

                units KB ;
                mandatory true ;
              }

            }

          }

          container network-header-len {
            description 'Length of network header.' ;
            presence "Length of network header" ;
            leaf network-header-length {
              description 'Length of network header.' ;
              type int32 {
                range -63..63 {
                  description 'Length of network header' ;
                }

              }

              mandatory true ;
            }

            ncd:revise-date 2020-06-02 ;
          }

          leaf statistical-share {
            description 'Set statistical share.' ;
            type boolean ;

            default false ;
            ncd:revise-date 2021-01-18 ;
          }

        }

        ncd:revise-date 2017-01-16 ;
      }

      container qos-policys {
        status obsolete {
          ncd:revise-date 2015-04-15 ;
        }

        description 'Bind qos-policy to interface.' ;
        list qos-policy {
          status obsolete {
            ncd:revise-date 2015-04-15 ;
          }

          description 'Configue QPPB(QOS Policy Propagation Through the Border Gateway Protocol).' ;
          key 'if-name option direction' ;
          leaf if-name {
            status obsolete {
              ncd:revise-date 2015-04-15 ;
            }

            description 'Name of an interface, support 1-31 characters.' ;
            type ncd:ifname {
              length 1..31 {
                description 'Name of the interface, support 1-31 characters' ;
              }

            }

          }

          leaf option {
            status obsolete {
              ncd:revise-date 2015-04-15 ;
            }

            description 'Specify ip precedence or qos id.' ;
            type enumeration {
              enum ip-precedence {
                value 3 ;
                description 'Set IP precedence' ;
              }

              enum qos-id {
                value 4 ;
                description 'Set qos id' ;
              }

            }

          }

          leaf direction {
            status obsolete {
              ncd:revise-date 2015-04-15 ;
            }

            description 'Specify the direction of IP.' ;
            type enumeration {
              enum source {
                value 1 ;
                description 'Check routemap by source IP' ;
              }

              enum destination {
                value 2 ;
                description 'Check routemap by destination IP' ;
              }

            }

          }

        }

      }

      container qos-policy-exs {
        description 'Bind qos-policy to interface.' ;
        list qos-policy-ex {
          description 'Configue QPPB(QOS Policy Propagation Through the Border Gateway Protocol).' ;
          key 'if-name option direction ip-protocol' ;
          leaf if-name {
            description 'Name of an interface, support 1-31 characters.' ;
            type ncd:ifname {
              length 1..31 {
                description 'Name of the interface, support 1-31 characters' ;
              }

            }

          }

          leaf option {
            description 'Specify ip precedence or qos id.' ;
            type enumeration {
              enum ip-precedence {
                value 3 ;
                description 'Set IP precedence' ;
              }

              enum qos-id {
                value 4 ;
                description 'Set qos id' ;
              }

            }

          }

          leaf direction {
            description 'Specify the direction of IP.' ;
            type enumeration {
              enum source {
                value 1 ;
                description 'Check routemap by source IP' ;
              }

              enum destination {
                value 2 ;
                description 'Check routemap by destination IP' ;
              }

            }

          }

          leaf ip-protocol {
            description 'Specify the type of IP protocol.' ;
            type enumeration {
              enum ipv4 {
                value 0 ;
                description 'IPv4 protocol' ;
              }

              enum ipv6 {
                value 1 ;
                description 'IPv6 protocol' ;
              }

            }

          }

        }

        ncd:revise-date 2015-04-15 ;
      }

      container mls-qos-modes {
        description 'Configure priority inherit on the interface.' ;
        list mls-qos-mode {
          description 'Configure priority inherit on the interface.' ;
          key if-name ;
          leaf if-name {
            description 'Configure the name of the attaching interface.' ;
            type ncd:ifname {
              length 1..31 {
                description 'Name of the attaching interface, support 1-31 characters' ;
              }

            }

          }

          choice inherit-mode {
            description 'Inherit mode.' ;
            mandatory true ;
            case uniform {
              description 'Select uniform inherit mode.' ;
              leaf uniform {
                description 'Specify uniform inherit mode.' ;
                type empty ;

                mandatory true ;
              }

            }

            case pipe {
              description 'Select pipe inherit mode.' ;
              container pipe {
                description 'Select pipe inherit mode.' ;
                leaf pipe {
                  description 'Specify pipe inherit mode.' ;
                  type empty ;

                  mandatory true ;
                }

                container servclass-color {
                  description 'Configure service-class and color.' ;
                  presence "Configure service-calss and color" ;
                  leaf service-class {
                    description 'Specify server class of PHB info.' ;
                    type qos-service-class ;

                    mandatory true ;
                  }

                  leaf color-type {
                    description 'Specify packets color.' ;
                    type qos-color-type ;

                    mandatory true ;
                  }

                }

              }

            }

            case short-pipe {
              description 'Select short-pipe inherit mode.' ;
              container short-pipe {
                description 'Select short-pipe inherit mode.' ;
                leaf short-pipe {
                  description 'Specify short-pipe inherit mode.' ;
                  type empty ;

                  mandatory true ;
                }

                container servclass-color {
                  description 'Configure service-class and color.' ;
                  presence "Configure service-calss and color" ;
                  leaf service-class {
                    description 'Specify server class of PHB info.' ;
                    type qos-service-class ;

                    mandatory true ;
                  }

                  leaf color-type {
                    description 'Specify packets color.' ;
                    type qos-color-type ;

                    mandatory true ;
                  }

                }

              }

            }

          }

        }

      }

      container qos-dot1p {
        description 'Configure 802.1p inherit on the interface.' ;
        container cvlan-ins {
          description 'Inherit from ingress 802.1p on inner VLAN.' ;
          list cvlan-in {
            description 'Inherit from ingress 802.1p on inner VLAN.' ;
            key if-name ;
            leaf if-name {
              description 'Configure the name of the attaching interface.' ;
              type ncd:ifname {
                length 1..31 {
                  description 'Name of the attaching interface, support 1-31 characters' ;
                }

              }

            }

          }

        }

        container cvlan-outs {
          description 'Inherit from egress 802.1p on inner VLAN.' ;
          list cvlan-out {
            description 'Inherit from egress 802.1p on inner VLAN.' ;
            key if-name ;
            leaf if-name {
              description 'Configure the name of the attaching interface.' ;
              type ncd:ifname {
                length 1..31 {
                  description 'Name of the attaching interface, support 1-31 characters' ;
                }

              }

            }

          }

        }

        container defaults {
          description 'Inherit by default way, that is, inherit from 802.1p on outer VLAN with ingress and egress.' ;
          list default {
            description 'Inherit by default way, that is, inherit from 802.1p on outer VLAN with ingress and egress.' ;
            key if-name ;
            leaf if-name {
              description 'Configure the name of the attaching interface.' ;
              type ncd:ifname {
                length 1..31 {
                  description 'Name of the attaching interface, support 1-31 characters' ;
                }

              }

            }

          }

        }

      }

      container ttl-qos-modes {
        description 'Configure TTL duplicate on the interface.' ;
        list ttl-qos-mode {
          description 'Configure TTL duplicate on the interface.' ;
          key if-name ;
          leaf if-name {
            description 'Configure the name of the attaching interface.' ;
            type ncd:ifname {
              length 1..31 {
                description 'Name of the attaching interface, support 1-31 characters' ;
              }

            }

          }

          leaf inherit-mode {
            description 'Specify inherit mode.' ;
            type enumeration {
              enum uniform {
                value 1 ;
                description 'Select uniform mode' ;
              }

              enum pipe {
                value 2 ;
                description 'Select pipe mode' ;
              }

            }

            mandatory true ;
          }

        }

      }

      container qos-stats {
        description 'To enable or disable the QoS flow statistics.' ;
        container stats-switch {
          description 'The QoS flow statistics switch.' ;
          list stats-switches {
            description 'The QoS flow statistics switch.' ;
            key 'if-name flow-direction' ;
            leaf if-name {
              description 'The interface which to be enabled statistics.' ;
              type ncd:ifname ;

            }

            leaf flow-direction {
              description 'The flow direction.' ;
              type qos-direction ;

            }

            leaf statistics-group {
              description 'Specify statistics group ID.' ;
              type uint32 {
                range 1..4000 ;

              }

              ncd:revise-date 2021-03-24 ;
            }

            leaf status {
              type hqos-stats-switch-status ;

              default on ;
              description 'Switch status.' ;
              if-feature hqos-stats-switch-status-off ;

              ncd:revise-date 2023-07-03 ;
            }

          }

        }

        container stats-switches-global {
          presence "hqos stats global switch" ;
          description 'The QoS flow statistics global switch.' ;
          leaf status {
            type qos-stats-global-switch-status ;

            description 'Switch status.' ;
            mandatory true ;
          }

          if-feature qos-stats-global-switch ;

          ncd:revise-date 2023-07-03 ;
        }

        ncd:revise-date 2015-11-04 ;
      }

      container pw-schedule-stats {
        description 'The configuration about PW schedule statistics.' ;
        container stats-switches {
          description 'The PW schedule statistics switch in output direction.' ;
          list stats-switch {
            description 'The PW schedule statistics switch in output direction.' ;
            key pw-name ;
            leaf pw-name {
              description 'Name of the PW, support 1-31 characters.' ;
              type string {
                length 1..31 {
                  description 'Name of the PW, support 1-31 characters.' ;
                }

              }

            }

            leaf statistics-group {
              description 'Specify statistics group ID.' ;
              type uint32 {
                range 1..4000 ;

              }

              ncd:revise-date 2021-03-24 ;
            }

            leaf status {
              type hqos-stats-switch-status ;

              description 'Switch status.' ;
              default on ;
              if-feature hqos-stats-switch-status-off ;

              ncd:revise-date 2023-07-03 ;
            }

          }

        }

        container stats-switch-ins {
          description 'The PW schedule statistics switch in input direction.' ;
          list stats-switch-in {
            description 'The PW schedule statistics switch in input direction.' ;
            key pw-name ;
            leaf pw-name {
              description 'Name of the PW, support 1-31 characters.' ;
              type string {
                length 1..31 {
                  description 'Name of the PW, support 1-31 characters.' ;
                }

              }

            }

            leaf statistics-group {
              description 'Specify statistics group ID.' ;
              type uint32 {
                range 1..4000 ;

              }

              ncd:revise-date 2021-03-24 ;
            }

            leaf status {
              type hqos-stats-switch-status ;

              description 'Switch status.' ;
              default on ;
              if-feature hqos-stats-switch-status-off ;

              ncd:revise-date 2023-07-03 ;
            }

          }

          ncd:revise-date 2021-01-18 ;
        }

        ncd:revise-date 2016-05-03 ;
      }

      container te-schedule-stats {
        description 'The configuration about TE schedule statistics.' ;
        container stats-switches {
          description 'The TE schedule statistics switch in output direction.' ;
          list stats-switch {
            description 'The TE schedule statistics switch in output direction.' ;
            key te-tunnel ;
            leaf te-tunnel {
              description 'Name of the attaching tunnel.' ;
              type ncd:ifname ;

            }

            leaf statistics-group {
              description 'Specify statistics group ID.' ;
              type uint32 {
                range 1..4000 ;

              }

            }

            leaf status {
              type hqos-stats-switch-status ;

              description 'Switch status.' ;
              default on ;
              if-feature hqos-stats-switch-status-off ;

              ncd:revise-date 2023-07-03 ;
            }

          }

        }

        container stats-switch-reverses {
          if-feature schedule-te-reverse ;

          description 'The TE schedule statistics switch in reverse direction.' ;
          list stats-switch-reverse {
            description 'The TE schedule statistics switch in reverse direction.' ;
            key te-tunnel ;
            leaf te-tunnel {
              description 'Name of the attaching tunnel.' ;
              type ncd:ifname ;

            }

            leaf statistics-group {
              description 'Specify statistics group ID.' ;
              type uint32 {
                range 1..4000 ;

              }

            }

            leaf status {
              type hqos-stats-switch-status ;

              description 'Switch status.' ;
              default on ;
              if-feature hqos-stats-switch-status-off ;

              ncd:revise-date 2023-07-03 ;
            }

          }

          ncd:revise-date 2022-09-08 ;
        }

        ncd:revise-date 2021-03-24 ;
      }

      container bgpad-schedule-stats {
        description 'The configuration about BGP-AD schedule statistics.' ;
        container stats-switches {
          description 'The BGP-AD schedule statistics switch.' ;
          list stats-switches {
            description 'The BGP-AD schedule statistics switch.' ;
            key 'vpls-name peer-router-id' ;
            leaf vpls-name {
              description 'Set VPLS instance name, support 1-32 characters.' ;
              type string {
                length 1..32 ;

              }

            }

            leaf peer-router-id {
              description 'Set peer router id.' ;
              type ncd:ipv4-address ;

            }

            leaf statistics-group {
              description 'Specify statistics group ID.' ;
              type uint32 {
                range 1..4000 ;

              }

              ncd:revise-date 2021-03-24 ;
            }

            leaf status {
              type hqos-stats-switch-status ;

              description 'Switch status.' ;
              default on ;
              if-feature hqos-stats-switch-status-off ;

              ncd:revise-date 2023-07-03 ;
            }

          }

        }

        ncd:revise-date 2021-01-11 ;
      }

      container qos-vni-instances {
        if-feature qos-vni-instance ;

        description 'Bind H-QoS policys to the vni-instance.' ;
        list qos-vni-instance {
          description 'Bind H-QoS policys to the vni-instance.' ;
          key 'vni direction' ;
          leaf vni {
            description 'VNI value.' ;
            type uint32 {
              range 1..16777215 {
                description 'VNI value.' ;
              }

            }

          }

          leaf direction {
            description 'Configure the direction.' ;
            type qos-direction ;

          }

          leaf pmap-name {
            description 'Name of the policy map bound on the vni-instance, support 1-31 characters.' ;
            type string {
              length 1..31 {
                description 'Name of the policy map bound on the vni-instance.' ;
              }

            }

            mandatory true ;
          }

        }

        ncd:revise-date 2016-06-30 ;
      }

      container flowspec {
        description 'Configure flowspec parameters.' ;
        container address-family-ips {
          description 'Configure IP address family.' ;
          list address-family-ip {
            description 'Configure IP address family.' ;
            key ip-type ;
            leaf ip-type {
              description 'Specify IP type.' ;
              type enumeration {
                enum ipv4 {
                  value 4 ;
                  description 'IPv4 type.' ;
                }

                enum ipv6 {
                  value 24 ;
                  description 'IPv6 type.' ;
                }

              }

            }

            container interfaces {
              description 'Specify interface to enable/disable flowspec.' ;
              list interface {
                description 'Specify interface to enable/disable flowspec.' ;
                key if-name ;
                leaf if-name {
                  description 'Interface name.' ;
                  type ncd:ifname ;

                }

                leaf flag {
                  description 'Configure the flag to indicate enable/disable flowspec feature.' ;
                  type enumeration {
                    enum enable {
                      value 1 ;
                      description 'Enable flowspec.' ;
                    }

                    enum disable {
                      value 0 ;
                      description 'Disable flowspec.' ;
                    }

                  }

                }

              }

            }

            container local-install {
              description 'Specify all interface to enable flowspec.' ;
              presence local-install ;
              leaf interface-all {
                description 'Specify all interface to enable flowspec.' ;
                type empty ;

                mandatory true ;
              }

            }

            container service-policys {
              description 'Configure H-QoS policy.' ;
              list service-policy {
                description 'Configure H-QoS policy.' ;
                key pmap-name ;
                leaf pmap-name {
                  description 'Name of attaching policy, support 1-31 characters.' ;
                  type string {
                    length 1..31 {
                      description 'Name of attaching policy, support 1-31 characters.' ;
                    }

                  }

                }

              }

            }

          }

        }

        container address-family-vrfs {
          description 'Configure VRF address family.' ;
          list address-family-vrf {
            description 'Configure VRF address family.' ;
            key 'ip-type vrf-name' ;
            leaf ip-type {
              description 'Specify IP type.' ;
              type enumeration {
                enum ipv4 {
                  value 4 ;
                  description 'IPv4 type.' ;
                }

                enum ipv6 {
                  value 24 ;
                  description 'IPv6 type.' ;
                }

              }

            }

            leaf vrf-name {
              description 'Virtual route forwarding name, support 1-32 characters.' ;
              type string {
                length 1..32 {
                  description 'Virtual route forwarding name, support 1-32 characters.' ;
                }

              }

            }

            container interfaces {
              description 'Specify interface to enable/disable flowspec.' ;
              list interface {
                description 'Specify interface to enable/disable flowspec.' ;
                key if-name ;
                leaf if-name {
                  description 'Interface name.' ;
                  type ncd:ifname ;

                }

                leaf flag {
                  description 'Configure the flag to indicate enable/disable flowspec feature.' ;
                  type enumeration {
                    enum enable {
                      value 1 ;
                      description 'Enable flowspec.' ;
                    }

                    enum disable {
                      value 0 ;
                      description 'Disable flowspec.' ;
                    }

                  }

                }

              }

            }

            container local-install {
              description 'Specify all interface to enable flowspec.' ;
              presence local-install ;
              leaf interface-all {
                description 'Specify all interface to enable flowspec.' ;
                type empty ;

                mandatory true ;
              }

            }

            container service-policys {
              description 'Configure H-QoS policy.' ;
              list service-policy {
                description 'Configure H-QoS policy.' ;
                key pmap-name ;
                leaf pmap-name {
                  description 'Name of attaching policy, support 1-31 characters.' ;
                  type string {
                    length 1..31 {
                      description 'Name of attaching policy, support 1-31 characters.' ;
                    }

                  }

                }

              }

            }

          }

        }

        container rule-excess-effect {
          if-feature rule-excess-effect ;

          description 'Configuring the switch of the best effort function of the flowspec excess rule.' ;
          leaf best-effort-effect {
            description 'Turn on the switch of the best effort function of the flowspec excess rule.' ;
            type empty ;

          }

          ncd:revise-date 2022-12-09 ;
        }

        ncd:revise-date 2017-06-12 ;
      }

      container qos-prioritys-remark {
        if-feature qos-prioritys-remark ;

        description 'Configure the type of priority remarked by QoS.' ;
        list qos-priority-remark {
          description 'Configure the type of priority remarked by QoS.' ;
          key 'if-name priority-type' ;
          leaf if-name {
            description 'Specify the name of interface applied, support 1-31 characters.' ;
            type ncd:ifname {
              length 1..31 {
                description 'Name of the interface, support 1-31 characters' ;
              }

            }

          }

          leaf priority-type {
            description 'Set the priority type remarked by interface.' ;
            type enumeration {
              enum 8021p {
                value 1 ;
                description 'Based on 802.1p' ;
              }

              enum ip-dscp {
                value 2 ;
                description 'Based on IP DSCP' ;
              }

              enum mpls-exp {
                value 3 ;
                description 'Based on MPLS EXP' ;
              }

            }

          }

          leaf enable-switch {
            if-feature ds-interf-priority-remark-enable ;

            description 'Configure the interface priority modification is enabled or disable.' ;
            type enumeration {
              enum enable {
                value 1 ;
                description 'The switch is enable.' ;
              }

              enum disable {
                value 2 ;
                description 'The switch is disable.' ;
              }

            }

            mandatory true ;
            ncd:revise-date 2021-01-25 ;
          }

        }

        ncd:revise-date 2018-08-18 ;
      }

      container queue-templates {
        description 'Configure the queue template.' ;
        list queue-template {
          description 'Configure the queue template.' ;
          key queue-temp-name ;
          leaf queue-temp-name {
            description 'Name of the queue template, support 1-31 characters.' ;
            type string {
              length 1..31 {
                description 'Name of the queue template (1-31 characters)' ;
              }

            }

          }

          container queue-nos {
            description 'Specify queue.' ;
            list queue-no {
              description 'Specify queue.' ;
              key queue ;
              leaf queue {
                description 'Select service class of PHB info.' ;
                type qos-service-class ;

              }

              container priority-level {
                description 'Configure PQ(Priority Queuing) priority level.' ;
                presence "Configure PQ priority level" ;
                leaf priority-value {
                  description 'Set the priority level of PQ.' ;
                  type uint32 {
                    range 1..16 ;

                  }

                  mandatory true ;
                }

              }

              container queue-limit {
                description 'Configure queue depth.' ;
                presence "Configure queue depth" ;
                leaf queue-depth {
                  description 'Set queue depth.' ;
                  type enumeration {
                    enum 64 {
                      value 3 ;
                      description 'Set queue depth to 64KB' ;
                    }

                    enum 128 {
                      value 14 ;
                      description 'Set queue depth to 128KB' ;
                    }

                    enum 512 {
                      value 4 ;
                      description 'Set queue depth to 512KB' ;
                    }

                    enum 1000 {
                      value 15 ;
                      description 'Set queue depth to 1000KB' ;
                    }

                    enum 4000 {
                      value 16 ;
                      description 'Set queue depth to 4000KB' ;
                    }

                    enum 8000 {
                      value 6 ;
                      description 'Set queue depth to 8000KB' ;
                    }

                    enum 24000 {
                      value 9 ;
                      description 'Set queue depth to 24000KB' ;
                    }

                    enum 64000 {
                      value 10 ;
                      description 'Set queue depth to 64000KB' ;
                    }

                    enum 96000 {
                      value 17 ;
                      description 'Set queue depth to 96000KB' ;
                    }

                    enum 192000 {
                      value 18 ;
                      description 'Set queue depth to 192000KB' ;
                    }

                    enum 1000000 {
                      value 13 ;
                      description 'Set queue depth to 1000000KB' ;
                    }

                    enum 128000 {
                      value 11 ;
                      description 'Set queue depth to 128000KB' ;
                    }

                    enum 16 {
                      value 1 ;
                      description 'Set queue depth to 16KB' ;
                    }

                    enum 16000 {
                      value 8 ;
                      description 'Set queue depth to 16000KB' ;
                    }

                    enum 2000 {
                      value 5 ;
                      description 'Set queue depth to 2000KB' ;
                    }

                    enum 24 {
                      value 2 ;
                      description 'Set queue depth to 24KB' ;
                    }

                    enum 512000 {
                      value 12 ;
                      description 'Set queue depth to 512000KB' ;
                    }

                    enum 7 {
                      value 7 ;
                      description 'Set queue depth to 7KB' ;
                    }

                    enum 8000000 {
                      value 21 ;
                      description 'Set queue depth to 8000000KB' ;
                    }

                    enum 600000 {
                      value 22 ;
                      description 'Set queue depth to 600000KB' ;
                    }

                    enum 660000 {
                      value 23 ;
                      description 'Set queue depth to 660000KB' ;
                    }

                    enum 680000 {
                      value 24 ;
                      description 'Set queue depth to 680000KB' ;
                    }

                    enum 3000000 {
                      value 25 ;
                      description 'Set queue depth to 3000000KB' ;
                    }

                    enum 4000000 {
                      value 26 ;
                      description 'Set queue depth to 4000000KB' ;
                    }

                    enum 5000000 {
                      value 27 ;
                      description 'Set queue depth to 5000000KB' ;
                    }

                  }

                  units KB ;
                  mandatory true ;
                }

              }

              container shape {
                description 'Configure shape.' ;
                presence "Configure shape" ;
                choice shape {
                  description 'Configure shape.' ;
                  mandatory true ;
                  case cir-cbs {
                    description 'Configure CIR CBS PIR and PBS.' ;
                    leaf cir {
                      description 'Configure the CIR (Committed Information Rate) value, default: kilobits per second.' ;
                      type uint32 {
                        range 8..4294967295 {
                          description 'The CIR value (default: kilobits per second),support <8-4294967295>.' ;
                        }

                      }

                      mandatory true ;
                    }

                    leaf cbs {
                      description 'Configure the CBS(Committed Burst Size) size, default: KB.' ;
                      type uint32 {
                        range 1..4294967295 {
                          description 'The CBS(Committed Burst Size) size (default: KB), support <1-4294967295>' ;
                        }

                      }

                    }

                    container pir-pbs {
                      description 'Configure PIR and PBS.' ;
                      presence pir ;
                      leaf pir-value {
                        description 'Configure the PIR(Peak Information Rate) value, default: kilobits per second.' ;
                        type uint32 {
                          range 8..4294967295 {
                            description 'The PIR value.' ;
                          }

                        }

                        mandatory true ;
                      }

                      leaf pbs-value {
                        description 'Configure the PBS(Peak Burst Size) size, default: KB.' ;
                        type uint32 {
                          range 1..4294967295 {
                            description 'The PBS.' ;
                          }

                        }

                      }

                      ncd:revise-date 2021-01-25 ;
                    }

                  }

                  case cir-percentage {
                    description 'Configure the CIR percentage.' ;
                    leaf percentage {
                      description 'Configure the CIR percentage.' ;
                      type uint8 {
                        range 1..100 {
                          description 'Set the CIR percentage,support <1-100>.' ;
                        }

                      }

                      mandatory true ;
                    }

                    container pir-percentage {
                      description 'Configure the  PIR percentage.' ;
                      leaf pir-percentage {
                        description 'Configure the  PIR percentage.' ;
                        type uint8 {
                          range 1..100 {
                            description 'Configure PIR with percentage form.' ;
                          }

                        }

                      }

                      ncd:revise-date 2021-01-25 ;
                    }

                  }

                  ncd:revise-date 2019-06-13 ;
                }

              }

              container random-detect {
                description 'Configure WRED(Weighted Random Early Detection) information.' ;
                presence "Configure WRED information" ;
                container color {
                  description 'Configure WRED thresholds based on color.' ;
                  presence "Configure WRED thresholds based on color" ;
                  container green {
                    description 'Green packets.' ;
                    presence "Green packets" ;
                    choice threshold {
                      description 'Set the threshold.' ;
                      mandatory true ;
                      case threshold-value {
                        description 'Set the threshold value.' ;
                        leaf min-threshold {
                          description 'Set the minimum threshold.' ;
                          type uint32 {
                            range 1..4294967295 {
                              description 'Set the minimum threshold in kilobytes' ;
                            }

                          }

                          units KB ;
                          mandatory true ;
                        }

                        leaf max-threshold {
                          description 'Set the maximum threshold.' ;
                          type uint32 {
                            range 1..4294967295 {
                              description 'Set the maximum threshold in kilobytes' ;
                            }

                          }

                          units KB ;
                          mandatory true ;
                        }

                      }

                      case threshold-percentage {
                        description 'Set the threshold percentage.' ;
                        container threshold-percentage {
                          description 'Set the threshold percentage.' ;
                          leaf min-threshold-percentage {
                            description 'Set the minimum threshold percentage, support <1-100>.' ;
                            type uint32 {
                              range 1..100 ;

                            }

                            mandatory true ;
                          }

                          leaf max-threshold-percentage {
                            description 'Set the maximum threshold percentage, support <1-100>.' ;
                            type uint32 {
                              range 1..100 ;

                            }

                            mandatory true ;
                          }

                        }

                        ncd:revise-date 2020-11-11 ;
                      }

                    }

                    leaf probility {
                      description 'Set mark probability denominator, support <1-100>.' ;
                      type uint32 {
                        range 1..100 {
                          description 'Set mark probability denominator' ;
                        }

                      }

                      mandatory true ;
                    }

                  }

                  container yellow {
                    description 'Yellow packets.' ;
                    presence "Yellow packets" ;
                    choice threshold {
                      description 'Set the threshold.' ;
                      mandatory true ;
                      case threshold-value {
                        description 'Set the threshold value.' ;
                        leaf min-threshold {
                          description 'Set the minimum threshold.' ;
                          type uint32 {
                            range 1..4294967295 {
                              description 'Set the minimum threshold in kilobytes' ;
                            }

                          }

                          units KB ;
                          mandatory true ;
                        }

                        leaf max-threshold {
                          description 'Set the maximum threshold.' ;
                          type uint32 {
                            range 1..4294967295 {
                              description 'Set the maximum threshold in kilobytes' ;
                            }

                          }

                          units KB ;
                          mandatory true ;
                        }

                      }

                      case threshold-percentage {
                        description 'Set the threshold percentage.' ;
                        container threshold-percentage {
                          description 'Set the threshold percentage.' ;
                          leaf min-threshold-percentage {
                            description 'Set the minimum threshold percentage, support <1-100>.' ;
                            type uint32 {
                              range 1..100 ;

                            }

                            mandatory true ;
                          }

                          leaf max-threshold-percentage {
                            description 'Set the maximum threshold percentage, support <1-100>.' ;
                            type uint32 {
                              range 1..100 ;

                            }

                            mandatory true ;
                          }

                        }

                        ncd:revise-date 2020-11-11 ;
                      }

                    }

                    leaf probility {
                      description 'Set mark probability denominator, support <1-100>.' ;
                      type uint32 {
                        range 1..100 {
                          description 'Set mark probability denominator' ;
                        }

                      }

                      mandatory true ;
                    }

                  }

                  container red {
                    description 'Red packets.' ;
                    presence "Red packets" ;
                    choice threshold {
                      description 'Set the threshold.' ;
                      mandatory true ;
                      case threshold-value {
                        description 'Set the threshold value.' ;
                        leaf min-threshold {
                          description 'Set the minimum threshold.' ;
                          type uint32 {
                            range 1..4294967295 {
                              description 'Set the minimum threshold in kilobytes' ;
                            }

                          }

                          units KB ;
                          mandatory true ;
                        }

                        leaf max-threshold {
                          description 'Set the maximum threshold.' ;
                          type uint32 {
                            range 1..4294967295 {
                              description 'Set the maximum threshold in kilobytes' ;
                            }

                          }

                          units KB ;
                          mandatory true ;
                        }

                      }

                      case threshold-percentage {
                        description 'Set the threshold percentage.' ;
                        container threshold-percentage {
                          description 'Set the threshold percentage.' ;
                          leaf min-threshold-percentage {
                            description 'Set the minimum threshold percentage, support <1-100>.' ;
                            type uint32 {
                              range 1..100 ;

                            }

                            mandatory true ;
                          }

                          leaf max-threshold-percentage {
                            description 'Set the maximum threshold percentage, support <1-100>.' ;
                            type uint32 {
                              range 1..100 ;

                            }

                            mandatory true ;
                          }

                        }

                        ncd:revise-date 2020-11-11 ;
                      }

                    }

                    leaf probility {
                      description 'Set mark probability denominator, support <1-100>.' ;
                      type uint32 {
                        range 1..100 {
                          description 'Set mark probability denominator' ;
                        }

                      }

                      mandatory true ;
                    }

                  }

                }

                container weight {
                  description 'Configure WRED exponential weight factor.' ;
                  presence "Configure WRED exponential weight factor" ;
                  leaf weight-value {
                    description 'Specify exponent used in weighted average calculation, support <1-16>.' ;
                    type uint32 {
                      range 1..16 {
                        description 'Range.' ;
                      }

                    }

                  }

                  ncd:revise-date 2021-01-25 ;
                }

                ncd:revise-date 2019-06-13 ;
              }

              choice schedule-weight {
                case wfq-weight {
                  container wfq-weight {
                    leaf percentage {
                      type uint32 {
                        range 1..127 ;

                      }

                      description 'Set the weight of WFQ.' ;
                      mandatory true ;
                    }

                    description 'Configure WFQ weight.' ;
                    presence "Configure WFQ weight" ;
                  }

                }

                case dwrr-weight {
                  container dwrr-weight {
                    leaf percentage {
                      type uint32 {
                        range 1..127 ;

                      }

                      description 'Set the weight of DWRR.' ;
                      mandatory true ;
                    }

                    description 'Configure DWRR weight.' ;
                    presence "Configure DWRR weight" ;
                  }

                  if-feature qos-queue-dwrr ;

                  ncd:revise-date 2023-07-19 ;
                }

                description 'Configure schedule weight. ' ;
              }

            }

          }

        }

        ncd:revise-date 2018-08-30 ;
      }

      container queue-interfaces {
        description 'Configure queue template bind on the interface.' ;
        list queue-interface {
          description 'Configure queue template bind on the interface.' ;
          key 'if-name if-direction' ;
          leaf if-name {
            description 'Configure the name of the attaching interface.' ;
            type ncd:ifname {
              length 1..31 {
                description 'Name of the attaching interface, support 1-31 characters' ;
              }

            }

          }

          leaf if-direction {
            description 'Configure the interface direction.' ;
            type enumeration {
              enum input {
                value 1 ;
                description 'Attaches to the input interface' ;
              }

              enum output {
                value 2 ;
                description 'Attaches to the output interface' ;
              }

            }

          }

          leaf queue-temp-name {
            description 'Name of the queue template bound on the interface, support 1-31 characters.' ;
            type string {
              length 1..31 {
                description 'Name of the queue template, support 1-31 characters' ;
              }

            }

            mandatory true ;
          }

          leaf statistical-share {
            description 'Set statistical share.' ;
            type boolean ;

          }

        }

        ncd:revise-date 2018-08-30 ;
      }

      container flow-behavior-application {
        description 'Configure flow-behavior application.' ;
        container flow-behavior-apply-global {
          description 'Flow-behavior applied to global.' ;
          presence "Flow-behavior applied to global" ;
          leaf pmap-name {
            description 'Name of the policy map bound on global, support 1-31 characters.' ;
            type string {
              length 1..31 {
                description 'Name of the policy map bound on the vni-instance.' ;
              }

            }

            mandatory true ;
          }

          leaf flow-behavior-apply-desc {
            description 'Description of flow behavior application, support 1-79 characters.' ;
            type ncd:string-with-blank {
              length 1..79 {
                description 'Description of flow behavior application, support 1-79 characters.' ;
              }

            }

            ncd:revise-date 2020-06-18 ;
          }

        }

        container flow-behavior-apply-vrfs {
          description 'Flow-behavior applied to VRF.' ;
          list flow-behavior-apply-vrf {
            description 'Flow-behavior applied to VRF.' ;
            key vrf ;
            leaf vrf {
              description 'Name of VRF.' ;
              type string ;

            }

            leaf pmap-name {
              description 'Name of the policy map bound on the VRF, support 1-31 characters.' ;
              type string {
                length 1..31 {
                  description 'Name of the policy map bound on the vni-instance.' ;
                }

              }

              mandatory true ;
            }

            leaf flow-behavior-apply-desc {
              description 'Description of flow behavior application, support 1-79 characters.' ;
              type ncd:string-with-blank {
                length 1..79 {
                  description 'Description of flow behavior application, support 1-79 characters.' ;
                }

              }

              ncd:revise-date 2020-06-18 ;
            }

          }

        }

        ncd:revise-date 2019-04-15 ;
      }

      container ttl-mode-global {
        description 'Configure global TTL duplicate.' ;
        presence "Configure global TTL duplicate" ;
        leaf inherit-mode {
          description 'Specify inherit mode.' ;
          type enumeration {
            enum uniform {
              value 1 ;
              description 'Select uniform mode' ;
            }

            enum pipe {
              value 2 ;
              description 'Select pipe mode' ;
            }

          }

          mandatory true ;
        }

        ncd:revise-date 2020-03-24 ;
      }

      container qos-global-prioritys-remark {
        if-feature qos-global-prioritys-remark ;

        description 'Configure the type of global priority and the global modification enable switch of QoS.' ;
        list qos-global-priority-remark {
          description 'Configure the type of global priority and the global modification enable switch of QoS.' ;
          key priority-type ;
          leaf priority-type {
            description 'Set the priority type remarked by global.' ;
            type enumeration {
              enum all {
                value 4 ;
                description 'Based on all.' ;
              }

            }

          }

          leaf enable-switch {
            description 'Configure the global priority modification is enabled or disable.' ;
            type enumeration {
              enum enable {
                value 1 ;
                description 'The switch is enable.' ;
              }

              enum disable {
                value 2 ;
                description 'The switch is disable.' ;
              }

            }

            mandatory true ;
          }

        }

        ncd:revise-date 2021-01-25 ;
      }

      container traffic-policy-stats {
        if-feature traffic-policy ;

        description 'To enable or disable the QoS traffic policy statistics.' ;
        container stats-switch-interfaces {
          description 'The QoS traffic policy statistics switch for interface.' ;
          list stats-switch-interface {
            description 'The QoS traffic policy statistics switch for interface.' ;
            key 'if-name direction' ;
            leaf if-name {
              description 'The interface which to be enabled statistics.' ;
              type ncd:ifname ;

            }

            leaf direction {
              description 'The direction which to be enabled statistics.' ;
              type qos-direction ;

            }

          }

        }

        container stats-switch-policy-maps {
          description 'The QoS traffic policy statistics switch for policy map.' ;
          list stats-switch-policy-map {
            description 'The QoS traffic policy statistics switch for policy map.' ;
            key 'policy-map-name direction' ;
            leaf policy-map-name {
              description 'The policy map which to be enabled statistics.' ;
              type string {
                length 1..31 {
                  description 'Name of the policy map, support 1-31 characters' ;
                }

              }

            }

            leaf direction {
              description 'The direction which to be enabled statistics.' ;
              type qos-direction ;

            }

          }

          ncd:revise-date 2021-12-17 ;
        }

        ncd:revise-date 2021-01-25 ;
      }

      container qos-pw-ds-domains {
        if-feature qos-pw-ds-domains ;

        description 'Configure the used diffserv domain template by PW interface.' ;
        list qos-pw-ds-domain {
          description 'Configure the PW binding DS domain.' ;
          key pw-name ;
          leaf pw-name {
            description 'Name of the PW, support 1-31 characters.' ;
            type string {
              length 1..31 {
                description 'Name of the PW, support 1-31 characters.' ;
              }

            }

          }

          leaf ds-domain-name {
            description 'Name of the diffserv domain, support 1-31 characters.' ;
            type string {
              length 1..31 {
                description 'Name of the diffserv domain, support 1-31 characters.' ;
              }

            }

            mandatory true ;
          }

        }

        ncd:revise-date 2021-01-25 ;
      }

      container qos-if-slice {
        status obsolete {
          ncd:revise-date 2023-06-16 ;
        }

        description 'Configure interface slice.' ;
        container qos-if-slice-bws {
          description 'Configure slice-id and bw applied to sub-interface.' ;
          list qos-if-slice-bw {
            if-feature qos-if-slice-bw ;

            description 'Configure slice-id and bw applied to sub-interface.' ;
            key 'if-name network-slice' ;
            leaf if-name {
              description 'Configure the name of the attaching sub-interface.' ;
              type ncd:ifname {
                length 1..31 {
                  description 'Name of the attaching interface, support 1-31 characters' ;
                }

              }

              status obsolete {
                ncd:revise-date 2023-06-16 ;
              }

            }

            leaf network-slice {
              description 'Configure the network-slice id, support <1-65535>.' ;
              type uint32 {
                range 1..65535 {
                  description 'Configure the network-slice id, support <1-65535>' ;
                }

              }

              status obsolete {
                ncd:revise-date 2023-06-16 ;
              }

            }

            leaf bandwidth {
              description 'Configure the bandwidth(default:mbps), support <1-1000000>.' ;
              type uint32 {
                range 1..1000000 {
                  description 'Configure the bandwidth, support <1-1000000>' ;
                }

              }

              mandatory true ;
              status obsolete {
                ncd:revise-date 2023-06-16 ;
              }

            }

            status obsolete {
              ncd:revise-date 2023-06-16 ;
            }

          }

          status obsolete {
            ncd:revise-date 2023-06-16 ;
          }

        }

        ncd:revise-date 2021-10-11 ;
      }

      container traffic-policy-vlan {
        if-feature traffic-policy ;

        description 'Bind QoS policys to vlan.' ;
        list traffic-policy-vlan {
          description 'Bind QoS policys to vlan.' ;
          key 'vlan direction' ;
          leaf vlan {
            description 'Configure the vlan.' ;
            type uint16 {
              range 1..4094 ;

            }

          }

          leaf direction {
            description 'Configure the direction.' ;
            type enumeration {
              enum input {
                value 1 ;
                description 'The input direction.' ;
              }

              enum output {
                value 2 ;
                description 'The output direction.' ;
              }

            }

          }

          leaf pmap-name {
            description 'Name of the policy map, support 1-31 characters.' ;
            type string {
              length 1..31 {
                description 'Name of the policy map, support 1-31 characters' ;
              }

            }

            mandatory true ;
          }

        }

        ncd:revise-date 2021-11-08 ;
      }

      container qos-stats-save {
        if-feature qos-stats-save ;

        description 'Configuring the switch to store QoS statistics information.' ;
        leaf csv-switch {
          description 'Turn on the storage function and save it in CSV format.' ;
          type empty ;

        }

        ncd:revise-date 2022-03-10 ;
      }

      container queue-if-stats {
        description 'To enable or disable the queue if statistics.' ;
        container stats-switches {
          description 'The queue if flow statistics switch.' ;
          list stats-switch {
            description 'The queue if statistics switch.' ;
            key 'if-name flow-direction' ;
            leaf if-name {
              description 'The interface which to be enabled statistics.' ;
              type ncd:ifname ;

            }

            leaf flow-direction {
              description 'The flow direction.' ;
              type qos-direction ;

            }

            leaf status {
              description 'Switch status.' ;
              type qos-stats-switch-status ;

              mandatory true ;
            }

          }

        }

        container alarm-switch {
          if-feature qos-queue-alarm ;

          description 'The queue if flow statistics alarm switch.' ;
          presence "Alarm switch" ;
          leaf status {
            description 'Switch status.' ;
            type enumeration {
              enum enable {
                value 0 ;
                description 'Enable alarm.' ;
              }

              enum disable {
                value 1 ;
                description 'Disable alarm.' ;
              }

            }

            mandatory true ;
          }

          ncd:revise-date 2022-07-11 ;
        }

        container drop-ratio-detect-period {
          if-feature qos-queue-alarm ;

          description 'Set drop ratio detect period.' ;
          presence "Drop ratio detect period" ;
          leaf period {
            description 'Set drop ratio detect period.' ;
            type enumeration {
              enum 30 {
                value 1 ;
                description 'Set drop ratio detect period 30s' ;
              }

              enum 60 {
                value 2 ;
                description 'Set drop ratio detect period 60s' ;
              }

            }

            mandatory true ;
          }

          ncd:revise-date 2022-07-11 ;
        }

        container drop-ratio-threshold {
          if-feature qos-queue-alarm ;

          description 'Set drop ratio threshold.' ;
          presence "Drop ratio threshold" ;
          choice drop-ratio-threshold {
            description 'Set drop ratio threshold.' ;
            mandatory true ;
            case drop-ratio-threshold {
              description 'Set drop ratio threshold.' ;
              leaf upper-threshold-percentage {
                description 'Set drop ratio upper threshold percentage(<0.00-100.00>).' ;
                type decimal64 {
                  fraction-digits 2 ;
                  range 0.00..100.00 ;

                }

              }

              leaf lower-threshold-percentage {
                description 'Set drop ratio lower threshold percentage(<0.00-100.00>).' ;
                type decimal64 {
                  fraction-digits 2 ;
                  range 0.00..100.00 ;

                }

              }

            }

          }

          ncd:revise-date 2022-07-11 ;
        }

        ncd:revise-date 2022-03-18 ;
      }

      container wred-templates {
        if-feature wred-template ;

        description 'Configure the WRED(Weighted Random Early Detection) template.' ;
        list wred-template {
          description 'Configure the WRED(Weighted Random Early Detection) template.' ;
          key wred-template-name ;
          leaf wred-template-name {
            description 'Name of the WRED(Weighted Random Early Detection) template (1-31 characters).' ;
            type string {
              length 1..31 {
                description 'Name of the WRED template (1-31 characters)' ;
              }

            }

          }

          container wred-actions {
            description 'Configure WRED(Weighted Random Early Detection) action information.' ;
            container colors {
              description 'Configure WRED(Weighted Random Early Detection) thresholds based on color.' ;
              list color {
                description 'Configure WRED(Weighted Random Early Detection) thresholds based on color.' ;
                key color-type ;
                leaf color-type {
                  description 'Set WRED color.' ;
                  type qos-color-type ;

                }

                choice threshold {
                  description 'Set the threshold.' ;
                  case threshold-value {
                    description 'Set the threshold value.' ;
                    leaf min-threshold {
                      description 'Set the minimum threshold in kilobytes, support <1-1024000>.' ;
                      type uint32 {
                        range 1..1024000 {
                          description 'The minimum threshold in kilobytes, support <1-1024000>' ;
                        }

                      }

                      units KB ;
                      mandatory true ;
                    }

                    leaf max-threshold {
                      description 'Set the maximum threshold in kilobytes, support <1-1024000>.' ;
                      type uint32 {
                        range 1..1024000 {
                          description 'The maximum threshold in kilobytes, support <1-1024000>' ;
                        }

                      }

                      units KB ;
                      mandatory true ;
                    }

                  }

                  case threshold-percentage {
                    description 'Set the threshold percentage.' ;
                    container threshold-percentage {
                      description 'Set the threshold percentage.' ;
                      leaf min-threshold-percentage {
                        description 'Set the minimum threshold percentage, support <1-100>.' ;
                        type uint32 {
                          range 1..100 {
                            description 'The minimum threshold percentage, support <1-100>' ;
                          }

                        }

                        mandatory true ;
                      }

                      leaf max-threshold-percentage {
                        description 'Set the maximum threshold percentage, support <1-100>.' ;
                        type uint32 {
                          range 1..100 {
                            description 'The maximum threshold percentage, support <1-100>' ;
                          }

                        }

                        mandatory true ;
                      }

                    }

                  }

                }

                leaf probability {
                  description 'Set mark probability denominator, support <1-100>.' ;
                  type uint8 {
                    range 1..100 {
                      description 'Set mark probability denominator, support <1-100>' ;
                    }

                  }

                  mandatory true ;
                }

              }

            }

            container precedences {
              description 'Configure WRED(Weighted Random Early Detection) thresholds based on precedence.' ;
              list precedence {
                description 'Configure WRED(Weighted Random Early Detection) thresholds based on precedence.' ;
                key prec-value ;
                leaf prec-value {
                  description 'Set the precedence value, such as MPLS EXP, VLAN 802.1p, IP DSCP, IP Precedence, support <0-7>.' ;
                  type uint16 {
                    range 0..7 {
                      description 'The IP-Precedence value, support <0-7>' ;
                    }

                  }

                }

                choice threshold {
                  description 'Set the threshold.' ;
                  case threshold-value {
                    description 'Set the threshold value.' ;
                    leaf min-threshold {
                      description 'Set the minimum threshold (default: kilobytes).' ;
                      type uint32 {
                        range 1..4294967295 {
                          description 'The minimum threshold (default: kilobytes), support <1-4294967295>' ;
                        }

                      }

                      mandatory true ;
                    }

                    leaf min-threshold-unit {
                      description 'Set min-threshold unit, such as kbytes, mbytes, gbytes.' ;
                      type qos-threshold-unit-type ;

                    }

                    leaf max-threshold {
                      description 'Set the maximum threshold (default: kilobytes).' ;
                      type uint32 {
                        range 1..4294967295 {
                          description 'The maximum threshold (default: kilobytes), support <1-4294967295>.' ;
                        }

                      }

                      mandatory true ;
                    }

                    leaf max-threshold-unit {
                      description 'Set max-threshold unit, such as kbytes, mbytes, gbytes.' ;
                      type qos-threshold-unit-type ;

                    }

                  }

                  case threshold-percentage {
                    description 'Set the threshold percentage.' ;
                    container threshold-percentage {
                      description 'Set the threshold percentage.' ;
                      leaf min-threshold-percentage {
                        description 'Set the minimum threshold percentage, support <1-100>.' ;
                        type uint32 {
                          range 1..100 {
                            description 'The minimum threshold percentage, support <1-100>' ;
                          }

                        }

                        mandatory true ;
                      }

                      leaf max-threshold-percentage {
                        description 'Set the maximum threshold percentage, support <1-100>.' ;
                        type uint32 {
                          range 1..100 {
                            description 'The maximum threshold percentage, support <1-100>' ;
                          }

                        }

                        mandatory true ;
                      }

                    }

                  }

                  case threshold-cachetime {
                    description 'Set the threshold cachetime.' ;
                    container threshold-cachetime {
                      description 'Set the threshold cachetime.' ;
                      leaf min-threshold-cachetime {
                        description 'Set the minimum threshold cachetime (default: ms).' ;
                        type uint32 {
                          range 1..1000 {
                            description 'The minimum threshold cachetime, support <1-1000>' ;
                          }

                        }

                        mandatory true ;
                      }

                      leaf max-threshold-cachetime {
                        description 'Set the maximum threshold cachetime (default: ms).' ;
                        type uint32 {
                          range 1..1000 {
                            description 'The maximum threshold cachetime, support <1-1000>' ;
                          }

                        }

                        mandatory true ;
                      }

                    }

                  }

                }

                leaf probability {
                  description 'Set mark probability denominator, support <1-100>.' ;
                  type uint32 {
                    range 1..100 {
                      description 'Set mark probability denominator, support <1-100>' ;
                    }

                  }

                  mandatory true ;
                }

              }

            }

            container weight {
              description 'Configure WRED(Weighted Random Early Detection) exponential weight factor.' ;
              presence "Configure WRED exponential weight factor" ;
              leaf weight-value {
                description 'Specify exponent used in weighted average calculation, support <1-16>.' ;
                type uint8 {
                  range 1..16 {
                    description 'Exponent used in weighted average calculation' ;
                  }

                }

                mandatory true ;
              }

            }

          }

        }

        ncd:revise-date 2022-06-27 ;
      }

      container flowspec-if-groups {
        if-feature flowspec-if-group ;

        description 'Configure flowspec interface group.' ;
        list flowspec-if-group {
          description 'Configure flowspec interface group.' ;
          key group-id ;
          leaf group-id {
            description 'Interface group ID.' ;
            type uint16 {
              range 0..16383 {
                description 'Interface group ID' ;
              }

            }

          }

          container if-names {
            description 'Configure flowspec interface.' ;
            list if-name {
              description 'Configure flowspec interface.' ;
              key if-name ;
              leaf if-name {
                description 'Configure flowspec interface.' ;
                type ncd:ifname ;

              }

            }

          }

        }

        ncd:revise-date 2022-10-10 ;
      }

      container qos-mark-if-prioritys {
        container qos-mark-if-dscps {
          list qos-mark-if-dscp {
            leaf if-name {
              description 'Configure the name of the mark interface.' ;
              type ncd:ifname {
                length 1..31 ;

              }

            }

            leaf dscp-value {
              type uint32 {
                range 0..63 ;

              }

              mandatory true ;
              description 'Configure the DSCP value of the mark interface.' ;
            }

            key if-name ;
            description 'Configure the interface DSCP mark.' ;
          }

          description 'Configure the interface DSCP mark.' ;
        }

        description 'Configure the interface priority mark.' ;
        if-feature qos-mark-if-priority ;

        ncd:revise-date 2023-04-18 ;
      }

      container qos-statistical-share-globals {
        if-feature qos-statistical-share-global ;

        list qos-statistical-share-global {
          leaf interface-name {
            description 'Name of the interface.' ;
            type ncd:ifname ;

          }

          leaf func-type {
            type enumeration {
              enum service-policy {
                value 1 ;
                description 'Based on service-policy function.' ;
              }

            }

            description 'QoS global statistical share type.' ;
          }

          leaf status {
            type enumeration {
              enum disable {
                value 0 ;
                description 'Based on disable status.' ;
              }

              enum enable {
                value 1 ;
                description 'Based on enable status.' ;
              }

            }

            description 'QoS global statistical share status.' ;
            mandatory true ;
          }

          description 'Configure QoS global statistical share on the interface.' ;
          key 'interface-name func-type' ;
        }

        description 'Configure QoS global statistical share on the interface.' ;
        ncd:revise-date 2024-04-01 ;
      }

      container qos-car-stats {
        container stats-switch-interfaces {
          list stats-switch-interface {
            leaf if-name {
              type ncd:ifname ;

              description 'The interface which to be enabled statistics.' ;
            }

            leaf direction {
              type qos-direction ;

              description 'The flow direction.' ;
            }

            description 'The QoS IF-CAR flow statistics switch.' ;
            key 'if-name direction' ;
          }

          description 'The QoS IF-CAR flow statistics switch.' ;
          if-feature qos-car-stats-if {
            ncd:revise-date 2024-05-09 ;
          }

        }

        description 'To enable or disable the QoS CAR statistics.' ;
        ncd:revise-date 2024-05-09 ;
      }

    }

  }

  container operation {
    config false ;
    description 'Operation model.' ;
    container qos {
      description 'Operation about QoS.' ;
      container stats-clear {
        description 'Clear QoS statistic data.' ;
        container pw-schedules {
          description 'Clear QoS statistic data of PW schedule.' ;
          list pw-schedule {
            description 'Clear QoS statistic data of PW schedule.' ;
            key pw-name ;
            leaf pw-name {
              description 'Name of the PW, support 1-31 characters.' ;
              type string {
                length 1..31 {
                  description 'Name of the PW, support 1-31 characters.' ;
                }

              }

            }

          }

        }

        container pw-in-schedules {
          description 'Clear QoS statistic data of ingress PW schedule.' ;
          list pw-in-schedule {
            description 'Clear QoS statistic data of ingress PW schedule.' ;
            key pw-name ;
            leaf pw-name {
              description 'Name of the PW, support 1-31 characters.' ;
              type string {
                length 1..31 {
                  description 'Name of the PW, support 1-31 characters.' ;
                }

              }

            }

          }

          ncd:revise-date 2021-01-18 ;
        }

        container te-schedules {
          description 'Clear QoS statistic data of TE schedule.' ;
          list te-schedule {
            description 'Clear QoS statistic data of TE schedule.' ;
            key te-tunnel ;
            leaf te-tunnel {
              description 'Name of the attaching tunnel.' ;
              type ncd:ifname ;

            }

          }

          ncd:revise-date 2021-03-24 ;
        }

        container te-reverse-schedules {
          if-feature schedule-te-reverse ;

          description 'Clear QoS statistic data of reverse TE schedule.' ;
          list te-reverse-schedule {
            description 'Clear QoS statistic data of reverse TE schedule.' ;
            key te-tunnel ;
            leaf te-tunnel {
              description 'Name of the attaching tunnel.' ;
              type ncd:ifname ;

            }

          }

          ncd:revise-date 2022-09-08 ;
        }

        container bgpad-schedules {
          description 'Clear QoS statistic data of BGP-AD schedule.' ;
          list bgpad-schedule {
            description 'Clear QoS statistic data of BGP-AD schedule.' ;
            key 'vpls-name peer-router-id' ;
            leaf vpls-name {
              description 'Set VPLS instance name, support 1-32 characters.' ;
              type string {
                length 1..32 ;

              }

            }

            leaf peer-router-id {
              description 'Set peer router id.' ;
              type ncd:ipv4-address ;

            }

          }

          ncd:revise-date 2021-01-11 ;
        }

        container interfaces {
          description 'Clear the QoS flow statistics.' ;
          list interface {
            description 'Clear the QoS flow statistics.' ;
            key 'if-name flow-direction' ;
            leaf if-name {
              description 'The interface which to be enabled statistics.' ;
              type ncd:ifname ;

            }

            leaf flow-direction {
              description 'The flow direction.' ;
              type qos-direction ;

            }

          }

          ncd:revise-date 2021-03-24 ;
        }

      }

      container traffic-policy-stats-clear {
        if-feature traffic-policy ;

        description 'Clear QoS traffic policy statistic data.' ;
        container stats-clear-interfaces {
          description 'Clear QoS traffic policy statistic data for interface.' ;
          list stats-clear-interface {
            description 'Clear QoS traffic policy statistic data for interface.' ;
            key 'if-name direction' ;
            leaf if-name {
              description 'The name of interface.' ;
              type ncd:ifname ;

            }

            leaf direction {
              description 'The direction to clear.' ;
              type qos-direction ;

            }

          }

        }

        container stats-clear-policy-maps {
          description 'Clear QoS traffic policy statistic data for policy map.' ;
          list stats-clear-policy-map {
            description 'Clear QoS traffic policy statistic data for policy map.' ;
            key 'policy-map-name direction' ;
            leaf policy-map-name {
              description 'The name of policy map.' ;
              type string {
                length 1..31 {
                  description 'Name of the policy map, support 1-31 characters' ;
                }

              }

            }

            leaf direction {
              description 'The direction to clear.' ;
              type qos-direction ;

            }

          }

          ncd:revise-date 2021-12-17 ;
        }

        ncd:revise-date 2021-01-25 ;
      }

      container qos-car-stats-clear {
        container stats-clear-interfaces {
          leaf if-name {
            type ncd:ifname ;

            description 'The name of interface.' ;
            mandatory true ;
          }

          leaf direction {
            type qos-direction ;

            description 'The flow direction.' ;
            mandatory true ;
          }

          choice match-type {
            description 'The match type of IF-CAR statistic.' ;
            case localport {
              container localport {
                leaf localport {
                  type empty ;

                  description 'Match localport.' ;
                  mandatory true ;
                }

                description 'Clear IF-CAR statistic data based on matching localport.' ;
                presence "match localport" ;
              }

              description 'Clear IF-CAR statistic data based on matching localport.' ;
            }

            case ipv4-access-list {
              container ipv4-access-list {
                leaf ipv4-acl-name {
                  type string {
                    length 1..31 {
                      description 'Name of IPv4 access list, support 1-31 characters.' ;
                    }

                  }

                  description 'Match IPv4 ACL name.' ;
                  mandatory true ;
                }

                description 'Clear IF-CAR statistic data based on matching IPv4 ACL.' ;
                presence "match ipv4 acl" ;
              }

              description 'Clear IF-CAR statistic data based on matching IPv4 ACL.' ;
            }

            case ipv6-access-list {
              container ipv6-access-list {
                leaf ipv6-acl-name {
                  type string {
                    length 1..31 {
                      description 'Name of IPv6 access list, support 1-31 characters.' ;
                    }

                  }

                  description 'Match IPv6 ACL name.' ;
                  mandatory true ;
                }

                description 'Clear IF-CAR statistic data based on matching IPv6 ACL.' ;
                presence "match ipv6 acl" ;
              }

              description 'Clear IF-CAR statistic data based on matching IPv6 ACL.' ;
            }

            case link-access-list {
              container link-access-list {
                leaf link-acl-name {
                  type string {
                    length 1..31 {
                      description 'Name of link access list, support 1-31 characters.' ;
                    }

                  }

                  description 'Match Link ACL name.' ;
                  mandatory true ;
                }

                description 'Clear IF-CAR statistic data based on matching link ACL.' ;
                presence "match link acl" ;
              }

              description 'Clear IF-CAR statistic data based on matching link ACL.' ;
            }

          }

          description 'Clear IF-CAR statistic data.' ;
          presence "stats clear interfaces" ;
          if-feature qos-car-stats-if {
            ncd:revise-date 2024-05-09 ;
          }

        }

        description 'Clear QoS CAR statistic data.' ;
        ncd:revise-date 2024-05-09 ;
      }

    }

    ncd:revise-date 2016-05-03 ;
  }

  container state {
    config false ;
    description 'State model.' ;
    container qos {
      description 'State about QoS.' ;
      container hqosstats {
        description 'Query HQoS statistics data.' ;
        list hqosstat {
          description 'Query HQoS statistics data.' ;
          key 'if dir p0 c1 p1 c2 p2 c3 p3 c4' ;
          leaf if {
            description 'The name of the attaching interface.' ;
            type ncd:ifname ;

          }

          leaf dir {
            description 'Configure the interface direction.' ;
            type enumeration {
              enum input {
                value 1 ;
                description 'Attaches to the input interface' ;
              }

              enum output {
                value 2 ;
                description 'Attaches to the output interface' ;
              }

            }

          }

          leaf p0 {
            description 'The 1st level policy-map name.' ;
            type string {
              length 1..31 {
                description 'The 1st level policy-map name.' ;
              }

            }

          }

          leaf c1 {
            description 'The 1st level class-map name.' ;
            type string {
              length 1..31 {
                description 'The 1st level class-map name.' ;
              }

            }

          }

          leaf p1 {
            description 'The 2nd level policy-map name.' ;
            type string {
              length 1..31 {
                description 'The 2nd level policy-map name.' ;
              }

            }

          }

          leaf c2 {
            description 'The 2nd level class-map name.' ;
            type string {
              length 1..31 {
                description 'The 2nd level class-map name.' ;
              }

            }

          }

          leaf p2 {
            description 'The 3rd level policy-map name.' ;
            type string {
              length 1..31 {
                description 'The 3rd level policy-map name.' ;
              }

            }

          }

          leaf c3 {
            description 'The 3rd level class-map name.' ;
            type string {
              length 1..31 {
                description 'The 3rd level class-map name.' ;
              }

            }

          }

          leaf p3 {
            description 'The 4th level policy-map name.' ;
            type string {
              length 1..31 {
                description 'The 4th level policy-map name.' ;
              }

            }

          }

          leaf c4 {
            description 'The 4th level class-map name.' ;
            type string {
              length 1..31 {
                description 'The 4th level class-map name.' ;
              }

            }

          }

          leaf transmit-pkts {
            description 'The transmit packtes.' ;
            type uint64 ;

          }

          leaf transmit-octets {
            description 'The transmit octets.' ;
            type uint64 ;

            units byte ;
          }

          leaf dropped-pkts {
            description 'The dropped packtes.' ;
            type uint64 ;

          }

          leaf dropped-octets {
            description 'The dropped octets.' ;
            type uint64 ;

            units byte ;
          }

          leaf transmit-pkts-rate {
            description 'The transmit packtes rate.' ;
            type uint64 ;

            units pps ;
          }

          leaf transmit-octets-rate {
            description 'The transmit octets rate.' ;
            type uint64 ;

            units Bps ;
            ncd:revise-date 2022-08-23 ;
          }

          leaf dropped-pkts-rate {
            description 'The dropped packtes rate.' ;
            type uint64 ;

            units pps ;
            ncd:revise-date 2022-08-23 ;
          }

          leaf dropped-octets-rate {
            description 'The dropped octets rate.' ;
            type uint64 ;

            units Bps ;
            ncd:revise-date 2022-08-23 ;
          }

          leaf used-queue-depth-pkts {
            description 'The used queue depth (Unit:packet).' ;
            type uint64 ;

            units packet ;
            ncd:revise-date 2022-08-23 ;
          }

          leaf used-queue-depth {
            description 'The used queue depth (Unit:byte).' ;
            type uint64 ;

            units byte ;
            ncd:revise-date 2022-08-23 ;
          }

          leaf pkts-loss-rate {
            description 'The packets loss rate.' ;
            type decimal64 {
              fraction-digits 4 ;
            }

            ncd:revise-date 2022-08-23 ;
          }

          leaf octets-loss-rate {
            description 'The octets loss rate.' ;
            type decimal64 {
              fraction-digits 4 ;
            }

            ncd:revise-date 2022-08-23 ;
          }

        }

      }

      container statistics {
        description 'Query QoS queue statistics data.' ;
        list statistic {
          description 'Query QoS queue statistics data.' ;
          key 'ifname direction' ;
          leaf ifname {
            description 'The name of the attaching interface.' ;
            type string {
              length 1..31 {
                description 'Name of the attaching interface, support 1-31 characters' ;
              }

            }

          }

          leaf direction {
            description 'Configure the interface direction.' ;
            type enumeration {
              enum input {
                value 1 ;
                description 'Attaches to the input interface' ;
              }

              enum output {
                value 2 ;
                description 'Attaches to the output interface' ;
              }

            }

          }

          container queues {
            description 'Query QoS queque statistics data.' ;
            list queue {
              description 'Query QoS queque statistics data.' ;
              key name ;
              leaf name {
                description 'The name of queue.' ;
                type qos-service-class ;

              }

              leaf transmit-pkts {
                description 'The transmit packtes.' ;
                type uint64 ;

              }

              leaf transmit-octets {
                description 'The transmit octets.' ;
                type uint64 ;

                units byte ;
              }

              leaf dropped-pkts {
                description 'The dropped packtes.' ;
                type uint64 ;

              }

              leaf dropped-octets {
                description 'The dropped octets.' ;
                type uint64 ;

                units byte ;
              }

              leaf transmit-pkts-rate {
                description 'The transmit packtes rate.' ;
                type uint64 ;

                units pps ;
              }

              leaf total-queue-depth {
                description 'The total queue depth.' ;
                type uint64 ;

                units byte ;
                ncd:revise-date 2021-09-15 ;
              }

              leaf used-queue-depth {
                description 'The used queue depth (Unit:byte).' ;
                type uint64 ;

                units byte ;
                ncd:revise-date 2021-09-15 ;
              }

              leaf transmit-octets-rate {
                description 'The transmit octets rate.' ;
                type uint64 ;

                units Bps ;
                ncd:revise-date 2022-08-23 ;
              }

              leaf transmit-bits-rate {
                description 'The transmit bits rate.' ;
                type uint64 ;

                units bps ;
                ncd:revise-date 2022-08-23 ;
              }

              leaf dropped-pkts-rate {
                description 'The dropped packtes rate.' ;
                type uint64 ;

                units pps ;
                ncd:revise-date 2022-08-23 ;
              }

              leaf dropped-bits-rate {
                description 'The dropped bits rate.' ;
                type uint64 ;

                units bps ;
                ncd:revise-date 2022-08-23 ;
              }

              leaf received-bits-rate {
                description 'The received bits rate.' ;
                type uint64 ;

                units bps ;
                ncd:revise-date 2022-12-26 ;
              }

              leaf used-queue-depth-pkts {
                description 'The used queue depth (Unit:packet).' ;
                type uint64 ;

                units packet ;
                ncd:revise-date 2022-08-23 ;
              }

              leaf pkts-loss-rate {
                description 'The packets loss rate.' ;
                type decimal64 {
                  fraction-digits 4 ;
                }

                ncd:revise-date 2022-08-23 ;
              }

              leaf octets-loss-rate {
                description 'The octets loss rate.' ;
                type decimal64 {
                  fraction-digits 4 ;
                }

                ncd:revise-date 2022-08-23 ;
              }

              leaf real-time-usage {
                description 'The real time usage.' ;
                type decimal64 {
                  fraction-digits 4 ;
                }

                ncd:revise-date 2022-08-23 ;
              }

            }

          }

          ncd:select ifname ;
          ncd:select "ifname direction" ;
        }

        ncd:revise-date 2021-08-11 ;
      }

      container queue-resource-stats {
        description 'QoS queue resource statistics data.' ;
        list boardstat {
          description 'Board queue resource statistics.' ;
          key board-name ;
          leaf board-name {
            description 'The board name.' ;
            type string {
              length 1..31 ;

            }

          }

          leaf in-total-num {
            description 'The total number of queue resources in the input direction.' ;
            type uint32 ;

          }

          leaf in-used-num {
            description 'The used number of queue resources in the input direction.' ;
            type uint32 ;

          }

          leaf out-total-num {
            description 'The total number of queue resources in the output direction.' ;
            type uint32 ;

          }

          leaf out-used-num {
            description 'The used number of queue resources in the output direction.' ;
            type uint32 ;

          }

        }

        ncd:revise-date 2021-08-23 ;
      }

      container flowspec-vrf-stats {
        description 'Query QoS VRF flowspec statistics data.' ;
        list flowspec-vrf-stat {
          description 'Query QoS VRF flowspec statistics data.' ;
          key 'address-family vrfName index' ;
          leaf address-family {
            description 'The address family.' ;
            type enumeration {
              enum ipv4 {
                value 4 ;
                description 'The address family type is IPv4.' ;
              }

              enum ipv6 {
                value 24 ;
                description 'The address family type is IPv6.' ;
              }

            }

          }

          leaf vrfName {
            description 'Virtual route forwarding name, support 1-32 characters.' ;
            type string {
              length 1..32 {
                description 'Virtual route forwarding name, support 1-32 characters.' ;
              }

            }

          }

          leaf index {
            description 'Flowspec statistics index.' ;
            type binary {
              length 32 {
                description 'The length of flowspec statistics index.' ;
              }

            }

          }

          container match {
            description 'Get match criteria of a class map.' ;
            container dscp {
              description 'Select DSCP as match criteria.' ;
              leaf dscp-value {
                description 'Get QoS dscp in range mode, support single DSCP value or range(max num:4;spacing mark:,) in <0-63>. For example,"6,10-30,40,50-60",etc.' ;
                type ncd:range ;

              }

            }

            container destination-ipv4-addr {
              description 'Select destination-address as match criteria.' ;
              leaf dst-address {
                description 'Destination IPv4 address.' ;
                type ncd:ipv4-address ;

              }

              leaf dst-address-mask {
                description 'Destination IPv4 maskcard bits.' ;
                type ncd:ipv4-mask ;

              }

            }

            container destination-ipv6-addr {
              description 'Select IPv6 destination-address as match criteria.' ;
              leaf dst-ipv6-addr {
                description 'IPv6 destination address.' ;
                type ncd:ipv6-address ;

              }

              leaf dst-ipv6-addr-prefix {
                description 'IPv6 destination maskcard length.' ;
                type uint8 {
                  range 0..128 {
                    description 'The range of the IPv6 address prefix.' ;
                  }

                }

              }

            }

            container source-ipv4-addr {
              description 'Select source-address as match criteria.' ;
              leaf src-address {
                description 'Source IPv4 address.' ;
                type ncd:ipv4-address ;

              }

              leaf src-address-mask {
                description 'Source IPv4 maskcard bits.' ;
                type ncd:ipv4-mask ;

              }

            }

            container source-ipv6-addr {
              description 'Select IPv6 source-address as match criteria.' ;
              leaf src-ipv6-addr {
                description 'IPv6 source address.' ;
                type ncd:ipv6-address ;

              }

              leaf src-ipv6-addr-prefix {
                description 'IPv6 source maskcard length.' ;
                type ncd:ipv6-mask-length ;

              }

            }

            container fragment-type {
              description 'Select fragment-type as match criteria.' ;
              leaf not {
                description 'Get logical negation of operation,
true  Match opposite
false Match current.' ;
                type boolean ;

              }

              leaf match-relation {
                description 'The rule of matching, see bellow:                
all  Match all of the fragment type
any  Match any of the fragment type.' ;
                type enumeration {
                  enum all {
                    value 0 ;
                    description 'Match all of the fragment type.' ;
                  }

                  enum any {
                    value 1 ;
                    description 'Match any of the fragment type.' ;
                  }

                }

              }

              leaf dont-fragment {
                description 'Match dont-fragment.' ;
                type boolean ;

              }

              leaf first-fragment {
                description 'Match first-fragment.' ;
                type boolean ;

              }

              leaf is-fragment {
                description 'Match is-fragment.' ;
                type boolean ;

              }

              leaf last-fragment {
                description 'Match last-fragment.' ;
                type boolean ;

              }

            }

            container port {
              description 'Select port as match criteria.' ;
              leaf port-value {
                description 'Get port value in range mode, support single port value or range(max num:4;spacing mark:,) in <0-65535>. For example,"1,300-400,1000,2000-4000",etc.' ;
                type ncd:range ;

              }

            }

            container destination-port {
              description 'Select destination-port as match criteria.' ;
              leaf dst-port-value {
                description 'Get destination-port value in range mode, support single destination-port value or range(max num:4;spacing mark:,) in <0-65535>. For example,"1,300-400,1000,2000-4000",etc.' ;
                type ncd:range ;

              }

            }

            container source-port {
              description 'Select source-port as match criteria.' ;
              leaf src-port-value {
                description 'Get source-port value in range mode, support single source-port value or range(max num:4;spacing mark:,) in <0-65535>. For example,"1,300-400,1000,2000-4000",etc.' ;
                type ncd:range ;

              }

            }

            container icmp-code {
              description 'Select icmp-code as match criteria.' ;
              leaf icmp-code-value {
                description 'Get icmp code in range mode, support single icmp-code value or range(max num:4;spacing mark:,) in <0-255>. For example,"6,10-30,40,50-60",etc.' ;
                type ncd:range ;

              }

            }

            container icmp-type {
              description 'Select icmp-type as match criteria.' ;
              leaf icmp-type-value {
                description 'Get icmp type in range mode, support single icmp-type value or range(max num:4;spacing mark:,) in <0-255>. For example,"6,10-30,40,50-60",etc.' ;
                type ncd:range ;

              }

            }

            container packet-length {
              description 'Select packet-length as match criteria.' ;
              leaf packet-length-value {
                description 'Get packet-length in range mode, support single packet-length value or range(max num:4;spacing mark:,) in <1-65535>. For example,"6,10-30,40,50-60",etc.' ;
                type ncd:range ;

              }

            }

            container protocol {
              description 'Select protocol as match criteria.' ;
              leaf protocol-value {
                description 'Get protocol in range mode, support single protocol value or range(max num:4;spacing mark:,) in <0-255>. For example,"6,10-30,40,50-60",etc.' ;
                type ncd:range ;

              }

            }

            container tcp-flags {
              description 'Select tcp-flag as match criteria.' ;
              list tcp-flag {
                description 'Select tcp-flag as match criteria.' ;
                key 'cwr ece urg ack psh rst syn fin' ;
                leaf cwr {
                  description 'Match on the CWR bit.' ;
                  type boolean ;

                }

                leaf ece {
                  description 'Match on the ECE bit.' ;
                  type boolean ;

                }

                leaf urg {
                  description 'Match on the URG bit.' ;
                  type boolean ;

                }

                leaf ack {
                  description 'Match on the ACK bit.' ;
                  type boolean ;

                }

                leaf psh {
                  description 'Match on the PSH bit.' ;
                  type boolean ;

                }

                leaf rst {
                  description 'Match on the RST bit.' ;
                  type boolean ;

                }

                leaf syn {
                  description 'Match on the SYN bit.' ;
                  type boolean ;

                }

                leaf fin {
                  description 'Match on the FIN bit.' ;
                  type boolean ;

                }

                leaf not {
                  description 'Get logical negation of operation,
true  Match opposite
false Match current.' ;
                  type boolean ;

                }

                leaf match-relation {
                  description 'The rule of matching, see bellow:                
all  Match all of the fragment type
any  Match any of the fragment type.' ;
                  type enumeration {
                    enum all {
                      value 0 ;
                      description 'Match all of the fragment type.' ;
                    }

                    enum any {
                      value 1 ;
                      description 'Match any of the fragment type.' ;
                    }

                  }

                }

                leaf relation-with-previous {
                  description 'The logical relationship with the previous tcp-flag match item, see bellow:                
and  The relationship to the previous tcp-flag is and
or   The relationship to the previous tcp-flag is or.' ;
                  type enumeration {
                    enum and {
                      value 1 ;
                      description 'The relationship to the previous tcp-flag match item is and.' ;
                    }

                    enum or {
                      value 2 ;
                      description 'The relationship to the previous tcp-flag match item is or.' ;
                    }

                  }

                }

                ncd:select "cwr ece urg ack psh rst syn fin" ;
              }

            }

            container flow-label {
              description 'Select flow-label as match criteria.' ;
              leaf flow-label-value {
                description 'Get flow label value.' ;
                type uint32 {
                  range 0..1048575 {
                    description 'The range of the flow label value.' ;
                  }

                }

              }

            }

            container next-header {
              description 'Select next-header as match criteria.' ;
              leaf next-header-value {
                description 'Get next-header in range mode, support single value or range(max num:4;spacing mark:,) in <0-255>. For example,"6,10-30,40,50-60",etc.' ;
                type ncd:range ;

              }

            }

          }

          container action {
            description 'Get the action of the flowspec.' ;
            container set {
              description 'Mark a packet.' ;
              container dscp {
                description 'Select DSCP as mark type.' ;
                leaf dscp-value {
                  description 'Get action of DSCP value, support <0-63>.' ;
                  type uint16 {
                    range 0..63 {
                      description 'DSCP value, support <0-63>' ;
                    }

                  }

                }

              }

            }

            container drop {
              description 'Get drop action.' ;
              leaf drop {
                description 'Get drop action.' ;
                type boolean ;

              }

            }

            container police {
              description 'Get traffic policing action.' ;
              leaf rate {
                description 'Get the rate value(default:kilobits per second).' ;
                type uint32 {
                  range 8..4294967295 {
                    description 'Get the rate value(default:kilobits per second).' ;
                  }

                }

              }

            }

            container redirect-nexthop {
              description 'Get redirect nexthop action.' ;
              container ip-address {
                description 'Get IPv4 address type of next-hop.' ;
                leaf ipv4-address {
                  description 'IPv4 address.' ;
                  type ncd:ipv4-address ;

                }

                leaf global {
                  description 'Global route.' ;
                  type boolean ;

                }

                leaf route-target {
                  description 'Whether route-target is configured as next-hop.' ;
                  type boolean ;

                }

                leaf rt-pattern {
                  description 'Route target, support three types as follow:
1. <0-65535>:<0-4294967295>
2. A.B.C.D:<0-65535>
3. <1-65535>.<0-65535>:<0-65535>.' ;
                  type string ;

                }

                leaf vrf-name {
                  description 'Virtual route forwarding name, support 1-32 characters.' ;
                  type string {
                    length 1..32 {
                      description 'Virtual route forwarding name, support 1-32 characters.' ;
                    }

                  }

                }

                leaf copy {
                  description 'Copy flag.' ;
                  type boolean ;

                }

              }

              container route-target {
                description 'Get route-target type of next-hop.' ;
                leaf route-target {
                  description 'Whether route-target is configured as next-hop.' ;
                  type boolean ;

                }

                leaf rt-pattern {
                  description 'Route target, support three types as follow:
1. <0-65535>:<0-4294967295>
2. A.B.C.D:<0-65535>
3. <1-65535>.<0-65535>:<0-65535>.' ;
                  type string ;

                }

              }

              container vrf {
                description 'Get virtual route forwarding type of next-hop.' ;
                leaf vrf-name {
                  description 'Virtual route forwarding name, support 1-32 characters.' ;
                  type string {
                    length 1..32 {
                      description 'Virtual route forwarding name, support 1-32 characters.' ;
                    }

                  }

                }

              }

              container ipv6-address {
                description 'Get IPv6 address type of next-hop.' ;
                leaf ipv6-address {
                  description 'IPv6 address.' ;
                  type ncd:ipv6-address ;

                }

                leaf global {
                  description 'Global route.' ;
                  type boolean ;

                }

                leaf route-target {
                  description 'Whether route-target is configured as next-hop.' ;
                  type boolean ;

                }

                leaf rt-pattern {
                  description 'Route target, support three types as follow:
1. <0-65535>:<0-4294967295>
2. A.B.C.D:<0-65535>
3. <1-65535>.<0-65535>:<0-65535>.' ;
                  type string ;

                }

                leaf vrf-name {
                  description 'Virtual route forwarding name, support 1-32 characters.' ;
                  type string {
                    length 1..32 {
                      description 'Virtual route forwarding name, support 1-32 characters.' ;
                    }

                  }

                }

                leaf color {
                  description 'Get color value, support 1-4294967295.' ;
                  type uint32 {
                    range 1..4294967295 ;

                  }

                }

                leaf prefix-sid {
                  description 'Get prefix SID value, <X:X:X:X:X:X:X:X>.' ;
                  type ncd:ipv6-address ;

                }

                leaf copy {
                  description 'Copy flag.' ;
                  type boolean ;

                }

              }

              container srv6-be {
                description 'Get srv6-be type of next-hop.' ;
                leaf srv6-be {
                  description 'Get srv6-be.' ;
                  type ncd:ipv6-address ;

                }

                leaf end-point {
                  description 'Get end-point.' ;
                  type ncd:ipv6-address ;

                }

                leaf copy {
                  description 'Copy flag.' ;
                  type boolean ;

                }

                ncd:revise-date 2022-09-26 ;
              }

            }

            container redirect-tunnel-id {
              description 'Get redirect tunnel ID.' ;
              leaf indirection-id {
                description 'Get indirection ID.' ;
                type uint32 {
                  range 1..4294967295 ;

                }

              }

              leaf copy {
                description 'Get copy flag.' ;
                type boolean ;

              }

            }

            container sampler {
              description 'Get sampler action.' ;
              leaf sampler {
                description 'Get sampler action.' ;
                type boolean ;

              }

            }

          }

          container if-groups {
            description 'Get interface group ID.' ;
            list if-group {
              description 'Get interface group ID.' ;
              key if-group-id ;
              leaf if-group-id {
                description 'Get interface group ID.' ;
                type uint16 {
                  range 0..16383 {
                    description 'Set interface group ID.' ;
                  }

                }

              }

            }

            ncd:revise-date 2022-10-10 ;
          }

          leaf matchPackets {
            description 'The number of matched packets.' ;
            type uint64 ;

          }

          leaf matchBytes {
            description 'The number of matched bytes.' ;
            type uint64 ;

            units byte ;
          }

          leaf transmitPackets {
            description 'The number of transmitted packets.' ;
            type uint64 ;

          }

          leaf transmitBytes {
            description 'The number of transmitted bytes.' ;
            type uint64 ;

            units byte ;
          }

          leaf dropPackets {
            description 'The number of dropped packets.' ;
            type uint64 ;

          }

          leaf dropBytes {
            description 'The number of dropped bytes.' ;
            type uint64 ;

          }

          ncd:select "address-family vrfName" ;
        }

        ncd:revise-date 2022-05-07 ;
      }

      container flowspec-ip-stats {
        description 'Query QoS IPv4 or IPv6 flowspec statistics data.' ;
        list flowspec-ip-stat {
          description 'Query QoS IPv4 or IPv6 flowspec statistics data.' ;
          key 'address-family index' ;
          leaf address-family {
            description 'The address family.' ;
            type enumeration {
              enum ipv4 {
                value 4 ;
                description 'The address family type is IPv4.' ;
              }

              enum ipv6 {
                value 24 ;
                description 'The address family type is IPv6.' ;
              }

            }

          }

          leaf index {
            description 'Flowspec statistics index.' ;
            type binary {
              length 32 {
                description 'The length of flowspec statistics index.' ;
              }

            }

          }

          container match {
            description 'Get match criteria of a class map.' ;
            container dscp {
              description 'Select DSCP as match criteria.' ;
              leaf dscp-value {
                description 'Get QoS dscp in range mode, support single DSCP value or range(max num:4;spacing mark:,) in <0-63>. For example,"6,10-30,40,50-60",etc.' ;
                type ncd:range ;

              }

            }

            container destination-ipv4-addr {
              description 'Select destination-address as match criteria.' ;
              leaf dst-address {
                description 'Destination IPv4 address.' ;
                type ncd:ipv4-address ;

              }

              leaf dst-address-mask {
                description 'Destination IPv4 maskcard bits.' ;
                type ncd:ipv4-mask ;

              }

            }

            container destination-ipv6-addr {
              description 'Select IPv6 destination-address as match criteria.' ;
              leaf dst-ipv6-addr {
                description 'IPv6 destination address.' ;
                type ncd:ipv6-address ;

              }

              leaf dst-ipv6-addr-prefix {
                description 'IPv6 destination maskcard length.' ;
                type uint8 {
                  range 0..128 {
                    description 'The range of the IPv6 address prefix.' ;
                  }

                }

              }

            }

            container source-ipv4-addr {
              description 'Select source-address as match criteria.' ;
              leaf src-address {
                description 'Source IPv4 address.' ;
                type ncd:ipv4-address ;

              }

              leaf src-address-mask {
                description 'Source IPv4 maskcard bits.' ;
                type ncd:ipv4-mask ;

              }

            }

            container source-ipv6-addr {
              description 'Select IPv6 source-address as match criteria.' ;
              leaf src-ipv6-addr {
                description 'IPv6 source address.' ;
                type ncd:ipv6-address ;

              }

              leaf src-ipv6-addr-prefix {
                description 'IPv6 source maskcard length.' ;
                type ncd:ipv6-mask-length ;

              }

            }

            container fragment-type {
              description 'Select fragment-type as match criteria.' ;
              leaf not {
                description 'Get logical negation of operation,
true  Match opposite
false Match current.' ;
                type boolean ;

              }

              leaf match-relation {
                description 'The rule of matching, see bellow:                
all  Match all of the fragment type
any  Match any of the fragment type.' ;
                type enumeration {
                  enum all {
                    value 0 ;
                    description 'Match all of the fragment type.' ;
                  }

                  enum any {
                    value 1 ;
                    description 'Match any of the fragment type.' ;
                  }

                }

              }

              leaf dont-fragment {
                description 'Match dont-fragment.' ;
                type boolean ;

              }

              leaf first-fragment {
                description 'Match first-fragment.' ;
                type boolean ;

              }

              leaf is-fragment {
                description 'Match is-fragment.' ;
                type boolean ;

              }

              leaf last-fragment {
                description 'Match last-fragment.' ;
                type boolean ;

              }

            }

            container port {
              description 'Select port as match criteria.' ;
              leaf port-value {
                description 'Get port value in range mode, support single port value or range(max num:4;spacing mark:,) in <0-65535>. For example,"1,300-400,1000,2000-4000",etc.' ;
                type ncd:range ;

              }

            }

            container destination-port {
              description 'Select destination-port as match criteria.' ;
              leaf dst-port-value {
                description 'Get destination-port value in range mode, support single destination-port value or range(max num:4;spacing mark:,) in <0-65535>. For example,"1,300-400,1000,2000-4000",etc.' ;
                type ncd:range ;

              }

            }

            container source-port {
              description 'Select source-port as match criteria.' ;
              leaf src-port-value {
                description 'Get source-port value in range mode, support single source-port value or range(max num:4;spacing mark:,) in <0-65535>. For example,"1,300-400,1000,2000-4000",etc.' ;
                type ncd:range ;

              }

            }

            container icmp-code {
              description 'Select icmp-code as match criteria.' ;
              leaf icmp-code-value {
                description 'Get icmp code in range mode, support single icmp-code value or range(max num:4;spacing mark:,) in <0-255>. For example,"6,10-30,40,50-60",etc.' ;
                type ncd:range ;

              }

            }

            container icmp-type {
              description 'Select icmp-type as match criteria.' ;
              leaf icmp-type-value {
                description 'Get icmp type in range mode, support single icmp-type value or range(max num:4;spacing mark:,) in <0-255>. For example,"6,10-30,40,50-60",etc.' ;
                type ncd:range ;

              }

            }

            container packet-length {
              description 'Select packet-length as match criteria.' ;
              leaf packet-length-value {
                description 'Get packet-length in range mode, support single packet-length value or range(max num:4;spacing mark:,) in <1-65535>. For example,"6,10-30,40,50-60",etc.' ;
                type ncd:range ;

              }

            }

            container protocol {
              description 'Select protocol as match criteria.' ;
              leaf protocol-value {
                description 'Get protocol in range mode, support single protocol value or range(max num:4;spacing mark:,) in <0-255>. For example,"6,10-30,40,50-60",etc.' ;
                type ncd:range ;

              }

            }

            container tcp-flags {
              description 'Select tcp-flag as match criteria.' ;
              list tcp-flag {
                description 'Select tcp-flag as match criteria.' ;
                key 'rst ack fin syn psh urg ece cwr' ;
                leaf cwr {
                  description 'Match on the CWR bit.' ;
                  type boolean ;

                }

                leaf ece {
                  description 'Match on the ECE bit.' ;
                  type boolean ;

                }

                leaf urg {
                  description 'Match on the URG bit.' ;
                  type boolean ;

                }

                leaf ack {
                  description 'Match on the ACK bit.' ;
                  type boolean ;

                }

                leaf psh {
                  description 'Match on the PSH bit.' ;
                  type boolean ;

                }

                leaf rst {
                  description 'Match on the RST bit.' ;
                  type boolean ;

                }

                leaf syn {
                  description 'Match on the SYN bit.' ;
                  type boolean ;

                }

                leaf fin {
                  description 'Match on the FIN bit.' ;
                  type boolean ;

                }

                leaf not {
                  description 'Get logical negation of operation,
true  Match opposite
false Match current.' ;
                  type boolean ;

                }

                leaf match-relation {
                  description 'The rule of matching, see bellow:                
all  Match all of the fragment type
any  Match any of the fragment type.' ;
                  type enumeration {
                    enum all {
                      value 0 ;
                      description 'Match all of the fragment type.' ;
                    }

                    enum any {
                      value 1 ;
                      description 'Match any of the fragment type.' ;
                    }

                  }

                }

                leaf relation-with-previous {
                  description 'The logical relationship with the previous tcp-flag match item, see bellow:                
and  The relationship to the previous tcp-flag is and
or   The relationship to the previous tcp-flag is or.' ;
                  type enumeration {
                    enum and {
                      value 1 ;
                      description 'The relationship to the previous tcp-flag match item is and.' ;
                    }

                    enum or {
                      value 2 ;
                      description 'The relationship to the previous tcp-flag match item is or.' ;
                    }

                  }

                }

                ncd:select "cwr ece urg ack psh rst syn fin" ;
              }

            }

            container flow-label {
              description 'Select flow-label as match criteria.' ;
              leaf flow-label-value {
                description 'Get flow label value.' ;
                type uint32 {
                  range 0..1048575 {
                    description 'The range of the flow label value.' ;
                  }

                }

              }

            }

            container next-header {
              description 'Select next-header as match criteria.' ;
              leaf next-header-value {
                description 'Get next-header in range mode, support single value or range(max num:4;spacing mark:,) in <0-255>. For example,"6,10-30,40,50-60",etc.' ;
                type ncd:range ;

              }

            }

          }

          container action {
            description 'Get the action of the flowspec.' ;
            container set {
              description 'Mark a packet.' ;
              container dscp {
                description 'Select DSCP as mark type.' ;
                leaf dscp-value {
                  description 'Get action of DSCP value, support <0-63>.' ;
                  type uint16 {
                    range 0..63 {
                      description 'DSCP value, support <0-63>' ;
                    }

                  }

                }

              }

            }

            container drop {
              description 'Get drop action.' ;
              leaf drop {
                description 'Get drop action.' ;
                type boolean ;

              }

            }

            container police {
              description 'Get traffic policing action.' ;
              leaf rate {
                description 'Get the rate value(default:kilobits per second).' ;
                type uint32 {
                  range 8..4294967295 {
                    description 'Get the rate value(default:kilobits per second).' ;
                  }

                }

              }

            }

            container redirect-nexthop {
              description 'Get redirect nexthop action.' ;
              container ip-address {
                description 'Get IPv4 address type of next-hop.' ;
                leaf ipv4-address {
                  description 'IPv4 address.' ;
                  type ncd:ipv4-address ;

                }

                leaf global {
                  description 'Global route.' ;
                  type boolean ;

                }

                leaf route-target {
                  description 'Whether route-target is configured as next-hop.' ;
                  type boolean ;

                }

                leaf rt-pattern {
                  description 'Route target, support three types as follow:
1. <0-65535>:<0-4294967295>
2. A.B.C.D:<0-65535>
3. <1-65535>.<0-65535>:<0-65535>.' ;
                  type string ;

                }

                leaf vrf-name {
                  description 'Virtual route forwarding name, support 1-32 characters.' ;
                  type string {
                    length 1..32 {
                      description 'Virtual route forwarding name, support 1-32 characters.' ;
                    }

                  }

                }

                leaf copy {
                  description 'Copy flag.' ;
                  type boolean ;

                }

              }

              container route-target {
                description 'Get route-target type of next-hop.' ;
                leaf route-target {
                  description 'Whether route-target is configured as next-hop.' ;
                  type boolean ;

                }

                leaf rt-pattern {
                  description 'Route target, support three types as follow:
1. <0-65535>:<0-4294967295>
2. A.B.C.D:<0-65535>
3. <1-65535>.<0-65535>:<0-65535>.' ;
                  type string ;

                }

              }

              container vrf {
                description 'Get virtual route forwarding type of next-hop.' ;
                leaf vrf-name {
                  description 'Virtual route forwarding name, support 1-32 characters.' ;
                  type string {
                    length 1..32 {
                      description 'Virtual route forwarding name, support 1-32 characters.' ;
                    }

                  }

                }

              }

              container ipv6-address {
                description 'Get IPv6 address type of next-hop.' ;
                leaf ipv6-address {
                  description 'IPv6 address.' ;
                  type ncd:ipv6-address ;

                }

                leaf global {
                  description 'Global route.' ;
                  type boolean ;

                }

                leaf route-target {
                  description 'Whether route-target is configured as next-hop.' ;
                  type boolean ;

                }

                leaf rt-pattern {
                  description 'Route target, support three types as follow:
1. <0-65535>:<0-4294967295>
2. A.B.C.D:<0-65535>
3. <1-65535>.<0-65535>:<0-65535>.' ;
                  type string ;

                }

                leaf vrf-name {
                  description 'Virtual route forwarding name, support 1-32 characters.' ;
                  type string {
                    length 1..32 {
                      description 'Virtual route forwarding name, support 1-32 characters.' ;
                    }

                  }

                }

                leaf color {
                  description 'Get color value, support 1-4294967295.' ;
                  type uint32 {
                    range 1..4294967295 ;

                  }

                }

                leaf prefix-sid {
                  description 'Get prefix SID value, <X:X:X:X:X:X:X:X>.' ;
                  type ncd:ipv6-address ;

                }

                leaf copy {
                  description 'Copy flag.' ;
                  type boolean ;

                }

              }

              container srv6-be {
                description 'Get srv6-be type of next-hop.' ;
                leaf srv6-be {
                  description 'Get srv6-be.' ;
                  type ncd:ipv6-address ;

                }

                leaf end-point {
                  description 'Get end-point.' ;
                  type ncd:ipv6-address ;

                }

                leaf copy {
                  description 'Copy flag.' ;
                  type boolean ;

                }

                ncd:revise-date 2022-09-26 ;
              }

            }

            container redirect-tunnel-id {
              description 'Get redirect tunnel ID.' ;
              leaf indirection-id {
                description 'Get indirection ID.' ;
                type uint32 {
                  range 1..4294967295 ;

                }

              }

              leaf copy {
                description 'Get copy flag.' ;
                type boolean ;

              }

            }

            container sampler {
              description 'Get sampler action.' ;
              leaf sampler {
                description 'Get sampler action.' ;
                type boolean ;

              }

            }

          }

          container if-groups {
            description 'Get interface group ID.' ;
            list if-group {
              description 'Get interface group ID.' ;
              key if-group-id ;
              leaf if-group-id {
                description 'Get interface group ID.' ;
                type uint16 {
                  range 0..16383 {
                    description 'Set interface group ID.' ;
                  }

                }

              }

            }

            ncd:revise-date 2022-10-10 ;
          }

          leaf matchPackets {
            description 'The number of matched packets.' ;
            type uint64 ;

          }

          leaf matchBytes {
            description 'The number of matched bytes.' ;
            type uint64 ;

            units byte ;
          }

          leaf transmitPackets {
            description 'The number of transmitted packets.' ;
            type uint64 ;

          }

          leaf transmitBytes {
            description 'The number of transmitted bytes.' ;
            type uint64 ;

            units byte ;
          }

          leaf dropPackets {
            description 'The number of dropped packets.' ;
            type uint64 ;

          }

          leaf dropBytes {
            description 'The number of dropped bytes.' ;
            type uint64 ;

          }

          ncd:select address-family ;
        }

        ncd:revise-date 2022-05-07 ;
      }

      container traffic-policy-if-stats {
        description 'Query QoS if key traffic policy statistics data.' ;
        list traffic-policy-if-stat {
          description 'Query QoS if key traffic policy statistics data.' ;
          key 'if dir pname cname' ;
          leaf if {
            description 'The name of the attaching interface.' ;
            type ncd:ifname ;

          }

          leaf dir {
            description 'Configure the interface direction.' ;
            type enumeration {
              enum input {
                value 1 ;
                description 'Attaches to the input interface' ;
              }

              enum output {
                value 2 ;
                description 'Attaches to the output interface' ;
              }

            }

          }

          leaf pname {
            description 'Policy map name.' ;
            type string {
              length 1..31 {
                description 'Policy map name.' ;
              }

            }

          }

          leaf cname {
            description 'Class map name.' ;
            type string {
              length 1..31 {
                description 'Class map name.' ;
              }

            }

          }

          leaf transmit-pkts-rate {
            description 'The transmit packtes rate.' ;
            type uint64 ;

            units pps ;
          }

          leaf transmit-octets-rate {
            description 'The transmit octets rate.' ;
            type uint64 ;

            units Bps ;
          }

          leaf dropped-pkts-rate {
            description 'The dropped packtes rate.' ;
            type uint64 ;

            units pps ;
          }

          leaf dropped-octets-rate {
            description 'The dropped octets rate.' ;
            type uint64 ;

            units Bps ;
          }

        }

        ncd:revise-date 2022-09-19 ;
      }

    }

    ncd:revise-date 2021-06-04 ;
  }

}
