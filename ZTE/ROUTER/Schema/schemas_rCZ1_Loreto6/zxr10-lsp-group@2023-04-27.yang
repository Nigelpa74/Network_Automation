module zxr10-lsp-group {
  namespace "http://www.zte.com.cn/zxr10/netconf/schema/rosng/lsp-group" ;
  prefix lspg ;
  yang-version 1 ;
  import zxr10-netconf-defs {
    prefix ncd ;
  }
  
  organization "ZTE Corporation" ;
  contact "ZTE Corporation  
     Nanjing Institute of ZTE Corporation 
     No.68 Zijinghua Rd. Yuhuatai District, Nanjing, China 
     Tel: +86-25-52870000" ;
  description 'The netconf module to describe the lsp-group.' ;
  revision 2023-04-27 {
    description 'Modify the range of the leaf /state/lsp-group/lsp-group-state/group-id.' ;
  }

  revision 2018-05-14 {
    description 'Add srv6_hotstandby type value of the leaf /state/lsp-group/lsp-group-state/group-type.' ;
  }

  revision 2016-10-10 {
    description 'Add a type value of the leaf /state/lsp-group/lsp-group-state/group-type.' ;
  }

  revision 2013-07-02 {
    description 'Initial version.' ;
  }

  container state {
    config false ;
    description 'State model information of lsp-group.' ;
    container lsp-group {
      description 'State data of lsp-group.' ;
      list lsp-group-state {
        description 'Query LSP protection group status information, the protection group ID generated by the system, can not be set. The minimum value of protection group ID is 1, and the maximum value of protection group ID depends on the performance parameter and its default value is 4096.Support queries without conditions and at protection group ID query.' ;
        max-elements 4096 ;
        key "group-id" ;
        leaf group-id {
          description 'The ID of lsp-group.' ;
          type uint32 {
            range 1..65535 {
              description 'ID of lsp-group.' ;
            }

          }

          ncd:revise-date 2023-04-27 ;
        }

        leaf group-type {
          description 'The type of lsp-group.' ;
          type enumeration {
            enum hotstandby {
              value 1 ;
              description 'This lsp-group type is hotstandby.' ;
            }

            enum facility {
              value 2 ;
              description 'This lsp-group type is facility.' ;
            }

            enum detour {
              value 3 ;
              description 'This lsp-group type is detour.' ;
            }

            enum sr_hotstandby {
              value 4 ;
              description 'This lsp-group type is sr_hotstandby.' ;
            }

            enum srv6_hotstandby {
              value 5 ;
              description 'This lsp-group type is srv6_hotstandby.' ;
            }

          }

        }

        leaf working-lsp-tunnel-id {
          description 'The tunnel ID of working LSP.' ;
          type uint32 ;

        }

        leaf working-lsp-id {
          description 'The LSP ID of working LSP.' ;
          type uint32 ;

        }

        leaf working-lsp-direction {
          description 'The direction of working LSP.' ;
          type uint8 ;

        }

        leaf protect-lsp-tunnel-id {
          description 'The tunnel ID of protection LSP.' ;
          type uint32 ;

        }

        leaf protect-lsp-id {
          description 'The LSP ID of protection LSP.' ;
          type uint32 ;

        }

        leaf protect-lsp-direction {
          description 'The direction of protection LSP.' ;
          type uint8 ;

        }

        leaf switch-state {
          description 'The switch state of this lsp-group.' ;
          type enumeration {
            enum switch {
              value 1 ;
              description 'Active LSP of this lsp-group is protection LSP.' ;
            }

            enum unswitch {
              value 2 ;
              description 'Active LSP of this lsp-group is working LSP.' ;
            }

          }

        }

      }

    }

  }

}
