module zxr10-cgn {
  namespace "http://www.zte.com.cn/zxr10/netconf/schema/rosng/cgn" ;
  prefix cgn ;
  yang-version 1 ;
  import zxr10-netconf-defs {
    prefix ncd ;
    revision-date 2014-06-24 ;
  }

  organization "ZTE Corporation" ;
  contact "ZTE Corporation
  Nanjing Institute of ZTE Corporation
  No.68 Zijinghua Rd. Yuhuatai District, Nanjing, China
  Tel: +86-25-52870000" ;
  description 'The netconf module to describe CGN.' ;
  revision 2025-04-10 {
    description 'Add feature http-alg-feature' ;
  }

  revision 2025-03-21 {
    description 'Add leaf:
configuration\cgn\alg-list\alg-list\pptp-nat64' ;
  }

  revision 2024-11-11 {
    description 'Add nodes:
configuration\cgn\log\keepalive-log\keepalive-enable
configuration\cgn\log\keepalive-log\keepalive-time
configuration\cgn\log\keepalive-log\keepalive-disable
Modify node:
configuration\cgn\log\log-style' ;
  }

  revision 2024-10-31 {
    description 'Modified some comments.' ;
  }

  revision 2024-08-16 {
    description 'add leafs as follows:
state\cgn\statistics\statistics2-list\alg-statistics\ipsec-alg-success-num
state\cgn\statistics\statistics2-list\alg-statistics\ipsec-alg-fail-num' ;
  }

  revision 2024-07-15 {
    description 'add container as follows:
configuration\cgn\domain-list\domain\esp-policy
add leafs as follows:
configuration\cgn\domain-list\domain\esp-policy\esp-timeout
configuration\cgn\domain-list\domain\esp-policy\gate-timeout
configuration\cgn\alg-list\alg-switch\ipsec' ;
  }

  revision 2024-04-01 {
    description 'Add nodes cgn/domain-list/domain/static-rule-list/static-rule/dest-ip' ;
  }

  revision 2024-03-12 {
    description 'Add nodes:
configuration\cgn\instance-list\default-instance\location-list\location\capacity
configuration\cgn\instance-list\instance\location-list\location\capacity' ;
  }

  revision 2023-12-05 {
    description 'Modify nodes:
configuration\cgn\pool-list\nat-pool\section-list\section\section-no range from 1-200 to 1-2000
configuration\cgn\pool-list\nat-pool\max-number range from 1-200 to 1-2000
configuration\cgn\pool-list\nat-pool\lock-ip-list\lock-ip\lock-ip-type\section\section-no range from 1-200 to 1-2000
configuration\cgn\pool-list\pat-pool\section-list\section\section-no range from 1-200 to 1-2000
configuration\cgn\pool-list\pat-pool\max-number range from 1-200 to 1-2000
configuration\cgn\pool-list\pat-pool\lock-ip-list\lock-ip\lock-ip-type\section\section-no range from 1-200 to 1-2000' ;
  }

  revision 2023-10-19 {
    description 'Modify max-private-address-num range from 1-500000 to 1-1000000' ;
  }

  revision 2023-03-27 {
    description 'Add nodes:
configuration\cgn\log-list\destination\ipflow\ipflow-list\log-type' ;
  }

  revision 2023-01-17 {
    description 'Section configure interface IP as global IP.
Add section-interface-feature.
Modify nodes:
configuration\cgn\pool-list\nat-pool\section-list\section\section-type\interface.
configuration\cgn\pool-list\pat-pool\section-list\section\section-type\interface.' ;
  }

  revision 2022-10-20 {
    description 'Add nodes:
configuration\cgn\advanced-and-pcp-service-list\advanced-service\hotack-delay-time' ;
  }

  revision 2022-04-14 {
    description 'Obsolete nodes as follows:
configuration\cgn\log-list\log\destination\ipflow\ipflow
configuration\cgn\log-list\log\destination\ipflow\flow-exporter-name
Add notes as follows:
configuration\cgn\log-list\log\destination\ipflow\ipflow-list' ;
  }

  revision 2022-03-02 {
    description 'Add nodes:
configuration\cgn\pool-list\pat-pool\max-idle-port-range' ;
  }

  revision 2021-08-27 {
    description 'Add nodes:
configuration\cgn\domain-list\max-trans-per-ipv4-addr-list' ;
  }

  revision 2021-06-18 {
    description 'Modify nodes:
configuration\cgn\domain-list\domain\static-rule-list\static-rule' ;
  }

  revision 2021-05-17 {
    description 'Modify as follows:
configuration\cgn\domain-list\domain\aftr-address
configuration\cgn\user-list\public-sl-nat64-user\nat64-ipv4-route-list\nat64-ipv4-route
configuration\cgn\user-list\vrf-sl-nat64-user\nat64-ipv4-route-list\nat64-ipv4-route
configuration\cgn\user-list\public-sl-nat64-eam-user\nat64-ipv4-route
configuration\cgn\user-list\vrf-sl-nat64-eam-user\nat64-ipv4-route' ;
  }

  revision 2021-04-23 {
    description 'Add the default of the choice as follows:
configuration\global\cgn-res-alloc-disconnect
Modify select as follows:
configuration\cgn\spr-list\spr-ipv4-interface
configuration\cgn\spr-list\spr-vrf-ipv4-interface
configuration\cgn\spr-list\spr-ipv6-interface
configuration\cgn\spr-list\spr-vrf-ipv6-interface' ;
  }

  revision 2021-02-26 {
    description 'Obsolete nodes as follows:
configuration\cgn\instance-list\default-instance\allocate-mode
configuration\cgn\instance-list\instance\allocate-mode
configuration\cgn\domain-list\domain\softwire-error-alarm-threshold
configuration\cgn\domain-list\domain\same-address-policy\same-addr-for-same-softwire
configuration\cgn\domain-list\domain\same-address-policy\same-addr-for-same-user
configuration\cgn\domain-list\domain\max-translations-list\max-translations\limit-type
configuration\cgn\pool-list\nat-pool\port-alarm-value

Add DSLite and NAT64 nodes.' ;
  }

  revision 2020-12-18 {
    description 'Add nodes:
configuration\cgn\domain-list\dnat-list
configuration\cgn\pool-list\nat-pool\dnat-mode' ;
  }

  revision 2020-11-04 {
    description 'Add nodes:
configuration\cgn\user-list\public-sl-nat66-user
configuration\cgn\user-list\vrf-sl-nat66-user' ;
  }

  revision 2020-08-11 {
    description 'Add nodes:
configuration\cgn\pool-list\pat-pool\location\auto\auto
configuration\cgn\pool-list\pat-pool\location\location-choice-clear\location-all-clear' ;
  }

  revision 2020-05-28 {
    description 'Add leafs as follows:
configuration\cgn\car-policy-template\car-policy-name\description
configuration\cgn\user-list\public-user\description
configuration\cgn\user-list\vrf-user\description
Modify leafs inbound-route-map length from 31 to 200' ;
  }

  revision 2020-05-16 {
    description 'Change the length of the poolname to 64.' ;
  }

  revision 2020-05-12 {
    description 'Add default value of leafs as follows:
configuration\cgn\pool-list\nat-pool\max-number
configuration\cgn\pool-list\pat-pool\max-number
Delete timeout default value of tcp-policy' ;
  }

  revision 2020-05-08 {
    description 'Modify leafs pool-name length from 32 to 31.
state\cgn\pool-utilization\pool\pool-name
state\cgn\pool-utilization\detail\pool-name
state\cgn\pool-utilization\ip\pool-name
Add default value of leafs as follows:
configuration\cgn\instance-list\default-instance\location-list\location\track
configuration\cgn\instance-list\instance\location-list\location\track
Add filter of choice as follows:
configuration\cgn\domain-list\domain\max-translations-list\max-translations' ;
  }

  revision 2020-03-21 {
    description 'modify leafs as follows:
configuration\cgn\pool-list\pat-pool\position
configuration\cgn\pool-list\nat-pool\position' ;
  }

  revision 2020-02-19 {
    description 'Add selects as follows:
state\cgn\local-ip\local-ip-public
state\cgn\local-ip\local-ip-vrf' ;
  }

  revision 2020-01-10 {
    description 'modify leafs as follows:
configuration\cgn\domain-list\domain\max-trans-per-apps
add container as follows:
configuration\cgn\domain-list\domain\bind-pool-list' ;
  }

  revision 2019-12-15 {
    description 'Add nodes as follows:
configuration\global\log-ipflow-template' ;
  }

  revision 2019-11-04 {
    description 'Add leafs as follows:
configuration\cgn\log-list\log\log-style1-start-end-time-with-zone
configuration\cgn\log-list\log\log-style1-duration
Add nodes as follows:
state\cgn\local-ip' ;
  }

  revision 2019-09-10 {
    description 'Add leafs as follows:
configuration\cgn\pool-list\pat-pool\port-forbidden-list' ;
  }

  revision 2019-08-09 {
    description 'Add leafs as follows:
configuration\cgn\domain-list\domain\max-trans-per-apps' ;
  }

  revision 2019-06-25 {
    description 'obsolete value as follows:
configuration\cgn\log-list\log\log-ahead' ;
  }

  revision 2019-05-05 {
    description 'Add leafs as follows:
configuration\cgn\pool-list\nat-pool\detect-retransmit-number
configuration\cgn\pool-list\nat-pool\detect-interval-day
configuration\cgn\pool-list\nat-pool\detect-interval-hour
configuration\cgn\pool-list\nat-pool\detect-interval-minute
configuration\cgn\pool-list\pat-pool\detect-retransmit-number
configuration\cgn\pool-list\pat-pool\detect-interval-day
configuration\cgn\pool-list\pat-pool\detect-interval-hour
configuration\cgn\pool-list\pat-pool\detect-interval-minute' ;
  }

  revision 2019-04-19 {
    description 'Add leafs as follows:
configuration\cgn\user-list\public-user\inbound-route-map
configuration\cgn\user-list\vrf-user\inbound-route-map' ;
  }

  revision 2019-03-13 {
    description 'Add leafs as follows:
configuration\cgn\pool-list\nat-pool\lock-ip-list
configuration\cgn\pool-list\pat-pool\lock-ip-list' ;
  }

  revision 2019-03-06 {
    description 'Add leafs as follows:
configuration\cgn\alarm-list\alarm\static-port-range-threshold' ;
  }

  revision 2018-11-14 {
    description 'Add leafs as follows:
configuration\cgn\pool-list\nat-pool\assign
configuration\cgn\pool-list\pat-pool\assign' ;
  }

  revision 2018-08-08 {
    description 'Add lists as follows:
configuration\global\cgn-res-alloc-disconnect\response-delay\response-delay-time
configuration\global\cgn-res-alloc-disconnect\forever\forever' ;
  }

  revision 2018-04-19 {
    description 'Static rule configure interface IP as global IP.
Add static-rule-interface-feature.
Add configuration\cgn\domain-list\domain\static-rule-list\static-rule\trans-mode\interface-pat.
Add configuration\cgn\domain-list\domain\static-rule-list\static-rule\trans-mode\interface-nat.' ;
  }

  revision 2018-01-26 {
    description 'Add lists as follows:
configuration\cgn\spr-list\spr-ipv4-interface
configuration\cgn\spr-list\spr-vrf-ipv4-interface' ;
  }

  revision 2017-12-28 {
    description 'Add leafs as follows:
configuration\cgn\pool-list\nat-pool\recycle
configuration\cgn\pool-list\pat-pool\recycle' ;
  }

  revision 2017-11-21 {
    description 'Modify configuration\cgn\domain-list\domain\max-translations-list\max-translations\translation-type
change Range 0~10000000 to 0~32000000 
change Reset 10000000 to 32000000
chage mimActions value 10000001 to 32000001
chage filter value 10000000 to 32000000' ;
  }

  revision 2017-11-02 {
    description 'Add nodes as follows:
configuration\cgn\spr-list\spr-ipv4\extend
configuration\cgn\spr-list\spr-vrf-ipv4\extend' ;
  }

  revision 2017-10-28 {
    description 'Add nodes as follows:
configuration\cgn\pool-list\pat-pool\max-static-port-range-blocks' ;
  }

  revision 2017-10-16 {
    description 'Add nodes as follows:
configuration\cgn\pool-list\nat-pool\position
configuration\cgn\pool-list\nat-pool\ippool-name
configuration\cgn\pool-list\nat-pool\low
configuration\cgn\pool-list\nat-pool\high
configuration\cgn\pool-list\nat-pool\mask
configuration\cgn\pool-list\nat-pool\max-number
configuration\cgn\pool-list\pat-pool\position
configuration\cgn\pool-list\pat-pool\ippool-name
configuration\cgn\pool-list\pat-pool\low
configuration\cgn\pool-list\pat-pool\high
configuration\cgn\pool-list\pat-pool\mask
configuration\cgn\pool-list\pat-pool\max-number' ;
  }

  revision 2017-08-03 {
    description 'Add nodes as follows:
configuration\cgn\advanced-and-pcp-service-list\advanced-service\pool-reuse
configuration\cgn\pool-list\pat-pool\port-reserved' ;
  }

  revision 2017-06-20 {
    description 'Add nodes as follows:
configuration\cgn\domain-list\domain\tcp-policy\unwell-known-fin-wait-timeout
configuration\cgn\domain-list\domain\tcp-policy\well-known-fin-wait-timeout
configuration\cgn\instance-list\default-instance\location-list\location\track
configuration\cgn\instance-list\instance\location-list\location\track' ;
  }

  revision 2017-05-27 {
    description 'Modify location\master-spu and location\slave-spu, IF filter-id 8 change to 13, which support SPFU, SPU, PFU, MPU;
Modify tcp-policy, udp-policy, icmp-policy, nat-policy(OperationChangeType:DELETE2RESET)' ;
  }

  revision 2017-04-17 {
    description 'Modify value as follows:
configuration\cgn\log-list\log\log-style(add enum item style3)' ;
  }

  revision 2017-03-27 {
    description 'Modify defalut value as follows:
configuration\cgn\pool-list\nat-pool\section-list\section\section-no(1~64 change to 1~200)
configuration\cgn\pool-list\pat-pool\section-list\section\section-no(1~64 change to 1~200)' ;
  }

  revision 2017-02-08 {
    description 'Add nodes as follows:
configuration\cgn\pool-list\nat-pool\hot-standby-route-metric
configuration\cgn\pool-list\nat-pool\hot-standby-route-priority
configuration\cgn\pool-list\nat-pool\location-node
configuration\cgn\pool-list\pat-pool\hot-standby-route-metric
configuration\cgn\pool-list\pat-pool\hot-standby-route-priority
configuration\cgn\pool-list\pat-pool\location-node
configuration\cgn\instance-list\default-instance\allocate-mode
configuration\cgn\instance-list\instance\allocate-mode
configuration\cgn\log-list\log\urllog-switch
Modify defalut value as follows:
configuration\cgn\advanced-and-pcp-service-list\pcp-service\pcp-switch(change to disable)
Obsolete nodes as follows:
configuration\cgn\domain-list\domain\tcp-policy\port-parity
configuration\cgn\domain-list\domain\udp-policy\port-parity' ;
  }

  revision 2016-11-15 {
    description 'Add nodes as follows:
configuration\global\cgn-outside-interface-list' ;
  }

  revision 2016-09-22 {
    description 'Add nodes as follows:
state\cgn\pool-utilization
state\cgn\statistics
configuration\cgn\domain-list\domain\max-translations-list
configuration\cgn\log-list\log\log-ahead
configuration\cgn\log-list\log\ipflow
configuration\cgn\alarm-list\alarm\translations-threshold-high-level
configuration\cgn\alarm-list\alarm\translations-threshold-middle-level
configuration\cgn\alarm-list\alarm\performance-statistics-switch
configuration\cgn\alarm-list\alarm\local-ip-threshold' ;
  }

  revision 2015-12-07 {
    description 'Initial version.' ;
  }

  feature static-rule-interface-feature {
    description 'Static rule interface feature.' ;
  }

  feature section-interface-feature {
    description 'Section interface feature.' ;
    ncd:revise-date 2023-01-17 ;
  }

  feature location-node-capacity-feature {
    description 'Location node capacity feature.' ;
    ncd:revise-date 2024-03-12 ;
  }

  feature static-rule-dest-ip-feature {
    description 'Static rule dest IP feature.' ;
    ncd:revise-date 2024-04-01 ;
  }

  feature http-alg-feature {
    description 'HTTP ALG feature.' ;
    ncd:revise-date 2025-04-10 ;
  }

  container state {
    config false ;
    description 'The state of CGN.' ;
    container cgn {
      description 'The CGN state.' ;
      container global-counters {
        description 'The global counters of CGN.' ;
        leaf trans-packet-num {
          description 'The number of packets successfully translated.' ;
          type uint32 ;

          default 0 ;
        }

        leaf port-deplete-num {
          description 'The number of packets discarded due to port resource depletion.' ;
          type uint32 ;

          default 0 ;
        }

        leaf quota-exceed-num {
          description 'The number of packets discarded because of the quota exceeded.' ;
          type uint32 ;

          default 0 ;
        }

        leaf trans-num {
          description 'Translations number.' ;
          type uint32 ;

          default 0 ;
        }

        leaf ipv4-address-num {
          description 'The number of private IPv4 addresses.' ;
          type uint32 ;

          default 0 ;
        }

        leaf private-ipv4-num {
          description 'The number of private IPv4 addresses.' ;
          type uint32 ;

          default 0 ;
        }

      }

      container translations-summary {
        description 'CGN translations summary.' ;
        container total-sum {
          description 'CGN translations total number.' ;
          leaf static-nat-trans-num {
            description 'Static NAT translations number.' ;
            type uint32 ;

          }

          leaf static-pat-trans-num {
            description 'Static PAT translations number.' ;
            type uint32 ;

          }

          leaf dynamic-nat-trans-num {
            description 'Dynamic NAT translations number.' ;
            type uint32 ;

          }

          leaf dynamic-pat-trans-num {
            description 'Dynamic PAT translations number.' ;
            type uint32 ;

          }

          leaf alg-trans-num {
            description 'ALG translations number.' ;
            type uint32 ;

          }

          leaf pcp-trans-num {
            description 'PCP translations number.' ;
            type uint32 ;

          }

          leaf local-ip-num {
            description 'Local IP number.' ;
            type uint32 ;

          }

          leaf total-translations-num {
            description 'Total translations number.' ;
            type uint32 ;

          }

        }

        list single-cpu-sum {
          description 'CGN translations number of one CPU.' ;
          key cpu-name ;
          leaf cpu-name {
            description 'CPU Name.' ;
            type ncd:cpu ;

          }

          leaf static-nat-trans-num {
            description 'Static NAT translations number.' ;
            type uint32 ;

          }

          leaf static-pat-trans-num {
            description 'Static NAT translations number.' ;
            type uint32 ;

          }

          leaf dynamic-nat-trans-num {
            description 'Dynamic NAT translations number.' ;
            type uint32 ;

          }

          leaf dynamic-pat-trans-num {
            description 'Dynamic PAT translations number.' ;
            type uint32 ;

          }

          leaf alg-trans-num {
            description 'ALG translations number.' ;
            type uint32 ;

          }

          leaf pcp-trans-num {
            description 'PCP translations number.' ;
            type uint32 ;

          }

          leaf local-ip-num {
            description 'Local IP number.' ;
            type uint32 ;

          }

        }

      }

      container pool-utilization {
        description 'Pool utilization.' ;
        container total {
          description 'Total.' ;
          leaf nat-used-ip-count {
            description 'NAT used IP count.' ;
            type uint32 ;

          }

          leaf nat-total-ip-count {
            description 'NAT total IP count.' ;
            type uint32 ;

          }

          leaf pat-total-ip-count {
            description 'PAT total IP count.' ;
            type uint32 ;

          }

          leaf tcp-used-port-count {
            description 'TCP used port count.' ;
            type uint32 ;

          }

          leaf udp-used-port-count {
            description 'UDP used port count.' ;
            type uint32 ;

          }

          leaf icmp-used-port-count {
            description 'ICMP used port count.' ;
            type uint32 ;

          }

          leaf tcp-total-port-count {
            description 'TCP total port count.' ;
            type uint32 ;

          }

          leaf udp-total-port-count {
            description 'UDP total port count.' ;
            type uint32 ;

          }

          leaf icmp-total-port-count {
            description 'ICMP total port count.' ;
            type uint32 ;

          }

        }

        list pool {
          description 'Pool.' ;
          key pool-name ;
          leaf pool-name {
            description 'Pool name.' ;
            type string {
              length 1..31 ;

            }

          }

          leaf nat-used-ip-count {
            description 'NAT used IP count.' ;
            type uint32 ;

          }

          leaf nat-total-ip-count {
            description 'NAT total IP count.' ;
            type uint32 ;

          }

          leaf pat-total-ip-count {
            description 'PAT total IP count.' ;
            type uint32 ;

          }

          leaf tcp-used-port-count {
            description 'TCP used port count.' ;
            type uint32 ;

          }

          leaf udp-used-port-count {
            description 'UDP used port count.' ;
            type uint32 ;

          }

          leaf icmp-used-port-count {
            description 'ICMP used port count.' ;
            type uint32 ;

          }

          leaf tcp-total-port-count {
            description 'TCP total port count.' ;
            type uint32 ;

          }

          leaf udp-total-port-count {
            description 'UDP total port count.' ;
            type uint32 ;

          }

          leaf icmp-total-port-count {
            description 'ICMP total port count.' ;
            type uint32 ;

          }

        }

        list cpu {
          description 'CPU.' ;
          key cpu-name ;
          leaf cpu-name {
            description 'CPU Name.' ;
            type ncd:cpu ;

          }

          leaf nat-used-ip-count {
            description 'NAT used IP count.' ;
            type uint32 ;

          }

          leaf nat-total-ip-count {
            description 'NAT total IP count.' ;
            type uint32 ;

          }

          leaf pat-total-ip-count {
            description 'PAT total IP count.' ;
            type uint32 ;

          }

          leaf tcp-used-port-count {
            description 'TCP used port count.' ;
            type uint32 ;

          }

          leaf udp-used-port-count {
            description 'UDP used port count.' ;
            type uint32 ;

          }

          leaf icmp-used-port-count {
            description 'ICMP used port count.' ;
            type uint32 ;

          }

          leaf tcp-total-port-count {
            description 'TCP total port count.' ;
            type uint32 ;

          }

          leaf udp-total-port-count {
            description 'UDP total port count.' ;
            type uint32 ;

          }

          leaf icmp-total-port-count {
            description 'ICMP total port count.' ;
            type uint32 ;

          }

        }

        list detail {
          description 'Detail.' ;
          key 'cpu-name pool-name' ;
          leaf cpu-name {
            description 'CPU Name.' ;
            type ncd:cpu ;

          }

          leaf pool-name {
            description 'Pool name.' ;
            type string {
              length 1..31 ;

            }

          }

          leaf nat-used-ip-count {
            description 'NAT used IP count.' ;
            type uint32 ;

          }

          leaf nat-total-ip-count {
            description 'NAT total IP count.' ;
            type uint32 ;

          }

          leaf pat-total-ip-count {
            description 'PAT total IP count.' ;
            type uint32 ;

          }

          leaf tcp-used-port-count {
            description 'TCP used port count.' ;
            type uint32 ;

          }

          leaf udp-used-port-count {
            description 'UDP used port count.' ;
            type uint32 ;

          }

          leaf icmp-used-port-count {
            description 'ICMP used port count.' ;
            type uint32 ;

          }

          leaf tcp-total-port-count {
            description 'TCP total port count.' ;
            type uint32 ;

          }

          leaf udp-total-port-count {
            description 'UDP total port count.' ;
            type uint32 ;

          }

          leaf icmp-total-port-count {
            description 'ICMP total port count.' ;
            type uint32 ;

          }

        }

        list ip {
          description 'IP.' ;
          key 'pool-name ip cpu-name' ;
          leaf pool-name {
            description 'Pool name.' ;
            type string {
              length 1..31 ;

            }

          }

          leaf ip {
            description 'IP address.' ;
            type ncd:ipv4-address-none-zero ;

          }

          leaf cpu-name {
            description 'CPU Name.' ;
            type ncd:cpu ;

          }

          leaf nat-used-ip-count {
            description 'NAT used IP count.' ;
            type uint32 ;

          }

          leaf nat-total-ip-count {
            description 'NAT total IP count.' ;
            type uint32 ;

          }

          leaf pat-total-ip-count {
            description 'PAT total IP count.' ;
            type uint32 ;

          }

          leaf tcp-used-port-count {
            description 'TCP used port count.' ;
            type uint32 ;

          }

          leaf udp-used-port-count {
            description 'UDP used port count.' ;
            type uint32 ;

          }

          leaf icmp-used-port-count {
            description 'ICMP used port count.' ;
            type uint32 ;

          }

          leaf tcp-total-port-count {
            description 'TCP total port count.' ;
            type uint32 ;

          }

          leaf udp-total-port-count {
            description 'UDP total port count.' ;
            type uint32 ;

          }

          leaf icmp-total-port-count {
            description 'ICMP total port count.' ;
            type uint32 ;

          }

        }

        ncd:revise-date 2016-09-22 ;
      }

      container statistics {
        description 'CGN statistics.' ;
        list statistics1-list {
          description 'Statistics list1.' ;
          key cpu-name ;
          leaf cpu-name {
            description 'CPU name.' ;
            type ncd:cpu ;

          }

          container packet-check-statistics {
            description 'Packet check statistics.' ;
            leaf ip-success-num {
              description 'The number of packets successfully checked.' ;
              type uint64 ;

              default 0 ;
            }

            leaf ip-fail-num {
              description 'The number of packets checked failed.' ;
              type uint64 ;

              default 0 ;
            }

            leaf ip-packet-length-error-num {
              description 'The number of packets that IP header length is inconsistent.' ;
              type uint64 ;

              default 0 ;
            }

            leaf exceed-max-length-num {
              description 'The number of packets exceeded maximum length.' ;
              type uint64 ;

              default 0 ;
            }

            leaf less-than-minimum-ip-head-length-num {
              description 'The number of packets the minimum IP header length check failed.' ;
              type uint64 ;

              default 0 ;
            }

            leaf illegal-source-address-num {
              description 'Illegal source address number.' ;
              type uint64 ;

              default 0 ;
            }

            leaf illegal-dest-address-num {
              description 'Illegal destination address number.' ;
              type uint64 ;

              default 0 ;
            }

            leaf ttl-zero-num {
              description 'TTL zero error number.' ;
              type uint64 ;

              default 0 ;
            }

            leaf illegal-ip-fragment-num {
              description 'Illegal IP fragment number.' ;
              type uint64 ;

              default 0 ;
            }

            leaf ip-wrong-checksum-num {
              description 'The number of wrong IP checksum packets.' ;
              type uint64 ;

              default 0 ;
            }

            leaf illegal-ip-protocol-num {
              description 'The number of Illegal IP protocol packets.' ;
              type uint64 ;

              default 0 ;
            }

            leaf ip-version-error-num {
              description 'The number of invalid IP version packets.' ;
              type uint64 ;

              default 0 ;
            }

            leaf ip-unknown-error-num {
              description 'Unknown error number.' ;
              type uint64 ;

              default 0 ;
            }

            leaf tcp-header-length-error-num {
              description 'The number of packets that TCP header length is inconsistent.' ;
              type uint64 ;

              default 0 ;
            }

            leaf tcp-port-zero-num {
              description 'The number of packets that source or destination port number is zero.' ;
              type uint64 ;

              default 0 ;
            }

            leaf illegal-sequence-and-flags-num {
              description 'Illegal sequence number and flags combinations packets number.' ;
              type uint64 ;

              default 0 ;
            }

            leaf tcp-first-packet-not-syn-num {
              description 'First packet not a SYN message packets number.' ;
              type uint64 ;

              default 0 ;
            }

            leaf tcp-wrong-checksum-num {
              description 'The number of wrong TCP checksum packets.' ;
              type uint64 ;

              default 0 ;
            }

            leaf data-len-less-than-min-udp-head-num {
              description 'The number of packets whose IP data length less than minimum UDP header length (8 bytes).' ;
              type uint64 ;

              default 0 ;
            }

            leaf udp-port-zero-num {
              description 'The number of packets that source or destination port number is zero.' ;
              type uint64 ;

              default 0 ;
            }

            leaf udp-wrong-checksum-num {
              description 'The number of wrong UDP checksum packets.' ;
              type uint64 ;

              default 0 ;
            }

            leaf data-len-less-than-min-icmp-head-num {
              description 'The number of packets whose IP data length less than minimum ICMP header length (8 bytes).' ;
              type uint64 ;

              default 0 ;
            }

            leaf icmp-length-error-num {
              description 'The number of packets that ICMP error length is inconsistent.' ;
              type uint64 ;

              default 0 ;
            }

            leaf icmp-invalid-type-num {
              description 'The number of invalid ICMP type packets.' ;
              type uint64 ;

              default 0 ;
            }

            leaf icmp-wrong-checksum-num {
              description 'The number of wrong ICMP checksum packets.' ;
              type uint64 ;

              default 0 ;
            }

            leaf other-error-num {
              description 'Other error number.' ;
              type uint64 ;

              default 0 ;
            }

          }

          container all-translation {
            description 'All translation statistics.' ;
            leaf success-num {
              description 'The number of packets successfully translated.' ;
              type uint64 ;

              default 0 ;
            }

            leaf fail-num {
              description 'The number of packets translated failed.' ;
              type uint64 ;

              default 0 ;
            }

            leaf send-icmp-error-success-num {
              description 'The number of packets sending ICMP error successfully.' ;
              type uint64 ;

              default 0 ;
            }

            leaf send-icmp-error-failed-num {
              description 'The number of packets sending ICMP error failed.' ;
              type uint64 ;

              default 0 ;
            }

            leaf send-packet-fail-num {
              description 'The number of sending packets failed.' ;
              type uint64 ;

              default 0 ;
            }

          }

          container pat-translation {
            description 'PAT translation statistics.' ;
            leaf tcp-success-num {
              description 'The number of TCP packets successfully translated.' ;
              type uint64 ;

              default 0 ;
            }

            leaf tcp-fail-num {
              description 'The number of TCP packets translated failed.' ;
              type uint64 ;

              default 0 ;
            }

            leaf tcp-policy-error-num {
              description 'The number of packets TCP policy checked failed.' ;
              type uint64 ;

              default 0 ;
            }

            leaf tcp-invalid-direction-num {
              description 'The number of TCP invalid direction packets.' ;
              type uint64 ;

              default 0 ;
            }

            leaf tcp-inbound-no-trans-num {
              description 'The number of inbound packets had no translation.' ;
              type uint64 ;

              default 0 ;
            }

            leaf tcp-subscriber-quota-exceed-num {
              description 'The number of TCP packets discarded because of the subscriber quota exceeded.' ;
              type uint64 ;

              default 0 ;
            }

            leaf tcp-protocol-quota-exceed-num {
              description 'The number of TCP packets discarded because of the protocol quota exceeded.' ;
              type uint64 ;

              default 0 ;
            }

            leaf tcp-policy-deny-num {
              description 'The number of packets TCP policy denied.' ;
              type uint64 ;

              default 0 ;
            }

            leaf tcp-policy-filter-num {
              description 'The number of packets TCP policy filtered.' ;
              type uint64 ;

              default 0 ;
            }

            leaf tcp-nat-resource-exhaust-num {
              description 'The number of packets NAT resource exhausted.' ;
              type uint64 ;

              default 0 ;
            }

            leaf tcp-pat-resource-exhaust-num {
              description 'The number of packets PAT resource exhausted.' ;
              type uint64 ;

              default 0 ;
            }

            leaf tcp-trans-insert-error-num {
              description 'Translation item exhausted number and translation inserted error number.' ;
              type uint64 ;

            }

            leaf tcp-other-error-num {
              description 'Other TCP error number.' ;
              type uint64 ;

              default 0 ;
            }

            leaf udp-success-num {
              description 'The number of UDP packets successfully translated.' ;
              type uint64 ;

              default 0 ;
            }

            leaf udp-fail-num {
              description 'The number of UDP packets translated failed.' ;
              type uint64 ;

              default 0 ;
            }

            leaf udp-policy-error-num {
              description 'The number of packets UDP policy checked failed.' ;
              type uint64 ;

              default 0 ;
            }

            leaf udp-invalid-direction-num {
              description 'The number of UDP invalid direction packets.' ;
              type uint64 ;

              default 0 ;
            }

            leaf udp-inbound-no-trans-num {
              description 'The number of inbound packets had no translation.' ;
              type uint64 ;

              default 0 ;
            }

            leaf udp-subscriber-quota-exceed-num {
              description 'The number of UDP packets discarded because of the subscriber quota exceeded.' ;
              type uint64 ;

              default 0 ;
            }

            leaf udp-protocol-quota-exceed-num {
              description 'The number of UDP packets discarded because of the protocol quota exceeded.' ;
              type uint64 ;

              default 0 ;
            }

            leaf udp-policy-deny-num {
              description 'The number of packets UDP policy denied.' ;
              type uint64 ;

              default 0 ;
            }

            leaf udp-policy-filter-num {
              description 'The number of packets UDP policy filtered.' ;
              type uint64 ;

              default 0 ;
            }

            leaf udp-nat-resource-exhaust-num {
              description 'The number of packets NAT resource exhausted.' ;
              type uint64 ;

              default 0 ;
            }

            leaf udp-pat-resource-exhaust-num {
              description 'The number of packets PAT resource exhausted.' ;
              type uint64 ;

              default 0 ;
            }

            leaf udp-trans-insert-error-num {
              description 'Translation item exhausted number and translation inserted error number.' ;
              type uint64 ;

            }

            leaf udp-other-error-num {
              description 'Other UDP error number.' ;
              type uint64 ;

              default 0 ;
            }

            leaf icmp-success-num {
              description 'The number of ICMP packets successfully translated.' ;
              type uint64 ;

              default 0 ;
            }

            leaf icmp-fail-num {
              description 'The number of ICMP packets translated failed.' ;
              type uint64 ;

              default 0 ;
            }

            leaf icmp-type-error-num {
              description 'ICMP type error number.' ;
              type uint64 ;

              default 0 ;
            }

            leaf icmp-policy-error-num {
              description 'The number of packets ICMP policy checked failed.' ;
              type uint64 ;

              default 0 ;
            }

            leaf icmp-invalid-direction-num {
              description 'The number of ICMP invalid direction packets.' ;
              type uint64 ;

              default 0 ;
            }

            leaf icmp-inbound-no-trans-num {
              description 'The number of inbound packets had no translation.' ;
              type uint64 ;

              default 0 ;
            }

            leaf icmp-subscriber-quota-exceed-num {
              description 'The number of ICMP packets discarded because of the subscriber quota exceeded.' ;
              type uint64 ;

              default 0 ;
            }

            leaf icmp-protocol-quota-exceed-num {
              description 'The number of ICMP packets discarded because of the protocol quota exceeded.' ;
              type uint64 ;

              default 0 ;
            }

            leaf icmp-policy-deny-num {
              description 'The number of packets ICMP policy denied.' ;
              type uint64 ;

              default 0 ;
            }

            leaf icmp-policy-filter-num {
              description 'The number of packets ICMP policy filtered.' ;
              type uint64 ;

              default 0 ;
            }

            leaf icmp-nat-resource-exhaust-num {
              description 'The number of packets NAT resource exhausted.' ;
              type uint64 ;

              default 0 ;
            }

            leaf icmp-pat-resource-exhaust-num {
              description 'The number of packets PAT resource exhausted.' ;
              type uint64 ;

              default 0 ;
            }

            leaf icmp-trans-insert-error-num {
              description 'Translation item exhausted number and translation inserted error number.' ;
              type uint64 ;

            }

            leaf icmp-other-error-num {
              description 'Other ICMP error number.' ;
              type uint64 ;

              default 0 ;
            }

          }

          container nat-translation {
            description 'NAT translation statistics.' ;
            leaf success-num {
              description 'The number of NAT packets successfully translated.' ;
              type uint64 ;

              default 0 ;
            }

            leaf fail-num {
              description 'The number of NAT packets translated failed.' ;
              type uint64 ;

              default 0 ;
            }

            leaf policy-error-num {
              description 'The number of packets NAT policy checked failed.' ;
              type uint64 ;

              default 0 ;
            }

            leaf invalid-direction-num {
              description 'The number of NAT invalid direction packets.' ;
              type uint64 ;

              default 0 ;
            }

            leaf inbound-no-trans-num {
              description 'The number of inbound packets had no translation.' ;
              type uint64 ;

              default 0 ;
            }

            leaf subscriber-quota-exceed-num {
              description 'The number of NAT packets discarded because of the subscriber quota exceeded.' ;
              type uint64 ;

              default 0 ;
            }

            leaf protocol-quota-exceed-num {
              description 'The number of NAT packets discarded because of the protocol quota exceeded.' ;
              type uint64 ;

              default 0 ;
            }

            leaf nat-policy-deny-num {
              description 'The number of packets NAT policy denied.' ;
              type uint64 ;

              default 0 ;
            }

            leaf nat-policy-filter-num {
              description 'The number of packets NAT policy filtered.' ;
              type uint64 ;

              default 0 ;
            }

            leaf nat-res-exhaust-num {
              description 'NAT resource exhausted number.' ;
              type uint64 ;

              default 0 ;
            }

            leaf trans-insert-error-num {
              description 'Translation item exhausted number and translation inserted error number.' ;
              type uint64 ;

            }

            leaf other-error-num {
              description 'Other NAT error number.' ;
              type uint64 ;

              default 0 ;
            }

          }

        }

        list statistics2-list {
          description 'Statistics list2.' ;
          key cpu-name ;
          leaf cpu-name {
            description 'CPU name.' ;
            type ncd:cpu ;

          }

          container alg-statistics {
            description 'ALG statistics.' ;
            leaf tcp-flag-success-num {
              description 'TCP(SYN, FIN, RST) successful packets number.' ;
              type uint64 ;

              default 0 ;
            }

            leaf tcp-flag-fail-num {
              description 'TCP(SYN, FIN, RST) failed packets number.' ;
              type uint64 ;

              default 0 ;
            }

            leaf icmp-alg-success-num {
              description 'The number of successful ICMP ALG packets.' ;
              type uint64 ;

              default 0 ;
            }

            leaf icmp-alg-fail-num {
              description 'The number of failed ICMP ALG packets.' ;
              type uint64 ;

              default 0 ;
            }

            leaf ftp-alg-success-num {
              description 'The number of successful FTP ALG packets.' ;
              type uint64 ;

              default 0 ;
            }

            leaf ftp-alg-fail-num {
              description 'The number of failed FTP ALG packets.' ;
              type uint64 ;

              default 0 ;
            }

            leaf dns-alg-success-num {
              description 'The number of successful DNS ALG packets.' ;
              type uint64 ;

              default 0 ;
            }

            leaf dns-alg-fail-num {
              description 'The number of failed DNS ALG packets.' ;
              type uint64 ;

              default 0 ;
            }

            leaf rtsp-alg-success-num {
              description 'The number of successful RTSP ALG packets.' ;
              type uint64 ;

              default 0 ;
            }

            leaf rtsp-alg-fail-num {
              description 'The number of failed RTSP ALG packets.' ;
              type uint64 ;

              default 0 ;
            }

            leaf sip-alg-success-num {
              description 'The number of successful SIP ALG packets.' ;
              type uint64 ;

              default 0 ;
            }

            leaf sip-alg-fail-num {
              description 'The number of failed SIP ALG packets.' ;
              type uint64 ;

              default 0 ;
            }

            leaf h323-alg-success-num {
              description 'The number of successful H323 ALG packets.' ;
              type uint64 ;

              default 0 ;
            }

            leaf h323-alg-fail-num {
              description 'The number of failed H323 ALG packets.' ;
              type uint64 ;

              default 0 ;
            }

            leaf ipsec-alg-success-num {
              type uint64 ;

              description 'The number of successful IPSEC ALG packets.' ;
              default 0 ;
              ncd:revise-date 2024-08-16 ;
            }

            leaf ipsec-alg-fail-num {
              type uint64 ;

              description 'The number of failed IPSEC ALG packets.' ;
              default 0 ;
              ncd:revise-date 2024-08-16 ;
            }

          }

          container forward-statistics {
            description 'Forward statistics.' ;
            leaf out-tcp-forward-success-num {
              description 'The number of outbound TCP packets forwarded successfully.' ;
              type uint64 ;

              default 0 ;
            }

            leaf out-tcp-forward-fail-num {
              description 'The number of outbound TCP packets forwarded failed.' ;
              type uint64 ;

              default 0 ;
            }

            leaf in-tcp-forward-success-num {
              description 'The number of inbound TCP packets forwarded successfully.' ;
              type uint64 ;

              default 0 ;
            }

            leaf in-tcp-forward-fail-num {
              description 'The number of inbound TCP packets forwarded failed.' ;
              type uint64 ;

              default 0 ;
            }

            leaf out-udp-forward-success-num {
              description 'The number of outbound UDP packets forwarded successfully.' ;
              type uint64 ;

              default 0 ;
            }

            leaf out-udp-forward-fail-num {
              description 'The number of outbound UDP packets forwarded failed.' ;
              type uint64 ;

              default 0 ;
            }

            leaf in-udp-forward-success-num {
              description 'The number of inbound UDP packets forwarded successfully.' ;
              type uint64 ;

              default 0 ;
            }

            leaf in-udp-forward-fail-num {
              description 'The number of inbound UDP packets forwarded failed.' ;
              type uint64 ;

              default 0 ;
            }

            leaf out-icmp-forward-success-num {
              description 'The number of outbound ICMP packets forwarded successfully.' ;
              type uint64 ;

              default 0 ;
            }

            leaf out-icmp-forward-fail-num {
              description 'The number of outbound ICMP packets forwarded failed.' ;
              type uint64 ;

              default 0 ;
            }

            leaf in-icmp-forward-success-num {
              description 'The number of inbound ICMP packets forwarded successfully.' ;
              type uint64 ;

              default 0 ;
            }

            leaf in-icmp-forward-fail-num {
              description 'The number of inbound ICMP packets forwarded failed.' ;
              type uint64 ;

              default 0 ;
            }

            leaf out-ip-forward-success-num {
              description 'The number of outbound IP packets forwarded successfully.' ;
              type uint64 ;

              default 0 ;
            }

            leaf out-ip-forward-fail-num {
              description 'The number of outbound IP packets forwarded failed.' ;
              type uint64 ;

              default 0 ;
            }

            leaf in-ip-forward-success-num {
              description 'The number of inbound IP packets forwarded successfully.' ;
              type uint64 ;

              default 0 ;
            }

            leaf in-ip-forward-fail-num {
              description 'The number of inbound IP packets forwarded failed.' ;
              type uint64 ;

              default 0 ;
            }

            leaf out-alg-upsend-num {
              description 'The number of outbound ALG upsended packets.' ;
              type uint64 ;

              default 0 ;
            }

            leaf in-alg-upsend-num {
              description 'The number of inbound ALG upsended packets.' ;
              type uint64 ;

              default 0 ;
            }

            leaf out-new-session-upsend-num {
              description 'The number of outbound new session upsended packets.' ;
              type uint64 ;

              default 0 ;
            }

            leaf out-pcp-upsend-num {
              description 'The number of PCP packets upsended.' ;
              type uint64 ;

              default 0 ;
            }

            leaf out-resource-exhaust-drop-packet-num {
              description 'The number of outbound packets dropped because of resource exhausted.' ;
              type uint64 ;

              default 0 ;
            }

            leaf out-resource-exhaust-drop-byte-num {
              description 'The number of outbound bytes dropped because of resource exhausted.' ;
              type uint64 ;

              default 0 ;
            }

            leaf out-no-trans-drop-packet-num {
              description 'The number of outbound packets dropped because of no translation entry.' ;
              type uint64 ;

              default 0 ;
            }

            leaf out-no-trans-drop-byte-num {
              description 'The number of outbound bytes dropped because of no translation entry.' ;
              type uint64 ;

              default 0 ;
            }

            leaf in-no-trans-drop-packet-num {
              description 'The number of inbound packets dropped because of no translation entry.' ;
              type uint64 ;

              default 0 ;
            }

            leaf in-no-trans-drop-byte-num {
              description 'The number of inbound bytes dropped because of no translation entry.' ;
              type uint64 ;

              default 0 ;
            }

            leaf log-channel-except-packet-num {
              description 'The packets number of log channel exception.' ;
              type uint64 ;

              default 0 ;
            }

            leaf log-channel-except-byte-num {
              description 'The bytes number of log channel exception.' ;
              type uint64 ;

              default 0 ;
            }

          }

        }

        ncd:revise-date 2016-09-22 ;
      }

      container local-ip {
        description 'Local IP.' ;
        list local-ip-public {
          description 'Local IP list.' ;
          key 'ipv4-address ipv6-address' ;
          leaf ipv4-address {
            description 'IPv4 address.' ;
            type ncd:ipv4-address ;

          }

          leaf ipv6-address {
            description 'IPv6 address.' ;
            type ncd:ipv6-address ;

          }

          leaf type {
            description 'Type.' ;
            type string ;

          }

          leaf ip-infomation {
            description 'IP information.' ;
            type string ;

          }

          leaf subscriber-id {
            description 'Subscriber ID.' ;
            type uint32 ;

          }

          leaf pcp-tcp-translations {
            description 'PCP TCP translations.' ;
            type uint32 ;

          }

          leaf pcp-udp-translations {
            description 'PCP UDP translations.' ;
            type uint32 ;

          }

          leaf dynamic-tcp-translations {
            description 'Dynamic TCP translations.' ;
            type uint32 ;

          }

          leaf dynamic-udp-translations {
            description 'Dynamic UDP translations.' ;
            type uint32 ;

          }

          leaf dynamic-icmp-translations {
            description 'Dynamic ICMP translations.' ;
            type uint32 ;

          }

          leaf dynamic-nat-translations {
            description 'Dynamic NAT translations.' ;
            type uint32 ;

          }

          leaf total-translations {
            description 'Total translations.' ;
            type uint32 ;

          }

          ncd:select "ipv4-address ipv6-address" ;
        }

        list local-ip-vrf {
          description 'Local IP list.' ;
          key 'vrf-name ipv4-address ipv6-address' ;
          leaf vrf-name {
            description 'VRF name.' ;
            type string {
              length 1..32 ;

            }

          }

          leaf ipv4-address {
            description 'IPv4 address.' ;
            type ncd:ipv4-address ;

          }

          leaf ipv6-address {
            description 'IPv6 address.' ;
            type ncd:ipv6-address ;

          }

          leaf type {
            description 'Type.' ;
            type string ;

          }

          leaf ip-infomation {
            description 'IP information.' ;
            type string ;

          }

          leaf subscriber-id {
            description 'Subscriber ID.' ;
            type uint32 ;

          }

          leaf pcp-tcp-translations {
            description 'PCP TCP translations.' ;
            type uint32 ;

          }

          leaf pcp-udp-translations {
            description 'PCP UDP translations.' ;
            type uint32 ;

          }

          leaf dynamic-tcp-translations {
            description 'Dynamic TCP translations.' ;
            type uint32 ;

          }

          leaf dynamic-udp-translations {
            description 'Dynamic UDP translations.' ;
            type uint32 ;

          }

          leaf dynamic-icmp-translations {
            description 'Dynamic ICMP translations.' ;
            type uint32 ;

          }

          leaf dynamic-nat-translations {
            description 'Dynamic NAT translations.' ;
            type uint32 ;

          }

          leaf total-translations {
            description 'Total translations.' ;
            type uint32 ;

          }

          ncd:select "vrf-name ipv4-address ipv6-address" ;
        }

        ncd:revise-date 2019-11-04 ;
      }

    }

  }

  container configuration {
    description 'The configuration of CGN.' ;
    container global {
      description 'Global configuration.' ;
      leaf spu-auto-add {
        description 'SPU auto add.' ;
        type enumeration {
          enum off {
            value 0 ;
          }

          enum on {
            value 1 ;
          }

        }

        default off ;
      }

      leaf all-translations-alarm-threshold {
        description 'All translations alarm threshold.' ;
        type uint32 {
          range 1..100 ;

        }

        default 100 ;
      }

      container cgn-outside-interface-list {
        description 'CGN outside interface list.' ;
        list cgn-outside-interface {
          description 'CGN outside interface.' ;
          key interface-name ;
          leaf interface-name {
            description 'Interface name.' ;
            type ncd:ifname ;

          }

        }

        ncd:revise-date 2016-11-15 ;
      }

      choice cgn-res-alloc-disconnect {
        description 'CGN resource allocate disconnect time.' ;
        default response-delay ;
        case response-delay {
          description 'Response delay.' ;
          leaf response-delay-time {
            description 'Response delay time.' ;
            type uint32 {
              range 0..2880 ;

            }

            default 240 ;
          }

        }

        case forever {
          description 'Forever.' ;
          leaf forever {
            description 'Forever.' ;
            type uint32 {
              range 0..1 ;

            }

            default 0 ;
          }

        }

        ncd:revise-date 2018-08-08 ;
      }

      container log-ipflow-template {
        description 'Log ipflow.' ;
        leaf create-translation-template-nat44 {
          description 'Configure create translation ipflow templates NAT44 switch.' ;
          type enumeration {
            enum disable {
              value 0 ;
            }

            enum enable {
              value 1 ;
            }

          }

          default enable ;
        }

        leaf create-session-template-nat44 {
          description 'Configure create session ipflow templates NAT44 switch.' ;
          type enumeration {
            enum disable {
              value 0 ;
            }

            enum enable {
              value 1 ;
            }

          }

          default enable ;
        }

        leaf create-portrange-template-nat44 {
          description 'Configure create portrange ipflow templates NAT44 switch.' ;
          type enumeration {
            enum disable {
              value 0 ;
            }

            enum enable {
              value 1 ;
            }

          }

          default enable ;
        }

        leaf delete-translation-template-nat44 {
          description 'Configure delete translation ipflow templates NAT44 switch.' ;
          type enumeration {
            enum disable {
              value 0 ;
            }

            enum enable {
              value 1 ;
            }

          }

          default enable ;
        }

        leaf delete-session-template-nat44 {
          description 'Configure delete session ipflow templates NAT44 switch.' ;
          type enumeration {
            enum disable {
              value 0 ;
            }

            enum enable {
              value 1 ;
            }

          }

          default enable ;
        }

        leaf delete-portrange-template-nat44 {
          description 'Configure delete portrange ipflow templates NAT44 switch.' ;
          type enumeration {
            enum disable {
              value 0 ;
            }

            enum enable {
              value 1 ;
            }

          }

          default enable ;
        }

        leaf create-translation-template-nat64 {
          description 'Configure create translation ipflow templates NAT64 switch.' ;
          type enumeration {
            enum disable {
              value 0 ;
            }

            enum enable {
              value 1 ;
            }

          }

          default enable ;
        }

        leaf create-session-template-nat64 {
          description 'Configure create session ipflow templates NAT64 switch.' ;
          type enumeration {
            enum disable {
              value 0 ;
            }

            enum enable {
              value 1 ;
            }

          }

          default enable ;
        }

        leaf create-portrange-template-nat64 {
          description 'Configure create portrange ipflow templates NAT64 switch.' ;
          type enumeration {
            enum disable {
              value 0 ;
            }

            enum enable {
              value 1 ;
            }

          }

          default enable ;
        }

        leaf delete-translation-template-nat64 {
          description 'Configure delete translation ipflow templates NAT64 switch.' ;
          type enumeration {
            enum disable {
              value 0 ;
            }

            enum enable {
              value 1 ;
            }

          }

          default enable ;
        }

        leaf delete-session-template-nat64 {
          description 'Configure delete session ipflow templates NAT64 switch.' ;
          type enumeration {
            enum disable {
              value 0 ;
            }

            enum enable {
              value 1 ;
            }

          }

          default enable ;
        }

        leaf delete-portrange-template-nat64 {
          description 'Configure delete portrange ipflow templates NAT64 switch.' ;
          type enumeration {
            enum disable {
              value 0 ;
            }

            enum enable {
              value 1 ;
            }

          }

          default enable ;
        }

        ncd:revise-date 2019-12-15 ;
      }

      leaf cgn-log-appname {
        description 'CGN log appname.' ;
        type string {
          length 1..31 ;

        }

        ncd:revise-date 2021-02-26 ;
      }

    }

    container cgn {
      description 'Configure CGN.' ;
      container instance-list {
        description 'The CGN instance list.' ;
        container default-instance {
          description 'Default instance.' ;
          presence default-instance ;
          leaf instance-info {
            description 'Instance information.' ;
            type empty ;

            mandatory true ;
          }

          container location-list {
            description 'The location list.' ;
            list location {
              description 'The location.' ;
              key node-id ;
              leaf node-id {
                description 'Node ID.' ;
                type uint32 {
                  range 1..64 ;

                }

              }

              leaf master-cpu {
                description 'Master CPU.' ;
                type ncd:cpu ;

                mandatory true ;
              }

              leaf slave-cpu {
                description 'Slave CPU.' ;
                type ncd:cpu ;

                default '' ;
              }

              leaf capacity {
                type enumeration {
                  enum max-16M {
                    description 'The maximum number of translations is 16000000' ;
                    value 1 ;
                  }

                  enum max-32M {
                    description 'The maximum number of translations is 32000000' ;
                    value 2 ;
                  }

                  enum not-config {
                    description 'No config capacity' ;
                    value 0 ;
                  }

                }

                description 'node capacity' ;
                if-feature location-node-capacity-feature {
                  ncd:revise-date 2024-03-12 ;
                }

                ncd:revise-date 2024-03-12 ;
              }

              container track {
                description 'Event track information.' ;
                presence track ;
                leaf type {
                  description 'Track type' ;
                  type enumeration {
                    enum object {
                      value 1 ;
                      description 'Track object' ;
                    }

                    enum group {
                      value 2 ;
                      description 'Track group' ;
                    }

                    enum null {
                      value 0 ;
                      description 'No track' ;
                    }

                  }

                  mandatory true ;
                }

                leaf name {
                  description 'Track name.' ;
                  type string ;

                  mandatory true ;
                }

                ncd:revise-date 2017-06-20 ;
              }

            }

          }

          leaf resource-exhaust-action {
            description 'Resource exhaustion behavior.' ;
            type enumeration {
              enum drop {
                value 0 ;
                description 'Drop if resource exhaust' ;
              }

              enum sendIcmpError {
                value 1 ;
                description 'Send ICMP error if resource exhaust' ;
              }

            }

            default drop ;
          }

          leaf max-blocks-number {
            description 'Maximum blocks of dynamic port range.' ;
            type uint8 {
              range 0..3 ;

            }

            default 0 ;
          }

          leaf statistics-switch {
            description 'Statistics switch.' ;
            type enumeration {
              enum on {
                value 1 ;
              }

              enum off {
                value 0 ;
              }

            }

            default off ;
          }

          leaf allocate-mode {
            status obsolete {
              ncd:revise-date 2021-02-26 ;
            }

            description 'Allocate mode of dynamic port range.' ;
            type enumeration {
              enum prefix {
                value 1 ;
              }

              enum softwire {
                value 0 ;
              }

            }

            default prefix ;
            ncd:revise-date 2017-02-08 ;
          }

          leaf resume-delay-time {
            description 'Resume delay time.' ;
            type uint8 {
              range 1..10 ;

            }

            ncd:revise-date 2021-02-26 ;
          }

        }

        list instance {
          description 'The instance.' ;
          key instance-name ;
          leaf instance-name {
            description 'Instance name.' ;
            type string {
              length 1..31 ;

            }

          }

          leaf instance-id {
            description 'Instance ID.' ;
            type uint32 {
              range 1..63 ;

            }

            mandatory true ;
          }

          container location-list {
            description 'The location list.' ;
            list location {
              description 'The location.' ;
              key node-id ;
              leaf node-id {
                description 'Node ID.' ;
                type uint32 {
                  range 1..64 ;

                }

              }

              leaf master-spu {
                description 'Master CPU.' ;
                type ncd:cpu ;

                mandatory true ;
              }

              leaf slave-spu {
                description 'Slave CPU.' ;
                type ncd:cpu ;

                default '' ;
              }

              leaf capacity {
                type enumeration {
                  enum max-16M {
                    value 1 ;
                    description 'The maximum number of translations is 16000000' ;
                  }

                  enum max-32M {
                    value 2 ;
                    description 'The maximum number of translations is 32000000' ;
                  }

                  enum not-config {
                    value 0 ;
                    description 'No config capacity' ;
                  }

                }

                if-feature location-node-capacity-feature ;

                description 'node capacity' ;
                ncd:revise-date 2024-03-12 ;
              }

              container track {
                description 'Event track information.' ;
                presence track ;
                leaf type {
                  description 'Track type.' ;
                  type enumeration {
                    enum object {
                      value 1 ;
                      description 'Track object' ;
                    }

                    enum group {
                      value 2 ;
                      description 'Track group' ;
                    }

                    enum null {
                      value 0 ;
                      description 'No track' ;
                    }

                  }

                  mandatory true ;
                }

                leaf name {
                  description 'Track name.' ;
                  type string ;

                  mandatory true ;
                }

                ncd:revise-date 2017-06-20 ;
              }

            }

          }

          leaf resource-exhaust-action {
            description 'Resource exhaustion behavior.' ;
            type enumeration {
              enum drop {
                value 0 ;
                description 'Drop if resource exhaust' ;
              }

              enum sendIcmpError {
                value 1 ;
                description 'Send ICMP error if resource exhaust' ;
              }

            }

            default drop ;
          }

          leaf max-blocks-number {
            description 'Maximum blocks of dynamic port range.' ;
            type uint8 {
              range 0..3 ;

            }

            default 0 ;
          }

          leaf statistics-switch {
            description 'Statistics switch.' ;
            type enumeration {
              enum on {
                value 1 ;
              }

              enum off {
                value 0 ;
              }

            }

            default off ;
          }

          leaf allocate-mode {
            status obsolete {
              ncd:revise-date 2021-02-26 ;
            }

            description 'Allocate mode of dynamic port range.' ;
            type enumeration {
              enum prefix {
                value 1 ;
              }

              enum softwire {
                value 0 ;
              }

            }

            default prefix ;
            ncd:revise-date 2017-02-08 ;
          }

          leaf resume-delay-time {
            description 'Resume delay time.' ;
            type uint8 {
              range 1..10 ;

            }

            ncd:revise-date 2021-02-26 ;
          }

        }

      }

      container car-policy-template {
        description 'CAR policy template.' ;
        list car-policy-list {
          description 'CAR policy list.' ;
          key car-policy-name ;
          leaf car-policy-name {
            description 'CAR policy name.' ;
            type string {
              length 1..31 ;

            }

          }

          leaf instance-name {
            description 'Instance name.' ;
            type ncd:string-quesiton-mark ;

            mandatory true ;
          }

          container inbound-car {
            description 'Inbound CAR.' ;
            presence inbound-car ;
            leaf inbound-cir {
              description 'Inbound committed information rate(kbps).' ;
              type uint32 {
                range 66..16777215 ;

              }

              mandatory true ;
            }

            leaf inbound-cbs {
              description 'Inbound committed burst size(KB).' ;
              type uint32 {
                range 15..2000000 ;

              }

              mandatory true ;
            }

            leaf inbound-pir {
              description 'Inbound peak information rate(kbps).' ;
              type uint32 {
                range 66..16777215 ;

              }

              mandatory true ;
            }

            leaf inbound-pbs {
              description 'Inbound peak burst size(KB).' ;
              type uint32 {
                range 15..2000000 ;

              }

              mandatory true ;
            }

          }

          container outbound-car {
            description 'Outbound CAR.' ;
            presence outbound-car ;
            leaf outbound-cir {
              description 'Outbound committed information rate(kbps).' ;
              type uint32 {
                range 66..16777215 ;

              }

              mandatory true ;
            }

            leaf outbound-cbs {
              description 'Outbound committed burst size(KB).' ;
              type uint32 {
                range 15..2000000 ;

              }

              mandatory true ;
            }

            leaf outbound-pir {
              description 'Outbound peak information rate(kbps).' ;
              type uint32 {
                range 66..16777215 ;

              }

              mandatory true ;
            }

            leaf outbound-pbs {
              description 'Outbound peak burst size(KB).' ;
              type uint32 {
                range 15..2000000 ;

              }

              mandatory true ;
            }

          }

          leaf description {
            description 'Description.' ;
            type string {
              length 1..64 ;

            }

            ncd:revise-date 2020-05-28 ;
          }

        }

      }

      container pool-list {
        description 'Pool list.' ;
        list nat-pool {
          description 'NAT pool.' ;
          key 'pool-id pool-name' ;
          leaf pool-id {
            description 'Pool ID.' ;
            type uint32 {
              range 0..1999 ;

            }

          }

          leaf pool-name {
            description 'Pool name.' ;
            type string {
              length 1..31 ;

            }

          }

          leaf dnat-mode {
            description 'DNAT.' ;
            type enumeration {
              enum enable {
                value 1 ;
              }

              enum disable {
                value 0 ;
              }

            }

            default disable ;
            ncd:revise-date 2020-12-18 ;
          }

          leaf instance-name {
            description 'Instance name.' ;
            type ncd:string-quesiton-mark ;

            mandatory true ;
          }

          leaf vrf-name {
            description 'VRF name.' ;
            type string {
              length 1..32 ;

            }

          }

          leaf description {
            description 'Description.' ;
            type string {
              length 1..63 ;

            }

          }

          leaf sib-instance {
            description 'SIB instance.' ;
            type uint32 {
              range 1..255 ;

            }

          }

          leaf port-alarm-value {
            status obsolete {
              ncd:revise-date 2021-02-26 ;
            }

            description 'Alarm threshold of IP utilization ratio.' ;
            type uint32 {
              range 1..100 ;

            }

            default 80 ;
          }

          choice hot-standby-policy {
            description 'Hot standby policy.' ;
            case all {
              description 'All.' ;
              leaf all-live-time {
                description 'Live time of all protocols.' ;
                type uint32 {
                  range 1..65535 ;

                }

              }

            }

            case protocol {
              description 'Protocol.' ;
              leaf ip-live-time {
                description 'Live time of IP protocol.' ;
                type uint32 {
                  range 1..65535 ;

                }

              }

              leaf alg-live-time {
                description 'Live time of ALG protocol.' ;
                type uint32 {
                  range 1..65535 ;

                }

              }

            }

          }

          leaf interface-name {
            description 'Interface name.' ;
            type ncd:ifname ;

          }

          container section-list {
            description 'Section list.' ;
            list section {
              description 'Section.' ;
              key section-no ;
              leaf section-no {
                description 'Section number.' ;
                type uint32 {
                  range 1..2000 ;

                }

              }

              choice section-type {
                description 'Section type.' ;
                mandatory true ;
                case ip {
                  description 'IP.' ;
                  leaf start-ip {
                    description 'Start IP address.' ;
                    type ncd:ipv4-address-none-zero ;

                    mandatory true ;
                  }

                  leaf end-ip {
                    description 'End IP address.' ;
                    type ncd:ipv4-address-none-zero ;

                  }

                }

                case range {
                  description 'IP range.' ;
                  leaf mask-length {
                    description 'Mask length.' ;
                    type ncd:ipv4-mask ;

                    mandatory true ;
                  }

                  leaf base-ip {
                    description 'Base IP.' ;
                    type ncd:ipv4-address-none-zero ;

                    mandatory true ;
                  }

                }

                case interface {
                  if-feature section-interface-feature {
                    ncd:revise-date 2023-01-17 ;
                  }

                  description 'Interface address.' ;
                  leaf interface-name {
                    description 'Interface name.' ;
                    type ncd:ifname ;

                    mandatory true ;
                  }

                }

              }

            }

          }

          leaf hot-standby-route-metric {
            description 'Route metric of low priority pool.' ;
            type uint32 {
              range 0..4261412864 ;

            }

            default 50 ;
            ncd:revise-date 2017-02-08 ;
          }

          leaf hot-standby-route-priority {
            description 'Route priority of low priority pool.' ;
            type uint32 {
              range 0..254 ;

            }

            default 50 ;
            ncd:revise-date 2017-02-08 ;
          }

          leaf location-node {
            description 'Location node.' ;
            type uint16 {
              range 1..64 ;

            }

            ncd:revise-date 2017-02-08 ;
          }

          leaf position {
            description 'The server position to obtain IP ranges.' ;
            type enumeration {
              enum local {
                value 1 ;
              }

              enum remote {
                value 2 ;
              }

              enum disable {
                value 0 ;
              }

            }

            default disable ;
            ncd:revise-date 2017-10-16 ;
          }

          leaf ippool-name {
            description 'IP pool name.' ;
            type string {
              length 1..64 ;

            }

            ncd:revise-date 2017-10-16 ;
          }

          leaf low {
            description 'The low threshold.' ;
            type uint32 {
              range 1..100 ;

            }

            default 20 ;
            ncd:revise-date 2017-10-16 ;
          }

          leaf high {
            description 'The high threshold.' ;
            type uint32 {
              range 1..100 ;

            }

            default 80 ;
            ncd:revise-date 2017-10-16 ;
          }

          leaf mask {
            description 'The mask of range.' ;
            type uint32 {
              range 20..32 ;

            }

            default 27 ;
            ncd:revise-date 2017-10-16 ;
          }

          leaf max-number {
            description 'The max number of ranges.' ;
            type uint32 {
              range 1..2000 ;

            }

            default 200 ;
            ncd:revise-date 2017-10-16 ;
          }

          leaf recycle {
            description 'Force recycle resources.' ;
            type enumeration {
              enum enable {
                value 1 ;
              }

              enum disable {
                value 0 ;
              }

            }

            default disable ;
            ncd:revise-date 2017-12-28 ;
          }

          leaf assign {
            description 'Assign obtain IP ranges policy.' ;
            type enumeration {
              enum none {
                value 0 ;
                description 'Assign policy none' ;
              }

              enum forward {
                value 1 ;
                description 'Assign policy forward' ;
              }

              enum backward {
                value 2 ;
                description 'Assign policy backward' ;
              }

            }

            default none ;
            ncd:revise-date 2018-11-14 ;
          }

          container lock-ip-list {
            description 'Lock IP list.' ;
            list lock-ip {
              description 'Lock IP.' ;
              key lock-ip-no ;
              leaf lock-ip-no {
                description 'Lock IP number.' ;
                type uint32 {
                  range 1..10 ;

                }

              }

              choice lock-ip-type {
                description 'Lock IP type.' ;
                case ip {
                  description 'IP.' ;
                  leaf start-ip {
                    description 'Start IP address.' ;
                    type ncd:ipv4-address-none-zero ;

                  }

                  leaf end-ip {
                    description 'End IP address.' ;
                    type ncd:ipv4-address-none-zero ;

                  }

                }

                case section {
                  description 'Section.' ;
                  leaf section-no {
                    description 'Section number.' ;
                    type uint32 {
                      range 1..2000 ;

                    }

                  }

                }

                case all {
                  description 'Lock all.' ;
                  leaf all {
                    description 'Lock all.' ;
                    type enumeration {
                      enum all {
                        value 1 ;
                        description 'Lock all.' ;
                      }

                    }

                  }

                }

              }

            }

            ncd:revise-date 2019-03-13 ;
          }

          leaf detect-retransmit-number {
            description 'Detect retransmit number.' ;
            type uint32 {
              range 0..10 ;

            }

            default 0 ;
            ncd:revise-date 2019-05-05 ;
          }

          leaf detect-interval-day {
            description 'Detect interval day number.' ;
            type uint32 {
              range 0..999 ;

            }

            default 0 ;
            ncd:revise-date 2019-05-05 ;
          }

          leaf detect-interval-hour {
            description 'Detect interval hour number.' ;
            type uint32 {
              range 0..23 ;

            }

            default 0 ;
            ncd:revise-date 2019-05-05 ;
          }

          leaf detect-interval-minute {
            description 'Detect interval minute number.' ;
            type uint32 {
              range 0..59 ;

            }

            default 0 ;
            ncd:revise-date 2019-05-05 ;
          }

          leaf ip-alarm-value {
            description 'Alarm threshold of IP utilization ratio.' ;
            type uint32 {
              range 1..100 ;

            }

            default 80 ;
            ncd:revise-date 2021-02-26 ;
          }

        }

        list pat-pool {
          description 'PAT pool.' ;
          key 'pool-id pool-name' ;
          leaf pool-id {
            description 'Pool ID.' ;
            type uint32 {
              range 0..1999 ;

            }

          }

          leaf pool-name {
            description 'Pool name.' ;
            type string {
              length 1..31 ;

            }

          }

          leaf instance-name {
            description 'Instance name.' ;
            type ncd:string-quesiton-mark ;

            mandatory true ;
          }

          leaf address-user-ratio {
            description 'User sharing ratio.' ;
            type uint32 {
              range 1..1000 ;

            }

          }

          leaf vrf-name {
            description 'VRF name.' ;
            type string {
              length 1..32 ;

            }

          }

          leaf description {
            description 'Description.' ;
            type string {
              length 1..63 ;

            }

          }

          leaf max-ports-per-address {
            description 'Max ports of each protocol for one address.' ;
            type uint32 {
              range 1..65535 ;

            }

            default 65535 ;
          }

          leaf portrange-size {
            description 'Port range size.' ;
            type uint32 {
              range 1..65536 ;

            }

          }

          leaf sib-instance {
            description 'SIB instance.' ;
            type uint32 {
              range 1..255 ;

            }

          }

          leaf port-alarm-value {
            description 'Alarm threshold of IP ports utilization ratio.' ;
            type uint32 {
              range 1..100 ;

            }

            default 80 ;
          }

          leaf port-range-alarm-value {
            description 'Alarm threshold of port range ports utilization ratio.' ;
            type uint32 {
              range 1..100 ;

            }

            default 80 ;
          }

          leaf share-ratio-alarm-value {
            description 'Alarm threshold of sharing ratio.' ;
            type uint32 {
              range 1..100 ;

            }

            default 80 ;
          }

          choice hot-standby-policy {
            description 'Hot standby policy.' ;
            case all {
              description 'All.' ;
              leaf all-live-time {
                description 'Live time of all protocols.' ;
                type uint32 {
                  range 1..65535 ;

                }

              }

            }

            case protocol {
              description 'Protocol.' ;
              leaf tcp-live-time {
                description 'Live time of TCP protocol.' ;
                type uint32 {
                  range 1..65535 ;

                }

              }

              leaf udp-live-time {
                description 'Live time of UDP protocol.' ;
                type uint32 {
                  range 1..65535 ;

                }

              }

              leaf icmp-live-time {
                description 'Live time of ICMP protocol.' ;
                type uint32 {
                  range 1..65535 ;

                }

              }

              leaf pcp-live-time {
                description 'Live time of PCP protocol.' ;
                type uint32 {
                  range 1..65535 ;

                }

              }

              leaf alg-live-time {
                description 'Live time of ALG protocol.' ;
                type uint32 {
                  range 1..65535 ;

                }

              }

            }

          }

          leaf portrange-start-port {
            description 'Start port.' ;
            type uint16 {
              range 1..65535 ;

            }

            default 1 ;
          }

          leaf portrange-end-port {
            description 'End port.' ;
            type uint16 {
              range 1..65535 ;

            }

            default 65535 ;
          }

          leaf portrange-block-alarm-value {
            description 'Alarm threshold of port range block ratio.' ;
            type uint32 {
              range 1..100 ;

            }

            default 80 ;
          }

          leaf pool-port-alarm-value {
            description 'Alarm threshold of ports utilization ratio.' ;
            type uint32 {
              range 1..100 ;

            }

            default 80 ;
          }

          leaf spr-block-alarm-value {
            description 'Alarm threshold of static port range block ratio.' ;
            type uint32 {
              range 1..100 ;

            }

            default 80 ;
          }

          leaf well-known-ports-forbidden {
            description 'Well known ports forbidden.' ;
            type enumeration {
              enum disable {
                value 0 ;
              }

              enum enable {
                value 1 ;
              }

            }

            default disable ;
          }

          leaf forbidden-start-port {
            description 'Start port of well known ports forbidden.' ;
            type uint32 {
              range 64..8192 ;

            }

          }

          leaf interface-name {
            description 'Interface name.' ;
            type ncd:ifname ;

          }

          container section-list {
            description 'Section list.' ;
            list section {
              description 'Section.' ;
              key section-no ;
              leaf section-no {
                description 'Section number.' ;
                type uint32 {
                  range 1..2000 ;

                }

              }

              choice section-type {
                description 'Section type.' ;
                mandatory true ;
                case ip {
                  description 'IP.' ;
                  leaf start-ip {
                    description 'Start IP address.' ;
                    type ncd:ipv4-address-none-zero ;

                    mandatory true ;
                  }

                  leaf end-ip {
                    description 'End IP address.' ;
                    type ncd:ipv4-address-none-zero ;

                  }

                }

                case range {
                  description 'IP range.' ;
                  leaf mask-length {
                    description 'Mask length.' ;
                    type ncd:ipv4-mask ;

                    mandatory true ;
                  }

                  leaf base-ip {
                    description 'Base IP.' ;
                    type ncd:ipv4-address-none-zero ;

                    mandatory true ;
                  }

                }

                case interface {
                  if-feature section-interface-feature {
                    ncd:revise-date 2023-01-17 ;
                  }

                  description 'Interface address.' ;
                  leaf interface-name {
                    description 'Interface name.' ;
                    type ncd:ifname ;

                    mandatory true ;
                  }

                }

              }

            }

          }

          leaf hot-standby-route-metric {
            description 'Route metric of low priority pool.' ;
            type uint32 {
              range 0..4261412864 ;

            }

            default 50 ;
            ncd:revise-date 2017-02-08 ;
          }

          leaf hot-standby-route-priority {
            description 'Route priority of low priority pool.' ;
            type uint32 {
              range 0..254 ;

            }

            default 50 ;
            ncd:revise-date 2017-02-08 ;
          }

          choice location {
            description 'Location.' ;
            case node {
              description 'Location node.' ;
              leaf location-node {
                description 'Location node.' ;
                type uint16 {
                  range 1..64 ;

                }

              }

              ncd:revise-date 2017-02-08 ;
            }

            case auto {
              description 'Location auto.' ;
              leaf auto {
                description 'Location auto.' ;
                type enumeration {
                  enum auto {
                    value 1 ;
                  }

                }

              }

              ncd:revise-date 2020-08-11 ;
            }

            case location-choice-clear {
              description 'Remove value of any entities which belong to any case within this choice.' ;
              container location-all-clear {
                description 'Remove this entitiy means to remove value of any entities which belong to any case within this choice.' ;
                presence location-all-clear ;
              }

              ncd:revise-date 2020-08-11 ;
            }

          }

          leaf port-reserved {
            description 'Port reserved.' ;
            type uint32 {
              range 0..4096 ;

            }

            default 64 ;
            ncd:revise-date 2017-08-03 ;
          }

          leaf position {
            description 'The server position to obtain IP ranges.' ;
            type enumeration {
              enum local {
                value 1 ;
              }

              enum remote {
                value 2 ;
              }

              enum disable {
                value 0 ;
              }

            }

            default disable ;
            ncd:revise-date 2017-10-16 ;
          }

          leaf ippool-name {
            description 'IP pool name.' ;
            type string {
              length 1..64 ;

            }

            ncd:revise-date 2017-10-16 ;
          }

          leaf low {
            description 'The low threshold.' ;
            type uint32 {
              range 1..100 ;

            }

            default 20 ;
            ncd:revise-date 2017-10-16 ;
          }

          leaf high {
            description 'The high threshold.' ;
            type uint32 {
              range 1..100 ;

            }

            default 80 ;
            ncd:revise-date 2017-10-16 ;
          }

          leaf mask {
            description 'The mask of range.' ;
            type uint32 {
              range 20..32 ;

            }

            default 27 ;
            ncd:revise-date 2017-10-16 ;
          }

          leaf max-number {
            description 'The max number of ranges.' ;
            type uint32 {
              range 1..2000 ;

            }

            default 200 ;
            ncd:revise-date 2017-10-16 ;
          }

          leaf max-static-port-range-blocks {
            description 'Max blocks of static portrange for one user.' ;
            type uint8 {
              range 1..4 ;

            }

            default 1 ;
            ncd:revise-date 2017-10-28 ;
          }

          leaf recycle {
            description 'Force recycle resources.' ;
            type enumeration {
              enum enable {
                value 1 ;
              }

              enum disable {
                value 0 ;
              }

            }

            default disable ;
            ncd:revise-date 2017-12-28 ;
          }

          leaf assign {
            description 'Assign obtain IP ranges policy.' ;
            type enumeration {
              enum none {
                value 0 ;
                description 'Assign policy none' ;
              }

              enum forward {
                value 1 ;
                description 'Assign policy forward' ;
              }

              enum backward {
                value 2 ;
                description 'Assign policy backward' ;
              }

            }

            default none ;
            ncd:revise-date 2018-11-14 ;
          }

          container lock-ip-list {
            description 'Lock IP list.' ;
            list lock-ip {
              description 'Lock IP.' ;
              key lock-ip-no ;
              leaf lock-ip-no {
                description 'Lock IP number.' ;
                type uint32 {
                  range 1..10 ;

                }

              }

              choice lock-ip-type {
                description 'Lock IP type.' ;
                case ip {
                  description 'IP.' ;
                  leaf start-ip {
                    description 'Start IP address.' ;
                    type ncd:ipv4-address-none-zero ;

                  }

                  leaf end-ip {
                    description 'End IP address.' ;
                    type ncd:ipv4-address-none-zero ;

                  }

                }

                case section {
                  description 'Section.' ;
                  leaf section-no {
                    description 'Section number.' ;
                    type uint32 {
                      range 1..2000 ;

                    }

                  }

                }

                case all {
                  description 'Lock all.' ;
                  leaf all {
                    description 'Lock all.' ;
                    type enumeration {
                      enum all {
                        value 1 ;
                        description 'Lock all.' ;
                      }

                    }

                  }

                }

              }

            }

            ncd:revise-date 2019-03-13 ;
          }

          leaf detect-retransmit-number {
            description 'Detect retransmit number.' ;
            type uint32 {
              range 0..10 ;

            }

            default 0 ;
            ncd:revise-date 2019-05-05 ;
          }

          leaf detect-interval-day {
            description 'Detect interval day number.' ;
            type uint32 {
              range 0..999 ;

            }

            default 0 ;
            ncd:revise-date 2019-05-05 ;
          }

          leaf detect-interval-hour {
            description 'Detect interval hour number.' ;
            type uint32 {
              range 0..23 ;

            }

            default 0 ;
            ncd:revise-date 2019-05-05 ;
          }

          leaf detect-interval-minute {
            description 'Detect interval minute number.' ;
            type uint32 {
              range 0..59 ;

            }

            default 0 ;
            ncd:revise-date 2019-05-05 ;
          }

          container port-forbidden-list {
            description 'Port forbidden list.' ;
            list port-forbidden {
              description 'Port forbidden.' ;
              key start-port ;
              leaf start-port {
                description 'Start port.' ;
                type uint32 {
                  range 1..65535 ;

                }

              }

              leaf end-port {
                description 'End port.' ;
                type uint32 {
                  range 1..65535 ;

                }

              }

            }

            ncd:revise-date 2019-09-10 ;
          }

          leaf max-idle-port-range {
            description 'Max idle port range number(0:not limit).' ;
            type uint32 {
              range 0..2097152 ;

            }

            default 0 ;
            ncd:revise-date 2022-03-02 ;
          }

        }

      }

      container domain-list {
        description 'Domain list.' ;
        list domain {
          description 'Domain.' ;
          key domain-name ;
          leaf domain-name {
            description 'Domain name.' ;
            type string {
              length 1..31 ;

            }

          }

          leaf domain-id {
            description 'Domain ID.' ;
            type uint32 {
              range 1..4000 ;

            }

            mandatory true ;
          }

          leaf type {
            description 'Domain type.' ;
            type enumeration {
              enum standalone {
                value 1 ;
                description 'Standalone CGN product.' ;
              }

              enum sr {
                value 2 ;
                description 'Service Router product.' ;
              }

              enum bras {
                value 3 ;
                description 'Brandband Remote Access Server/Broadband product.' ;
              }

              enum xgw {
                value 4 ;
                description 'Wireless Core Network packet switch node (GGSN).' ;
              }

            }

            mandatory true ;
          }

          leaf ip-version-issued {
            description 'IP version issued.' ;
            type enumeration {
              enum ipv4-issued {
                value 1 ;
                description 'Configure as NAT44 or NAT46.' ;
              }

              enum ipv6-issued {
                value 2 ;
                description 'Configure as DualStack-Lite or NAT64.' ;
              }

            }

            mandatory true ;
          }

          leaf instance-name {
            description 'Instance name.' ;
            type ncd:string-quesiton-mark ;

            mandatory true ;
          }

          leaf description {
            description 'Description.' ;
            type string {
              length 1..63 ;

            }

          }

          leaf quota-exceed-action {
            description 'The action of quota exceeded.' ;
            type enumeration {
              enum discard {
                value 0 ;
                description 'Discard the packet if exceed max translations' ;
              }

              enum send-icmp-error {
                value 1 ;
                description 'Send ICMP error if exceed max translations' ;
              }

            }

            default discard ;
          }

          leaf softwire-error-alarm-threshold {
            status obsolete {
              ncd:revise-date 2021-02-26 ;
            }

            description 'Configure softwire error alarm threshold' ;
            type uint32 {
              range 1..4294967295 ;

            }

            default 4294967295 ;
          }

          leaf dns-no-limit {
            description "Don't limit the PAT sessions that destination port is DNS." ;
            type enumeration {
              enum enable {
                value 1 ;
                description 'Enable limit of DNS sessions' ;
              }

              enum disable {
                value 0 ;
                description 'Disable limit of DNS sessions' ;
              }

            }

            default disable ;
          }

          leaf max-private-address-num {
            description 'The max IPv4 number of the same user.' ;
            type uint32 {
              range 1..1000000 {
                description 'The max IPv4 number of the same user' ;
              }

            }

            default 200000 ;
          }

          leaf new-session-create-speed {
            description 'Speed of new session created.' ;
            type uint32 {
              range 0..50000 {
                description 'Configure speed (pps)' ;
              }

            }

          }

          container dynamic-rule-list {
            description 'Dynamic rule list.' ;
            list dynamic-rule {
              description 'Dynamic rule.' ;
              key rule-id ;
              leaf rule-id {
                description 'Rule ID.' ;
                type uint32 {
                  range 1..2000 ;

                }

              }

              leaf acl-type {
                description 'ACL type.' ;
                type enumeration {
                  enum ipv4-list {
                    value 1 ;
                    description 'Specify IPv4 access list.' ;
                  }

                  enum ipv6-list {
                    value 2 ;
                    description 'Specify IPv6 access list.' ;
                  }

                }

                mandatory true ;
              }

              leaf acl-name {
                description 'ACL Name.' ;
                type string {
                  length 1..31 ;

                }

                mandatory true ;
              }

              choice action {
                description 'Action.' ;
                mandatory true ;
                case permit {
                  description 'Permit.' ;
                  container permit {
                    description 'Permit.' ;
                    leaf permit {
                      description 'Permit.' ;
                      type enumeration {
                        enum permit {
                          value 1 ;
                        }

                      }

                      mandatory true ;
                    }

                    leaf pool-name {
                      description 'Pool name.' ;
                      type string {
                        length 1..31 ;

                      }

                    }

                    leaf interface-name {
                      description 'Interface name.' ;
                      type ncd:ifname ;

                    }

                    leaf flow-ip {
                      description 'Flow IP address.' ;
                      type ncd:ipv4-address-none-zero ;

                    }

                  }

                }

                case drop {
                  description 'Drop.' ;
                  container drop {
                    description 'Drop.' ;
                    leaf drop {
                      description 'Drop.' ;
                      type enumeration {
                        enum drop {
                          value 2 ;
                        }

                      }

                      mandatory true ;
                    }

                    leaf interface-name {
                      description 'Interface name.' ;
                      type ncd:ifname ;

                    }

                  }

                }

                case deny {
                  description 'Deny.' ;
                  container deny {
                    description 'Deny.' ;
                    leaf deny {
                      description 'Deny.' ;
                      type enumeration {
                        enum deny {
                          value 3 ;
                        }

                      }

                      mandatory true ;
                    }

                    leaf interface-name {
                      description 'Interface name.' ;
                      type ncd:ifname ;

                    }

                  }

                }

              }

            }

          }

          container static-rule-list {
            description 'Static rule list.' ;
            list static-rule {
              description 'Static rule.' ;
              key rule-id ;
              leaf rule-id {
                description 'Rule ID.' ;
                type uint32 {
                  range 1..2000 ;

                }

              }

              choice user-type {
                description 'User type.' ;
                mandatory true ;
                case softwire {
                  description 'Softwire.' ;
                  container softwire {
                    description 'Softwire.' ;
                    leaf cpe-ipv6-address {
                      description 'IPv6 address of CPE.' ;
                      type ncd:ipv6-address ;

                      mandatory true ;
                    }

                    leaf aftr-ipv6-address {
                      description 'IPv6 address of AFTR.' ;
                      type ncd:ipv6-address ;

                      mandatory true ;
                    }

                    leaf local-ip {
                      description 'Local IP address.' ;
                      type ncd:ipv4-address-none-zero ;

                      mandatory true ;
                    }

                    leaf dslite-vrf {
                      description 'VRF of DSLITE.' ;
                      type string {
                        length 1..32 ;

                      }

                      ncd:revise-date 2021-02-26 ;
                    }

                  }

                }

                case vrf {
                  description 'VRF.' ;
                  container vrf {
                    description 'VRF.' ;
                    leaf vrf-name {
                      description 'VRF name.' ;
                      type string {
                        length 1..32 ;

                      }

                      mandatory true ;
                    }

                    leaf local-ip {
                      description 'Local IP address.' ;
                      type ncd:ipv4-address-none-zero ;

                      mandatory true ;
                    }

                  }

                }

                case cpe {
                  description 'CPE.' ;
                  container cpe {
                    description 'CPE.' ;
                    leaf cpe-ipv6-address {
                      description 'IPv6 address of CPE.' ;
                      type ncd:ipv6-address ;

                      mandatory true ;
                    }

                    leaf cpe-vrf {
                      description 'VRF of CPE.' ;
                      type string {
                        length 1..32 ;

                      }

                    }

                    leaf nat64-prefix {
                      description 'NAT64 prefix.' ;
                      type ncd:ipv6-address ;

                      mandatory true ;
                    }

                    leaf nat64-prefix-vrf {
                      description 'VRF of NAT64 prefix.' ;
                      type string {
                        length 1..32 ;

                      }

                    }

                    leaf nat64-prefix-length {
                      description 'Prefix length of NAT64.' ;
                      type enumeration {
                        enum 96 {
                          value 96 ;
                        }

                        enum 32 {
                          value 32 ;
                          description '32' ;
                        }

                        enum 40 {
                          value 40 ;
                          description '40' ;
                        }

                        enum 48 {
                          value 48 ;
                          description '48' ;
                        }

                        enum 56 {
                          value 56 ;
                          description '56' ;
                        }

                        enum 64 {
                          value 64 ;
                          description '64' ;
                        }

                      }

                      mandatory true ;
                    }

                  }

                }

                case public {
                  description 'Public.' ;
                  container public {
                    description 'Public.' ;
                    leaf local-ip {
                      description 'Local IP address.' ;
                      type ncd:ipv4-address-none-zero ;

                      mandatory true ;
                    }

                  }

                }

              }

              choice trans-mode {
                description 'Translation mode.' ;
                mandatory true ;
                case pat {
                  description 'PAT.' ;
                  container pat {
                    description 'PAT.' ;
                    leaf local-port {
                      description 'Local port.' ;
                      type uint16 {
                        range 1..65535 ;

                      }

                      mandatory true ;
                    }

                    leaf local-end-port {
                      description 'Local end port.' ;
                      type uint16 {
                        range 1..65535 ;

                      }

                      ncd:revise-date 2021-06-18 ;
                    }

                    leaf global-ip {
                      description 'Global IP address.' ;
                      type ncd:ipv4-address-none-zero ;

                      mandatory true ;
                    }

                    leaf global-port {
                      description 'Global port.' ;
                      type uint16 {
                        range 1..65535 ;

                      }

                      mandatory true ;
                    }

                    leaf global-end-port {
                      description 'Global end port.' ;
                      type uint16 {
                        range 1..65535 ;

                      }

                      ncd:revise-date 2021-06-18 ;
                    }

                    leaf protocol {
                      description 'Protocol.' ;
                      type enumeration {
                        enum tcp {
                          value 6 ;
                        }

                        enum udp {
                          value 17 ;
                        }

                      }

                      mandatory true ;
                    }

                  }

                }

                case nat {
                  description 'NAT.' ;
                  container nat {
                    description 'NAT.' ;
                    leaf global-ip {
                      description 'Global IP address.' ;
                      type ncd:ipv4-address-none-zero ;

                      mandatory true ;
                    }

                  }

                }

                case interface-pat {
                  if-feature static-rule-interface-feature ;

                  description 'Interface PAT.' ;
                  container if-pat {
                    description 'PAT.' ;
                    leaf local-port {
                      description 'Local port.' ;
                      type uint16 {
                        range 1..65535 ;

                      }

                      mandatory true ;
                    }

                    leaf local-end-port {
                      description 'Local end port.' ;
                      type uint16 {
                        range 1..65535 ;

                      }

                      ncd:revise-date 2021-06-18 ;
                    }

                    leaf if-name {
                      description 'Interface name.' ;
                      type ncd:ifname ;

                      mandatory true ;
                    }

                    leaf global-port {
                      description 'Global port.' ;
                      type uint16 {
                        range 1..65535 ;

                      }

                      mandatory true ;
                    }

                    leaf global-end-port {
                      description 'Global end port.' ;
                      type uint16 {
                        range 1..65535 ;

                      }

                      ncd:revise-date 2021-06-18 ;
                    }

                    leaf protocol {
                      description 'Protocol.' ;
                      type enumeration {
                        enum tcp {
                          value 6 ;
                        }

                        enum udp {
                          value 17 ;
                        }

                      }

                      mandatory true ;
                    }

                  }

                  ncd:revise-date 2018-04-19 ;
                }

                case interface-nat {
                  if-feature static-rule-interface-feature ;

                  description 'Interface NAT.' ;
                  container if-nat {
                    description 'NAT.' ;
                    leaf if-name {
                      description 'Interface name.' ;
                      type ncd:ifname ;

                      mandatory true ;
                    }

                  }

                  ncd:revise-date 2018-04-19 ;
                }

              }

              leaf car-policy {
                description 'CAR policy.' ;
                type string {
                  length 1..31 ;

                }

              }

              leaf time-range {
                description 'Time range.' ;
                type string {
                  length 1..31 ;

                }

              }

              container dest-ip {
                leaf dest-ip {
                  type ncd:ipv4-address-none-zero ;

                  description 'Destination IP.' ;
                  mandatory true ;
                }

                if-feature static-rule-dest-ip-feature {
                  ncd:revise-date 2024-04-01 ;
                }

                description 'Destination IP.' ;
                presence dest-ip ;
                leaf dest-ip-mask {
                  type ncd:ipv4-mask {
                    pattern '([1-9][0-9]*\.[1-9][0-9]*\.[1-9][0-9]*\.[1-9][0-9]*)|([1-9][0-9]*\.0\.0\.0)|(0\.[1-9][0-9]*\.0\.0)|(0\.0\.[1-9][0-9]*\.0)|(0\.0\.0\.[1-9][0-9]*)|([1-9][0-9]*\.[1-9][0-9]*\.0\.0)|(0\.[1-9][0-9]*\.[1-9][0-9]*\.0)|(0\.0\.[1-9][0-9]*\.[1-9][0-9]*)|([1-9][0-9]*\.0\.0\.[1-9][0-9]*)|(0\.[1-9][0-9]*\.0\.[1-9][0-9]*)|([1-9][0-9]*\.0\.[1-9][0-9]*\.0)|([1-9][0-9]*\.[1-9][0-9]*\.[1-9][0-9]*\.0)|([1-9][0-9]*\.[1-9][0-9]*\.0\.[1-9][0-9]*)|([1-9][0-9]*\.0\.[1-9][0-9]*\.[1-9][0-9]*)|(0\.[1-9][0-9]*\.[1-9][0-9]*\.[1-9][0-9]*)' ;

                  }

                  description 'Destination IP mask.' ;
                  mandatory true ;
                }

                ncd:revise-date 2024-04-01 ;
              }

            }

          }

          container same-address-policy {
            description 'Same address policy.' ;
            presence same-address-policy ;
            leaf same-addr-for-same-ipv4 {
              description 'Allocate the same global IP for one local IPv4 address.' ;
              type enumeration {
                enum must {
                  value 2 ;
                }

                enum try-best {
                  value 1 ;
                }

                enum random {
                  value 0 ;
                }

              }

              default random ;
            }

            leaf same-addr-for-same-softwire {
              status obsolete {
                ncd:revise-date 2021-02-26 ;
              }

              description 'Allocate the same global IP for one softwire.' ;
              type enumeration {
                enum must {
                  value 2 ;
                }

                enum try-best {
                  value 1 ;
                }

                enum random {
                  value 0 ;
                }

              }

              default random ;
            }

            leaf same-addr-for-same-user {
              status obsolete {
                ncd:revise-date 2021-02-26 ;
              }

              description 'Allocate the same global IP for one user.' ;
              type enumeration {
                enum must {
                  value 2 ;
                }

                enum try-best {
                  value 1 ;
                }

                enum random {
                  value 0 ;
                }

              }

              default random ;
            }

            leaf same-addr-for-same-ipv6 {
              description 'Allocate the same global IP for one local IPv6 address.' ;
              type enumeration {
                enum must {
                  value 2 ;
                }

                enum try-best {
                  value 1 ;
                }

                enum random {
                  value 0 ;
                }

              }

              default random ;
              ncd:revise-date 2021-02-26 ;
            }

          }

          container different-address-policy {
            description 'Different address policy.' ;
            presence diff-address-policy ;
            list different-addr-tcp-udp {
              description 'Allocate different address for TCP or UDP.' ;
              key 'protocol-type dest-port' ;
              leaf protocol-type {
                description 'Protocol type.' ;
                type enumeration {
                  enum tcp {
                    value 6 ;
                  }

                  enum udp {
                    value 17 ;
                  }

                }

              }

              leaf dest-port {
                description 'Destination port.' ;
                type uint16 {
                  range 1..65535 ;

                }

              }

              leaf description {
                description 'Description.' ;
                type string {
                  length 1..31 ;

                }

                mandatory true ;
              }

            }

            list different-addr-icmp {
              description 'Allocate different address for ICMP.' ;
              max-elements 1 ;
              key protocol-type ;
              leaf protocol-type {
                description 'Protocol type.' ;
                type enumeration {
                  enum icmp {
                    value 1 ;
                  }

                }

              }

              leaf description {
                description 'Description.' ;
                type string {
                  length 1..31 ;

                }

                mandatory true ;
              }

            }

          }

          container tcp-policy {
            description 'TCP policy.' ;
            presence tcp-policy ;
            leaf filtering-mode {
              description 'Filtering mode.' ;
              type enumeration {
                enum endpoint-independent {
                  value 1 ;
                }

                enum address-dependent {
                  value 2 ;
                }

                enum address-and-port-dependent {
                  value 3 ;
                }

              }

              default endpoint-independent ;
            }

            leaf mapping-mode {
              description 'Mapping mode.' ;
              type enumeration {
                enum endpoint-independent {
                  value 1 ;
                }

                enum address-dependent {
                  value 2 ;
                }

                enum address-and-port-dependent {
                  value 3 ;
                }

              }

              default endpoint-independent ;
            }

            leaf refreshing-mode {
              description 'Refreshing mode.' ;
              type enumeration {
                enum inbound {
                  value 1 ;
                }

                enum outbound {
                  value 2 ;
                }

                enum both-bounds {
                  value 3 ;
                }

              }

              default outbound ;
            }

            leaf well-known-port-timeout {
              description 'Timeout of well-known port.The default value is the performance parameter customized by the product.' ;
              type uint16 {
                range 1..7200 ;

              }

            }

            leaf well-known-syn-timeout {
              description 'Timeout of well-known TCP SYN.The default value is the performance parameter customized by the product.' ;
              type uint16 {
                range 1..7200 ;

              }

            }

            leaf well-known-fin-rst-timeout {
              description 'Timeout of well-known TCP FIN or TCP RST.The default value is the performance parameter customized by the product.' ;
              type uint16 {
                range 1..7200 ;

              }

            }

            leaf unwell-known-port-timeout {
              description 'Timeout of unwell-known port.The default value is the performance parameter customized by the product.' ;
              type uint16 {
                range 1..7200 ;

              }

            }

            leaf unwell-known-syn-timeout {
              description 'Timeout of unwell-known TCP SYN.The default value is the performance parameter customized by the product.' ;
              type uint16 {
                range 1..7200 ;

              }

            }

            leaf unwell-known-fin-rst-timeout {
              description 'Timeout of unwell-known TCP FIN or TCP RST.The default value is the performance parameter customized by the product.' ;
              type uint16 {
                range 1..7200 ;

              }

            }

            leaf port-parity {
              status obsolete {
                ncd:revise-date 2017-02-08 ;
              }

              description 'Parity of port.' ;
              type enumeration {
                enum enable {
                  value 1 ;
                }

                enum disable {
                  value 0 ;
                }

              }

              default disable ;
            }

            leaf port-random {
              description 'Randomization of port.' ;
              type enumeration {
                enum enable {
                  value 1 ;
                }

                enum disable {
                  value 0 ;
                }

              }

              default disable ;
            }

            container allowed-port-range {
              description 'Allowed port range.' ;
              presence allowed-range-port ;
              leaf start-port {
                description 'Start port.' ;
                type uint16 {
                  range 1..65535 ;

                }

                mandatory true ;
              }

              leaf end-port {
                description 'End port.' ;
                type uint16 {
                  range 1..65535 ;

                }

                mandatory true ;
              }

            }

            container forbidden-port-range {
              description 'Forbidden port range.' ;
              presence forbidden-port-range ;
              leaf start-port {
                description 'Start port.' ;
                type uint16 {
                  range 1..65535 ;

                }

                mandatory true ;
              }

              leaf end-port {
                description 'End port.' ;
                type uint16 {
                  range 1..65535 ;

                }

                mandatory true ;
              }

            }

            leaf well-known-fin-wait-timeout {
              description 'Timeout of well-known TCP FIN wait.' ;
              type uint16 {
                range 0..7200 ;

              }

              default 0 ;
              ncd:revise-date 2017-06-20 ;
            }

            leaf unwell-known-fin-wait-timeout {
              description 'Timeout of unwell-known TCP FIN wait.' ;
              type uint16 {
                range 0..7200 ;

              }

              default 0 ;
              ncd:revise-date 2017-06-20 ;
            }

          }

          container udp-policy {
            description 'UDP policy.' ;
            presence udp-policy ;
            leaf filtering-mode {
              description 'Filtering mode.' ;
              type enumeration {
                enum endpoint-independent {
                  value 1 ;
                }

                enum address-dependent {
                  value 2 ;
                }

                enum address-and-port-dependent {
                  value 3 ;
                }

              }

              default endpoint-independent ;
            }

            leaf mapping-mode {
              description 'Mapping mode.' ;
              type enumeration {
                enum endpoint-independent {
                  value 1 ;
                }

                enum address-dependent {
                  value 2 ;
                }

                enum address-and-port-dependent {
                  value 3 ;
                }

              }

              default endpoint-independent ;
            }

            leaf refreshing-mode {
              description 'Refreshing mode.' ;
              type enumeration {
                enum inbound {
                  value 1 ;
                }

                enum outbound {
                  value 2 ;
                }

                enum both-bounds {
                  value 3 ;
                }

              }

              default outbound ;
            }

            leaf well-known-port-timeout {
              description 'Timeout of well-known port.' ;
              type uint16 {
                range 1..7200 ;

              }

              default 180 ;
            }

            leaf unwell-known-port-timeout {
              description 'Timeout of unwell-known port.' ;
              type uint16 {
                range 1..7200 ;

              }

              default 180 ;
            }

            leaf port-parity {
              status obsolete {
                ncd:revise-date 2017-02-08 ;
              }

              description 'Parity of port.' ;
              type enumeration {
                enum enable {
                  value 1 ;
                }

                enum disable {
                  value 0 ;
                }

              }

              default disable ;
            }

            leaf port-random {
              description 'Randomization of port.' ;
              type enumeration {
                enum enable {
                  value 1 ;
                }

                enum disable {
                  value 0 ;
                }

              }

              default disable ;
            }

            container allowed-port-range {
              description 'Configure allowed port range.' ;
              presence allowed-range-port ;
              leaf start-port {
                description 'Start port.' ;
                type uint16 {
                  range 1..65535 ;

                }

                mandatory true ;
              }

              leaf end-port {
                description 'End port.' ;
                type uint16 {
                  range 1..65535 ;

                }

                mandatory true ;
              }

            }

            container forbidden-port-range {
              description 'Configure forbidden port range.' ;
              presence forbidden-port-range ;
              leaf start-port {
                description 'Start port.' ;
                type uint16 {
                  range 1..65535 ;

                }

                mandatory true ;
              }

              leaf end-port {
                description 'End port.' ;
                type uint16 {
                  range 1..65535 ;

                }

                mandatory true ;
              }

            }

          }

          container icmp-policy {
            description 'ICMP policy.' ;
            leaf filtering-mode {
              description 'Filtering mode.' ;
              type enumeration {
                enum endpoint-independent {
                  value 1 ;
                }

                enum address-dependent {
                  value 2 ;
                }

              }

              default endpoint-independent ;
            }

            leaf mapping-mode {
              description 'Mapping mode.' ;
              type enumeration {
                enum endpoint-independent {
                  value 1 ;
                }

                enum address-dependent {
                  value 2 ;
                }

              }

              default endpoint-independent ;
            }

            leaf refreshing-mode {
              description 'Refreshing mode.' ;
              type enumeration {
                enum inbound {
                  value 1 ;
                }

                enum outbound {
                  value 2 ;
                }

                enum both-bounds {
                  value 3 ;
                }

              }

              default outbound ;
            }

            leaf timeout {
              description 'Timeout.' ;
              type uint16 {
                range 1..7200 ;

              }

              default 60 ;
            }

          }

          container nat-policy {
            description 'NAT policy.' ;
            leaf filtering-mode {
              description 'Filtering mode.' ;
              type enumeration {
                enum endpoint-independent {
                  value 1 ;
                }

                enum address-dependent {
                  value 2 ;
                }

              }

              default endpoint-independent ;
            }

            leaf mapping-mode {
              description 'Mapping mode.' ;
              type enumeration {
                enum endpoint-independent {
                  value 1 ;
                }

                enum address-dependent {
                  value 2 ;
                }

              }

              default endpoint-independent ;
            }

            leaf refreshing-mode {
              description 'Refreshing mode.' ;
              type enumeration {
                enum inbound {
                  value 1 ;
                }

                enum outbound {
                  value 2 ;
                }

                enum both-bounds {
                  value 3 ;
                }

              }

              default outbound ;
            }

            leaf timeout {
              description 'Timeout.' ;
              type uint16 {
                range 1..7200 ;

              }

              default 120 ;
            }

          }

          container esp-policy {
            leaf esp-timeout {
              type uint16 {
                range 30..3600 ;

              }

              description 'Timeout of ESP.' ;
              default 360 ;
            }

            description 'ESP policy.' ;
            leaf gate-timeout {
              type uint16 {
                range 2..3600 ;

              }

              description 'Timeout of gate.' ;
              default 30 ;
            }

            ncd:revise-date 2024-07-15 ;
          }

          container domain-rate-limit-list {
            description 'Rate limit list of domain.' ;
            list domain-rate-limit {
              description 'Rate limit of domain.' ;
              key type ;
              leaf type {
                description 'Type.' ;
                type enumeration {
                  enum tcp {
                    value 1 ;
                    description 'Configure TCP rate limiting' ;
                  }

                  enum udp {
                    value 2 ;
                    description 'Configure UDP rate limiting' ;
                  }

                  enum icmp {
                    value 3 ;
                    description 'Configure ICMP rate limiting' ;
                  }

                  enum subscriber {
                    value 4 ;
                    description 'Configure subscriber rate limiting' ;
                  }

                }

              }

              leaf car-policy-name {
                description 'CAR policy name.' ;
                type string ;

                mandatory true ;
              }

              leaf instance-name {
                description 'Instance name.' ;
                type ncd:string-quesiton-mark ;

                mandatory true ;
              }

            }

          }

          container max-translations-list {
            description 'Max translations list.' ;
            list max-translations {
              description 'Max translations.' ;
              key 'limit-type limit-protocol' ;
              leaf limit-type {
                description 'Limit type.' ;
                type enumeration {
                  enum per-subscriber {
                    value 1 ;
                    status obsolete ;

                  }

                  enum per-softwire {
                    value 2 ;
                    status obsolete ;

                  }

                  enum per-ipv4 {
                    value 3 ;
                  }

                  enum per-ipv6 {
                    value 4 ;
                  }

                }

              }

              leaf limit-protocol {
                description 'Limit protocol.' ;
                type enumeration {
                  enum tcp {
                    value 1 ;
                  }

                  enum udp {
                    value 2 ;
                  }

                  enum icmp {
                    value 3 ;
                  }

                  enum nat {
                    value 4 ;
                  }

                  enum all {
                    value 5 ;
                  }

                }

              }

              choice translations-type {
                description 'Translations type.' ;
                mandatory true ;
                case dynamic {
                  description 'Dynamic.' ;
                  leaf dynamic {
                    description 'Dynamic.' ;
                    type uint32 {
                      range 0..32000000 ;

                    }

                    mandatory true ;
                  }

                }

                case pcp {
                  description 'PCP.' ;
                  leaf pcp {
                    description 'PCP.' ;
                    type uint32 {
                      range 0..32000000 ;

                    }

                    mandatory true ;
                  }

                }

                case all {
                  description 'All.' ;
                  leaf all-dynamic {
                    description 'All dynamic.' ;
                    type uint32 {
                      range 0..32000000 ;

                    }

                    mandatory true ;
                  }

                  leaf all-pcp {
                    description 'All PCP.' ;
                    type uint32 {
                      range 0..32000000 ;

                    }

                    mandatory true ;
                  }

                }

              }

              container time-range {
                description 'Time range.' ;
                presence time-range ;
                leaf time-range {
                  description 'Time range.' ;
                  type string {
                    length 1..31 ;

                  }

                  mandatory true ;
                }

                choice translation-type {
                  description 'Translation type.' ;
                  mandatory true ;
                  case dynamic {
                    description 'Dynamic.' ;
                    leaf dynamic {
                      description 'Dynamic.' ;
                      type uint32 {
                        range 0..32000000 ;

                      }

                      mandatory true ;
                    }

                  }

                  case pcp {
                    description 'PCP.' ;
                    leaf pcp {
                      description 'PCP.' ;
                      type uint32 {
                        range 0..32000000 ;

                      }

                      mandatory true ;
                    }

                  }

                  case all {
                    description 'All.' ;
                    leaf all-dynamic {
                      description 'All dynamic.' ;
                      type uint32 {
                        range 0..32000000 ;

                      }

                      mandatory true ;
                    }

                    leaf all-pcp {
                      description 'All PCP.' ;
                      type uint32 {
                        range 0..32000000 ;

                      }

                      mandatory true ;
                    }

                  }

                }

              }

            }

            ncd:revise-date 2016-09-22 ;
          }

          container max-trans-per-apps {
            description 'Max translations per app list.' ;
            list max-trans-per-app {
              description 'Max translations per app.' ;
              key 'type protocol port' ;
              leaf type {
                description 'Type.' ;
                type enumeration {
                  enum per-ipv4 {
                    value 1 ;
                  }

                  enum per-ipv6 {
                    value 2 ;
                  }

                }

              }

              leaf protocol {
                description 'Protocol.' ;
                type enumeration {
                  enum tcp {
                    value 1 ;
                  }

                  enum udp {
                    value 2 ;
                  }

                }

              }

              leaf port {
                description 'Port.' ;
                type uint32 {
                  range 1..65535 ;

                }

              }

              leaf total {
                description 'Total number.' ;
                type uint32 {
                  range 0..32000000 ;

                }

                mandatory true ;
              }

            }

            ncd:revise-date 2019-08-09 ;
          }

          container bind-pool-list {
            description 'Bind pool list.' ;
            list bind-pool {
              description 'Bind pool.' ;
              key pool-name ;
              leaf pool-name {
                description 'Pool name.' ;
                type string {
                  length 1..31 ;

                }

              }

            }

            ncd:revise-date 2020-01-10 ;
          }

          container dnat-list {
            description 'DNAT list.' ;
            list dnat-static-public {
              description 'DNAT static public policy.' ;
              key start-ipv4 ;
              leaf start-ipv4 {
                description 'The start private IPv4 address.' ;
                type ncd:ipv4-address-none-zero ;

              }

              leaf end-ipv4 {
                description 'The end private IPv4 address.' ;
                type ncd:ipv4-address-none-zero ;

                mandatory true ;
              }

              leaf pool-name {
                description 'Pool name.' ;
                type string {
                  length 1..31 ;

                }

                mandatory true ;
              }

            }

            list dnat-static-vrf {
              description 'DNAT static VRF policy.' ;
              key 'vrf-name start-ipv4' ;
              leaf vrf-name {
                description 'VRF name.' ;
                type string {
                  length 1..32 ;

                }

              }

              leaf start-ipv4 {
                description 'The start private IPv4 address.' ;
                type ncd:ipv4-address-none-zero ;

              }

              leaf end-ipv4 {
                description 'The end private IPv4 address.' ;
                type ncd:ipv4-address-none-zero ;

                mandatory true ;
              }

              leaf pool-name {
                description 'Pool name.' ;
                type string {
                  length 1..31 ;

                }

                mandatory true ;
              }

            }

            ncd:revise-date 2020-12-18 ;
          }

          container aftr-address {
            description 'AFTR address.' ;
            presence aftr-address ;
            container address {
              description 'AFTR address.' ;
              presence address ;
              leaf instance-name {
                description 'Instance name.' ;
                type ncd:string-quesiton-mark ;

                mandatory true ;
              }

              leaf aftr-address {
                description 'AFTR address.' ;
                type ncd:ipv6-address ;

                mandatory true ;
              }

              ncd:revise-date 2021-05-17 ;
            }

            container aftr-address-vrf {
              description 'AFTR address with VRF.' ;
              presence aftr-address-vrf ;
              leaf instance-name {
                description 'Instance name.' ;
                type ncd:string-quesiton-mark ;

                mandatory true ;
              }

              leaf aftr-address {
                description 'AFTR address.' ;
                type ncd:ipv6-address ;

                mandatory true ;
              }

              leaf vrf-name {
                description 'VRF name.' ;
                type string {
                  length 1..32 ;

                }

                mandatory true ;
              }

              ncd:revise-date 2021-05-17 ;
            }

            ncd:revise-date 2021-02-26 ;
          }

          container aftr-interface {
            description 'AFTR interface.' ;
            presence aftr-interface ;
            leaf instance-name {
              description 'Instance name.' ;
              type ncd:string-quesiton-mark ;

              mandatory true ;
            }

            leaf interface-name {
              description 'Interface name.' ;
              type ncd:ifname {
                length 1..31 ;

              }

              mandatory true ;
            }

            ncd:revise-date 2021-02-26 ;
          }

          container aftr-nat64-prefix {
            description 'NAT64 prefix.' ;
            list aftr-nat64-prefix {
              description 'NAT64 prefix.' ;
              key 'instance-name nat64-prefix nat64-prefix-length state-type' ;
              leaf instance-name {
                description 'Instance name.' ;
                type ncd:string-quesiton-mark ;

              }

              leaf nat64-prefix {
                description 'NAT64 prefix.' ;
                type ncd:ipv6-address ;

              }

              leaf nat64-prefix-length {
                description 'Prefix length of NAT64.' ;
                type enumeration {
                  enum 32 {
                    value 32 ;
                    description '32' ;
                  }

                  enum 40 {
                    value 40 ;
                    description '40' ;
                  }

                  enum 48 {
                    value 48 ;
                    description '48' ;
                  }

                  enum 56 {
                    value 56 ;
                    description '56' ;
                  }

                  enum 64 {
                    value 64 ;
                    description '64' ;
                  }

                  enum 96 {
                    value 96 ;
                    description '96' ;
                  }

                }

              }

              leaf state-type {
                description 'State type.' ;
                type enumeration {
                  enum stateful {
                    value 1 ;
                    description 'Stateful' ;
                  }

                  enum stateless {
                    value 2 ;
                    description 'Stateless' ;
                  }

                }

              }

            }

            list aftr-nat64-prefix-vrf {
              description 'VRF NAT64 prefix.' ;
              key 'instance-name nat64-prefix nat64-prefix-length state-type vrf-name' ;
              leaf instance-name {
                description 'Instance name.' ;
                type ncd:string-quesiton-mark ;

              }

              leaf nat64-prefix {
                description 'NAT64 prefix.' ;
                type ncd:ipv6-address ;

              }

              leaf nat64-prefix-length {
                description 'Prefix length of NAT64.' ;
                type enumeration {
                  enum 32 {
                    value 32 ;
                    description '32' ;
                  }

                  enum 40 {
                    value 40 ;
                    description '40' ;
                  }

                  enum 48 {
                    value 48 ;
                    description '48' ;
                  }

                  enum 56 {
                    value 56 ;
                    description '56' ;
                  }

                  enum 64 {
                    value 64 ;
                    description '64' ;
                  }

                  enum 96 {
                    value 96 ;
                    description '96' ;
                  }

                }

              }

              leaf state-type {
                description 'State type.' ;
                type enumeration {
                  enum stateful {
                    value 1 ;
                    description 'Stateful' ;
                  }

                  enum stateless {
                    value 2 ;
                    description 'Stateless' ;
                  }

                }

              }

              leaf vrf-name {
                description 'VRF name.' ;
                type string {
                  length 1..32 ;

                }

              }

            }

            ncd:revise-date 2021-02-26 ;
          }

          container max-trans-per-ipv4-addr-list {
            description 'Max translations per IPv4 address list.' ;
            list max-trans-per-ipv4-addr-vrf {
              description 'Max translations per IPv4 address.' ;
              key 'vrf-name start-ip end-ip' ;
              leaf vrf-name {
                description 'VRF name.' ;
                type string {
                  length 1..32 ;

                }

              }

              leaf start-ip {
                description 'Start IP address.' ;
                type ncd:ipv4-address-none-zero ;

              }

              leaf end-ip {
                description 'End IP address.' ;
                type ncd:ipv4-address-none-zero ;

              }

              leaf max-translations-num {
                description 'Max translations number.' ;
                type uint32 {
                  range 0..32000000 ;

                }

                mandatory true ;
              }

            }

            list max-trans-per-ipv4-addr-public {
              description 'Max translations per IPv4 address.' ;
              key 'start-ip end-ip' ;
              leaf start-ip {
                description 'Start IP address.' ;
                type ncd:ipv4-address-none-zero ;

              }

              leaf end-ip {
                description 'End IP address.' ;
                type ncd:ipv4-address-none-zero ;

              }

              leaf max-translations-num {
                description 'Max translations number.' ;
                type uint32 {
                  range 0..32000000 ;

                }

                mandatory true ;
              }

            }

            ncd:revise-date 2021-08-27 ;
          }

        }

      }

      container spr-list {
        description 'Static port-range list.' ;
        list spr-ipv4 {
          description 'Static port-range of public.' ;
          key 'instance-name start-ipv4' ;
          leaf instance-name {
            description 'Instance name.' ;
            type ncd:string-quesiton-mark {
              length 1..31 ;

            }

          }

          leaf start-ipv4 {
            description 'The start private IPv4 address.' ;
            type ncd:ipv4-address-none-zero ;

          }

          leaf end-ipv4 {
            description 'The end private IPv4 address.' ;
            type ncd:ipv4-address-none-zero ;

            mandatory true ;
          }

          leaf pool-id {
            description 'Pool ID.' ;
            type uint32 {
              range 0..1999 ;

            }

            mandatory true ;
          }

          leaf domain-id {
            description 'Domain ID.' ;
            type uint32 {
              range 1..4000 ;

            }

          }

          leaf extend {
            description 'Extend mode.' ;
            type enumeration {
              enum enable {
                value 1 ;
              }

              enum disable {
                value 0 ;
              }

            }

            default disable ;
            ncd:revise-date 2017-11-02 ;
          }

          ncd:select pool-id ;
          ncd:select start-ipv4 ;
        }

        list spr-ipv4-interface {
          description 'Static port-range of public.' ;
          key 'instance-name start-ipv4 interface-name' ;
          leaf instance-name {
            description 'Instance name.' ;
            type ncd:string-quesiton-mark {
              length 1..31 ;

            }

          }

          leaf start-ipv4 {
            description 'The start private IPv4 address.' ;
            type ncd:ipv4-address-none-zero ;

          }

          leaf interface-name {
            description 'Interface name.' ;
            type ncd:ifname {
              length 1..31 ;

            }

          }

          leaf end-ipv4 {
            description 'The end private IPv4 address.' ;
            type ncd:ipv4-address-none-zero ;

            mandatory true ;
          }

          leaf pool-id {
            description 'Pool ID.' ;
            type uint32 {
              range 0..1999 ;

            }

            mandatory true ;
          }

          leaf domain-id {
            description 'Domain ID.' ;
            type uint32 {
              range 1..4000 ;

            }

          }

          ncd:revise-date 2018-01-26 ;
          ncd:select pool-id ;
          ncd:select start-ipv4 ;
          ncd:select interface-name ;
        }

        list spr-vrf-ipv4 {
          description 'Static port-range of VRF.' ;
          key 'instance-name vrf-name start-ipv4' ;
          leaf instance-name {
            description 'Instance name.' ;
            type ncd:string-quesiton-mark {
              length 1..31 ;

            }

          }

          leaf vrf-name {
            description 'VRF name.' ;
            type string {
              length 1..32 ;

            }

          }

          leaf start-ipv4 {
            description 'The start private IPv4 address.' ;
            type ncd:ipv4-address-none-zero ;

          }

          leaf end-ipv4 {
            description 'The end private IPv4 address.' ;
            type ncd:ipv4-address-none-zero ;

            mandatory true ;
          }

          leaf pool-id {
            description 'Pool ID.' ;
            type uint32 {
              range 0..1999 ;

            }

            mandatory true ;
          }

          leaf domain-id {
            description 'Domain ID.' ;
            type uint32 {
              range 1..4000 ;

            }

          }

          leaf extend {
            description 'Extend mode.' ;
            type enumeration {
              enum enable {
                value 1 ;
              }

              enum disable {
                value 0 ;
              }

            }

            default disable ;
            ncd:revise-date 2017-11-02 ;
          }

          ncd:select pool-id ;
          ncd:select "vrf-name start-ipv4" ;
        }

        list spr-vrf-ipv4-interface {
          description 'Static port-range of VRF.' ;
          key 'instance-name vrf-name start-ipv4 interface-name' ;
          leaf instance-name {
            description 'Instance name.' ;
            type ncd:string-quesiton-mark {
              length 1..31 ;

            }

          }

          leaf vrf-name {
            description 'VRF name.' ;
            type string {
              length 1..32 ;

            }

          }

          leaf start-ipv4 {
            description 'The start private IPv4 address.' ;
            type ncd:ipv4-address-none-zero ;

          }

          leaf interface-name {
            description 'Interface name.' ;
            type ncd:ifname {
              length 1..31 ;

            }

          }

          leaf end-ipv4 {
            description 'The end private IPv4 address.' ;
            type ncd:ipv4-address-none-zero ;

            mandatory true ;
          }

          leaf pool-id {
            description 'Pool ID.' ;
            type uint32 {
              range 0..1999 ;

            }

            mandatory true ;
          }

          leaf domain-id {
            description 'Domain ID.' ;
            type uint32 {
              range 1..4000 ;

            }

          }

          ncd:revise-date 2018-01-26 ;
          ncd:select pool-id ;
          ncd:select "vrf-name start-ipv4" ;
          ncd:select interface-name ;
        }

        list spr-ipv6 {
          description 'IPv6 static port-range of public.' ;
          key 'instance-name start-ipv6 start-ipv6-mask' ;
          leaf instance-name {
            description 'Instance name.' ;
            type ncd:string-quesiton-mark {
              length 1..31 ;

            }

          }

          leaf start-ipv6 {
            description 'The start private IPv6 address.' ;
            type ncd:ipv6-address ;

          }

          leaf start-ipv6-mask {
            description 'Start IPv6 mask.' ;
            type ncd:ipv6-mask-length ;

          }

          leaf end-ipv6 {
            description 'The end private IPv6 address.' ;
            type ncd:ipv6-address ;

            mandatory true ;
          }

          leaf end-ipv6-mask {
            description 'End IPv6 mask.' ;
            type ncd:ipv6-mask-length ;

            mandatory true ;
          }

          leaf pool-id {
            description 'Pool ID.' ;
            type uint32 {
              range 0..1999 ;

            }

            mandatory true ;
          }

          leaf domain-id {
            description 'Domain ID.' ;
            type uint32 {
              range 1..4000 ;

            }

          }

          leaf extend {
            description 'Extend mode.' ;
            type enumeration {
              enum enable {
                value 1 ;
              }

              enum disable {
                value 0 ;
              }

            }

            default disable ;
          }

          ncd:revise-date 2021-02-26 ;
          ncd:select pool-id ;
          ncd:select "start-ipv6 start-ipv6-mask" ;
        }

        list spr-ipv6-interface {
          description 'IPv6 public static port-range with interface.' ;
          key 'instance-name start-ipv6 start-ipv6-mask interface-name' ;
          leaf instance-name {
            description 'Instance name.' ;
            type ncd:string-quesiton-mark {
              length 1..31 ;

            }

          }

          leaf start-ipv6 {
            description 'The start private IPv6 address.' ;
            type ncd:ipv6-address ;

          }

          leaf start-ipv6-mask {
            description 'Start IPv6 mask.' ;
            type ncd:ipv6-mask-length ;

          }

          leaf interface-name {
            description 'Interface name.' ;
            type ncd:ifname {
              length 1..31 ;

            }

          }

          leaf end-ipv6 {
            description 'The end private IPv6 address.' ;
            type ncd:ipv6-address ;

            mandatory true ;
          }

          leaf end-ipv6-mask {
            description 'End IPv6 mask.' ;
            type ncd:ipv6-mask-length ;

            mandatory true ;
          }

          leaf pool-id {
            description 'Pool ID.' ;
            type uint32 {
              range 0..1999 ;

            }

            mandatory true ;
          }

          leaf domain-id {
            description 'Domain ID.' ;
            type uint32 {
              range 1..4000 ;

            }

          }

          ncd:revise-date 2021-02-26 ;
          ncd:select pool-id ;
          ncd:select "start-ipv6 start-ipv6-mask" ;
          ncd:select interface-name ;
        }

        list spr-vrf-ipv6 {
          description 'IPv6 VRF Static port-range.' ;
          key 'instance-name vrf-name start-ipv6 start-ipv6-mask' ;
          leaf instance-name {
            description 'Instance name.' ;
            type ncd:string-quesiton-mark {
              length 1..31 ;

            }

          }

          leaf vrf-name {
            description 'VRF name.' ;
            type string {
              length 1..32 ;

            }

          }

          leaf start-ipv6 {
            description 'The start private IPv6 address.' ;
            type ncd:ipv6-address ;

          }

          leaf start-ipv6-mask {
            description 'Start IPv6 mask.' ;
            type ncd:ipv6-mask-length ;

          }

          leaf end-ipv6 {
            description 'The end private IPv6 address.' ;
            type ncd:ipv6-address ;

            mandatory true ;
          }

          leaf end-ipv6-mask {
            description 'End IPv6 mask.' ;
            type ncd:ipv6-mask-length ;

            mandatory true ;
          }

          leaf pool-id {
            description 'Pool ID.' ;
            type uint32 {
              range 0..1999 ;

            }

            mandatory true ;
          }

          leaf domain-id {
            description 'Domain ID.' ;
            type uint32 {
              range 1..4000 ;

            }

          }

          leaf extend {
            description 'Extend mode.' ;
            type enumeration {
              enum enable {
                value 1 ;
              }

              enum disable {
                value 0 ;
              }

            }

            default disable ;
          }

          ncd:revise-date 2021-02-26 ;
          ncd:select pool-id ;
          ncd:select "vrf-name start-ipv6 start-ipv6-mask" ;
        }

        list spr-vrf-ipv6-interface {
          description 'IPv6 VRF static port-range with interface.' ;
          key 'instance-name vrf-name start-ipv6 start-ipv6-mask interface-name' ;
          leaf instance-name {
            description 'Instance name.' ;
            type ncd:string-quesiton-mark {
              length 1..31 ;

            }

          }

          leaf vrf-name {
            description 'VRF name.' ;
            type string {
              length 1..32 ;

            }

          }

          leaf start-ipv6 {
            description 'The start private IPv6 address.' ;
            type ncd:ipv6-address ;

          }

          leaf start-ipv6-mask {
            description 'Start IPv6 mask.' ;
            type ncd:ipv6-mask-length ;

          }

          leaf interface-name {
            description 'Interface name.' ;
            type ncd:ifname {
              length 1..31 ;

            }

          }

          leaf end-ipv6 {
            description 'The end private IPv6 address.' ;
            type ncd:ipv6-address ;

            mandatory true ;
          }

          leaf end-ipv6-mask {
            description 'End IPv6 mask.' ;
            type ncd:ipv6-mask-length ;

            mandatory true ;
          }

          leaf pool-id {
            description 'Pool ID.' ;
            type uint32 {
              range 0..1999 ;

            }

            mandatory true ;
          }

          leaf domain-id {
            description 'Domain ID.' ;
            type uint32 {
              range 1..4000 ;

            }

          }

          ncd:revise-date 2021-02-26 ;
          ncd:select pool-id ;
          ncd:select "vrf-name start-ipv6 start-ipv6-mask" ;
          ncd:select interface-name ;
        }

      }

      container user-list {
        description 'User list.' ;
        list public-sl-nat66-user {
          description 'Public SL NAT66 user.' ;
          max-elements 1 ;
          key 'instance-name prefix-address mask-length' ;
          leaf instance-name {
            description 'Instance name.' ;
            type ncd:string-quesiton-mark ;

          }

          leaf prefix-address {
            description 'Prefix address.' ;
            type ncd:ipv6-address ;

          }

          leaf mask-length {
            description 'Mask length.' ;
            type uint8 {
              range 1..128 ;

            }

          }

          container rule-list {
            description 'Rule list.' ;
            list rule {
              description 'Dynamic rule.' ;
              key rule-id ;
              leaf rule-id {
                description 'Rule ID.' ;
                type uint32 {
                  range 1..10 ;

                }

              }

              leaf acl-name {
                description 'ACL Name.' ;
                type string {
                  length 1..31 ;

                }

                mandatory true ;
              }

              choice action {
                description 'Action.' ;
                mandatory true ;
                case permit {
                  description 'Permit.' ;
                  container permit {
                    description 'Permit.' ;
                    leaf permit {
                      description 'Permit.' ;
                      type enumeration {
                        enum permit {
                          value 1 ;
                        }

                      }

                      mandatory true ;
                    }

                    leaf translate-prefix-address {
                      description 'Translate prefix address.' ;
                      type ncd:ipv6-address ;

                    }

                    leaf mask-length {
                      description 'Mask length.' ;
                      type ncd:ipv6-mask-length ;

                    }

                    leaf interface-name {
                      description 'Interface name.' ;
                      type ncd:ifname ;

                    }

                  }

                }

              }

            }

          }

          container interface-list {
            description 'Interface list.' ;
            list interface {
              description 'Interface.' ;
              key interface-name ;
              leaf interface-name {
                description 'Interface name.' ;
                type ncd:ifname ;

              }

            }

          }

          ncd:revise-date 2020-11-04 ;
        }

        list vrf-sl-nat66-user {
          description 'VRF SL NAT66 user.' ;
          key 'vrf-name instance-name prefix-address mask-length' ;
          leaf vrf-name {
            description 'VRF name.' ;
            type string {
              length 1..32 ;

            }

          }

          leaf instance-name {
            description 'Instance name.' ;
            type ncd:string-quesiton-mark ;

          }

          leaf prefix-address {
            description 'Prefix address.' ;
            type ncd:ipv6-address ;

          }

          leaf mask-length {
            description 'Mask length.' ;
            type ncd:ipv6-mask-length {
              range 1..128 ;

            }

          }

          container rule-list {
            description 'Rule list.' ;
            list rule {
              description 'Dynamic rule.' ;
              key rule-id ;
              leaf rule-id {
                description 'Rule ID.' ;
                type uint32 {
                  range 1..10 ;

                }

              }

              leaf acl-name {
                description 'ACL Name.' ;
                type string {
                  length 1..31 ;

                }

                mandatory true ;
              }

              choice action {
                description 'Action.' ;
                mandatory true ;
                case permit {
                  description 'Permit.' ;
                  container permit {
                    description 'Permit.' ;
                    leaf permit {
                      description 'Permit.' ;
                      type enumeration {
                        enum permit {
                          value 1 ;
                        }

                      }

                      mandatory true ;
                    }

                    leaf translate-prefix-address {
                      description 'Translate prefix address.' ;
                      type ncd:ipv6-address ;

                    }

                    leaf mask-length {
                      description 'Mask length.' ;
                      type ncd:ipv6-mask-length ;

                    }

                    leaf interface-name {
                      description 'Interface name.' ;
                      type ncd:ifname ;

                    }

                  }

                }

              }

            }

          }

          container interface-list {
            description 'Interface list.' ;
            list interface {
              description 'Interface.' ;
              key interface-name ;
              leaf interface-name {
                description 'Interface name.' ;
                type ncd:ifname ;

              }

            }

          }

          ncd:revise-date 2020-11-04 ;
        }

        list public-user {
          description 'Public user.' ;
          max-elements 1 ;
          key instance-name ;
          leaf instance-name {
            description 'Instance name.' ;
            type ncd:string-quesiton-mark ;

          }

          leaf subscriber-id {
            description 'Subscriber ID.' ;
            type uint32 {
              range 1..8000 ;

            }

            mandatory true ;
          }

          leaf nat-domain-id {
            description 'NAT domain ID.' ;
            type uint32 {
              range 1..4000 ;

            }

            mandatory true ;
          }

          leaf dpi-policy {
            description 'DPI policy.' ;
            type string {
              length 1..31 ;

            }

          }

          container interface-list {
            description 'Interface list.' ;
            list interface {
              description 'Interface.' ;
              key interface-name ;
              leaf interface-name {
                description 'Interface name.' ;
                type ncd:ifname ;

              }

            }

          }

          leaf inbound-route-map {
            description 'Inbound route map name.' ;
            type string ;

            ncd:revise-date 2019-04-19 ;
          }

          leaf description {
            description 'Description.' ;
            type string {
              length 1..64 ;

            }

            ncd:revise-date 2020-05-28 ;
          }

        }

        list vrf-user {
          description 'VRF user.' ;
          key 'vrf-name instance-name' ;
          leaf vrf-name {
            description 'VRF name.' ;
            type string {
              length 1..32 ;

            }

          }

          leaf instance-name {
            description 'Instance name.' ;
            type ncd:string-quesiton-mark ;

          }

          leaf subscriber-id {
            description 'Subscriber ID.' ;
            type uint32 {
              range 1..8000 ;

            }

            mandatory true ;
          }

          leaf nat-domain-id {
            description 'NAT domain ID.' ;
            type uint32 {
              range 1..4000 ;

            }

            mandatory true ;
          }

          leaf dpi-policy {
            description 'DPI policy.' ;
            type string {
              length 1..31 ;

            }

          }

          container interface-list {
            description 'Interface list.' ;
            list interface {
              description 'Interface.' ;
              key interface-name ;
              leaf interface-name {
                description 'Interface name.' ;
                type ncd:ifname ;

              }

            }

          }

          leaf inbound-route-map {
            description 'Inbound route map name.' ;
            type string ;

            ncd:revise-date 2019-04-19 ;
          }

          leaf description {
            description 'Description.' ;
            type string {
              length 1..64 ;

            }

            ncd:revise-date 2020-05-28 ;
          }

        }

        list public-prefix-user {
          description 'Public prefix user.' ;
          max-elements 1 ;
          key 'instance-name prefix-address mask-length' ;
          leaf instance-name {
            description 'Instance name.' ;
            type ncd:string-quesiton-mark ;

          }

          leaf prefix-address {
            description 'Prefix address.' ;
            type ncd:ipv6-address ;

          }

          leaf mask-length {
            description 'Mask length.' ;
            type uint8 {
              range 1..128 ;

            }

          }

          leaf nat-domain-id {
            description 'NAT domain ID.' ;
            type uint32 {
              range 1..4000 ;

            }

            mandatory true ;
          }

          leaf dpi-policy {
            description 'DPI policy.' ;
            type string {
              length 1..31 ;

            }

          }

          leaf description {
            description 'Description.' ;
            type string {
              length 1..64 ;

            }

          }

          leaf user-prefix-length {
            description 'User prefix length.' ;
            type uint8 {
              range 1..128 ;

            }

            default 128 ;
          }

          leaf xlat {
            description 'XLAT flag.' ;
            type enumeration {
              enum enable {
                value 1 ;
                description 'Enable' ;
              }

              enum disable {
                value 0 ;
                description 'Disable' ;
              }

            }

            default disable ;
          }

          ncd:revise-date 2021-02-26 ;
        }

        list vrf-prefix-user {
          description 'VRF prefix user.' ;
          key 'instance-name prefix-address mask-length vrf-name' ;
          leaf instance-name {
            description 'Instance name.' ;
            type ncd:string-quesiton-mark ;

          }

          leaf prefix-address {
            description 'Prefix address.' ;
            type ncd:ipv6-address ;

          }

          leaf mask-length {
            description 'Mask length.' ;
            type uint8 {
              range 1..128 ;

            }

          }

          leaf vrf-name {
            description 'VRF name.' ;
            type string {
              length 1..32 ;

            }

          }

          leaf nat-domain-id {
            description 'NAT domain ID.' ;
            type uint32 {
              range 1..4000 ;

            }

            mandatory true ;
          }

          leaf dpi-policy {
            description 'DPI policy.' ;
            type string {
              length 1..31 ;

            }

          }

          leaf description {
            description 'Description.' ;
            type string {
              length 1..64 ;

            }

          }

          leaf user-prefix-length {
            description 'User prefix length.' ;
            type uint8 {
              range 1..128 ;

            }

            default 128 ;
          }

          leaf xlat {
            description 'XLAT flag.' ;
            type enumeration {
              enum enable {
                value 1 ;
                description 'Enable' ;
              }

              enum disable {
                value 0 ;
                description 'Disable' ;
              }

            }

            default disable ;
          }

          ncd:revise-date 2021-02-26 ;
        }

        list public-mask-length-user {
          description 'Public mask length user.' ;
          max-elements 1 ;
          key 'instance-name mask-length nat-domain-id' ;
          leaf instance-name {
            description 'Instance name.' ;
            type ncd:string-quesiton-mark ;

          }

          leaf mask-length {
            description 'Mask length.' ;
            type uint8 {
              range 1..128 ;

            }

          }

          leaf nat-domain-id {
            description 'NAT domain ID.' ;
            type uint32 {
              range 1..4000 ;

            }

          }

          leaf dpi-policy {
            description 'DPI policy.' ;
            type string {
              length 1..31 ;

            }

          }

          leaf description {
            description 'Description.' ;
            type string {
              length 1..64 ;

            }

          }

          leaf xlat {
            description 'XLAT flag.' ;
            type enumeration {
              enum enable {
                value 1 ;
                description 'Enable' ;
              }

              enum disable {
                value 0 ;
                description 'Disable' ;
              }

            }

            default disable ;
          }

          container interface-list {
            description 'Interface list.' ;
            list interface {
              description 'Interface.' ;
              key interface-name ;
              leaf interface-name {
                description 'Interface name.' ;
                type ncd:ifname ;

              }

            }

          }

          ncd:revise-date 2021-02-26 ;
        }

        list vrf-mask-length-user {
          description 'VRF mask length user.' ;
          key 'instance-name mask-length nat-domain-id vrf-name' ;
          leaf instance-name {
            description 'Instance name.' ;
            type ncd:string-quesiton-mark ;

          }

          leaf mask-length {
            description 'Mask length.' ;
            type uint8 {
              range 1..128 ;

            }

          }

          leaf nat-domain-id {
            description 'NAT domain ID.' ;
            type uint32 {
              range 1..4000 ;

            }

          }

          leaf vrf-name {
            description 'VRF name.' ;
            type string {
              length 1..32 ;

            }

          }

          leaf dpi-policy {
            description 'DPI policy.' ;
            type string {
              length 1..31 ;

            }

          }

          leaf description {
            description 'Description.' ;
            type string {
              length 1..64 ;

            }

          }

          leaf xlat {
            description 'XLAT flag.' ;
            type enumeration {
              enum enable {
                value 1 ;
                description 'Enable' ;
              }

              enum disable {
                value 0 ;
                description 'Disable' ;
              }

            }

            default disable ;
          }

          container interface-list {
            description 'Interface list.' ;
            list interface {
              description 'Interface.' ;
              key interface-name ;
              leaf interface-name {
                description 'Interface name.' ;
                type ncd:ifname ;

              }

            }

          }

          ncd:revise-date 2021-02-26 ;
        }

        list public-sl-nat64-user {
          description 'Public stateless NAT64 user.' ;
          max-elements 1 ;
          key 'prefix-address mask-length instance-name' ;
          leaf prefix-address {
            description 'Prefix address.' ;
            type ncd:ipv6-address ;

          }

          leaf mask-length {
            description 'Mask length.' ;
            type enumeration {
              enum 32 {
                value 32 ;
                description '32' ;
              }

              enum 40 {
                value 40 ;
                description '40' ;
              }

              enum 48 {
                value 48 ;
                description '48' ;
              }

              enum 56 {
                value 56 ;
                description '56' ;
              }

              enum 64 {
                value 64 ;
                description '64' ;
              }

              enum 96 {
                value 96 ;
                description '96' ;
              }

            }

          }

          leaf instance-name {
            description 'Instance name.' ;
            type ncd:string-quesiton-mark ;

          }

          leaf nat-domain-id {
            description 'NAT domain ID.' ;
            type uint32 {
              range 1..4000 ;

            }

            mandatory true ;
          }

          leaf dpi-policy {
            description 'DPI policy.' ;
            type string {
              length 1..31 ;

            }

          }

          leaf description {
            description 'Description.' ;
            type string {
              length 1..64 ;

            }

          }

          leaf without-u {
            description 'Without U.' ;
            type enumeration {
              enum enable {
                value 1 ;
                description 'Enable' ;
              }

              enum disable {
                value 0 ;
                description 'Disable' ;
              }

            }

            default disable ;
          }

          container nat64-ipv4-route-list {
            description 'NAT64 IPv4 route list.' ;
            list nat64-ipv4-route {
              description 'NAT64 IPv4 route.' ;
              key ipv4-address ;
              leaf ipv4-address {
                description 'IPv4 address.' ;
                type ncd:ipv4-address-none-zero ;

              }

              leaf ipv4-mask {
                description 'IPv4 mask.' ;
                type ncd:ipv4-address-none-zero ;

                mandatory true ;
              }

              choice mode {
                description 'Mode.' ;
                mandatory true ;
                case mode-1vs1 {
                  description '1:1 mode.' ;
                  leaf mode-1vs1 {
                    description '1:1 mode.' ;
                    type enumeration {
                      enum 1:1 {
                        value 1 ;
                      }

                    }

                    mandatory true ;
                  }

                }

                case mode-1vsN {
                  description '1:N mode.' ;
                  leaf mode-1vsN {
                    description '1:N mode.' ;
                    type enumeration {
                      enum 1:n {
                        value 2 ;
                      }

                    }

                    mandatory true ;
                  }

                  leaf divi-q-value {
                    description 'Double IVI Q value.' ;
                    type uint8 {
                      range 1..12 ;

                    }

                    mandatory true ;
                  }

                }

              }

            }

            list vrf-nat64-ipv4-route {
              description 'NAT64 IPv4 route with VRF.' ;
              key 'ipv4-address ipv4-route-vrf' ;
              leaf ipv4-route-vrf {
                description 'IPv4 route VRF name.' ;
                type string {
                  length 1..32 ;

                }

              }

              leaf ipv4-address {
                description 'IPv4 address.' ;
                type ncd:ipv4-address-none-zero ;

              }

              leaf ipv4-mask {
                description 'IPv4 mask.' ;
                type ncd:ipv4-address-none-zero ;

                mandatory true ;
              }

              choice mode {
                description 'Mode.' ;
                mandatory true ;
                case mode-1vs1 {
                  description '1:1 mode.' ;
                  leaf mode-1vs1 {
                    description '1:1 mode.' ;
                    type enumeration {
                      enum 1:1 {
                        value 1 ;
                      }

                    }

                    mandatory true ;
                  }

                }

                case mode-1vsN {
                  description '1:N mode.' ;
                  leaf mode-1vsN {
                    description '1:N mode.' ;
                    type enumeration {
                      enum 1:n {
                        value 2 ;
                      }

                    }

                    mandatory true ;
                  }

                  leaf divi-q-value {
                    description 'Double IVI Q value.' ;
                    type uint8 {
                      range 1..12 ;

                    }

                    mandatory true ;
                  }

                }

              }

              ncd:revise-date 2021-05-17 ;
            }

          }

          ncd:revise-date 2021-02-26 ;
        }

        list vrf-sl-nat64-user {
          description 'VRF stateless NAT64 user.' ;
          key 'prefix-address mask-length instance-name vrf-name' ;
          leaf prefix-address {
            description 'Prefix address.' ;
            type ncd:ipv6-address ;

          }

          leaf mask-length {
            description 'Mask length.' ;
            type enumeration {
              enum 32 {
                value 32 ;
                description '32' ;
              }

              enum 40 {
                value 40 ;
                description '40' ;
              }

              enum 48 {
                value 48 ;
                description '48' ;
              }

              enum 56 {
                value 56 ;
                description '56' ;
              }

              enum 64 {
                value 64 ;
                description '64' ;
              }

              enum 96 {
                value 96 ;
                description '96' ;
              }

            }

          }

          leaf instance-name {
            description 'Instance name.' ;
            type ncd:string-quesiton-mark ;

          }

          leaf vrf-name {
            description 'VRF name.' ;
            type string {
              length 1..32 ;

            }

          }

          leaf nat-domain-id {
            description 'NAT domain ID.' ;
            type uint32 {
              range 1..4000 ;

            }

            mandatory true ;
          }

          leaf dpi-policy {
            description 'DPI policy.' ;
            type string {
              length 1..31 ;

            }

          }

          leaf description {
            description 'Description.' ;
            type string {
              length 1..64 ;

            }

          }

          leaf without-u {
            description 'Without U.' ;
            type enumeration {
              enum enable {
                value 1 ;
                description 'Enable' ;
              }

              enum disable {
                value 0 ;
                description 'Disable' ;
              }

            }

            default disable ;
          }

          container nat64-ipv4-route-list {
            description 'NAT64 IPv4 route list.' ;
            list nat64-ipv4-route {
              description 'NAT64 IPv4 route.' ;
              key ipv4-address ;
              leaf ipv4-address {
                description 'IPv4 address.' ;
                type ncd:ipv4-address-none-zero ;

              }

              leaf ipv4-mask {
                description 'IPv4 mask.' ;
                type ncd:ipv4-address-none-zero ;

                mandatory true ;
              }

              choice mode {
                description 'Mode.' ;
                mandatory true ;
                case mode-1vs1 {
                  description '1:1 mode.' ;
                  leaf mode-1vs1 {
                    description '1:1 mode.' ;
                    type enumeration {
                      enum 1:1 {
                        value 1 ;
                      }

                    }

                    mandatory true ;
                  }

                }

                case mode-1vsN {
                  description '1:N mode.' ;
                  leaf mode-1vsN {
                    description '1:N mode.' ;
                    type enumeration {
                      enum 1:n {
                        value 2 ;
                      }

                    }

                    mandatory true ;
                  }

                  leaf divi-q-value {
                    description 'Double IVI Q value.' ;
                    type uint8 {
                      range 1..12 ;

                    }

                    mandatory true ;
                  }

                }

              }

            }

            list vrf-nat64-ipv4-route {
              description 'NAT64 IPv4 route with VRF.' ;
              key 'ipv4-address ipv4-route-vrf' ;
              leaf ipv4-route-vrf {
                description 'IPv4 route VRF name.' ;
                type string {
                  length 1..32 ;

                }

              }

              leaf ipv4-address {
                description 'IPv4 address.' ;
                type ncd:ipv4-address-none-zero ;

              }

              leaf ipv4-mask {
                description 'IPv4 mask.' ;
                type ncd:ipv4-address-none-zero ;

                mandatory true ;
              }

              choice mode {
                description 'Mode.' ;
                mandatory true ;
                case mode-1vs1 {
                  description '1:1 mode.' ;
                  leaf mode-1vs1 {
                    description '1:1 mode.' ;
                    type enumeration {
                      enum 1:1 {
                        value 1 ;
                      }

                    }

                    mandatory true ;
                  }

                }

                case mode-1vsN {
                  description '1:N mode.' ;
                  leaf mode-1vsN {
                    description '1:N mode.' ;
                    type enumeration {
                      enum 1:n {
                        value 2 ;
                      }

                    }

                    mandatory true ;
                  }

                  leaf divi-q-value {
                    description 'Double IVI Q value.' ;
                    type uint8 {
                      range 1..12 ;

                    }

                    mandatory true ;
                  }

                }

              }

              ncd:revise-date 2021-05-17 ;
            }

          }

          ncd:revise-date 2021-02-26 ;
        }

        list public-sl-nat64-eam-user {
          description 'Public stateless NAT64 EAM user.' ;
          max-elements 1 ;
          key 'instance-name prefix-address mask-length' ;
          leaf instance-name {
            description 'Instance name.' ;
            type ncd:string-quesiton-mark ;

          }

          leaf prefix-address {
            description 'Prefix address.' ;
            type ncd:ipv6-address ;

          }

          leaf mask-length {
            description 'Mask length.' ;
            type uint8 {
              range 1..128 ;

            }

          }

          leaf nat-domain-id {
            description 'NAT domain ID.' ;
            type uint32 {
              range 1..4000 ;

            }

            mandatory true ;
          }

          leaf description {
            description 'Description.' ;
            type string {
              length 1..64 ;

            }

          }

          leaf without-u {
            description 'Without U.' ;
            type enumeration {
              enum enable {
                value 1 ;
                description 'Enable' ;
              }

              enum disable {
                value 0 ;
                description 'Disable' ;
              }

            }

            default disable ;
          }

          container nat64-ipv4-route {
            description 'NAT64 IPv4 route.' ;
            presence nat64-ipv4-route ;
            container ipv4-route {
              description 'NAT64 IPv4 route.' ;
              presence ipv4-route ;
              leaf ipv4-address {
                description 'IPv4 address.' ;
                type ncd:ipv4-address-none-zero ;

                mandatory true ;
              }

              leaf ipv4-mask {
                description 'IPv4 mask.' ;
                type ncd:ipv4-address-none-zero ;

                mandatory true ;
              }

              ncd:revise-date 2021-05-17 ;
            }

            container vrf-ipv4-route {
              description 'NAT64 IPv4 route with VRF.' ;
              presence vrf-ipv4-route ;
              leaf ipv4-address {
                description 'IPv4 address.' ;
                type ncd:ipv4-address-none-zero ;

                mandatory true ;
              }

              leaf ipv4-mask {
                description 'IPv4 mask.' ;
                type ncd:ipv4-address-none-zero ;

                mandatory true ;
              }

              leaf ipv4-route-vrf {
                description 'IPv4 route VRF name.' ;
                type string {
                  length 1..32 ;

                }

                mandatory true ;
              }

              ncd:revise-date 2021-05-17 ;
            }

          }

          ncd:revise-date 2021-02-26 ;
        }

        list vrf-sl-nat64-eam-user {
          description 'VRF stateless NAT64 EAM user.' ;
          key 'instance-name prefix-address mask-length vrf-name' ;
          leaf instance-name {
            description 'Instance name.' ;
            type ncd:string-quesiton-mark ;

          }

          leaf prefix-address {
            description 'Prefix address.' ;
            type ncd:ipv6-address ;

          }

          leaf mask-length {
            description 'Mask length.' ;
            type uint8 {
              range 1..128 ;

            }

          }

          leaf vrf-name {
            description 'VRF name.' ;
            type string {
              length 1..32 ;

            }

          }

          leaf nat-domain-id {
            description 'NAT domain ID.' ;
            type uint32 {
              range 1..4000 ;

            }

            mandatory true ;
          }

          leaf description {
            description 'Description.' ;
            type string {
              length 1..64 ;

            }

          }

          leaf without-u {
            description 'Without U.' ;
            type enumeration {
              enum enable {
                value 1 ;
                description 'Enable' ;
              }

              enum disable {
                value 0 ;
                description 'Disable' ;
              }

            }

            default disable ;
          }

          container nat64-ipv4-route {
            description 'NAT64 IPv4 route.' ;
            presence nat64-ipv4-route ;
            container ipv4-route {
              description 'NAT64 IPv4 route.' ;
              presence ipv4-route ;
              leaf ipv4-address {
                description 'IPv4 address.' ;
                type ncd:ipv4-address-none-zero ;

                mandatory true ;
              }

              leaf ipv4-mask {
                description 'IPv4 mask.' ;
                type ncd:ipv4-address-none-zero ;

                mandatory true ;
              }

              ncd:revise-date 2021-05-17 ;
            }

            container vrf-ipv4-route {
              description 'NAT64 IPv4 route with VRF.' ;
              presence vrf-ipv4-route ;
              leaf ipv4-address {
                description 'IPv4 address.' ;
                type ncd:ipv4-address-none-zero ;

                mandatory true ;
              }

              leaf ipv4-mask {
                description 'IPv4 mask.' ;
                type ncd:ipv4-address-none-zero ;

                mandatory true ;
              }

              leaf ipv4-route-vrf {
                description 'IPv4 route VRF name.' ;
                type string {
                  length 1..32 ;

                }

                mandatory true ;
              }

              ncd:revise-date 2021-05-17 ;
            }

          }

          ncd:revise-date 2021-02-26 ;
        }

      }

      container log-list {
        description 'Log list.' ;
        list log {
          description 'Log.' ;
          key instance-name ;
          leaf instance-name {
            description 'Instance name.' ;
            type ncd:string-quesiton-mark ;

          }

          leaf log-switch {
            description 'Log switch.' ;
            type enumeration {
              enum disable {
                value 0 ;
              }

              enum enable {
                value 1 ;
              }

            }

            default disable ;
          }

          choice destination {
            description 'Destination.' ;
            case syslog {
              description 'Syslog.' ;
              leaf syslog {
                description 'Syslog.' ;
                type empty ;

              }

            }

            case ipflow {
              description 'Ipflow.' ;
              leaf ipflow {
                status obsolete {
                  ncd:revise-date 2022-04-14 ;
                }

                description 'Ipflow.' ;
                type empty ;

                mandatory true ;
              }

              leaf flow-exporter-name {
                status obsolete {
                  ncd:revise-date 2022-04-14 ;
                }

                description 'Flow exporter name.' ;
                type string {
                  length 1..32 ;

                }

                mandatory true ;
              }

              list ipflow-list {
                description 'Ipflow list.' ;
                key flow-exporter-name ;
                leaf flow-exporter-name {
                  description 'Flow exporter name.' ;
                  type string {
                    length 1..32 ;

                  }

                }

                leaf log-type {
                  description 'Log type.' ;
                  type enumeration {
                    enum all {
                      value 0 ;
                      description 'Send all log.' ;
                    }

                    enum translation {
                      value 1 ;
                      description 'Send translation log.' ;
                    }

                    enum portrange {
                      value 2 ;
                      description 'Send portrange log.' ;
                    }

                  }

                  ncd:revise-date 2023-03-27 ;
                }

                ncd:revise-date 2022-04-14 ;
              }

            }

            case local {
              description 'Local.' ;
              leaf local {
                description 'Local.' ;
                type empty ;

              }

            }

          }

          leaf log-buffer-size {
            description 'Log buffer size.' ;
            type int16 {
              range 10..64 ;

            }

            default 16 ;
          }

          leaf format {
            description 'Format.' ;
            type enumeration {
              enum text {
                value 0 ;
              }

              enum binary {
                value 1 ;
              }

            }

            default text ;
          }

          leaf syslog-merging {
            description 'Syslog merging.' ;
            type enumeration {
              enum disable {
                value 0 ;
              }

              enum enable {
                value 1 ;
              }

            }

            default disable ;
          }

          leaf log-style {
            description 'Log style.' ;
            type enumeration {
              enum style1 {
                value 0 ;
              }

              enum style2 {
                value 1 ;
              }

              enum style3 {
                value 2 ;
              }

              enum style4 {
                value 3 ;
              }

            }

            default style1 ;
          }

          leaf log-style1-start-end-time-with-zone {
            description 'Record start and end time with zone of the style1 log.' ;
            type enumeration {
              enum disable {
                value 0 ;
              }

              enum enable {
                value 1 ;
              }

            }

            default disable ;
            ncd:revise-date 2019-11-04 ;
          }

          leaf log-style1-start-end-time {
            description 'Record start and end time of the style1 log.' ;
            type enumeration {
              enum disable {
                value 0 ;
              }

              enum enable {
                value 1 ;
              }

            }

            default disable ;
          }

          leaf log-style1-year {
            description 'Record year of the in style1 log.' ;
            type enumeration {
              enum disable {
                value 0 ;
              }

              enum enable {
                value 1 ;
              }

            }

            default disable ;
          }

          leaf log-style1-duration {
            description 'Record duration of the style1 log.' ;
            type enumeration {
              enum disable {
                value 0 ;
              }

              enum enable {
                value 1 ;
              }

            }

            default disable ;
            ncd:revise-date 2019-11-04 ;
          }

          leaf log-style2-duration {
            description 'Generate style2 log according to session duration.' ;
            type int16 {
              range 0..10 ;

            }

            default 0 ;
          }

          leaf log-portrange-detail {
            description 'Generate session log when port range pool is used.' ;
            type enumeration {
              enum disable {
                value 0 ;
              }

              enum enable {
                value 1 ;
              }

            }

            default disable ;
          }

          leaf portrange-log-create {
            description 'Generate log when port range is allocated.' ;
            type enumeration {
              enum disable {
                value 0 ;
              }

              enum enable {
                value 1 ;
              }

            }

            default disable ;
          }

          leaf portrange-log-delete {
            description 'Generate log when port range is released.' ;
            type enumeration {
              enum disable {
                value 0 ;
              }

              enum enable {
                value 1 ;
              }

            }

            default disable ;
          }

          leaf portrange-log-first-session-create {
            description 'Generate log when port range is used firstly.' ;
            type enumeration {
              enum disable {
                value 0 ;
              }

              enum enable {
                value 1 ;
              }

            }

            default disable ;
          }

          leaf portrange-log-last-session-delete {
            description 'Generate log when port range is no longer used.' ;
            type enumeration {
              enum disable {
                value 0 ;
              }

              enum enable {
                value 1 ;
              }

            }

            default disable ;
          }

          leaf log-translation-when {
            description 'Generate log according to creating or deleting session.' ;
            type enumeration {
              enum created-and-deleted {
                value 0 ;
              }

              enum created {
                value 1 ;
              }

              enum deleted {
                value 2 ;
              }

            }

            default created-and-deleted ;
          }

          leaf log-protocol-tcp {
            description 'Log protocol of TCP.' ;
            type enumeration {
              enum disable {
                value 0 ;
              }

              enum enable {
                value 1 ;
              }

            }

            default enable ;
          }

          leaf log-protocol-udp {
            description 'Log protocol of UDP.' ;
            type enumeration {
              enum disable {
                value 0 ;
              }

              enum enable {
                value 1 ;
              }

            }

            default enable ;
          }

          leaf log-protocol-icmp {
            description 'Log protocol of ICMP.' ;
            type enumeration {
              enum disable {
                value 0 ;
              }

              enum enable {
                value 1 ;
              }

            }

            default enable ;
          }

          leaf resource-exhaust-action {
            description 'The action of resource exhausted.' ;
            type enumeration {
              enum stop-logging {
                value 0 ;
              }

              enum stop-cgn-service {
                value 1 ;
              }

            }

            default stop-logging ;
          }

          leaf stop-service-on-err {
            description 'Stop service on logging error.' ;
            type enumeration {
              enum disable {
                value 0 ;
              }

              enum enable {
                value 1 ;
              }

            }

            default disable ;
          }

          leaf bras-inside-port {
            description 'Inside port of BRAS.' ;
            type enumeration {
              enum disable {
                value 0 ;
              }

              enum enable {
                value 1 ;
              }

            }

            default disable ;
          }

          leaf bras-mapping-mode {
            description 'Mapping mode of BRAS.' ;
            type enumeration {
              enum disable {
                value 0 ;
              }

              enum enable {
                value 1 ;
              }

            }

            default disable ;
          }

          leaf bras-filtering-mode {
            description 'Filtering mode of BRAS.' ;
            type enumeration {
              enum disable {
                value 0 ;
              }

              enum enable {
                value 1 ;
              }

            }

            default disable ;
          }

          leaf bras-inbound-packets {
            description 'Inbound packets of BRAS.' ;
            type enumeration {
              enum disable {
                value 0 ;
              }

              enum enable {
                value 1 ;
              }

            }

            default disable ;
          }

          leaf bras-outbound-packets {
            description 'Outbound packets of BRAS.' ;
            type enumeration {
              enum disable {
                value 0 ;
              }

              enum enable {
                value 1 ;
              }

            }

            default disable ;
          }

          leaf bras-inbound-bytes {
            description 'Inbound bytes of BRAS.' ;
            type enumeration {
              enum disable {
                value 0 ;
              }

              enum enable {
                value 1 ;
              }

            }

            default disable ;
          }

          leaf bras-outbound-bytes {
            description 'Outbound bytes of BRAS.' ;
            type enumeration {
              enum disable {
                value 0 ;
              }

              enum enable {
                value 1 ;
              }

            }

            default disable ;
          }

          leaf dslite-inside-port {
            description 'Inside port of DSLITE or NAT64.' ;
            type enumeration {
              enum disable {
                value 0 ;
              }

              enum enable {
                value 1 ;
              }

            }

            default disable ;
          }

          leaf dslite-mapping-mode {
            description 'Mapping mode of DSLITE or NAT64.' ;
            type enumeration {
              enum disable {
                value 0 ;
              }

              enum enable {
                value 1 ;
              }

            }

            default disable ;
          }

          leaf dslite-filtering-mode {
            description 'Filtering mode of DSLITE or NAT64.' ;
            type enumeration {
              enum disable {
                value 0 ;
              }

              enum enable {
                value 1 ;
              }

            }

            default disable ;
          }

          leaf dslite-inbound-packets {
            description 'Inbound packets of DSLITE or NAT64.' ;
            type enumeration {
              enum disable {
                value 0 ;
              }

              enum enable {
                value 1 ;
              }

            }

            default disable ;
          }

          leaf dslite-outbound-packets {
            description 'Outbound packets of DSLITE or NAT64.' ;
            type enumeration {
              enum disable {
                value 0 ;
              }

              enum enable {
                value 1 ;
              }

            }

            default disable ;
          }

          leaf dslite-inbound-bytes {
            description 'Inbound bytes of DSLITE or NAT64.' ;
            type enumeration {
              enum disable {
                value 0 ;
              }

              enum enable {
                value 1 ;
              }

            }

            default disable ;
          }

          leaf dslite-outbound-bytes {
            description 'Outbound bytes of DSLITE or NAT64.' ;
            type enumeration {
              enum disable {
                value 0 ;
              }

              enum enable {
                value 1 ;
              }

            }

            default disable ;
          }

          leaf dslite-cpe-address {
            description 'CPE address of DSLITE or NAT64.' ;
            type enumeration {
              enum disable {
                value 0 ;
              }

              enum enable {
                value 1 ;
              }

            }

            default disable ;
          }

          leaf xgw-inside-port {
            description 'Inside port of XGW.' ;
            type enumeration {
              enum disable {
                value 0 ;
              }

              enum enable {
                value 1 ;
              }

            }

            default disable ;
          }

          leaf xgw-mapping-mode {
            description 'Mapping mode of XGW.' ;
            type enumeration {
              enum disable {
                value 0 ;
              }

              enum enable {
                value 1 ;
              }

            }

            default disable ;
          }

          leaf xgw-filtering-mode {
            description 'Filtering mode of XGW.' ;
            type enumeration {
              enum disable {
                value 0 ;
              }

              enum enable {
                value 1 ;
              }

            }

            default disable ;
          }

          leaf xgw-inbound-packets {
            description 'Inbound packets of XGW.' ;
            type enumeration {
              enum disable {
                value 0 ;
              }

              enum enable {
                value 1 ;
              }

            }

            default disable ;
          }

          leaf xgw-outbound-packets {
            description 'Outbound packets of XGW.' ;
            type enumeration {
              enum disable {
                value 0 ;
              }

              enum enable {
                value 1 ;
              }

            }

            default disable ;
          }

          leaf xgw-inbound-bytes {
            description 'Inbound bytes of XGW.' ;
            type enumeration {
              enum disable {
                value 0 ;
              }

              enum enable {
                value 1 ;
              }

            }

            default disable ;
          }

          leaf xgw-outbound-bytes {
            description 'Outbound bytes of XGW.' ;
            type enumeration {
              enum disable {
                value 0 ;
              }

              enum enable {
                value 1 ;
              }

            }

            default disable ;
          }

          leaf syslog-vrf {
            description 'VRF of syslog.' ;
            type enumeration {
              enum disable {
                value 0 ;
              }

              enum enable {
                value 1 ;
              }

            }

            default disable ;
          }

          leaf syslog-cgn-ip {
            description 'CGN IP of syslog.' ;
            type enumeration {
              enum disable {
                value 0 ;
              }

              enum enable {
                value 1 ;
              }

            }

            default disable ;
            ncd:revise-date 2021-02-26 ;
          }

          leaf syslog-destination-ip {
            description 'Destination IP of syslog.' ;
            type enumeration {
              enum disable {
                value 0 ;
              }

              enum enable {
                value 1 ;
              }

            }

            default disable ;
          }

          leaf syslog-destination-port {
            description 'Destination port of syslog.' ;
            type enumeration {
              enum disable {
                value 0 ;
              }

              enum enable {
                value 1 ;
              }

            }

            default disable ;
          }

          leaf syslog-inbound-packets {
            description 'Inbound packets of syslog.' ;
            type enumeration {
              enum disable {
                value 0 ;
              }

              enum enable {
                value 1 ;
              }

            }

            default disable ;
          }

          leaf syslog-outbound-packets {
            description 'Outbound packets of syslog.' ;
            type enumeration {
              enum disable {
                value 0 ;
              }

              enum enable {
                value 1 ;
              }

            }

            default disable ;
          }

          leaf syslog-inbound-bytes {
            description 'Inbound bytes of syslog.' ;
            type enumeration {
              enum disable {
                value 0 ;
              }

              enum enable {
                value 1 ;
              }

            }

            default disable ;
          }

          leaf syslog-outbound-bytes {
            description 'Outbound bytes of syslog.' ;
            type enumeration {
              enum disable {
                value 0 ;
              }

              enum enable {
                value 1 ;
              }

            }

            default disable ;
          }

          leaf sr-inside-port {
            description 'Inside port of SR.' ;
            type enumeration {
              enum disable {
                value 0 ;
              }

              enum enable {
                value 1 ;
              }

            }

            default disable ;
          }

          leaf sr-mapping-mode {
            description 'Mapping mode of SR.' ;
            type enumeration {
              enum disable {
                value 0 ;
              }

              enum enable {
                value 1 ;
              }

            }

            default disable ;
          }

          leaf sr-filtering-mode {
            description 'Filtering mode of SR.' ;
            type enumeration {
              enum disable {
                value 0 ;
              }

              enum enable {
                value 1 ;
              }

            }

            default disable ;
          }

          leaf sr-inbound-packets {
            description 'Inbound packets of SR.' ;
            type enumeration {
              enum disable {
                value 0 ;
              }

              enum enable {
                value 1 ;
              }

            }

            default disable ;
          }

          leaf sr-outbound-packets {
            description 'Outbound packets of SR.' ;
            type enumeration {
              enum disable {
                value 0 ;
              }

              enum enable {
                value 1 ;
              }

            }

            default disable ;
          }

          leaf sr-inbound-bytes {
            description 'Inbound bytes of SR.' ;
            type enumeration {
              enum disable {
                value 0 ;
              }

              enum enable {
                value 1 ;
              }

            }

            default disable ;
          }

          leaf sr-outbound-bytes {
            description 'Outbound bytes of SR.' ;
            type enumeration {
              enum disable {
                value 0 ;
              }

              enum enable {
                value 1 ;
              }

            }

            default disable ;
          }

          leaf log-ahead {
            status obsolete {
              ncd:revise-date 2019-06-25 ;
            }

            description 'Send log ahead when non-flow time expired.' ;
            type int32 {
              range 60..1800 ;

            }

            ncd:revise-date 2016-09-22 ;
          }

          container log-ipflow {
            description 'Log ipflow.' ;
            leaf ipflow-session-create-start-time {
              description 'Start time of ipflow log when session is created.' ;
              type enumeration {
                enum disable {
                  value 0 ;
                }

                enum enable {
                  value 1 ;
                }

              }

              default disable ;
            }

            leaf ipflow-session-delete-start-time {
              description 'Start time of ipflow log when session is deleted.' ;
              type enumeration {
                enum disable {
                  value 0 ;
                }

                enum enable {
                  value 1 ;
                }

              }

              default disable ;
            }

            leaf ipflow-session-delete-cgn-ip {
              description 'Outside source IP of ipflow log when session is deleted.' ;
              type enumeration {
                enum disable {
                  value 0 ;
                }

                enum enable {
                  value 1 ;
                }

              }

              default disable ;
            }

            leaf ipflow-session-delete-end-time {
              description 'End time of ipflow log when session is deleted.' ;
              type enumeration {
                enum disable {
                  value 0 ;
                }

                enum enable {
                  value 1 ;
                }

              }

              default disable ;
            }

            leaf ipflow-session-delete-inbound-bytes {
              description 'Inbound bytes of ipflow log when session is deleted.' ;
              type enumeration {
                enum disable {
                  value 0 ;
                }

                enum enable {
                  value 1 ;
                }

              }

              default disable ;
            }

            leaf ipflow-session-delete-inbound-packets {
              description 'Inbound packets of ipflow log when session is deleted.' ;
              type enumeration {
                enum disable {
                  value 0 ;
                }

                enum enable {
                  value 1 ;
                }

              }

              default disable ;
            }

            leaf ipflow-session-delete-outbound-bytes {
              description 'Outbound bytes of ipflow log when session is deleted.' ;
              type enumeration {
                enum disable {
                  value 0 ;
                }

                enum enable {
                  value 1 ;
                }

              }

              default disable ;
            }

            leaf ipflow-session-delete-outbound-packets {
              description 'Outbound packets of ipflow log when session is deleted.' ;
              type enumeration {
                enum disable {
                  value 0 ;
                }

                enum enable {
                  value 1 ;
                }

              }

              default disable ;
            }

            leaf ipflow-session-delete-vpn-id {
              description 'VPN ID of ipflow log when session is deleted.' ;
              type enumeration {
                enum disable {
                  value 0 ;
                }

                enum enable {
                  value 1 ;
                }

              }

              default disable ;
            }

            leaf ipflow-session-delete-cgn-port {
              description 'Outside source port of ipflow log when session is deleted.' ;
              type enumeration {
                enum disable {
                  value 0 ;
                }

                enum enable {
                  value 1 ;
                }

              }

              default disable ;
            }

            ncd:revise-date 2016-09-22 ;
          }

          leaf urllog-switch {
            description 'URL log switch.' ;
            type enumeration {
              enum enable {
                value 1 ;
              }

              enum disable {
                value 0 ;
              }

            }

            default disable ;
            ncd:revise-date 2017-02-08 ;
          }

          choice keepalive {
            case enable {
              leaf keepalive-enable {
                type enumeration {
                  enum enable {
                    value 1 ;
                  }

                }

                description 'Enable keep alive log.' ;
                mandatory true ;
              }

              leaf keepalive-time {
                description 'Minutes of keep alive.' ;
                type int32 {
                  range 15..6000 ;

                }

                default 1440 ;
              }

              description 'Enable.' ;
            }

            case disable {
              leaf keepalive-disable {
                type enumeration {
                  enum disable {
                    value 0 ;
                  }

                }

                description 'Disable keep alive log.' ;
              }

              description 'Disable.' ;
            }

            description 'Keep alive log.' ;
            ncd:revise-date 2024-11-11 ;
          }

        }

      }

      container advanced-and-pcp-service-list {
        description 'Advanced service and PCP service list.' ;
        list advanced-service {
          description 'Advanced service.' ;
          key instance-name ;
          leaf instance-name {
            description 'CGN instance name.' ;
            type ncd:string-quesiton-mark {
              length 1..31 ;

            }

          }

          leaf advanced-switch {
            description 'Switch of advanced service.' ;
            type enumeration {
              enum enable {
                value 1 ;
              }

              enum disable {
                value 0 ;
              }

            }

            default disable ;
          }

          choice tcp-mss-clamp {
            description 'TCP MSS clamps.' ;
            default tcp-mss-switch ;
            case tcp-mss-switch {
              description 'TCP MSS switch.' ;
              leaf disable {
                description 'Disable.' ;
                type enumeration {
                  enum disable {
                    value 0 ;
                  }

                }

              }

            }

            case tcp-mss-auto {
              description 'Negotiate TCP MSS automatically.' ;
              leaf auto {
                description 'Auto.' ;
                type enumeration {
                  enum auto {
                    value 1 ;
                  }

                }

              }

            }

            case tcp-mss-value {
              description 'TCP MSS value.' ;
              leaf value {
                description 'Value.' ;
                type uint16 {
                  range 64..9216 ;

                }

              }

            }

          }

          leaf tcp-state-track {
            description 'TCP state tracking.' ;
            type enumeration {
              enum enable {
                value 1 ;
              }

              enum disable {
                value 0 ;
              }

            }

            default disable ;
          }

          leaf session-mode {
            description 'Session mode.' ;
            type enumeration {
              enum enable {
                value 1 ;
              }

              enum disable {
                value 0 ;
              }

            }

            default disable ;
          }

          leaf pool-reuse {
            description 'Pool reuse.' ;
            type enumeration {
              enum enable {
                value 1 ;
              }

              enum disable {
                value 0 ;
              }

            }

            default disable ;
            ncd:revise-date 2017-08-03 ;
          }

          leaf hotback-delay-time {
            description 'Hotback translations delay time. Unit: Seconds.' ;
            type uint16 {
              range 2..120 ;

            }

            ncd:revise-date 2022-10-20 ;
          }

        }

        list pcp-service {
          description 'PCP service.' ;
          key instance-name ;
          leaf instance-name {
            description 'Instance name.' ;
            type ncd:string-quesiton-mark {
              length 1..31 ;

            }

          }

          leaf pcp-switch {
            description 'PCP switch.' ;
            type enumeration {
              enum enable {
                value 1 ;
              }

              enum disable {
                value 0 ;
              }

            }

            default disable ;
          }

          leaf min-life-time {
            description 'Mapping minimum life time.' ;
            type uint32 {
              range 120..86400 ;

            }

            default 120 ;
          }

          leaf max-life-time {
            description 'Maximal life time.' ;
            type uint32 {
              range 120..86400 ;

            }

            default 86400 ;
          }

          leaf ipv4-acl {
            description 'IPv4 access control list.' ;
            type string {
              length 1..31 ;

            }

          }

          leaf ipv6-acl {
            description 'IPv6 access control list.' ;
            type string {
              length 1..31 ;

            }

          }

        }

        list protocol-session-timeout {
          description 'Session timeout for different protocol.' ;
          max-elements 512 ;
          key 'instance-name protocol destination-port' ;
          leaf instance-name {
            description 'Instance name.' ;
            type ncd:string-quesiton-mark {
              length 1..31 ;

            }

          }

          leaf protocol {
            description 'Protocol.' ;
            type enumeration {
              enum tcp {
                value 6 ;
              }

              enum udp {
                value 17 ;
              }

            }

          }

          leaf destination-port {
            description 'Destination port.' ;
            type uint16 {
              range 1..65535 ;

            }

          }

          leaf description {
            description 'Description.' ;
            type string {
              length 1..63 ;

            }

            mandatory true ;
          }

          leaf timeout {
            description 'Timeout.' ;
            type uint16 {
              range 1..7200 ;

            }

            mandatory true ;
          }

        }

      }

      container alg-list {
        description 'ALG list.' ;
        list alg-switch {
          description 'ALG switch.' ;
          key instance-name ;
          leaf instance-name {
            description 'Instance name.' ;
            type ncd:string-quesiton-mark ;

          }

          leaf ftp {
            description 'FTP.' ;
            type enumeration {
              enum enable {
                value 1 ;
                description 'Enable FTP ALG' ;
              }

              enum disable {
                value 0 ;
                description 'Disable FTP ALG' ;
              }

            }

            default disable ;
          }

          leaf icmp {
            description 'ICMP.' ;
            type enumeration {
              enum enable {
                value 1 ;
                description 'Enable ICMP ALG' ;
              }

              enum disable {
                value 0 ;
                description 'Disable ICMP ALG' ;
              }

            }

            default disable ;
          }

          leaf dns {
            description 'DNS.' ;
            type enumeration {
              enum enable {
                value 1 ;
                description 'Enable DNS ALG' ;
              }

              enum disable {
                value 0 ;
                description 'Disable DNS ALG' ;
              }

            }

            default disable ;
          }

          leaf rtsp {
            description 'RTSP.' ;
            type enumeration {
              enum enable {
                value 1 ;
                description 'Enable RTSP ALG' ;
              }

              enum disable {
                value 0 ;
                description 'Disable RTSP ALG' ;
              }

            }

            default disable ;
          }

          leaf h323 {
            description 'H323.' ;
            type enumeration {
              enum enable {
                value 1 ;
                description 'Enable H323 ALG' ;
              }

              enum disable {
                value 0 ;
                description 'Disable H323 ALG' ;
              }

            }

            default disable ;
          }

          leaf sip {
            description 'SIP.' ;
            type enumeration {
              enum enable {
                value 1 ;
                description 'Enable SIP ALG' ;
              }

              enum disable {
                value 0 ;
                description 'Disable SIP ALG' ;
              }

            }

            default disable ;
          }

          leaf pptp {
            description 'PPTP.' ;
            type enumeration {
              enum enable {
                value 1 ;
                description 'Enable PPTP ALG' ;
              }

              enum disable {
                value 0 ;
                description 'Disable PPTP ALG' ;
              }

            }

            default disable ;
          }

          leaf http {
            description 'HTTP.' ;
            type enumeration {
              enum enable {
                value 1 ;
                description 'Enable HTTP ALG' ;
              }

              enum disable {
                value 0 ;
                description 'Disable HTTP ALG' ;
              }

            }

            default disable ;
            if-feature http-alg-feature {
              ncd:revise-date 2025-04-10 ;
            }

          }

          leaf dhcp {
            description 'DHCP.' ;
            type enumeration {
              enum enable {
                value 1 ;
                description 'Enable DHCP ALG' ;
              }

              enum disable {
                value 0 ;
                description 'Disable DHCP ALG' ;
              }

            }

            default disable ;
          }

          leaf ipsec {
            type enumeration {
              enum enable {
                description 'Enable IPSEC ALG' ;
                value 1 ;
              }

              enum disable {
                description 'Disable IPSEC ALG' ;
                value 0 ;
              }

            }

            description 'IPSEC.' ;
            default disable ;
            ncd:revise-date 2024-07-15 ;
          }

          leaf ftp-nat64 {
            description 'NAT64 FTP.' ;
            type enumeration {
              enum enable {
                value 1 ;
                description 'Enable FTP ALG' ;
              }

              enum disable {
                value 0 ;
                description 'Disable FTP ALG' ;
              }

            }

            default disable ;
            ncd:revise-date 2021-02-26 ;
          }

          leaf icmp-nat64 {
            description 'NAT64 ICMP.' ;
            type enumeration {
              enum enable {
                value 1 ;
                description 'Enable ICMP ALG' ;
              }

              enum disable {
                value 0 ;
                description 'Disable ICMP ALG' ;
              }

            }

            default disable ;
            ncd:revise-date 2021-02-26 ;
          }

          leaf dns-nat64 {
            description 'NAT64 DNS.' ;
            type enumeration {
              enum enable {
                value 1 ;
                description 'Enable DNS ALG' ;
              }

              enum disable {
                value 0 ;
                description 'Disable DNS ALG' ;
              }

            }

            default disable ;
            ncd:revise-date 2021-02-26 ;
          }

          leaf rtsp-nat64 {
            description 'NAT64 RTSP.' ;
            type enumeration {
              enum enable {
                value 1 ;
                description 'Enable RTSP ALG' ;
              }

              enum disable {
                value 0 ;
                description 'Disable RTSP ALG' ;
              }

            }

            default disable ;
            ncd:revise-date 2021-02-26 ;
          }

          leaf http-nat64 {
            description 'NAT64 HTTP.' ;
            type enumeration {
              enum enable {
                value 1 ;
                description 'Enable HTTP ALG' ;
              }

              enum disable {
                value 0 ;
                description 'Disable HTTP ALG' ;
              }

            }

            default disable ;
            ncd:revise-date 2021-02-26 ;
          }

          leaf pptp-nat64 {
            type enumeration {
              enum enable {
                value 1 ;
                description 'Enable PPTP ALG' ;
              }

              enum disable {
                value 0 ;
                description 'Disable PPTP ALG' ;
              }

            }

            description 'NAT64 PPTP.' ;
            default disable ;
            ncd:revise-date 2025-03-21 ;
          }

        }

        list alg-port {
          description 'ALG port.' ;
          max-elements 16 ;
          key 'instance-name protocol port' ;
          leaf instance-name {
            description 'Instance name.' ;
            type ncd:string-quesiton-mark ;

          }

          leaf protocol {
            description 'Protocol.' ;
            type enumeration {
              enum tcp {
                value 6 ;
                description 'TCP' ;
              }

            }

          }

          leaf port {
            description 'Port.' ;
            type uint16 {
              range 1..65535 {
                description '1-65535' ;
              }

            }

          }

          leaf alg-type {
            description 'ALG type.' ;
            type enumeration {
              enum ftp {
                value 0 ;
                description 'FTP' ;
              }

            }

            mandatory true ;
          }

        }

        list alg-nat64-port {
          description 'NAT64 ALG port.' ;
          max-elements 16 ;
          key 'instance-name protocol port' ;
          leaf instance-name {
            description 'Instance name.' ;
            type ncd:string-quesiton-mark ;

          }

          leaf protocol {
            description 'Protocol.' ;
            type enumeration {
              enum tcp {
                value 6 ;
                description 'TCP' ;
              }

              enum udp {
                value 17 ;
                description 'UDP' ;
              }

            }

          }

          leaf port {
            description 'Port.' ;
            type uint16 {
              range 1..65535 {
                description '1-65535' ;
              }

            }

          }

          leaf description {
            description 'Description.' ;
            type string {
              length 1..31 ;

            }

            mandatory true ;
          }

          ncd:revise-date 2021-02-26 ;
        }

      }

      container alarm-list {
        description 'Alarm list.' ;
        list alarm {
          description 'Alarm.' ;
          key instance-name ;
          leaf instance-name {
            description 'Instance name.' ;
            type ncd:string-quesiton-mark ;

          }

          leaf alarm-switch {
            description 'Alarm switch.' ;
            type enumeration {
              enum enable {
                value 1 ;
                description 'Start CGN alarm' ;
              }

              enum disable {
                value 0 ;
                description 'Stop CGN alarm' ;
              }

            }

            default disable ;
          }

          leaf warning-switch {
            description 'Warning switch.' ;
            type enumeration {
              enum enable {
                value 0 ;
                description 'Start CGN warning' ;
              }

              enum disable {
                value 1 ;
                description 'Stop CGN warning' ;
              }

            }

            default enable ;
          }

          leaf port-range-block-alarm-switch {
            description 'Alarm switch of port range block utilization.' ;
            type enumeration {
              enum enable {
                value 1 ;
                description 'Start alarm' ;
              }

              enum disable {
                value 0 ;
                description 'Stop alarm' ;
              }

            }

            default disable ;
          }

          leaf ip-resource-threshold {
            description 'IP resource alarm threshold of NAT pool.' ;
            type uint16 {
              range 1..100 {
                description '<1-100>' ;
              }

            }

            default 80 ;
          }

          leaf port-resource-threshold {
            description 'Port resource alarm threshold of PAT pool.' ;
            type uint16 {
              range 1..100 {
                description '<1-100>' ;
              }

            }

            default 80 ;
          }

          leaf translations-threshold-high-level {
            description 'High level threshold of translations.' ;
            type uint16 {
              range 1..100 ;

            }

            ncd:revise-date 2016-09-22 ;
          }

          leaf translations-threshold-middle-level {
            description 'Middle level threshold of translations.' ;
            type uint16 {
              range 1..100 ;

            }

            ncd:revise-date 2016-09-22 ;
          }

          leaf translations-threshold {
            description 'Translations alarm threshold.' ;
            type uint16 {
              range 1..100 {
                description '<1-100>' ;
              }

            }

            default 80 ;
          }

          leaf performance-statistics-switch {
            description 'Performance statistics switch.' ;
            type enumeration {
              enum on {
                value 1 ;
                description 'Start CGN performance statistics switch.' ;
              }

              enum off {
                value 0 ;
                description 'Stop CGN performance statistics switch.' ;
              }

            }

            default off ;
            ncd:revise-date 2016-09-22 ;
          }

          container local-ip-threshold {
            description 'Local IP threshold.' ;
            leaf high-level {
              description 'High level threshold of local IP.' ;
              type int16 {
                range 1..100 ;

              }

            }

            leaf middle-level {
              description 'Middle level threshold of local IP.' ;
              type int16 {
                range 1..100 ;

              }

            }

            leaf low-level {
              description 'Low level threshold of local IP.' ;
              type int16 {
                range 1..100 ;

              }

              default 80 ;
            }

            ncd:revise-date 2016-09-22 ;
          }

          leaf static-port-range-threshold {
            description 'Static port range alarm threshold.' ;
            type uint8 {
              range 1..100 ;

            }

            default 95 ;
            ncd:revise-date 2019-03-06 ;
          }

        }

      }

    }

    container aftr {
      leaf aftr-switch {
        description 'AFTR switch.' ;
        type enumeration {
          enum enable {
            value 1 ;
            description 'Enable' ;
          }

          enum disable {
            value 0 ;
            description 'Disable' ;
          }

        }

        default enable ;
      }

      leaf protect-action-forward {
        description 'Protect forward.' ;
        type enumeration {
          enum enable {
            value 1 ;
          }

          enum disable {
            value 0 ;
          }

        }

        default disable ;
      }

      description 'AFTR.' ;
      ncd:revise-date 2021-02-26 ;
    }

  }

}
