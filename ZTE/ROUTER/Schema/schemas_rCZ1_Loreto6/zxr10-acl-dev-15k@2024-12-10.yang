module zxr10-acl-dev-15k {
  namespace "http://www.zte.com.cn/zxr10/netconf/schema/rosng/acl-dev-15k" ;
  prefix acl-dev-15k ;
  import zxr10-acl {
    prefix acl ;
  }

  organization "ZTE Corporation" ;
  contact "ZTE Corporation  
     Nanjing Institute of ZTE Corporation 
     No.68 Zijinghua Rd. Yuhuatai District, Nanjing, China 
     Tel: +86-25-52870000" ;
  description '15k project deviation function.' ;
  revision 2024-12-10 {
    description 'Add deviation nodes:
1./acl:configuration/acl:acl/acl:access-list/acl:ipv6-mixed-access-list/acl:rule/acl:src-mac-addr/acl:src-mac-range
2./acl:configuration/acl:acl/acl:access-list/acl:ipv6-mixed-access-list/acl:rule/acl:dest-mac-addr/acl:dest-mac-range' ;
  }

  revision 2022-02-09 {
    description '15K project deviation function.
1. The general template head type that 15K supported is only l2-head,
2. The general template offset range that 15K supported is 0-72.' ;
  }

  deviation "/acl:configuration/acl:acl/acl:templates/acl:udf-template-generals/acl:udf-template-general/acl:format/acl:segment1/acl:head-type1" {
    description 'Configure general head type' ;
    deviate replace {
      type enumeration {
        enum l2-head {
          value 1 ;
        }

      }

    }

  }

  deviation "/acl:configuration/acl:acl/acl:templates/acl:udf-template-generals/acl:udf-template-general/acl:format/acl:segment2/acl:head-type2" {
    description 'Configure general head type' ;
    deviate replace {
      type enumeration {
        enum l2-head {
          value 1 ;
        }

      }

    }

  }

  deviation "/acl:configuration/acl:acl/acl:templates/acl:udf-template-generals/acl:udf-template-general/acl:format/acl:segment3/acl:head-type3" {
    description 'Configure general head type' ;
    deviate replace {
      type enumeration {
        enum l2-head {
          value 1 ;
        }

      }

    }

  }

  deviation "/acl:configuration/acl:acl/acl:templates/acl:udf-template-generals/acl:udf-template-general/acl:format/acl:segment4/acl:head-type4" {
    description 'Configure general head type' ;
    deviate replace {
      type enumeration {
        enum l2-head {
          value 1 ;
        }

      }

    }

  }

  deviation "/acl:configuration/acl:acl/acl:templates/acl:udf-template-generals/acl:udf-template-general/acl:format/acl:segment5/acl:head-type5" {
    description 'Configure general head type' ;
    deviate replace {
      type enumeration {
        enum l2-head {
          value 1 ;
        }

      }

    }

  }

  deviation "/acl:configuration/acl:acl/acl:templates/acl:udf-template-generals/acl:udf-template-general/acl:format/acl:segment6/acl:head-type6" {
    description 'Configure general head type' ;
    deviate replace {
      type enumeration {
        enum l2-head {
          value 1 ;
        }

      }

    }

  }

  deviation "/acl:configuration/acl:acl/acl:templates/acl:udf-template-generals/acl:udf-template-general/acl:format/acl:segment7/acl:head-type7" {
    description 'Configure general head type' ;
    deviate replace {
      type enumeration {
        enum l2-head {
          value 1 ;
        }

      }

    }

  }

  deviation "/acl:configuration/acl:acl/acl:templates/acl:udf-template-generals/acl:udf-template-general/acl:format/acl:segment8/acl:head-type8" {
    description 'Configure general head type' ;
    deviate replace {
      type enumeration {
        enum l2-head {
          value 1 ;
        }

      }

    }

  }

  deviation "/acl:configuration/acl:acl/acl:templates/acl:udf-template-generals/acl:udf-template-general/acl:format/acl:segment1/acl:offset1" {
    description 'Configure offset' ;
    deviate replace {
      type uint8 {
        range 0..72 ;

      }

    }

  }

  deviation "/acl:configuration/acl:acl/acl:templates/acl:udf-template-generals/acl:udf-template-general/acl:format/acl:segment2/acl:offset2" {
    description 'Configure offset' ;
    deviate replace {
      type uint8 {
        range 0..72 ;

      }

    }

  }

  deviation "/acl:configuration/acl:acl/acl:templates/acl:udf-template-generals/acl:udf-template-general/acl:format/acl:segment3/acl:offset3" {
    description 'Configure offset' ;
    deviate replace {
      type uint8 {
        range 0..72 ;

      }

    }

  }

  deviation "/acl:configuration/acl:acl/acl:templates/acl:udf-template-generals/acl:udf-template-general/acl:format/acl:segment4/acl:offset4" {
    description 'Configure offset' ;
    deviate replace {
      type uint8 {
        range 0..72 ;

      }

    }

  }

  deviation "/acl:configuration/acl:acl/acl:templates/acl:udf-template-generals/acl:udf-template-general/acl:format/acl:segment5/acl:offset5" {
    description 'Configure offset' ;
    deviate replace {
      type uint8 {
        range 0..72 ;

      }

    }

  }

  deviation "/acl:configuration/acl:acl/acl:templates/acl:udf-template-generals/acl:udf-template-general/acl:format/acl:segment6/acl:offset6" {
    description 'Configure offset' ;
    deviate replace {
      type uint8 {
        range 0..72 ;

      }

    }

  }

  deviation "/acl:configuration/acl:acl/acl:templates/acl:udf-template-generals/acl:udf-template-general/acl:format/acl:segment7/acl:offset7" {
    description 'Configure offset' ;
    deviate replace {
      type uint8 {
        range 0..72 ;

      }

    }

  }

  deviation "/acl:configuration/acl:acl/acl:templates/acl:udf-template-generals/acl:udf-template-general/acl:format/acl:segment8/acl:offset8" {
    description 'Configure offset' ;
    deviate replace {
      type uint8 {
        range 0..72 ;

      }

    }

  }

  deviation "/acl:configuration/acl:acl/acl:access-list/acl:ipv6-mixed-access-list/acl:rule/acl:src-mac-addr/acl:src-mac-range" {
    deviate not-supported ;

    description 'Source MAC address range.' ;
  }

  deviation "/acl:configuration/acl:acl/acl:access-list/acl:ipv6-mixed-access-list/acl:rule/acl:dest-mac-addr/acl:dest-mac-range" {
    deviate not-supported ;

    description 'Destination MAC address range.' ;
  }

}
