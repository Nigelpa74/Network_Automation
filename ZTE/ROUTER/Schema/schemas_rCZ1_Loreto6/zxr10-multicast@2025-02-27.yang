module zxr10-multicast {
  namespace "http://www.zte.com.cn/zxr10/netconf/schema/rosng/multicast" ;
  prefix mr ;
  yang-version 1 ;
  import zxr10-netconf-defs {
    prefix ncd ;
  }

  organization "ZTE Corporation" ;
  contact "ZTE Corporation  
     Nanjing Institute of ZTE Corporation 
     No.68 Zijinghua Rd. Yuhuatai District, Nanjing, China 
     Tel: +86-25-52870000" ;
  description 'The netconf module of describing multicast.' ;
  revision 2025-02-27 {
    description '1.Add the leaf:/configuration/ip-multicast/vrf-multicasts/vrf-multicast/mvpn/leaf-info-required;' ;
  }
  revision 2024-07-05 {
    description '1.modify tool-version from none to 1.0.
2.Add the labels of ZSRV2@JW,高端路由器HighEndRouter.T8000@JW,高端分组HighEndPacket.15K@JW,MSE.xGW@JW for the feature of mvpn-cross-as.
3.Add the labels of SWITCH.89@GM,SWITCH.89@JW,高端路由器HighEndRouter.T8000@JW,高端分组HighEndPacket.15K@JW for the feature of mvpn-switch-threshold.' ;
  }

  revision 2024-03-26 {
    description '1.Add the labels of PC.SWITCH and SWITCH.89 for the feature of mvpn-switch-threshold.' ;
  }

  revision 2023-10-12 {
    description '1.Add the containers:/state/multicast/public/mvpn/ipmsi-infos;
/state/multicast/public/mvpn/spmsi-infos;
/state/multicast/public/mvpn/pmsi-summarys;
/state/multicast/private/mvpn/ipmsi-infos;
/state/multicast/private/mvpn/spmsi-infos;
/state/multicast/private/mvpn/pmsi-summarys.' ;
  }

  revision 2023-09-11 {
    description '1.Add the container: /configuration/ip-multicast/multicast/mroute-usage-rate;' ;
  }

  revision 2023-03-09 {
    description '1.Add the leaf of mvpn-pim-hello-silent: /configuration/ip-multicast/vrf-multicasts/vrf-multicast/;
2.Add the leaf of mvpn-pim-hello-silent: /configuration/ip-multicast/multicast/global/;' ;
  }

  revision 2022-12-26 {
    description '1.Add the leaf of mvpn-frr-support-ipmsi: /configuration/ip-multicast/vrf-multicasts/vrf-multicast/;
2.Add the leaf of mvpn-frr-support-ipmsi: /configuration/ip-multicast/multicast/global/;
3.Add the leaf of mvpn-switchover-threshold-infinity: /configuration/ip-multicast/multicast/global/;' ;
  }

  revision 2022-11-14 {
    description '1.Add the leaf of mvpn-export-msdp: /configuration/ip-multicast/vrf-multicasts/vrf-multicast/;
2.Add the leaf of mvpn-export-msdp: /configuration/ip-multicast/multicast/global/;
3.Add the leaf of mvpn-import-msdp: /configuration/ip-multicast/multicast/global/;' ;
  }

  revision 2022-06-16 {
    description '1.Add the type of the leaf:/configuration/ip-multicast/vrf-multicasts/vrf-multicast/mvpn/provider-tunnel
2.modify the description of the leaf:/state/multicast/private/mvpn/instances/instance/mtunnel-type.
3.Add the type of the leaf:/state/multicast/private/mvpn/instances/instance/mtunnel-type' ;
  }

  revision 2022-05-18 {
    description '1.Add the leaf:/configuration/ip-multicast/multicast/global/bgp-auto-discovery-inter-as;' ;
  }

  revision 2022-02-10 {
    description '1.Add the container:/configuration/ip-multicast/vrf-multicasts/vrf-multicast/mvpn-spmsi-policys;' ;
  }

  revision 2022-01-13 {
    description 'Add the labels of MSR.ASR,MSR.ZSRV2,PTN.6500,PTN.6700,PTN.65V5,PTN.61-SSP,PTN.61V5_1,HighEndRouter.T8000,MSE.M6000,MSE.xGW,FN.C600,FN.C89E,OTN.9700,OTN.8700,OTN.7000,MW.NR8000,V6000.vBRAS-C,V6000.CDB and ROSNG-V.COMMON for the feature of mvpn-cross-as.' ;
  }

  revision 2022-01-04 {
    description '1.Add the leaf:/configuration/ip-multicast/vrf-multicasts/vrf-multicast/mvpn-source-active-acl;' ;
  }

  revision 2021-12-08 {
    description 'Add new node to query global or vpn multicast route summary for telemetry.' ;
  }

  revision 2021-12-07 {
    description '1.Add the leaf of mvpn-import-msdp: /configuration/ip-multicast/vrf-multicasts/vrf-multicast/;' ;
  }

  revision 2021-10-13 {
    description '1.Add the leaf:
/configuration/ip-multicast/multicast/global/mvpn-upstream-pe-select;
2.Add enum item to the leaf:
/configuration/ip-multicast/vrf-multicasts/vrf-multicast/mvpn-upstream-pe-select;' ;
  }

  revision 2021-09-11 {
    description '1.Modify the range of the leafes:/state/multicast/private/mvpn/mdts/mdt/data-group-mask-len;/state/multicast/private/mvpn/instances/instance/data-group-mask-len' ;
  }

  revision 2021-08-16 {
    description '1.Add the leaf:/state/multicast/public/nexthops/nexthop/ecmp/remote-pe.
2.Modify the type of the leaves: 
/state/multicast/public/nexthops/nexthop/ecmp/nexthop
/state/multicast/public/nexthops/nexthop/ecmp/real-nexthop
/state/multicast/private/nexthops/nexthop/ecmp/nexthop
/state/multicast/private/nexthops/nexthop/ecmp/remote-pe
/state/multicast/private/nexthops/nexthop/ecmp/real-nexthop' ;
  }

  revision 2021-07-01 {
    description '1.Add the leafes:
/configuration/ip-multicast/multicast/global/mvpn-frr-detect-type;
/configuration/ip-multicast/multicast/global/mvpn-frr-egress-wtr-infinity;
/configuration/ip-multicast/multicast/global/mvpn-frr-policy-acl;
/configuration/ip-multicast/vrf-multicasts/vrf-multicast/mvpn-frr-egress-wtr-infinity;
/configuration/ip-multicast/vrf-multicasts/vrf-multicast/mvpn-frr-policy-acl;' ;
  }

  revision 2021-04-08 {
    description '1.Modify the type of the leafes:
/state/multicast/public/mvpn/instance/origin-ip.
/state/multicast/public/mvpn/instance/te-id.
/state/multicast/public/mvpn/auto-discovery-route/intra-ases/intra-as/origin-ip.
/state/multicast/public/mvpn/auto-discovery-route/spmsi-ads/spmsi-ad/origin-ip.
/state/multicast/public/mvpn/auto-discovery-route/leaf-ads/leaf-ad/origin-ip.
/state/multicast/public/mvpn/auto-discovery-route/leaf-ads/leaf-ad/sub-origin-ip.
/state/multicast/public/mvpn/public-auto-discovery-route/intra-ases/intra-as/origin-ip.
/state/multicast/public/mvpn/public-auto-discovery-route/spmsi-ads/spmsi-ad/origin-ip.
/state/multicast/public/mvpn/public-auto-discovery-route/leaf-ads/leaf-ad/origin-ip.
/state/multicast/public/mvpn/public-auto-discovery-route/leaf-ads/leaf-ad/sub-origin-ip.
/state/multicast/public/mvpn/public-auto-discovery-route/source-actives/source-active/nexthop.
/state/multicast/public/mvpn/public-auto-discovery-route/xg-joins/xg-join/nexthop.
/state/multicast/public/mvpn/public-auto-discovery-route/sg-joins/sg-join/nexthop.
/state/multicast/public/mvpn/mribs/mrib/upstream-pe.
/state/multicast/public/mvpn/mribs/mrib/spmsi-auto-discoveries/spmsi-auto-discovery/origin-ip.
/state/multicast/public/mvpn/mribs/mrib/leaf-auto-discoveries/leaf-auto-discovery/origin-ip.
/state/multicast/public/mvpn/mribs/mrib/leaf-auto-discoveries/leaf-auto-discovery/sub-origin-ip.
/state/multicast/public/mvpn/segments/segment/leaf-lists/leaf-list/origin-ip.
/state/multicast/private/mvpn/instance/origin-ip.
/state/multicast/private/mvpn/instance/te-id.
/state/multicast/private/mvpn/auto-discovery-route/intra-ases/intra-as/origin-ip.
/state/multicast/private/mvpn/auto-discovery-route/spmsi-ads/spmsi-ad/origin-ip.
/state/multicast/private/mvpn/auto-discovery-route/leaf-ads/leaf-ad/origin-ip.
/state/multicast/private/mvpn/auto-discovery-route/leaf-ads/leaf-ad/sub-origin-ip.
/state/multicast/private/mvpn/auto-discovery-route/source-actives/source-active/nexthop.
/state/multicast/private/mvpn/auto-discovery-route/xg-joins/xg-join/nexthop.
/state/multicast/private/mvpn/auto-discovery-route/sg-joins/sg-join/nexthop.
/state/multicast/private/mvpn/mribs/mrib/upstream-pe.
/state/multicast/private/mvpn/mribs/mrib/spmsi-auto-discoveries/spmsi-auto-discovery/origin-ip.
/state/multicast/private/mvpn/mribs/mrib/leaf-auto-discoveries/leaf-auto-discovery/origin-ip.
/state/multicast/private/mvpn/mribs/mrib/leaf-auto-discoveries/leaf-auto-discovery/sub-origin-ip.
2.Add the leaf of pim-neighbor-auto-discovery: /configuration/ip-multicast/multicast/global/;' ;
  }

  revision 2021-03-17 {
    description '1.Add the leaf of entropy: /configuration/ip-multicast/multicast/biers/bier/;
2.Add the container of msid: /configuration/ip-multicast/multicast/;' ;
  }

  revision 2021-01-19 {
    description '1.Add the leaf of ecmp-select-reference-bandwidth: /configuration/ip-multicast/multicast/global/;
2.Add the leaf of ecmp-select-reference-bandwidth: /configuration/ip-multicast/vrf-multicasts/vrf-multicast/;' ;
  }

  revision 2020-12-22 {
    description 'Add the leaf of bsl: /configuration/ip-multicast/multicast/biers/bier;' ;
  }

  revision 2020-10-27 {
    description 'Add the containers /configuration/ip-multicast/multicast/spmsi-bier-infos; /configuration/ip-multicast/vrf-multicasts/vrf-multicast/spmsi-bier-infos;' ;
  }

  revision 2020-09-21 {
    description '1.modify the range of the leaf: /configuration/ip-multicast/multicast/global/multipath-sghash;
2.modify the range of the leaf: /configuration/ip-multicast/vrf-multicasts/vrf-multicast/multipath-sghash;
3.modify the name of enum item of the leaf: /configuration/ip-multicast/multicast/global/multipath-sghash;
4.modify the name of enum item of the leaf: /configuration/ip-multicast/vrf-multicasts/vrf-multicast/multipath-sghash.' ;
  }

  revision 2020-06-20 {
    description 'Add the BIER description:/state/multicast/public/mvpn/auto-discovery-routes;/state/multicast/private/mvpn/auto-discovery-routes.
Add the list /state/multicast/public/mroutes/mroute;/state/multicast/private/mroutes/mroute/bier-info.
Add the containers /state/multicast/public/mvpn/mribs;
/state/multicast/public/mvpn/public-auto-discovery-route;
/state/multicast/public/mvpn/public-ad-summary;
/state/multicast/public/mvpn/protect-groups;
Add the leafs /configuration/ip-multicast/vrf-multicasts/vrf-multicast/mvpn/bfd-enable;
/configuration/ip-multicast/vrf-multicasts/vrf-multicast/mvpn/bfd-template;
/configuration/ip-multicast/multicast/mvpn/bfd-enable;
/configuration/ip-multicast/multicast/mvpn/bfd-template;
/configuration/ip-multicast/multicast/global/mvpn-frr-policy;

/configuration/ip-multicast/multicast/global/mvpn-frr-egress-wtr;
Modify the DerivedType to string-all of the leafs:
/state/multicast/public/mvpn/mtunnels/mtunnel/vrf-name;
/state/multicast/public/mvpn/mtunnels/mtunnel/mrts/mrt/sub-vrf-name;
/state/multicast/private/mroutes/mroute/vpn-extranet/vrf-name;' ;
  }

  revision 2019-12-31 {
    description '1.modify the range and description of the leaf:/state/multicast/public/mvpn/mtunnels/mtunnel/vrf-name.' ;
  }

  revision 2019-11-28 {
    description 'Add the enumeration of the leaf:/configuration/ip-multicast/vrf-multicasts/vrf-multicast/mvpn-upstream-pe-select' ;
  }

  revision 2019-11-06 {
    description 'Add evpn-tunnel container to /configuration/ip-multicast/multicast;
Add the leafs of mvpn-spt-only/mvpn-send-site-only/mvpn-receive-site-only/mvpn-spmsi-tunnel: /configuration/ip-multicast/vrf-multicasts/vrf-multicast;' ;
  }

  revision 2019-09-29 {
    description 'Add nexthop-path-lists and rpf-vector-path-lists containers to /configuration/ip-multicast/multicast.' ;
  }

  revision 2019-08-29 {
    description 'Add router-id container to /configuration/ip-multicast/multicast and /configuration/ip-multicast/vrf-multicasts/vrf-multicast.' ;
  }

  revision 2019-07-15 {
    description '1.Add mvpn-wildcards-spmsi and mvpn-upstream-pe-select leaf nodes to /configuration/ip-multicast/vrf-multicasts/vrf-multicast.
2.Add mvpn-spmsi-aggregation container to /configuration/ip-multicast/vrf-multicasts/vrf-multicast.
3.Add mtunnels container to /state/multicast/public/mvpn.
4.Add mdt-tlvs container to /state/multicast/private/mvpn.' ;
  }

  revision 2019-04-12 {
    description 'Add the leafs of mvpn-frr-policy/mvpn-frr-detect-type/mvpn-frr-ingress-wtr/mvpn-frr-egress-wtr: /configuration/ip-multicast/vrf-multicasts/vrf-multicast;
Delete the mandatory attribute of the leafs local-adr and remote-addr: /configuration/ip-multicast/vrf-multicasts/vrf-multicast/mvpn-frr-peer-bfd-ipv4s/mvpn-frr-peer-bfd-ipv4;' ;
  }

  revision 2019-02-25 {
    description '1.Add the leaf of ecmp-select-cost-first: /configuration/ip-multicast/multicast/global/ecmp-select-cost-first;
2.Add the leaf of ecmp-select-cost-first: /configuration/ip-multicast/vrf-multicasts/vrf-multicast/pecmp-select-cost-first;' ;
  }

  revision 2019-01-21 {
    description '1.Add the leaf of mvpn-switchover-holdtime: /configuration/ip-multicast/vrf-multicasts/vrf-multicast/mvpn-switchover-holdtime;
2.Add the leaf of pim-neighbor-auto-discovery: /configuration/ip-multicast/vrf-multicasts/vrf-multicast/pim-neighbor-auto-discovery;
3.Add the container of p2mp-template: /configuration/ip-multicast/vrf-multicasts/vrf-multicast;
4.Add the container of mvpn-frr-peer-bfd-ipv4s: /configuration/ip-multicast/vrf-multicasts/vrf-multicast;' ;
  }

  revision 2018-08-10 {
    description 'Add the enumeration of the leaf: 
/configuration/ip-multicast/vrf-multicasts/vrf-multicast/mvpn/provider-tunnel;
/state/multicast/public/mvpn/instances/instance/mtunnel-type;

/state/multicast/public/mvpn/mtibs/mtib/tunnel-type;
/state/multicast/public/mvpn/segments/segment/in-tunnel-type;

/state/multicast/public/mvpn/segments/segment/out-tunnel-type;
/state/multicast/private/mvpn/instances/instance/mtunnel-type;
/state/multicast/private/mvpn/mtibs/mtib/tunnel-type;
Add the leaf of sub-domain-id: /configuration/ip-multicast/vrf-multicasts/vrf-multicast/mvpn/sub-domain-id;' ;
  }

  revision 2018-08-03 {
    description '1.modify the range of the leaf:/configuration/ip-multicast/multicast/global/mroute-limit.
2.modify the range of the leaf:/configuration/ip-multicast/multicast/global/mroute-limit-p-instance.
3.modify the range of the leaf:/configuration/ip-multicast/vrf-multicasts/vrf-multicast/mroute-limit-c-instance.' ;
  }

  revision 2017-11-14 {
    description 'Add the labels of 6100 for the features of mvpn-cross-as and mvpn-switch-threshold;' ;
  }

  revision 2017-11-02 {
    description 'modify the maxElements of bier:/configuration/ip-multicast/multicast/biers/bier' ;
  }

  revision 2017-10-18 {
    description '1.Add the container of biers: /configuration/ip-multicast/multicast.' ;
  }

  revision 2017-09-26 {
    description 'Add the enumeration of the leaf: /configuration/ip-multicast/vrf-multicasts/vrf-multicast/mvpn/provider-tunnel.' ;
  }

  revision 2017-06-21 {
    description '1.Add the feature of mvpn-switch-threshold.
2.Add If_Features of mvpn-switch-threshold for /configuration/ip-multicast/vrf-multicasts/vrf-multicast/mvpn-switchover-threshold;' ;
  }

  revision 2017-06-05 {
    description 'Add the leaf of mvpn-switchover-threshold-infinity: /configuration/ip-multicast/vrf-multicasts/vrf-multicast;
Add the labels of 15K and M6000-S for the feature of mvpn-cross-as;
Delete the If_Features for the leaf of /configuration/ip-multicast/vrf-multicasts/vrf-multicast/mvpn-switchover-interval;' ;
  }

  revision 2017-02-21 {
    description 'Add the container of mvpn-switchover-threshold: /configuration/ip-multicast/vrf-multicasts/vrf-multicast;' ;
  }

  revision 2017-01-09 {
    description '1.Add track-name leaf node to /configuration/ip-multicast/multicast/nexthops/nexthop.
2.Add track-name leaf node to /configuration/ip-multicast/vrf-multicasts/vrf-multicast/nexthops/nexthop.' ;
  }

  revision 2016-11-29 {
    description '1.add the containers of segment-border,mtunnel and mvpn: /configuration/ip-multicast/multicast;
2.add the leaves of bgp-auto-discovery-inter-as, bgp-auto-discovery-segmented and mvpn-switchover-interval: /configuration/ip-multicast/vrf-multicasts/vrf-multicast;
3.add the container of mvpn:/state/multicast/public;
4.obsolete the container of ad-routes and add the container of auto-discovery-routes: /state/multicast/private/mvpn;
5.modify the description and type of sub-vrf-name, add the leaf of sub-tunnel-state and select: /state/multicast/private/mvpn/mtibs/mtib/multi-imports/multi-import;
6.obsolete the container of spmsi-ads and add the container of spmsi-auto-discoveries: /state/multicast/private/mvpn/mribs/mrib/;
7.obsolete the container of leaf-ads and add the container of leaf-auto-discoveries: /state/multicast/private/mvpn/mribs/mrib/;
8.modify description of source-active, xg-join, sg-join: /state/multicast/private/mvpn/mribs/mrib/source-actives/source-active, /state/multicast/private/mvpn/mribs/mrib/xg-joins/xg-join and /state/multicast/private/mvpn/mribs/mrib/sg-joins/sg-join;
9.add the container of ad-summarys: /state/multicast/private/mvpn;
10.add the feature of mvpn-cross-as.' ;
  }

  revision 2015-12-09 {
    description '1.add containers of nexthop-fallbacks: /configuration/ip-multicast/multicast/ and /configuration/ip-multicast/vrf-multicasts/vrf-multicast/.
2.add the leaf of fallback-vrf: /state/multicast/public/mroutes/mroute/, /state/multicast/public/nexthops/nexthop/, /state/multicast/private/mroutes/mroute/ and /state/multicast/private/nexthops/nexthop/.
3.add the list of fallback-extranet: /state/multicast/public/mroutes/mroute/ and /state/multicast/private/mroutes/mroute/.
4.add the list of vpn-extranet: /state/multicast/private/mroutes/mroute/.' ;
  }

  revision 2015-11-26 {
    description '1.add mroute-limit-p-instance leaf node to /configuration/ip-multicast/multicast/global/.
2.add mroute-limit-c-instance leaf node to /configuration/ip-multicast/vrf-multicasts/vrf-multicast/.
3.modify the description of the leaf node: /configuration/ip-multicast/multicast/global/mroute-limit.
4.modify the description of the leaf node: /configuration/ip-multicast/multicast/global/downstream-limit.' ;
  }

  revision 2015-11-20 {
    description '1.modify the description of the leaf: /configuration/ip-multicast/multicast/golbal/rpf-proxy-vector.
2.add the leaf: /configuration/ip-multicast/multicast/global/rpf-proxy-vector-mbgp.' ;
  }

  revision 2015-10-17 {
    description 'modify the derivedtype of the leaf: /configuration/ip-multicast/vrf-multicasts/vrf-multicast/mdt-data/mdt-data/mdt-data-group/mask.' ;
  }

  revision 2015-08-28 {
    description '1:add the key of the list: /state/multicast/public/nexthops/nexthop;
2:delete the key of the list: /state/multicast/public/nexthops/nexthop/ecmp;
3:delete the leaf of the list: /state/multicast/public/nexthops/nexthop/ecmp/type;
4:add the key of the list: /state/multicast/private/nexthops/nexthop;
5:delete the key of the list: /state/multicast/private/nexthops/nexthop/ecmp;
6:delete the leaf of the list: /state/multicast/private/nexthops/nexthop/ecmp/type;
7:modify the description of the leaf: /state/multicast/public/mroutes/mroute/mrt-flag;
8:modify the description of the leaf: /state/multicast/private/mroutes/mroute/mrt-flag;' ;
  }

  revision 2015-08-12 {
    description '1.modify the description of the leaf: /state/multicast/public/mroutes/mroute/mrt-flag,iif-flag;
2.modify the description of the leaf: /state/multicast/public/mroutes/mroute/oif-list/oif-flag;
3.modify the description of the leaf: /state/multicast/private/mroutes/mroute/mrt-flag,iif-flag;
4.modify the description of the leaf: /state/multicast/private/mroutes/mroute/oif-list/oif-flag;
5:add the selects of the list: /state/multicast/public/briefs/brief;
6:add the selects of the list: /state/multicast/private/briefs/brief;
7:add the selects of the list: /state/multicast/private/nexthops/nexthop;
8:delete the range of the leaf: /state/multicast/private/mvpn/mtibs/mtib/tunnel-id;
9:delete the range of the leaf: /state/multicast/private/mvpn/mribs/mrib/rpf-tunnel-id;
10:add the container: /state/multicast/private/mvpn/ad-routes/ad-route/xg-joins;
11:add the container: /state/multicast/private/mvpn/mribs/mrib/xg-joins;
12.modify the description of the leaf: /state/multicast/private/mvpn/mdts/mdt/data-tree-num;
13.modify the description of the leaf: /state/multicast/private/mvpn/mdts/mdt/next-spmsi-index;
14.modify the description of the leaf: /state/multicast/private/mvpn/mdts/mdt/mtunnel-state;' ;
  }

  revision 2015-08-04 {
    description 'Remove the config of operation.' ;
  }

  revision 2015-03-31 {
    description 'Add state and operation of MULTICAST.' ;
  }

  revision 2015-03-04 {
    description '1.modify the description of the container and leaf: /configuration/ip-multicast/multicast/monitor ,flt,forward-policy,smdms,ttls ;
2.modify the description of the container and leaf: /configuration/vrf-multicasts/vrf-multicast/vrfname ,mdt-default,mdt-data,flt,forward-policys ;' ;
  }

  revision 2015-02-28 {
    description '1.Add slave leaf node to /configuration/ip-multicast/multicast/nexthops/nexthop.
2.Add slave leaf node to /configuration/ip-multicast/vrf-multicasts/vrf-multicast/nexthops/nexthop.' ;
  }

  revision 2015-02-11 {
    description '1.modify the length of the leaf: /configuration/ip-multicast/vrf-multicasts/vrf-multicast/vrfname ;' ;
  }

  revision 2015-01-20 {
    description '1.modify the range and description of the leaf: /configuration/ip-multicast/multicast/global/downstream-limit ;
2.modify the description of the leaf: /configuration/ip-multicast/multicast/global/mroute-limit ;' ;
  }

  revision 2014-09-01 {
    description '1.modify the range of the leaf: /configuration/ip-multicast/multicast/global/multipath-sghash;
2.modify the range of the leaf: /configuration/ip-multicast/vrf-multicasts/vrf-multicast/multipath-sghash;
3.modify the name of enum item of the leaf: /configuration/ip-multicast/multicast/global/multipath-sghash;
4.modify the name of enum item of the leaf: /configuration/ip-multicast/vrf-multicasts/vrf-multicast/multipath-sghash.' ;
  }

  revision 2014-07-25 {
    description "1.Add mdt-auto-discovery leaf node to /configuration/ip-multicast/vrf-multicasts/vrf-multicast.

    2./configuration/ip-multicast/vrf-multicasts/vrf-multicast/mdt-default's leaf node is changed to the choice node of mdt-default.

    3./configuration/ip-multicast/vrf-multicasts/vrf-multicast/mdt-data's leaf nodes are changed to the choice node of mdt-data." ;
  }

  revision 2014-04-10 {
    description 'modify the rang of mroute-limit from 1..131070 to 1..131072 
delete the default value of tos-value' ;
  }

  revision 2014-02-21 {
    description 'Initial version' ;
  }

  feature mvpn-cross-as {
    description 'Only for the use of HighEndPacket.15K,HighEndPacket.15K-GM,PC.MSE,6100 and MSE.M6000-S;add for the use of MSR.ASR,MSR.ZSRV2,PTN.6500,PTN.6700,PTN.65V5,PTN.61-SSP,PTN.61V5_1,HighEndRouter.T8000,MSE.M6000,MSE.xGW,FN.C600,FN.C89E,OTN.9700,OTN.8700,OTN.7000,MW.NR8000,V6000.vBRAS-C,V6000.CDB and ROSNG-V.COMMON.' ;
  }

  feature mvpn-switch-threshold {
    description 'Only for the use of HighEndPacket.15K,HighEndPacket.15K-GM,6100 and PC.MSE.' ;
  }

  container configuration {
    description 'Configuration model.' ;
    container ip-multicast {
      description 'Ip multicast' ;
      container multicast {
        description 'Multicast routing' ;
        presence multicast ;
        container global {
          description 'Global config' ;
          leaf mroute-limit {
            description "The max number of the multicast routes. It's top limit depends on ability of the device." ;
            type uint32 {
              range 1..262144 {
                description 'The max number of the multicast routes.' ;
              }

            }

          }

          leaf bgp-auto-discovery-inter-as {
            if-feature mvpn-cross-as ;

            description 'BGP auto-discovery of inter-AS MVPN.' ;
            type empty ;

            ncd:revise-date 2022-05-18 ;
          }

          leaf nsf-time {
            description 'NSF lifetime' ;
            type int32 {
              range 30..1800 {
                description 'NSF lifetime' ;
              }

            }

            units second ;
            default 60 ;
          }

          leaf downstream-limit {
            description "The max number of the multicast route forward table downstreams. It's top limit depends on ability of the device." ;
            type int32 {
              range 1..1024 {
                description 'The max number of the multicast route forward table downstreams.' ;
              }

            }

          }

          leaf damping-threshold {
            description 'Mroute flap damping threshold' ;
            type uint32 {
              range 2..100 {
                description 'Mroute flap damping threshold' ;
              }

            }

            default 5 ;
          }

          leaf multipath-sghash {
            description 'Multipath' ;
            type enumeration {
              enum s-hash-basic {
                value 1 ;
                description 'Multicast s-hash-basic' ;
              }

              enum sg-hash-basic {
                value 2 ;
                description 'Multicast s-g-hash basic' ;
              }

              enum sg-hash-nexthop-based {
                value 3 ;
                description 'Multicast s-g-hash next-hop-based' ;
              }

              enum sg-hash-balance {
                value 4 ;
                description 'Multicast s-g-hash balance' ;
              }

              enum g-hash-basic {
                value 5 ;
                description 'Multicast g-hash-basic' ;
              }

            }

          }

          leaf longest-match {
            description 'Nexthop longest match' ;
            type empty ;

          }

          leaf static-first {
            description 'Nexthop static first' ;
            type empty ;

          }

          leaf tos-value {
            description 'DSCP value' ;
            type uint8 {
              range 0..63 {
                description 'DSCP value' ;
              }

            }

          }

          leaf damping-enable {
            description 'Mroute flap damping enable' ;
            type empty ;

          }

          leaf rpf-proxy-vector {
            description 'RPF proxy vector for MDT.' ;
            type empty ;

          }

          leaf rpf-proxy-vector-mbgp {
            description 'RPF proxy vector ACL for MBGP.' ;
            type string {
              length 1..31 ;

            }

            ncd:revise-date 2015-11-20 ;
          }

          leaf mroute-limit-p-instance {
            description "The max number of the multicast routes attached to the global instance. It's top limit depends on ability of the device." ;
            type uint32 {
              range 1..262144 {
                description 'The max number of the multicast routes attached to the global instance.' ;
              }

            }

            ncd:revise-date 2015-11-26 ;
          }

          leaf ecmp-select-cost-first {
            description 'ECMP selecting of multicast route' ;
            type empty ;

            ncd:revise-date 2019-02-25 ;
          }

          leaf mvpn-frr-policy {
            description 'MVPN FRR policy.
2:hot-root-standby' ;
            type enumeration {
              enum hot-root-standby {
                value 2 ;
              }

            }

            ncd:revise-date 2020-06-20 ;
          }

          leaf mvpn-frr-detect-type {
            description 'MVPN FRR detect type.
1:stream detect' ;
            type enumeration {
              enum stream {
                value 1 ;
              }

            }

            ncd:revise-date 2021-07-01 ;
          }

          leaf mvpn-frr-egress-wtr {
            description 'Egress WTR delay time(second).' ;
            type uint16 {
              range 1..600 ;

            }

            ncd:revise-date 2020-06-20 ;
          }

          leaf ecmp-select-reference-bandwidth {
            description 'Select multicast nexthop based on reference bandwidth in terms of 10Gbps.' ;
            type empty ;

            ncd:revise-date 2021-01-19 ;
          }

          leaf mvpn-switchover-threshold-infinity {
            description 'ACL for MVPN tunnel never switch to data tree.' ;
            type string {
              length 1..31 ;

            }

            ncd:revise-date 2022-12-26 ;
          }

          leaf pim-neighbor-auto-discovery {
            description 'PIM neighbor auto discovery' ;
            type empty ;

            ncd:revise-date 2021-04-08 ;
          }

          leaf mvpn-frr-egress-wtr-infinity {
            description 'MVPN FRR egress WTR infinity.' ;
            type empty ;

            ncd:revise-date 2021-07-01 ;
          }

          leaf mvpn-frr-policy-acl {
            description 'MVPN FRR policy ACL.' ;
            type string {
              length 1..31 ;

            }

            ncd:revise-date 2021-07-01 ;
          }

          leaf mvpn-frr-support-ipmsi {
            description 'MVPN FRR support I-PMSI.' ;
            type empty ;

            ncd:revise-date 2022-12-26 ;
          }

          leaf mvpn-upstream-pe-select {
            description 'MVPN upstream PE select policy
1:lowest-addr-first
2:bgp-route-policy
3:bytewise-exclusive-or-hash' ;
            type enumeration {
              enum lowest-addr-first {
                value 1 ;
              }

              enum bgp-route-policy {
                value 2 ;
              }

              enum bytewise-exclusive-or-hash {
                value 3 ;
              }

            }

            ncd:revise-date 2021-10-13 ;
          }

          leaf mvpn-import-msdp {
            description 'MVPN SA import from MSDP.' ;
            type empty ;

            ncd:revise-date 2022-11-14 ;
          }

          leaf mvpn-export-msdp {
            description 'MVPN SA export to MSDP.' ;
            type empty ;

            ncd:revise-date 2022-11-14 ;
          }

          leaf mvpn-pim-hello-silent {
            description 'Disables the sending and receiving of PIM hello packets over MVPN tunnel.' ;
            type empty ;

            ncd:revise-date 2023-03-09 ;
          }

        }

        container monitor {
          description 'Monitor config' ;
          container intfs {
            description 'Monitor interface' ;
            list intf {
              description 'Monitor interface' ;
              max-elements 20 ;
              key intf-name ;
              leaf intf-name {
                description 'Interface name' ;
                type ncd:ifname {
                  length 1..31 ;

                }

              }

            }

          }

          container routers {
            description 'Monitor multicast routing table' ;
            list router {
              description 'Monitor multicast route table' ;
              max-elements 1000 ;
              key 'intf source group' ;
              leaf intf {
                description 'Interface name' ;
                type ncd:ifname {
                  length 1..31 ;

                }

              }

              leaf source {
                description 'Source address' ;
                type ncd:ipv4-address ;

              }

              leaf group {
                description 'Group address' ;
                type ncd:ipv4-address ;

              }

            }

          }

          container router-nointfs {
            description 'Monitor multicast route table' ;
            list router-nointf {
              description 'Monitor multicast route table' ;
              max-elements 1000 ;
              key 'source group' ;
              leaf source {
                description 'Source address' ;
                type ncd:ipv4-address ;

              }

              leaf group {
                description 'Group address' ;
                type ncd:ipv4-address ;

              }

            }

          }

        }

        container flt {
          description 'Filter config' ;
          container routes {
            description 'Monitor multicast route mode' ;
            list route {
              description 'Monitor multicast route mode' ;
              max-elements 1000 ;
              key 'source group' ;
              leaf source {
                description 'Source address' ;
                type ncd:ipv4-address ;

              }

              leaf group {
                description 'Group address' ;
                type ncd:ipv4-address ;

              }

              leaf flt-mode {
                description 'Route mode' ;
                type enumeration {
                  enum include {
                    value 0 ;
                    description 'Include mode' ;
                  }

                  enum exclude {
                    value 1 ;
                    description 'Exclude mode' ;
                  }

                }

                mandatory true ;
              }

            }

          }

          container rintfs {
            description 'Monitor multicast route interface' ;
            list rintf {
              description 'Monitor multicast route interface' ;
              max-elements 1000 ;
              key 'interface source group' ;
              leaf interface {
                description 'Interface name' ;
                type ncd:ifname {
                  length 1..31 ;

                }

              }

              leaf source {
                description 'Source address' ;
                type ncd:ipv4-address ;

              }

              leaf group {
                description 'Group address' ;
                type ncd:ipv4-address ;

              }

              leaf mr-type {
                description 'Route interface type' ;
                type enumeration {
                  enum add {
                    value 0 ;
                    description 'Route interface type' ;
                  }

                  enum delete {
                    value 1 ;
                    description 'Route interface type' ;
                  }

                }

                mandatory true ;
              }

            }

          }

          container fintfs {
            description 'Monitor multicast interface' ;
            list fintf {
              description 'Monitor multicast interface' ;
              max-elements 1000 ;
              key interface ;
              leaf interface {
                description 'Interface name' ;
                type ncd:ifname {
                  length 1..31 ;

                }

              }

              leaf mr-mode {
                description 'Route interface mode' ;
                type enumeration {
                  enum include {
                    value 0 ;
                    description 'Include mode' ;
                  }

                  enum exclude {
                    value 1 ;
                    description 'exclude mode' ;
                  }

                }

                mandatory true ;
              }

              leaf mr-type {
                description 'Route interface type' ;
                type enumeration {
                  enum add {
                    value 0 ;
                    description 'Add type' ;
                  }

                  enum delete {
                    value 1 ;
                    description 'Delete type' ;
                  }

                }

                mandatory true ;
              }

            }

          }

        }

        container forward-policy {
          description 'Forward policy' ;
          presence forward ;
          leaf acl {
            description 'Access list name' ;
            type string {
              length 1..31 ;

            }

          }

          leaf option {
            description 'Forward multicast traffic option' ;
            type enumeration {
              enum per-packet {
                value 1 ;
                description 'Forward multicast traffic by packet' ;
              }

              enum per-user {
                value 2 ;
                description 'Forward multicast traffic by user' ;
              }

              enum per-stream {
                value 3 ;
                description 'Forward multicast traffic by stream' ;
              }

            }

            mandatory true ;
          }

        }

        container biers {
          description 'Multicast BIER.' ;
          list bier {
            description 'Bit index explicit replication.' ;
            max-elements 256 ;
            key subdomain-id ;
            leaf subdomain-id {
              description 'Subdomain ID.' ;
              type uint8 {
                range 0..255 ;

              }

            }

            leaf bsl {
              description 'Bitstring length.' ;
              type enumeration {
                enum 256 {
                  value 3 ;
                }

                enum 512 {
                  value 4 ;
                }

              }

              ncd:revise-date 2020-12-22 ;
            }

            leaf entropy {
              description 'Entropy enable.' ;
              type empty ;

              ncd:revise-date 2021-03-17 ;
            }

            container bfer-indexs {
              description 'Bit forwarding egress routers index.' ;
              list bfer-index {
                description 'BFER index.' ;
                max-elements 65535 ;
                key 'index prefix' ;
                leaf index {
                  description 'BFER index.' ;
                  type uint32 {
                    range 1..100 ;

                  }

                }

                leaf prefix {
                  description 'BFER prefix.' ;
                  type ncd:ipv4-address ;

                }

              }

            }

          }

          ncd:revise-date 2017-10-18 ;
        }

        container nexthops {
          description 'Multicast static nexthop' ;
          list nexthop {
            description 'Multicast static nexthop' ;
            max-elements 3200 ;
            key 'intf-name ip-addr ip-mask next-hop-addr' ;
            leaf intf-name {
              description 'Interface name' ;
              type ncd:ifname {
                length 1..31 ;

              }

            }

            leaf ip-addr {
              description 'Prefix of destination IP address' ;
              type ncd:ipv4-address ;

            }

            leaf ip-mask {
              description 'Network mask' ;
              type ncd:ipv4-mask ;

            }

            leaf next-hop-addr {
              description 'Nexthop' ;
              type ncd:ipv4-address ;

            }

            leaf slave {
              description 'slave nexthop' ;
              type empty ;

            }

            leaf track-name {
              description 'Nexthop track name' ;
              type string {
                length 1..31 ;

              }

              ncd:revise-date 2017-01-09 ;
            }

            container nexthop-routes {
              description 'Select mroute' ;
              list nexthop-route {
                description 'Select mroute' ;
                max-elements 500 ;
                key 'ip-source ip-group' ;
                leaf ip-source {
                  description 'Source address' ;
                  type ncd:ipv4-address ;

                }

                leaf ip-group {
                  description 'Group address' ;
                  type ncd:ipv4-address ;

                }

              }

            }

          }

        }

        container nexthop-fallbacks {
          description 'Alternate routing table for nexthop lookup.' ;
          list nexthop-fallback {
            description 'Alternate routing table for nexthop lookup.' ;
            key 'ip-addr ip-mask' ;
            leaf ip-addr {
              description 'Prefix of destination IP address.' ;
              type ncd:ipv4-address ;

            }

            leaf ip-mask {
              description 'Network mask.' ;
              type ncd:ipv4-mask ;

            }

            leaf vrf-name {
              description 'VRF name.' ;
              type string {
                length 1..32 ;

              }

              mandatory true ;
            }

          }

          ncd:revise-date 2015-12-09 ;
        }

        container nexthop-path-lists {
          description 'Multicast static nexthop for RPF vector path list.' ;
          list nexthop-path-list {
            description 'Multicast static nexthop for RPF vector path list.' ;
            key 'ip-addr ip-mask' ;
            leaf ip-addr {
              description 'Prefix of destination IP address.' ;
              type ncd:ipv4-address ;

            }

            leaf ip-mask {
              description 'Network mask.' ;
              type ncd:ipv4-mask ;

            }

            leaf rpf-path-name {
              description 'RPF path name.' ;
              type string {
                length 1..31 ;

              }

              mandatory true ;
            }

          }

          ncd:revise-date 2019-09-29 ;
        }

        container smdms {
          description 'configure L2 oif mapping mode' ;
          list smdm {
            description 'configure L2 oif mapping mode' ;
            key intf-name ;
            leaf intf-name {
              description 'Interface name' ;
              type ncd:ifname ;

            }

          }

        }

        container ttls {
          description 'Multicast forwarding TTL limit' ;
          list ttl {
            description 'Multicast forwarding TTL limit' ;
            key intf-name ;
            leaf intf-name {
              description 'Interface name' ;
              type ncd:ifname ;

            }

            leaf ttl-num {
              description 'TTL limit' ;
              type int32 {
                range 1..255 ;

              }

              mandatory true ;
            }

          }

        }

        container boundarys {
          description 'Multicast forwarding boundary' ;
          list boundary {
            description 'Multicast forwarding boundary' ;
            max-elements 64 ;
            key intf-name ;
            leaf intf-name {
              description 'Interface name' ;
              type ncd:ifname {
                length 1..31 ;

              }

            }

            leaf aclname {
              description 'Access list name for group  prefix' ;
              type string {
                length 1..31 ;

              }

              mandatory true ;
            }

          }

        }

        container rejectinbounds {
          description 'Multicast reject inbound data' ;
          list rejectinbound {
            description 'Multicast reject inbound data' ;
            max-elements 64 ;
            key intfname ;
            leaf intfname {
              description 'Multicast reject inbound  interface name' ;
              type ncd:ifname ;

            }

          }

        }

        container segment-border {
          if-feature mvpn-cross-as ;

          description 'Border router for segmented multicast.' ;
          container intra-as {
            description 'Intra-AS segment border router.' ;
            presence intra-as ;
            leaf intra-as-enable {
              description 'Intra-AS enable.' ;
              type empty ;

              mandatory true ;
            }

            leaf intra-seg-nexthop {
              description 'Segmented nexthop of Intra-AS.' ;
              type empty ;

            }

          }

          container inter-as {
            description 'Inter-AS segment border router.' ;
            presence inter-as ;
            leaf inter-as-enable {
              description 'Inter-AS enable.' ;
              type empty ;

              mandatory true ;
            }

            leaf inter-seg-nexthop {
              description 'Segmented nexthop of Inter-AS.' ;
              type empty ;

            }

          }

          ncd:revise-date 2016-11-29 ;
        }

        container mtunnel {
          if-feature mvpn-cross-as ;

          description 'Interface used to set MDT source address' ;
          presence mtunnel ;
          leaf intf-name {
            description 'Interface name' ;
            type ncd:ifname {
              length 1..31 ;

            }

            mandatory true ;
          }

          ncd:revise-date 2016-11-29 ;
        }

        container mvpn {
          if-feature mvpn-cross-as ;

          description 'MVPN provider mtunnel' ;
          presence tunnel ;
          leaf provider-tunnel {
            description 'MVPN provider mtunnel' ;
            type enumeration {
              enum rsvp-te {
                value 1 ;
                description 'Provide rsvp-te  mtunnel' ;
              }

              enum mldp-p2mp {
                value 2 ;
                description 'Provide mldp-p2mp mtunnel' ;
              }

              enum bier {
                value 11 ;
                description 'Provide bier mtunnel' ;
              }

            }

            mandatory true ;
          }

          leaf sub-domain-id {
            description 'BIER sub-domain-id.' ;
            type uint8 {
              range 0..255 ;

            }

            ncd:revise-date 2020-06-20 ;
          }

          leaf bfd-enable {
            description 'BFD enable.' ;
            type empty ;

            ncd:revise-date 2020-06-20 ;
          }

          leaf bfd-template {
            description 'BFD template name.' ;
            type string {
              length 1..31 ;

            }

            ncd:revise-date 2020-06-20 ;
          }

          ncd:revise-date 2016-11-29 ;
        }

        container router-id {
          description 'Multicast router ID.' ;
          presence router-id ;
          leaf router-id {
            description 'Multicast router ID.' ;
            type ncd:ipv4-address ;

            mandatory true ;
          }

          ncd:revise-date 2019-08-29 ;
        }

        container rpf-vector-path-lists {
          description 'RPF proxy vector for path list.' ;
          list rpf-vector-path-list {
            description 'RPF proxy vector for path list.' ;
            key 'rpf-path-name rpf-path-index' ;
            leaf rpf-path-name {
              description 'RPF path name.' ;
              type string {
                length 1..31 ;

              }

            }

            leaf rpf-path-index {
              description 'RPF path index.' ;
              type uint32 {
                range 1..65535 ;

              }

            }

            leaf vector-address {
              description 'RPF vector address.' ;
              type ncd:ipv4-address ;

              mandatory true ;
            }

            leaf vector-type {
              description 'RPF vector type.' ;
              type enumeration {
                enum loose {
                  value 0 ;
                }

                enum strict {
                  value 4 ;
                }

              }

              mandatory true ;
            }

          }

          ncd:revise-date 2019-09-29 ;
        }

        container evpn-tunnel {
          description 'EVPN tunnel' ;
          presence evpn-tunnel ;
          leaf intf-name {
            description 'Interface name' ;
            type ncd:ifname {
              length 1..31 ;

            }

            mandatory true ;
          }

          ncd:revise-date 2019-11-06 ;
        }

        container spmsi-bier-infos {
          description 'MVPN S-PMSI BIER information.' ;
          list spmsi-bier-info {
            description 'MVPN S-PMSI BIER information.' ;
            key subdomain-id ;
            leaf subdomain-id {
              description 'Subdomain ID.' ;
              type uint8 {
                range 0..255 ;

              }

            }

            leaf acl-name {
              description 'ACL name.' ;
              type string {
                length 1..31 ;

              }

              mandatory true ;
            }

          }

          ncd:revise-date 2020-10-27 ;
        }

        container msid {
          description 'MSID.' ;
          presence msid ;
          leaf prefix-addr {
            description 'Prefix address.' ;
            type ncd:ipv6-address ;

            mandatory true ;
          }

          leaf prefix-len {
            description 'Prefix mask length.' ;
            type uint8 {
              range 32..108 ;

            }

            mandatory true ;
          }

          ncd:revise-date 2021-03-17 ;
        }

        container mroute-usage-rates {
          description 'Multicast route usage rate.' ;
          list mroute-usage-rate {
            description 'Multicast route usage rate.' ;
            key mroute-type ;
            leaf mroute-type {
              description 'Multicast route type.' ;
              type enumeration {
                enum xg {
                  value 1 ;
                  description 'The multicast (*,G) route' ;
                }

                enum sg {
                  value 2 ;
                  description 'The multicast (S,G) route' ;
                }

                enum total {
                  value 3 ;
                  description 'The multicast total route' ;
                }

              }

            }

            leaf threshold {
              description 'Multicast route generation threshold to set.' ;
              type uint32 {
                range 1..100 {
                  description 'Threshold value (%) at which to give a warning.' ;
                }

              }

              default 80 ;
            }

            leaf clear-threshold {
              description 'Multicast route clearance threshold to set.' ;
              type uint32 {
                range 1..100 {
                  description 'Threshold value (%) at which to clear the warning.' ;
                }

              }

              default 72 ;
            }

          }

          ncd:revise-date 2023-09-11 ;
        }

      }

      container vrf-multicasts {
        description 'VRF instance' ;
        list vrf-multicast {
          description 'VRF instance' ;
          key vrfname ;
          leaf vrfname {
            description 'VRF name' ;
            type string {
              length 1..32 ;

            }

          }

          leaf longest-match {
            description 'Nexthop longest match' ;
            type empty ;

          }

          leaf static-first {
            description 'Nexthop static first' ;
            type empty ;

          }

          leaf multipath-sghash {
            description 'Multipath' ;
            type enumeration {
              enum s-hash-basic {
                value 1 ;
                description 'Multicast s-hash' ;
              }

              enum sg-hash-basic {
                value 2 ;
                description 'Multicast s-g-hash basic' ;
              }

              enum sg-hash-nexthop-based {
                value 3 ;
                description 'Multicast s-g-hash next-hop-based' ;
              }

              enum sg-hash-balance {
                value 4 ;
                description 'Multicast s-g-hash balance' ;
              }

              enum g-hash-basic {
                value 5 ;
                description 'Multicast g-hash-basic' ;
              }

            }

          }

          leaf mdt-auto-discovery {
            description 'MDT auto discovery' ;
            type empty ;

          }

          leaf mroute-limit-c-instance {
            description "The max number of the multicast routes attached to the VRF instance. It's top limit depends on ability of the device." ;
            type uint32 {
              range 1..262144 {
                description 'The max number of the multicast routes attached to the VRF instance.' ;
              }

            }

            ncd:revise-date 2015-11-26 ;
          }

          leaf bgp-auto-discovery-inter-as {
            if-feature mvpn-cross-as ;

            description 'BGP auto-discovery of inter-AS MVPN.' ;
            type empty ;

            ncd:revise-date 2016-11-29 ;
          }

          leaf bgp-auto-discovery-segmented {
            if-feature mvpn-cross-as ;

            description 'BGP auto-discovery of segmented multicast.' ;
            type empty ;

            ncd:revise-date 2016-11-29 ;
          }

          leaf mvpn-switchover-holdtime {
            description 'Holdtime which data tree switch back to default tree' ;
            type uint16 {
              range 30..600 ;

            }

            ncd:revise-date 2019-01-21 ;
          }

          leaf mvpn-switchover-interval {
            description 'Delay time which default tree switch to data tree' ;
            type uint16 {
              range 3..65535 ;

            }

            ncd:revise-date 2016-11-29 ;
          }

          leaf mvpn-switchover-threshold-infinity {
            description 'ACL for MVPN tunnel never switch to data tree.' ;
            type string {
              length 1..31 ;

            }

            ncd:revise-date 2017-06-05 ;
          }

          leaf pim-neighbor-auto-discovery {
            description 'PIM neighbor auto discovery' ;
            type empty ;

            ncd:revise-date 2019-01-21 ;
          }

          leaf ecmp-select-cost-first {
            description 'ECMP selecting of multicast route' ;
            type empty ;

            ncd:revise-date 2019-02-25 ;
          }

          leaf mvpn-upstream-pe-select {
            description 'MVPN upstream PE select policy
1:lowest-addr-first
2:bgp-route-policy
3:bytewise-exclusive-or-hash' ;
            type enumeration {
              enum lowest-addr-first {
                value 1 ;
              }

              enum bgp-route-policy {
                value 2 ;
              }

              enum bytewise-exclusive-or-hash {
                value 3 ;
              }

            }

            ncd:revise-date 2019-07-15 ;
          }

          leaf mvpn-frr-policy {
            description 'MVPN FRR policy.
1:warm-root-standby
2:hot-root-standby' ;
            type enumeration {
              enum warm-root-standby {
                value 1 ;
              }

              enum hot-root-standby {
                value 2 ;
              }

            }

            ncd:revise-date 2019-04-12 ;
          }

          leaf mvpn-frr-detect-type {
            description 'MVPN FRR detect type.
1:stream detect
2:peer BFD detect' ;
            type enumeration {
              enum stream {
                value 1 ;
              }

              enum peer-bfd {
                value 2 ;
              }

            }

            ncd:revise-date 2019-04-12 ;
          }

          leaf mvpn-frr-ingress-wtr {
            description 'Ingress WTR delay time(second).' ;
            type uint16 {
              range 1..600 ;

            }

            ncd:revise-date 2019-04-12 ;
          }

          leaf mvpn-frr-egress-wtr {
            description 'Egress WTR delay time(second).' ;
            type uint16 {
              range 1..600 ;

            }

            ncd:revise-date 2019-04-12 ;
          }

          leaf mvpn-wildcards-spmsi {
            description 'MVPN wildcards SPMSI.' ;
            type empty ;

            ncd:revise-date 2019-07-15 ;
          }

          leaf mvpn-spt-only {
            description 'MVPN spt only mode' ;
            type empty ;

            ncd:revise-date 2019-11-06 ;
          }

          leaf mvpn-send-site-only {
            description 'MVPN send site only mode' ;
            type empty ;

            ncd:revise-date 2019-11-06 ;
          }

          leaf mvpn-receive-site-only {
            description 'MVPN receive site only mode' ;
            type empty ;

            ncd:revise-date 2019-11-06 ;
          }

          leaf mvpn-spmsi-tunnel {
            description 'MVPN SPMSI mtunnel' ;
            type enumeration {
              enum rsvp-te {
                value 1 ;
                description 'Provide rsvp-te  mtunnel' ;
              }

              enum mldp-p2mp {
                value 2 ;
                description 'Provide mldp-p2mp mtunnel' ;
              }

              enum ingress-replication {
                value 6 ;
                description 'Provide ingress replication mtunnel' ;
              }

            }

            ncd:revise-date 2019-11-06 ;
          }

          leaf ecmp-select-reference-bandwidth {
            description 'Select multicast nexthop based on reference bandwidth in terms of 10Gbps.' ;
            type empty ;

            ncd:revise-date 2021-01-19 ;
          }

          leaf mvpn-frr-egress-wtr-infinity {
            description 'MVPN FRR egress WTR infinity.' ;
            type empty ;

            ncd:revise-date 2021-07-01 ;
          }

          leaf mvpn-frr-policy-acl {
            description 'MVPN FRR policy ACL.' ;
            type string {
              length 1..31 ;

            }

            ncd:revise-date 2021-07-01 ;
          }

          leaf mvpn-frr-support-ipmsi {
            description 'MVPN FRR support I-PMSI.' ;
            type empty ;

            ncd:revise-date 2022-12-26 ;
          }

          leaf mvpn-source-active-acl {
            description 'MVPN source active A-D route ACL.' ;
            type string {
              length 1..31 ;

            }

            ncd:revise-date 2022-01-04 ;
          }

          leaf mvpn-import-msdp {
            description 'MVPN SA import from MSDP.' ;
            type empty ;

            ncd:revise-date 2021-12-08 ;
          }

          leaf mvpn-export-msdp {
            description 'MVPN SA export to MSDP.' ;
            type empty ;

            ncd:revise-date 2022-11-14 ;
          }

          leaf mvpn-pim-hello-silent {
            description 'Disables the sending and receiving of PIM hello packets over MVPN tunnel.' ;
            type empty ;

            ncd:revise-date 2023-03-09 ;
          }

          container mvpn-switchover-threshold {
            if-feature mvpn-switch-threshold ;

            description 'MVPN tunnel switchover threshold.' ;
            presence mvpn-switchover-threshold ;
            leaf threshold {
              description 'MVPN tunnel switchover threshold(Kbps).' ;
              type uint32 {
                range 1..4294967295 ;

              }

              mandatory true ;
            }

            leaf acl {
              description 'ACL for MVPN tunnel switchover.' ;
              type string {
                length 1..31 ;

              }

              mandatory true ;
            }

            ncd:revise-date 2017-02-21 ;
          }

          container mtunnel {
            description 'Interface used to set MDT source address' ;
            presence mtunnel ;
            leaf intf-name {
              description 'Interface name' ;
              type ncd:ifname {
                length 1..31 ;

              }

              mandatory true ;
            }

          }

          container mdt-default {
            description 'Default MDT' ;
            choice mdt-default {
              description 'Default MDT' ;
              case mdt-default-group {
                description 'MDT default group' ;
                leaf group {
                  description 'IP multicast group address' ;
                  type ncd:ipv4-address-none-zero ;

                  mandatory true ;
                }

              }

              case mpls-mldp {
                description 'MDT P2MP mLDP default distribution tree' ;
                container mdt-defaults {
                  description 'Default MDT' ;
                  list mdt-default {
                    description 'Default MDT' ;
                    max-elements 3200 ;
                    key root-addr ;
                    leaf root-addr {
                      description 'Remote root address' ;
                      type ncd:ipv4-address-none-zero ;

                    }

                  }

                }

              }

            }

          }

          container mdt-data {
            description 'Data MDT' ;
            choice mdt-data {
              description 'Data MDT' ;
              case mdt-data-group {
                description 'MDT data group' ;
                leaf acl {
                  description 'Access list name' ;
                  type string {
                    length 1..31 ;

                  }

                }

                leaf group {
                  description 'IP multicast group address' ;
                  type ncd:ipv4-address-none-zero ;

                  mandatory true ;
                }

                leaf mask {
                  description 'Wildcard bits' ;
                  type ncd:ipv4-imask ;

                  mandatory true ;
                }

              }

              case mpls-mldp {
                description 'MDT P2MP mLDP data distribution tree' ;
                leaf num-tree {
                  description 'Data tree number' ;
                  type uint32 {
                    range 1..5000 {
                      description 'MDT data num tree' ;
                    }

                  }

                  mandatory true ;
                }

              }

            }

          }

          container flt {
            description 'Filter config' ;
            container rintfs {
              description 'Monitor multicast route interface' ;
              list rintf {
                description 'Monitor multicast route interface' ;
                max-elements 1000 ;
                key 'interface source group' ;
                leaf interface {
                  description 'Interface name' ;
                  type ncd:ifname {
                    length 1..31 ;

                  }

                }

                leaf source {
                  description 'Source address' ;
                  type ncd:ipv4-address ;

                }

                leaf group {
                  description 'Group address' ;
                  type ncd:ipv4-address ;

                }

                leaf type {
                  description 'Route interface type' ;
                  type enumeration {
                    enum add {
                      value 0 ;
                      description 'Route interface type' ;
                    }

                    enum delete {
                      value 1 ;
                      description 'Route interface type' ;
                    }

                  }

                  mandatory true ;
                }

              }

            }

            container fintfs {
              description 'Monitor multicast interface' ;
              list fintf {
                description 'Monitor multicast interface' ;
                max-elements 1000 ;
                key interface ;
                leaf interface {
                  description 'Interface name' ;
                  type ncd:ifname {
                    length 1..31 ;

                  }

                }

                leaf mode {
                  description 'Route interface mode' ;
                  type enumeration {
                    enum include {
                      value 0 ;
                      description 'Route interface mode' ;
                    }

                    enum exclude {
                      value 1 ;
                      description 'Route interface mode' ;
                    }

                  }

                  mandatory true ;
                }

                leaf type {
                  description 'Route interface type' ;
                  type enumeration {
                    enum add {
                      value 0 ;
                      description 'Add type' ;
                    }

                    enum delete {
                      value 1 ;
                      description 'Delete type' ;
                    }

                  }

                  mandatory true ;
                }

              }

            }

            container routes {
              description 'Monitor multicast route mode' ;
              list route {
                description 'Monitor multicast route mode' ;
                max-elements 1000 ;
                key 'source group' ;
                leaf source {
                  description 'Source address' ;
                  type ncd:ipv4-address ;

                }

                leaf group {
                  description 'Group address' ;
                  type ncd:ipv4-address ;

                }

                leaf mode {
                  description 'Route mode' ;
                  type enumeration {
                    enum include {
                      value 0 ;
                      description 'Include mode' ;
                    }

                    enum exclude {
                      value 1 ;
                      description 'Exclude mode' ;
                    }

                  }

                  mandatory true ;
                }

              }

            }

          }

          container forward-policys {
            description 'Forward policy' ;
            presence forward ;
            leaf acl {
              description 'Access list name' ;
              type string {
                length 1..31 ;

              }

            }

            leaf options {
              description 'Forward multicast traffic option' ;
              type enumeration {
                enum per-packet {
                  value 1 ;
                  description 'Forward multicast traffic by packet' ;
                }

                enum per-user {
                  value 2 ;
                  description 'Forward multicast traffic by user' ;
                }

                enum per-stream {
                  value 3 ;
                  description 'Forward multicast traffic by stream' ;
                }

              }

              mandatory true ;
            }

          }

          container nexthops {
            description 'Multicast static nexthop' ;
            list nexthop {
              description 'Multicast static nexthop' ;
              max-elements 3200 ;
              key 'intf-name ip-addr ip-mask next-hop-addr' ;
              leaf intf-name {
                description 'Interface name' ;
                type ncd:ifname {
                  length 1..31 ;

                }

              }

              leaf ip-addr {
                description 'Prefix of destination IP address' ;
                type ncd:ipv4-address ;

              }

              leaf ip-mask {
                description 'Network mask' ;
                type ncd:ipv4-mask ;

              }

              leaf next-hop-addr {
                description 'Nexthop' ;
                type ncd:ipv4-address ;

              }

              leaf slave {
                description 'slave nexthop' ;
                type empty ;

              }

              leaf track-name {
                description 'Nexthop track name' ;
                type string {
                  length 1..31 ;

                }

                ncd:revise-date 2017-01-09 ;
              }

            }

          }

          container nexthop-fallbacks {
            description 'Alternate routing table for nexthop lookup.' ;
            list nexthop-fallback {
              description 'Alternate routing table for nexthop lookup.' ;
              key 'ip-addr ip-mask' ;
              leaf ip-addr {
                description 'Prefix of destination IP address.' ;
                type ncd:ipv4-address ;

              }

              leaf ip-mask {
                description 'Network mask.' ;
                type ncd:ipv4-mask ;

              }

              container instance {
                description 'Fallback instance.' ;
                choice instance {
                  description 'Fallback instance.' ;
                  mandatory true ;
                  case p-instance {
                    description 'Public instance.' ;
                    leaf global {
                      description 'Public instance.' ;
                      type empty ;

                    }

                  }

                  case c-instance {
                    description 'Customer instance.' ;
                    leaf vrf-name {
                      description 'VRF name.' ;
                      type string {
                        length 1..32 ;

                      }

                    }

                  }

                }

              }

            }

            ncd:revise-date 2015-12-09 ;
          }

          container mvpn {
            description 'MVPN provider mtunnel' ;
            presence tunnel ;
            leaf provider-tunnel {
              description 'MVPN provider mtunnel' ;
              type enumeration {
                enum rsvp-te {
                  value 1 ;
                  description 'Provide rsvp-te  mtunnel' ;
                }

                enum mldp-p2mp {
                  value 2 ;
                  description 'Provide mldp-p2mp mtunnel' ;
                }

                enum ingress-replication {
                  value 6 ;
                  description 'Provide ingress replication mtunnel' ;
                }

                enum bier {
                  value 11 ;
                  description 'Provide bier mtunnel' ;
                }

                enum static-vxlan {
                  value 126 ;
                  description 'Provide static-vxlan mtunnel' ;
                }

              }

              mandatory true ;
            }

            leaf sub-domain-id {
              description 'BIER sub-domain-id.' ;
              type uint8 {
                range 0..255 ;

              }

              ncd:revise-date 2018-08-10 ;
            }

            leaf bfd-enable {
              description 'BFD enable.' ;
              type empty ;

              ncd:revise-date 2020-06-20 ;
            }

            leaf bfd-template {
              description 'BFD template name.' ;
              type string {
                length 1..31 ;

              }

              ncd:revise-date 2020-06-20 ;
            }

            leaf leaf-info-required {
              description 'Leaf Information Required bit set in Intra-AS I-PMSI A-D route.' ;
              type empty ;

              ncd:revise-date 2025-02-27 ;
            }

          }

          container p2mp-template {
            description 'MVPN TE P2MP template' ;
            presence p2mp-template ;
            leaf name {
              description 'Template name(1-32 characters)' ;
              type string {
                length 1..32 {
                  description 'Template name' ;
                }

              }

              mandatory true ;
            }

            ncd:revise-date 2019-01-21 ;
          }

          container mvpn-frr-peer-bfd-ipv4s {
            description 'MVPN frr peer-bfd config information' ;
            list mvpn-frr-peer-bfd-ipv4 {
              description 'MVPN frr peer-bfd config information' ;
              key 'local-addr remote-addr' ;
              leaf local-addr {
                description 'Specify local IPv4 address' ;
                type ncd:ipv4-address-none-zero ;

              }

              leaf remote-addr {
                description 'Specify remote IPv4 address' ;
                type ncd:ipv4-address-none-zero ;

              }

            }

            ncd:revise-date 2019-01-21 ;
          }

          container mvpn-spmsi-aggregation {
            description 'MVPN SPMSI aggregation config information.' ;
            choice mvpn-spmsi-aggregation {
              description 'MVPN SPMSI aggregation config information.' ;
              case type {
                description 'MVPN SPMSI aggregation source-based.' ;
                leaf type {
                  description 'MVPN SPMSI aggregation type.' ;
                  type enumeration {
                    enum source-based {
                      value 1 ;
                    }

                  }

                  mandatory true ;
                }

              }

              case count {
                description 'MVPN SPMSI aggregation count.' ;
                leaf count {
                  description 'MVPN SPMSI aggregation count.' ;
                  type uint32 {
                    range 1..131072 ;

                  }

                  mandatory true ;
                }

              }

            }

            ncd:revise-date 2019-07-15 ;
          }

          container router-id {
            description 'Multicast router ID.' ;
            presence router-id ;
            leaf router-id {
              description 'Multicast router ID.' ;
              type ncd:ipv4-address ;

              mandatory true ;
            }

            ncd:revise-date 2019-08-29 ;
          }

          container spmsi-bier-infos {
            description 'MVPN S-PMSI BIER information.' ;
            list spmsi-bier-info {
              description 'MVPN S-PMSI BIER information.' ;
              key subdomain-id ;
              leaf subdomain-id {
                description 'Subdomain ID.' ;
                type uint8 {
                  range 0..255 ;

                }

              }

              leaf acl-name {
                description 'ACL name.' ;
                type string {
                  length 1..31 ;

                }

                mandatory true ;
              }

            }

            ncd:revise-date 2020-10-27 ;
          }

          container mvpn-spmsi-policys {
            description 'MVPN S-PMSI policy for group prefix and source prefix.' ;
            list mvpn-spmsi-policy {
              description 'MVPN S-PMSI policy for group prefix and source prefix.' ;
              key 'group-addr group-mask source-addr source-mask' ;
              leaf group-addr {
                description 'Group address.' ;
                type ncd:ipv4-address ;

              }

              leaf group-mask {
                description 'Group mask.' ;
                type ncd:ipv4-mask ;

              }

              leaf source-addr {
                description 'Source address.' ;
                type ncd:ipv4-address ;

              }

              leaf source-mask {
                description 'Source mask.' ;
                type ncd:ipv4-mask ;

              }

              choice policy {
                description 'MVPN S-PMSI policy.' ;
                mandatory true ;
                case tunnel-type {
                  description 'MVPN S-PMSI tunnel type.' ;
                  leaf tunnel-type {
                    description 'MVPN S-PMSI tunnel type.' ;
                    type enumeration {
                      enum rsvp-te {
                        value 1 ;
                      }

                      enum mldp-p2mp {
                        value 2 ;
                      }

                    }

                    mandatory true ;
                  }

                  leaf template-name {
                    description 'Template name(1-32 characters).' ;
                    type string {
                      length 1..32 ;

                    }

                  }

                  leaf threshold-value {
                    description 'MVPN tunnel switchover threshold(Kbps).' ;
                    type uint32 {
                      range 1..4294967295 ;

                    }

                  }

                }

                case threshold {
                  description 'MVPN tunnel switchover threshold(Kbps).' ;
                  leaf threshold {
                    description 'MVPN tunnel switchover threshold(Kbps).' ;
                    type uint32 {
                      range 1..4294967295 ;

                    }

                    mandatory true ;
                  }

                }

                case threshold-infinity {
                  description 'MVPN tunnel never switch to data tree.' ;
                  leaf threshold-infinity {
                    description 'MVPN tunnel never switch to data tree.' ;
                    type empty ;

                    mandatory true ;
                  }

                }

              }

            }

            ncd:revise-date 2022-02-10 ;
          }

        }

      }

    }

  }

  container state {
    config false ;
    description 'State module.' ;
    container multicast {
      description 'Multicast module show info.' ;
      container public {
        description 'Public mode of multicast' ;
        container mroutes {
          description 'Multicast route information.' ;
          list mroute {
            description 'Multicast route information.' ;
            key 'group-addr source-addr' ;
            leaf group-addr {
              description 'Group address' ;
              type ncd:ipv4-address ;

            }

            leaf source-addr {
              description 'Source address' ;
              type ncd:ipv4-address ;

            }

            leaf rp-addr {
              description 'RP address' ;
              type ncd:ipv4-address ;

            }

            leaf iif-name {
              description 'Incoming interface name' ;
              type ncd:string-all {
                length 0..31 ;

              }

            }

            leaf secondary-rpf-intf {
              description 'Secondary RPF interface name' ;
              type ncd:string-all {
                length 0..31 ;

              }

            }

            leaf mrt-flag {
              description 'Mroute flag.
NS:SPT upsend,RT:Reg upsend,MT:Tunnel,NTP:NTP join,DPU:Damping enable,DPD:Damping del,B:Bidir,SU:Slave in use.' ;
              type ncd:string-all {
                length 0..31 ;

              }

            }

            leaf mrt-type {
              description 'Mroute type:"STATIC","DYNAMIC".' ;
              type ncd:string-all {
                length 0..19 ;

              }

            }

            leaf iif-flag {
              description 'Incoming interface flag.
NS:SPT upsend.' ;
              type ncd:string-all {
                length 0..31 ;

              }

            }

            leaf fallback-vrf {
              description 'The upstream VRF name of mroute.' ;
              type string {
                length 0..32 ;

              }

              ncd:revise-date 2015-12-09 ;
            }

            list oif-list {
              description 'Downstream interface list' ;
              key 'oif-name type' ;
              leaf oif-name {
                description 'Downstream interface name' ;
                type ncd:string-all {
                  length 0..31 ;

                }

              }

              leaf type {
                description 'Save the breakpoint types of the outcoming interface, not used for the query criteria.
For xg,1:mroute outcoming interface,2:outcoming interface added by xg filter,3:outcoming interface added by xg global filter.
For sg,1:mroute outcoming interface,2:outcoming interface added by sg filter,3:outcoming interface added by xg filter,4:outcoming interface added by sg global filter.' ;
                type int32 ;

              }

              leaf oif-flag {
                description 'Downstream interface flag.
F:Forward,RT:Reg upsend,MT:Tunnel,S:Syn mrt,DF:DF,FLT:Flt add, FD:Flt del.' ;
                type ncd:string-all ;

              }

              leaf mvrf-name {
                description 'Mdt route VRF name' ;
                type ncd:string-all {
                  length 0..32 ;

                }

              }

              ncd:select oif-name ;
            }

            list fallback-extranet {
              description 'Fallback extranet receiver info.' ;
              key vrf-name ;
              leaf vrf-name {
                description 'VRF name.' ;
                type string {
                  length 1..32 ;

                }

              }

              ncd:revise-date 2015-12-09 ;
            }

            list bier-info {
              description 'Bit index explicit replication information.' ;
              key 'subdomain-id bfer-prefix' ;
              leaf subdomain-id {
                description 'Subdomain ID.' ;
                type uint8 {
                  range 0..255 ;

                }

              }

              leaf bfer-prefix {
                description 'BFER prefix.' ;
                type string {
                  length 1..39 ;

                }

              }

              leaf bfr-id {
                description 'BFR ID.' ;
                type uint16 {
                  range 0..65535 ;

                }

              }

              ncd:revise-date 2020-06-20 ;
              ncd:select bfer-prefix ;
            }

            ncd:select "group-addr source-addr iif-name" ;
            ncd:select "group-addr source-addr" ;
            ncd:select "group-addr iif-name" ;
            ncd:select "source-addr iif-name" ;
            ncd:select source-addr ;
            ncd:select group-addr ;
            ncd:select iif-name ;
          }

        }

        container summary {
          description 'The summary information of mroute' ;
          leaf xg-count {
            description 'XG summary' ;
            type uint32 ;

          }

          leaf sg-count {
            description 'SG summary' ;
            type uint32 ;

          }

          leaf mroute-count {
            description 'XG and SG mroute summary' ;
            type uint32 ;

          }

        }

        container briefs {
          description 'The brief information of mroute' ;
          list brief {
            description 'The brief information of mroute' ;
            key 'group source' ;
            leaf group {
              description 'Group address' ;
              type ncd:ipv4-address ;

            }

            leaf source {
              description 'Source address' ;
              type ncd:ipv4-address ;

            }

            leaf type {
              description 'Mroute type:"STATIC","DYNAMIC".' ;
              type string {
                length 1..11 ;

              }

            }

            ncd:select "group source" ;
            ncd:select group ;
            ncd:select source ;
          }

        }

        container nexthops {
          description 'The nexthop information of mroute' ;
          list nexthop {
            description 'The nexthop information of mroute' ;
            key 'dest-addr type' ;
            leaf dest-addr {
              description 'Destination address' ;
              type ncd:ipv4-address ;

            }

            leaf type {
              description 'Type:"Mstatic nexthop","Mdt nexthop","Mbgp nexthop","Migp nexthop","Rtm nexthop"' ;
              type ncd:string-all {
                length 0..31 ;

              }

              ncd:revise-date 2015-08-28 ;
            }

            leaf time {
              description 'Nexthop create time' ;
              type ncd:string-all {
                length 0..31 ;

              }

            }

            leaf user {
              description 'Nexthop user:"PIM","DM","MSDP","MSN","MVPN"' ;
              type ncd:string-all {
                length 0..31 ;

              }

            }

            leaf metric {
              description 'Metric' ;
              type uint32 ;

            }

            leaf preference {
              description 'Preference' ;
              type uint32 ;

            }

            leaf mask-len {
              description 'Mask length' ;
              type uint16 ;

            }

            leaf flag {
              description 'Flag.
L:Local,C:Connect,UNR:Unreachable unicast,CTOP:Across the backbone' ;
              type ncd:string-all {
                length 0..31 ;

              }

            }

            leaf fallback-vrf {
              description 'The VRF name of fallback nexthop.' ;
              type string {
                length 0..32 ;

              }

              ncd:revise-date 2015-12-09 ;
            }

            list ecmp {
              description 'ECMP information' ;
              key 'nexthop oif-name' ;
              leaf nexthop {
                description 'Nexthop address' ;
                type string {
                  length 1..39 ;

                }

              }

              leaf oif-name {
                description 'Downstream interface name' ;
                type ncd:string-all {
                  length 0..31 ;

                }

              }

              leaf oif-flag {
                description 'Downstream interface flag.
Mdt:Mdt nexthop
Down:Interface down
S:Slave 
M:Master' ;
                type ncd:string-all {
                  length 0..31 ;

                }

              }

              leaf remote-pe {
                description 'Remote PE address.' ;
                type string {
                  length 0..39 ;

                }

                ncd:revise-date 2021-08-16 ;
              }

              leaf real-nexthop {
                description 'Real nexthop address.' ;
                type string {
                  length 0..39 ;

                }

              }

              ncd:select "nexthop oif-name" ;
            }

            ncd:select dest-addr ;
          }

        }

        container mvpn {
          if-feature mvpn-cross-as ;

          description 'MVPN module show info.' ;
          container instance {
            description 'MVPN instance information.' ;
            leaf rd {
              description 'RD.' ;
              type string {
                length 0..23 ;

              }

              ncd:revise-date 2021-04-08 ;
            }

            leaf import-rt {
              description 'MVPN import RT.' ;
              type string {
                length 0..63 ;

              }

              ncd:revise-date 2021-04-08 ;
            }

            leaf origin-ip {
              description 'Origin IP address.' ;
              type string {
                length 0..39 ;

              }

            }

            leaf te-id {
              description 'TE root ID.' ;
              type string {
                length 0..39 ;

              }

            }

            leaf origin-state {
              description 'Origin state.
"Un-routable"
"Routable,Local"
"Routable,Not Local"' ;
              type ncd:string-all {
                length 0..23 ;

              }

            }

            leaf te-state {
              description 'TE state.
"in-use"
"Not in-use"' ;
              type ncd:string-all {
                length 0..15 ;

              }

            }

            leaf mtunnel-type {
              description 'Mtunnel type.
0:No-Tunnel
1:TE-P2MP
2:mLDP-P2MP
3:PIM-SSM
4:PIM-SM
5:PIM-BIDIR
6:INGRESS-RPL
7:mLDP-MP2MP
8:PIM-MDT
11:BIER' ;
              type enumeration {
                enum No-Tunnel {
                  value 0 ;
                }

                enum TE-P2MP {
                  value 1 ;
                }

                enum mLDP-P2MP {
                  value 2 ;
                }

                enum PIM-SSM {
                  value 3 ;
                }

                enum PIM-SM {
                  value 4 ;
                }

                enum PIM-BIDIR {
                  value 5 ;
                }

                enum INGRESS-RPL {
                  value 6 ;
                }

                enum mLDP-MP2MP {
                  value 7 ;
                }

                enum PIM-MDT {
                  value 8 ;
                }

                enum BIER {
                  value 11 ;
                }

              }

            }

            leaf route-state {
              description 'Route state.
0:Disable
1:Enable' ;
              type enumeration {
                enum Disable {
                  value 0 ;
                }

                enum Enable {
                  value 1 ;
                }

              }

            }

            leaf mldp-state {
              description 'MLDP state.
0:Disable
1:Enable' ;
              type enumeration {
                enum Disable {
                  value 0 ;
                }

                enum Enable {
                  value 1 ;
                }

              }

            }

            leaf us-protocol {
              description 'Upstream Protocol.
0:Unknown
1:BGP
2:PIM' ;
              type enumeration {
                enum Unknown {
                  value 0 ;
                }

                enum BGP {
                  value 1 ;
                }

                enum PIM {
                  value 2 ;
                }

              }

            }

            leaf mtunnel-name {
              description 'Mtunnel name.' ;
              type ncd:ifname {
                length 0..31 ;

              }

            }

            leaf mtunnel-state {
              description 'Mtunnel state.
"up / PIM enable"
"down / PIM enable"
"up / PIM disable"
"down / PIM disable"' ;
              type ncd:string-all {
                length 0..23 ;

              }

            }

            leaf mtunnel-addr {
              description 'Mtunnel address.' ;
              type ncd:ipv4-address ;

            }

          }

          container auto-discovery-route {
            description 'MVPN auto discovery route information.' ;
            container intra-ases {
              description 'Intra-AS auto discovery route.' ;
              list intra-as {
                description 'Intra-AS auto discovery route.' ;
                key 'rd origin-ip' ;
                leaf rd {
                  description 'RD.' ;
                  type string {
                    length 0..23 ;

                  }

                }

                leaf origin-ip {
                  description 'Origin IP address.' ;
                  type string {
                    length 1..39 ;

                  }

                }

                leaf root-tunnel {
                  description 'Root Tunnel.
Flags: L- Local,R- Remote,J- Join Ptnl,S- Start Ptnl,T0- No Ptnl 
       T1- RSVP-TE,T2- mLDP-P2MP,T3- PIM-SSM,T4- PIM-SM,T5- PIM-Bidir
       T6- Ingress-Replication,T7- mLDP-MP2MP,T11- BIER
(flags:type:label:id)/Flags' ;
                  type ncd:string-all {
                    length 0..119 ;

                  }

                }

                leaf leaf-tunnel {
                  description 'Leaf Tunnel.
Flags: L- Local,R- Remote,J- Join Ptnl,S- Start Ptnl,T0- No Ptnl 
       T1- RSVP-TE,T2- mLDP-P2MP,T3- PIM-SSM,T4- PIM-SM,T5- PIM-Bidir
       T6- Ingress-Replication,T7- mLDP-MP2MP,T11- BIER
(flags:type:label:id)/Flags' ;
                  type ncd:string-all {
                    length 0..119 ;

                  }

                }

                leaf ir-tunnel {
                  description 'Ingress replication tunnel.
Flags: L- Local,R- Remote,J- Join Ptnl,S- Start Ptnl,T0- No Ptnl 
       T1- RSVP-TE,T2- mLDP-P2MP,T3- PIM-SSM,T4- PIM-SM,T5- PIM-Bidir
       T6- Ingress-Replication,T7- mLDP-MP2MP,T11- BIER
(flags:type:label:id)/Flags' ;
                  type ncd:string-all {
                    length 0..119 ;

                  }

                }

                ncd:select origin-ip ;
              }

            }

            container inter-ases {
              description 'Inter-AS auto discovery route.' ;
              list inter-as {
                description 'Inter-AS auto discovery route.' ;
                key 'rd source-as' ;
                leaf rd {
                  description 'RD.' ;
                  type string {
                    length 0..23 ;

                  }

                }

                leaf source-as {
                  description 'Source autonomous system number.' ;
                  type uint32 ;

                }

                leaf root-tunnel {
                  description 'Root Tunnel.
Flags: L- Local,R- Remote,J- Join Ptnl,S- Start Ptnl,T0- No Ptnl 
       T1- RSVP-TE,T2- mLDP-P2MP,T3- PIM-SSM,T4- PIM-SM,T5- PIM-Bidir
       T6- Ingress-Replication,T7- mLDP-MP2MP,T11- BIER
(flags:type:label:id)/Flags' ;
                  type ncd:string-all {
                    length 0..119 ;

                  }

                }

                leaf leaf-tunnel {
                  description 'Leaf Tunnel.
Flags: L- Local,R- Remote,J- Join Ptnl,S- Start Ptnl,T0- No Ptnl 
       T1- RSVP-TE,T2- mLDP-P2MP,T3- PIM-SSM,T4- PIM-SM,T5- PIM-Bidir
       T6- Ingress-Replication,T7- mLDP-MP2MP,T11- BIER
(flags:type:label:id)/Flags' ;
                  type ncd:string-all {
                    length 0..119 ;

                  }

                }

                leaf ir-tunnel {
                  description 'Ingress replication tunnel.
Flags: L- Local,R- Remote,J- Join Ptnl,S- Start Ptnl,T0- No Ptnl 
       T1- RSVP-TE,T2- mLDP-P2MP,T3- PIM-SSM,T4- PIM-SM,T5- PIM-Bidir
       T6- Ingress-Replication,T7- mLDP-MP2MP,T11- BIER
(flags:type:label:id)/Flags' ;
                  type ncd:string-all {
                    length 0..119 ;

                  }

                }

                ncd:select source-as ;
              }

            }

            container spmsi-ads {
              description 'Spmsi-AD auto discovery route.' ;
              list spmsi-ad {
                description 'Spmsi-AD auto discovery route.' ;
                key 'rd source group origin-ip' ;
                leaf rd {
                  description 'RD.' ;
                  type string {
                    length 0..23 ;

                  }

                }

                leaf source {
                  description 'Source address.' ;
                  type ncd:ipv4-address ;

                }

                leaf group {
                  description 'Group address.' ;
                  type ncd:ipv4-address ;

                }

                leaf origin-ip {
                  description 'Origin IP address.' ;
                  type string {
                    length 1..39 ;

                  }

                }

                leaf root-tunnel {
                  description 'Root Tunnel.
Flags: L- Local,R- Remote,J- Join Ptnl,S- Start Ptnl,T0- No Ptnl 
       T1- RSVP-TE,T2- mLDP-P2MP,T3- PIM-SSM,T4- PIM-SM,T5- PIM-Bidir
       T6- Ingress-Replication,T7- mLDP-MP2MP,T11- BIER
(flags:type:label:id)/Flags' ;
                  type ncd:string-all {
                    length 0..119 ;

                  }

                }

                leaf leaf-tunnel {
                  description 'Leaf Tunnel.
Flags: L- Local,R- Remote,J- Join Ptnl,S- Start Ptnl,T0- No Ptnl 
       T1- RSVP-TE,T2- mLDP-P2MP,T3- PIM-SSM,T4- PIM-SM,T5- PIM-Bidir
       T6- Ingress-Replication,T7- mLDP-MP2MP,T11- BIER
(flags:type:label:id)/Flags' ;
                  type ncd:string-all {
                    length 0..119 ;

                  }

                }

                leaf ir-tunnel {
                  description 'Ingress replication tunnel.
Flags: L- Local,R- Remote,J- Join Ptnl,S- Start Ptnl,T0- No Ptnl 
       T1- RSVP-TE,T2- mLDP-P2MP,T3- PIM-SSM,T4- PIM-SM,T5- PIM-Bidir
       T6- Ingress-Replication,T7- mLDP-MP2MP,T11- BIER
(flags:type:label:id)/Flags' ;
                  type ncd:string-all {
                    length 0..119 ;

                  }

                }

                ncd:select source ;
                ncd:select group ;
                ncd:select origin-ip ;
                ncd:select "source group" ;
                ncd:select "source origin-ip" ;
                ncd:select "group origin-ip" ;
                ncd:select "source group origin-ip" ;
              }

            }

            container leaf-ads {
              description 'Leaf-AD auto discovery route.' ;
              list leaf-ad {
                description 'Leaf-AD auto discovery route.' ;
                key 'type sub-rd sub-source sub-group sub-origin-ip sub-source-as origin-ip' ;
                leaf type {
                  description 'AD route type.
1:Intra-AS
2:Inter-AS
3:Spmsi-AD' ;
                  type enumeration {
                    enum Intra-AS {
                      value 1 ;
                    }

                    enum Inter-AS {
                      value 2 ;
                    }

                    enum Spmsi-AD {
                      value 3 ;
                    }

                  }

                }

                leaf sub-rd {
                  description 'Sub RD.' ;
                  type string {
                    length 0..23 ;

                  }

                }

                leaf sub-source {
                  description 'Sub source address.' ;
                  type ncd:ipv4-address ;

                }

                leaf sub-group {
                  description 'Sub group address.' ;
                  type ncd:ipv4-address ;

                }

                leaf sub-origin-ip {
                  description 'Sub origin IP address.' ;
                  type string {
                    length 1..39 ;

                  }

                }

                leaf sub-source-as {
                  description 'Sub source autonomous system number.' ;
                  type uint32 ;

                }

                leaf origin-ip {
                  description 'Origin IP address.' ;
                  type string {
                    length 1..39 ;

                  }

                }

                leaf p-tunnel {
                  description 'Public tunnel.
Flags: L- Local,R- Remote,J- Join Ptnl,S- Start Ptnl,T0- No Ptnl 
       T1- RSVP-TE,T2- mLDP-P2MP,T3- PIM-SSM,T4- PIM-SM,T5- PIM-Bidir
       T6- Ingress-Replication,T7- mLDP-MP2MP,T11- BIER
(flags:type:label:id)/Flags' ;
                  type ncd:string-all {
                    length 0..119 ;

                  }

                }

                ncd:select origin-ip ;
              }

            }

          }

          container public-auto-discovery-route {
            description 'MVPN auto discovery route information of public instance.' ;
            container intra-ases {
              description 'Intra-AS auto discovery route.' ;
              list intra-as {
                description 'Intra-AS auto discovery route.' ;
                key 'rd origin-ip' ;
                leaf rd {
                  description 'RD.' ;
                  type string {
                    length 0..23 ;

                  }

                }

                leaf origin-ip {
                  description 'Origin IP address.' ;
                  type string {
                    length 1..39 ;

                  }

                }

                leaf root-tunnel {
                  description 'Root Tunnel.
Flags: L- Local,R- Remote,J- Join Ptnl,S- Start Ptnl,T0- No Ptnl 
       T1- RSVP-TE,T2- mLDP-P2MP,T3- PIM-SSM,T4- PIM-SM,T5- PIM-Bidir
       T6- Ingress-Replication,T7- mLDP-MP2MP,T11- BIER
(flags:type:label:id)/Flags' ;
                  type ncd:string-all {
                    length 0..119 ;

                  }

                }

                leaf leaf-tunnel {
                  description 'Leaf Tunnel.
Flags: L- Local,R- Remote,J- Join Ptnl,S- Start Ptnl,T0- No Ptnl 
       T1- RSVP-TE,T2- mLDP-P2MP,T3- PIM-SSM,T4- PIM-SM,T5- PIM-Bidir
       T6- Ingress-Replication,T7- mLDP-MP2MP,T11- BIER
(flags:type:label:id)/Flags' ;
                  type ncd:string-all {
                    length 0..119 ;

                  }

                }

                leaf ir-tunnel {
                  description 'Ingress replication tunnel.
Flags: L- Local,R- Remote,J- Join Ptnl,S- Start Ptnl,T0- No Ptnl 
       T1- RSVP-TE,T2- mLDP-P2MP,T3- PIM-SSM,T4- PIM-SM,T5- PIM-Bidir
       T6- Ingress-Replication,T7- mLDP-MP2MP,T11- BIER
(flags:type:label:id)/Flags' ;
                  type ncd:string-all {
                    length 0..119 ;

                  }

                }

                ncd:select origin-ip ;
              }

            }

            container inter-ases {
              description 'Inter-AS auto discovery route.' ;
              list inter-as {
                description 'Inter-AS auto discovery route.' ;
                key 'rd source-as' ;
                leaf rd {
                  description 'RD.' ;
                  type string {
                    length 0..23 ;

                  }

                }

                leaf source-as {
                  description 'Source autonomous system number.' ;
                  type uint32 ;

                }

                leaf root-tunnel {
                  description 'Root Tunnel.
Flags: L- Local,R- Remote,J- Join Ptnl,S- Start Ptnl,T0- No Ptnl 
       T1- RSVP-TE,T2- mLDP-P2MP,T3- PIM-SSM,T4- PIM-SM,T5- PIM-Bidir
       T6- Ingress-Replication,T7- mLDP-MP2MP,T11- BIER
(flags:type:label:id)/Flags' ;
                  type ncd:string-all {
                    length 0..119 ;

                  }

                }

                leaf leaf-tunnel {
                  description 'Leaf Tunnel.
Flags: L- Local,R- Remote,J- Join Ptnl,S- Start Ptnl,T0- No Ptnl 
       T1- RSVP-TE,T2- mLDP-P2MP,T3- PIM-SSM,T4- PIM-SM,T5- PIM-Bidir
       T6- Ingress-Replication,T7- mLDP-MP2MP,T11- BIER
(flags:type:label:id)/Flags' ;
                  type ncd:string-all {
                    length 0..119 ;

                  }

                }

                leaf ir-tunnel {
                  description 'Ingress replication tunnel.
Flags: L- Local,R- Remote,J- Join Ptnl,S- Start Ptnl,T0- No Ptnl 
       T1- RSVP-TE,T2- mLDP-P2MP,T3- PIM-SSM,T4- PIM-SM,T5- PIM-Bidir
       T6- Ingress-Replication,T7- mLDP-MP2MP,T11- BIER
(flags:type:label:id)/Flags' ;
                  type ncd:string-all {
                    length 0..119 ;

                  }

                }

                ncd:select source-as ;
              }

            }

            container spmsi-ads {
              description 'Spmsi-AD auto discovery route.' ;
              list spmsi-ad {
                description 'Spmsi-AD auto discovery route.' ;
                key 'rd source group origin-ip' ;
                leaf rd {
                  description 'RD.' ;
                  type string {
                    length 0..23 ;

                  }

                }

                leaf source {
                  description 'Source address.' ;
                  type ncd:ipv4-address ;

                }

                leaf group {
                  description 'Group address.' ;
                  type ncd:ipv4-address ;

                }

                leaf origin-ip {
                  description 'Origin IP address.' ;
                  type string {
                    length 1..39 ;

                  }

                }

                leaf root-tunnel {
                  description 'Root Tunnel.
Flags: L- Local,R- Remote,J- Join Ptnl,S- Start Ptnl,T0- No Ptnl 
       T1- RSVP-TE,T2- mLDP-P2MP,T3- PIM-SSM,T4- PIM-SM,T5- PIM-Bidir
       T6- Ingress-Replication,T7- mLDP-MP2MP,T11- BIER
(flags:type:label:id)/Flags' ;
                  type ncd:string-all {
                    length 0..119 ;

                  }

                }

                leaf leaf-tunnel {
                  description 'Leaf Tunnel.
Flags: L- Local,R- Remote,J- Join Ptnl,S- Start Ptnl,T0- No Ptnl 
       T1- RSVP-TE,T2- mLDP-P2MP,T3- PIM-SSM,T4- PIM-SM,T5- PIM-Bidir
       T6- Ingress-Replication,T7- mLDP-MP2MP,T11- BIER
(flags:type:label:id)/Flags' ;
                  type ncd:string-all {
                    length 0..119 ;

                  }

                }

                leaf ir-tunnel {
                  description 'Ingress replication tunnel.
Flags: L- Local,R- Remote,J- Join Ptnl,S- Start Ptnl,T0- No Ptnl 
       T1- RSVP-TE,T2- mLDP-P2MP,T3- PIM-SSM,T4- PIM-SM,T5- PIM-Bidir
       T6- Ingress-Replication,T7- mLDP-MP2MP,T11- BIER
(flags:type:label:id)/Flags' ;
                  type ncd:string-all {
                    length 0..119 ;

                  }

                }

                ncd:select source ;
                ncd:select group ;
                ncd:select origin-ip ;
                ncd:select "source group" ;
                ncd:select "source origin-ip" ;
                ncd:select "group origin-ip" ;
                ncd:select "source group origin-ip" ;
              }

            }

            container leaf-ads {
              description 'Leaf-AD auto discovery route.' ;
              list leaf-ad {
                description 'Leaf-AD auto discovery route.' ;
                key 'type sub-rd sub-source sub-group sub-origin-ip sub-source-as origin-ip' ;
                leaf type {
                  description 'AD route type.
1:Intra-AS
2:Inter-AS
3:Spmsi-AD' ;
                  type enumeration {
                    enum Intra-AS {
                      value 1 ;
                    }

                    enum Inter-AS {
                      value 2 ;
                    }

                    enum Spmsi-AD {
                      value 3 ;
                    }

                  }

                }

                leaf sub-rd {
                  description 'Sub RD.' ;
                  type string {
                    length 0..23 ;

                  }

                }

                leaf sub-source {
                  description 'Sub source address.' ;
                  type ncd:ipv4-address ;

                }

                leaf sub-group {
                  description 'Sub group address.' ;
                  type ncd:ipv4-address ;

                }

                leaf sub-origin-ip {
                  description 'Sub origin IP address.' ;
                  type string {
                    length 1..39 ;

                  }

                }

                leaf sub-source-as {
                  description 'Sub source autonomous system number.' ;
                  type uint32 ;

                }

                leaf origin-ip {
                  description 'Origin IP address.' ;
                  type string {
                    length 1..39 ;

                  }

                }

                leaf p-tunnel {
                  description 'Public tunnel.
Flags: L- Local,R- Remote,J- Join Ptnl,S- Start Ptnl,T0- No Ptnl 
       T1- RSVP-TE,T2- mLDP-P2MP,T3- PIM-SSM,T4- PIM-SM,T5- PIM-Bidir
       T6- Ingress-Replication,T7- mLDP-MP2MP,T11- BIER
(flags:type:label:id)/Flags' ;
                  type ncd:string-all {
                    length 0..119 ;

                  }

                }

                ncd:select origin-ip ;
              }

            }

            container source-actives {
              description 'Source active auto discovery route.' ;
              list source-active {
                description 'Source active auto discovery route.' ;
                key 'ad-state rd source group' ;
                leaf ad-state {
                  description 'AD route state.
0:Remote
1:Local' ;
                  type enumeration {
                    enum Remote {
                      value 0 ;
                    }

                    enum Local {
                      value 1 ;
                    }

                  }

                }

                leaf rd {
                  description 'RD.' ;
                  type string {
                    length 0..23 ;

                  }

                }

                leaf source {
                  description 'Source address.' ;
                  type ncd:ipv4-address ;

                }

                leaf group {
                  description 'Group address.' ;
                  type ncd:ipv4-address ;

                }

                leaf nexthop {
                  description 'Nexthop address.' ;
                  type string {
                    length 0..39 ;

                  }

                }

                ncd:select source ;
                ncd:select group ;
                ncd:select "source group" ;
              }

            }

            container xg-joins {
              description 'XG join route.' ;
              list xg-join {
                description 'XG join route.' ;
                key 'ad-state rd source-as rp-addr group' ;
                leaf ad-state {
                  description 'AD route state.
0:Remote
1:Local' ;
                  type enumeration {
                    enum Remote {
                      value 0 ;
                    }

                    enum Local {
                      value 1 ;
                    }

                  }

                }

                leaf rd {
                  description 'RD.' ;
                  type string {
                    length 0..23 ;

                  }

                }

                leaf source-as {
                  description 'Source autonomous system number.' ;
                  type uint32 ;

                }

                leaf rp-addr {
                  description 'RP address.' ;
                  type ncd:ipv4-address ;

                }

                leaf group {
                  description 'Group address.' ;
                  type ncd:ipv4-address ;

                }

                leaf nexthop {
                  description 'Nexthop address.' ;
                  type string {
                    length 0..39 ;

                  }

                }

                ncd:select rp-addr ;
                ncd:select group ;
                ncd:select "rp-addr group" ;
              }

            }

            container sg-joins {
              description 'SG join route.' ;
              list sg-join {
                description 'SG join route.' ;
                key 'ad-state rd source-as source group' ;
                leaf ad-state {
                  description 'AD route state.
0:Remote
1:Local' ;
                  type enumeration {
                    enum Remote {
                      value 0 ;
                    }

                    enum Local {
                      value 1 ;
                    }

                  }

                }

                leaf rd {
                  description 'RD.' ;
                  type string {
                    length 0..23 ;

                  }

                }

                leaf source-as {
                  description 'Source autonomous system number.' ;
                  type uint32 ;

                }

                leaf source {
                  description 'Source address.' ;
                  type ncd:ipv4-address ;

                }

                leaf group {
                  description 'Group address.' ;
                  type ncd:ipv4-address ;

                }

                leaf nexthop {
                  description 'Nexthop address.' ;
                  type string {
                    length 0..39 ;

                  }

                }

                ncd:select source ;
                ncd:select group ;
                ncd:select "source group" ;
              }

            }

            ncd:revise-date 2020-06-20 ;
          }

          container mtibs {
            description 'MVPN tunnel information.' ;
            list mtib {
              description 'MVPN tunnel information.' ;
              key 'tunnel-id tunnel-type' ;
              leaf tunnel-id {
                description 'Tunnel ID.' ;
                type uint32 ;

              }

              leaf tunnel-type {
                description 'Tunnel type.
0:No-Tunnel
1:TE-P2MP
2:mLDP-P2MP
3:PIM-SSM
4:PIM-SM
5:PIM-BIDIR
6:INGRESS-RPL
7:mLDP-MP2MP
11:BIER' ;
                type enumeration {
                  enum No-Tunnel {
                    value 0 ;
                  }

                  enum TE-P2MP {
                    value 1 ;
                  }

                  enum mLDP-P2MP {
                    value 2 ;
                  }

                  enum PIM-SSM {
                    value 3 ;
                  }

                  enum PIM-SM {
                    value 4 ;
                  }

                  enum PIM-BIDIR {
                    value 5 ;
                  }

                  enum INGRESS-RPL {
                    value 6 ;
                  }

                  enum mLDP-MP2MP {
                    value 7 ;
                  }

                  enum BIER {
                    value 11 ;
                  }

                }

              }

              leaf tunnel-state {
                description 'Tunnel state.
0:Root
1:Leaf' ;
                type enumeration {
                  enum Root {
                    value 0 ;
                  }

                  enum Leaf {
                    value 1 ;
                  }

                }

              }

              leaf leaf-require {
                description 'Leaf require.
0:N
1:Y' ;
                type enumeration {
                  enum N {
                    value 0 ;
                  }

                  enum Y {
                    value 1 ;
                  }

                }

              }

              leaf protocol-state {
                description 'Protocol state.
0:Up
1:Down
2:Join
3:Leave' ;
                type enumeration {
                  enum Up {
                    value 0 ;
                  }

                  enum Down {
                    value 1 ;
                  }

                  enum Join {
                    value 2 ;
                  }

                  enum Leave {
                    value 3 ;
                  }

                }

              }

              leaf tunnel-label {
                description 'Tunnel label.' ;
                type uint32 ;

              }

              leaf tunnel-attr {
                description 'Tunnel attribute.' ;
                type ncd:string-all {
                  length 0..119 ;

                }

              }

              leaf leave-delay {
                description 'Leave delay.' ;
                type string {
                  length 0..15 ;

                }

              }

              container multi-imports {
                description 'Multi-import VPN information.' ;
                list multi-import {
                  description 'Multi-import VPN information.' ;
                  key sub-vrf-name ;
                  leaf sub-vrf-name {
                    description 'Multi-import VPN Routing/Forwarding instance name.' ;
                    type ncd:string-all {
                      length 1..32 ;

                    }

                  }

                  leaf sub-tunnel-state {
                    description 'Tunnel state.' ;
                    type ncd:string-all {
                      length 0..15 ;

                    }

                  }

                  ncd:select sub-vrf-name ;
                }

              }

              ncd:select "tunnel-id tunnel-type" ;
            }

          }

          container ipmsi-infos {
            description 'MVPN IPMSI information.' ;
            list ipmsi-info {
              description 'MVPN IPMSI information.' ;
              key 'tunnel-id tunnel-type' ;
              leaf tunnel-id {
                description 'Tunnel ID.' ;
                type uint32 ;

              }

              leaf tunnel-type {
                description 'Tunnel type.
0:No-Tunnel
1:TE-P2MP
2:mLDP-P2MP
3:PIM-SSM
4:PIM-SM
5:PIM-BIDIR
6:INGRESS-RPL
7:mLDP-MP2MP
11:BIER' ;
                type enumeration {
                  enum No-Tunnel {
                    value 0 ;
                  }

                  enum TE-P2MP {
                    value 1 ;
                  }

                  enum mLDP-P2MP {
                    value 2 ;
                  }

                  enum PIM-SSM {
                    value 3 ;
                  }

                  enum PIM-SM {
                    value 4 ;
                  }

                  enum PIM-BIDIR {
                    value 5 ;
                  }

                  enum INGRESS-RPL {
                    value 6 ;
                  }

                  enum mLDP-MP2MP {
                    value 7 ;
                  }

                  enum BIER {
                    value 11 ;
                  }

                }

              }

              leaf tunnel-state {
                description 'Tunnel state.' ;
                type ncd:string-all {
                  length 0..15 ;

                }

              }

              leaf tunnel-attr {
                description 'Tunnel attribute.' ;
                type ncd:string-all {
                  length 0..119 ;

                }

              }

              leaf gbier-info {
                description 'GBIER information.' ;
                type ncd:string-all {
                  length 0..119 ;

                }

              }

              leaf root-info {
                description 'Root information.' ;
                type ncd:string-all {
                  length 0..79 ;

                }

              }

              container leaf-infos {
                description 'Leaf information.' ;
                list leaf-info {
                  description 'Leaf information.' ;
                  key 'egress-pe mpls-label' ;
                  leaf egress-pe {
                    description 'Egress PE.' ;
                    type ncd:string-all {
                      length 1..39 ;

                    }

                  }

                  leaf mpls-label {
                    description 'MPLS label.' ;
                    type uint32 ;

                  }

                  leaf bier-prefix {
                    description 'BIER prefix address..' ;
                    type ncd:string-all {
                      length 0..39 ;

                    }

                  }

                  leaf bier-bfr-id {
                    description 'BIER BFR ID.' ;
                    type uint16 ;

                  }

                  ncd:select egress-pe ;
                }

              }

              ncd:select "tunnel-id tunnel-type" ;
            }

            ncd:revise-date 2023-10-12 ;
          }

          container spmsi-infos {
            description 'MVPN SPMSI information.' ;
            list spmsi-info {
              description 'MVPN SPMSI information.' ;
              key 'tunnel-id tunnel-type' ;
              leaf tunnel-id {
                description 'Tunnel ID.' ;
                type uint32 ;

              }

              leaf tunnel-type {
                description 'Tunnel type.
0:No-Tunnel
1:TE-P2MP
2:mLDP-P2MP
3:PIM-SSM
4:PIM-SM
5:PIM-BIDIR
6:INGRESS-RPL
7:mLDP-MP2MP
11:BIER' ;
                type enumeration {
                  enum No-Tunnel {
                    value 0 ;
                  }

                  enum TE-P2MP {
                    value 1 ;
                  }

                  enum mLDP-P2MP {
                    value 2 ;
                  }

                  enum PIM-SSM {
                    value 3 ;
                  }

                  enum PIM-SM {
                    value 4 ;
                  }

                  enum PIM-BIDIR {
                    value 5 ;
                  }

                  enum INGRESS-RPL {
                    value 6 ;
                  }

                  enum mLDP-MP2MP {
                    value 7 ;
                  }

                  enum BIER {
                    value 11 ;
                  }

                }

              }

              leaf tunnel-state {
                description 'Tunnel state.' ;
                type ncd:string-all {
                  length 0..15 ;

                }

              }

              leaf tunnel-attr {
                description 'Tunnel attribute.' ;
                type ncd:string-all {
                  length 0..119 ;

                }

              }

              leaf gbier-info {
                description 'GBIER information.' ;
                type ncd:string-all {
                  length 0..119 ;

                }

              }

              leaf root-info {
                description 'Root information.' ;
                type ncd:string-all {
                  length 0..79 ;

                }

              }

              container leaf-infos {
                description 'Leaf information.' ;
                list leaf-info {
                  description 'Leaf information.' ;
                  key 'egress-pe mpls-label' ;
                  leaf egress-pe {
                    description 'Egress PE.' ;
                    type ncd:string-all {
                      length 1..39 ;

                    }

                  }

                  leaf mpls-label {
                    description 'MPLS label.' ;
                    type uint32 ;

                  }

                  leaf bier-prefix {
                    description 'BIER prefix address..' ;
                    type ncd:string-all {
                      length 0..39 ;

                    }

                  }

                  leaf bier-bfr-id {
                    description 'BIER BFR ID.' ;
                    type uint16 ;

                  }

                  ncd:select egress-pe ;
                }

              }

              ncd:select "tunnel-id tunnel-type" ;
            }

            ncd:revise-date 2023-10-12 ;
          }

          container pmsi-summary {
            description 'The summary information of PMSI tunnel.' ;
            leaf ipmsi-number {
              description 'IPMSI tunnel summary.' ;
              type uint32 ;

            }

            leaf spmsi-number {
              description 'SPMSI tunnel summary.' ;
              type uint32 ;

            }

            ncd:revise-date 2023-10-12 ;
          }

          container mribs {
            description 'MVPN route information.' ;
            list mrib {
              description 'MVPN route information.' ;
              key 'source group' ;
              leaf source {
                description 'Source address.' ;
                type ncd:ipv4-address ;

              }

              leaf group {
                description 'Group address.' ;
                type ncd:ipv4-address ;

              }

              leaf intf-state {
                description 'Interface state.
IFT - Receive from P-tunnel
OFT - Send to P-tunnel
OFNL - Downstream join state' ;
                type string {
                  length 0..15 ;

                }

              }

              leaf upstream-tunnel {
                description 'Upstream tunnel.' ;
                type ncd:string-all {
                  length 0..79 ;

                }

              }

              leaf upstream-pe {
                description 'Upstream PE address.' ;
                type string {
                  length 0..39 ;

                }

              }

              leaf rpf-tunnel-id {
                description 'RPF tunnel ID.' ;
                type uint32 ;

              }

              leaf rpf-vrf-name {
                description 'RPF VPN Routing/Forwarding instance name.' ;
                type string {
                  length 0..32 ;

                }

              }

              leaf downstream-tunnel {
                description 'Downstream tunnel.' ;
                type ncd:string-all {
                  length 0..79 ;

                }

              }

              leaf switch-tunnel {
                description 'Switch tunnel.' ;
                type ncd:string-all {
                  length 0..79 ;

                }

              }

              leaf switch-time {
                description 'Switch time.' ;
                type string {
                  length 0..15 ;

                }

              }

              container spmsi-auto-discoveries {
                description 'Spmsi-AD auto discovery route.' ;
                list spmsi-auto-discovery {
                  description 'Spmsi-AD auto discovery route.' ;
                  key 'rd source group origin-ip' ;
                  leaf rd {
                    description 'RD.' ;
                    type string {
                      length 0..23 ;

                    }

                  }

                  leaf source {
                    description 'Source address.' ;
                    type ncd:ipv4-address ;

                  }

                  leaf group {
                    description 'Group address.' ;
                    type ncd:ipv4-address ;

                  }

                  leaf origin-ip {
                    description 'Origin IP address.' ;
                    type string {
                      length 1..39 ;

                    }

                  }

                  leaf root-tunnel {
                    description 'Root tunnel.' ;
                    type ncd:string-all {
                      length 0..79 ;

                    }

                  }

                  leaf ad-state {
                    description 'AD route state.
0:Remote
1:Local
2:Local/Remote' ;
                    type enumeration {
                      enum Remote {
                        value 0 ;
                      }

                      enum Local {
                        value 1 ;
                      }

                      enum "Local/Remote" {
                        value 2 ;
                      }

                    }

                  }

                  leaf leaf-tunnel {
                    description 'Leaf tunnel.' ;
                    type ncd:string-all {
                      length 0..79 ;

                    }

                  }

                  leaf ir-tunnel {
                    description 'Ingress replication tunnel.' ;
                    type ncd:string-all {
                      length 0..79 ;

                    }

                  }

                  leaf uptime {
                    description 'Uptime.' ;
                    type string {
                      length 0..15 ;

                    }

                  }

                  ncd:select origin-ip ;
                }

              }

              container leaf-auto-discoveries {
                description 'Leaf-AD auto discovery route.' ;
                list leaf-auto-discovery {
                  description 'Leaf-AD auto discovery route.' ;
                  key 'type sub-rd sub-source sub-group sub-origin-ip origin-ip' ;
                  leaf type {
                    description 'AD route type.
1:Intra-AS
2:Inter-AS
3:Spmsi-AD' ;
                    type enumeration {
                      enum Intra-AS {
                        value 1 ;
                      }

                      enum Inter-AS {
                        value 2 ;
                      }

                      enum Spmsi-AD {
                        value 3 ;
                      }

                    }

                  }

                  leaf sub-rd {
                    description 'Sub RD.' ;
                    type string {
                      length 0..23 ;

                    }

                  }

                  leaf sub-source {
                    description 'Sub source address.' ;
                    type ncd:ipv4-address ;

                  }

                  leaf sub-group {
                    description 'Sub group address.' ;
                    type ncd:ipv4-address ;

                  }

                  leaf sub-origin-ip {
                    description 'Sub origin IP address.' ;
                    type string {
                      length 1..39 ;

                    }

                  }

                  leaf origin-ip {
                    description 'Origin IP address.' ;
                    type string {
                      length 1..39 ;

                    }

                  }

                  leaf ad-state {
                    description 'AD route state.
0:Remote
1:Local
2:Local/Remote' ;
                    type enumeration {
                      enum Remote {
                        value 0 ;
                      }

                      enum Local {
                        value 1 ;
                      }

                      enum "Local/Remote" {
                        value 2 ;
                      }

                    }

                  }

                  leaf uptime {
                    description 'Uptime.' ;
                    type string {
                      length 0..15 ;

                    }

                  }

                  ncd:select origin-ip ;
                }

              }

              container source-actives {
                description 'Source active auto discovery route.' ;
                list source-active {
                  description 'Source active auto discovery route.' ;
                  key 'ad-state rd source group' ;
                  leaf ad-state {
                    description 'AD route state.
0:Remote
1:Local' ;
                    type enumeration {
                      enum Remote {
                        value 0 ;
                      }

                      enum Local {
                        value 1 ;
                      }

                    }

                  }

                  leaf rd {
                    description 'RD.' ;
                    type string {
                      length 0..23 ;

                    }

                  }

                  leaf source {
                    description 'Source address.' ;
                    type ncd:ipv4-address ;

                  }

                  leaf group {
                    description 'Group address.' ;
                    type ncd:ipv4-address ;

                  }

                  leaf uptime {
                    description 'Uptime.' ;
                    type string {
                      length 0..15 ;

                    }

                  }

                  ncd:select ad-state ;
                }

              }

              container xg-joins {
                description 'XG join route.' ;
                list xg-join {
                  description 'XG join route.' ;
                  key 'ad-state rd source-as rp-addr group' ;
                  leaf ad-state {
                    description 'AD route state.
0:Remote
1:Local' ;
                    type enumeration {
                      enum Remote {
                        value 0 ;
                      }

                      enum Local {
                        value 1 ;
                      }

                    }

                  }

                  leaf rd {
                    description 'RD.' ;
                    type string {
                      length 0..23 ;

                    }

                  }

                  leaf source-as {
                    description 'Source autonomous system number.' ;
                    type uint32 ;

                  }

                  leaf rp-addr {
                    description 'RP address.' ;
                    type ncd:ipv4-address ;

                  }

                  leaf group {
                    description 'Group address.' ;
                    type ncd:ipv4-address ;

                  }

                  leaf uptime {
                    description 'Uptime.' ;
                    type string {
                      length 0..15 ;

                    }

                  }

                  ncd:select ad-state ;
                }

              }

              container sg-joins {
                description 'SG join route.' ;
                list sg-join {
                  description 'SG join route.' ;
                  key 'ad-state rd source-as source group' ;
                  leaf ad-state {
                    description 'AD route state.
0:Remote
1:Local' ;
                    type enumeration {
                      enum Remote {
                        value 0 ;
                      }

                      enum Local {
                        value 1 ;
                      }

                    }

                  }

                  leaf rd {
                    description 'RD.' ;
                    type string {
                      length 0..23 ;

                    }

                  }

                  leaf source-as {
                    description 'Source autonomous system number.' ;
                    type uint32 ;

                  }

                  leaf source {
                    description 'Source address.' ;
                    type ncd:ipv4-address ;

                  }

                  leaf group {
                    description 'Group address.' ;
                    type ncd:ipv4-address ;

                  }

                  leaf uptime {
                    description 'Uptime.' ;
                    type string {
                      length 0..15 ;

                    }

                  }

                  ncd:select ad-state ;
                }

              }

              ncd:select source ;
              ncd:select group ;
              ncd:select "source group" ;
            }

            ncd:revise-date 2020-06-20 ;
          }

          container segments {
            description 'MVPN segment information.' ;
            list segment {
              description 'MVPN segment information.' ;
              key index ;
              leaf index {
                description 'Segment index.' ;
                type uint32 ;

              }

              leaf in-tunnel-id {
                description 'In tunnel ID.' ;
                type uint32 ;

              }

              leaf in-tunnel-type {
                description 'In tunnel type.
0:No-Tunnel
1:TE-P2MP
2:mLDP-P2MP
3:PIM-SSM
4:PIM-SM
5:PIM-BIDIR
6:Ingress-Replication
7:mLDP-MP2MP
11:BIER' ;
                type enumeration {
                  enum No-Tunnel {
                    value 0 ;
                  }

                  enum TE-P2MP {
                    value 1 ;
                  }

                  enum mLDP-P2MP {
                    value 2 ;
                  }

                  enum PIM-SSM {
                    value 3 ;
                  }

                  enum PIM-SM {
                    value 4 ;
                  }

                  enum PIM-BIDIR {
                    value 5 ;
                  }

                  enum Ingress-Replication {
                    value 6 ;
                  }

                  enum mLDP-MP2MP {
                    value 7 ;
                  }

                  enum BIER {
                    value 11 ;
                  }

                }

              }

              leaf in-leaf-require {
                description 'In tunnel leaf require.
0:N
1:Y' ;
                type enumeration {
                  enum N {
                    value 0 ;
                  }

                  enum Y {
                    value 1 ;
                  }

                }

              }

              leaf in-tunnel-label {
                description 'In tunnel label.' ;
                type uint32 ;

              }

              leaf in-tunnel-attr {
                description 'In tunnel attribute.' ;
                type ncd:string-all {
                  length 0..119 ;

                }

              }

              leaf out-tunnel-id {
                description 'Out tunnel ID.' ;
                type uint32 ;

              }

              leaf out-tunnel-type {
                description 'Out tunnel type.
0:No-Tunnel
1:TE-P2MP
2:mLDP-P2MP
3:PIM-SSM
4:PIM-SM
5:PIM-BIDIR
6:Ingress-Replication
7:mLDP-MP2MP
11:BIER' ;
                type enumeration {
                  enum No-Tunnel {
                    value 0 ;
                  }

                  enum TE-P2MP {
                    value 1 ;
                  }

                  enum mLDP-P2MP {
                    value 2 ;
                  }

                  enum PIM-SSM {
                    value 3 ;
                  }

                  enum PIM-SM {
                    value 4 ;
                  }

                  enum PIM-BIDIR {
                    value 5 ;
                  }

                  enum Ingress-Replication {
                    value 6 ;
                  }

                  enum mLDP-MP2MP {
                    value 7 ;
                  }

                  enum BIER {
                    value 11 ;
                  }

                }

              }

              leaf out-leaf-require {
                description 'Out tunnel leaf require.
0:N
1:Y' ;
                type enumeration {
                  enum N {
                    value 0 ;
                  }

                  enum Y {
                    value 1 ;
                  }

                }

              }

              leaf out-tunnel-label {
                description 'Out tunnel label.' ;
                type uint32 ;

              }

              leaf out-tunnel-attr {
                description 'Out tunnel attribute.' ;
                type ncd:string-all {
                  length 0..119 ;

                }

              }

              container leaf-lists {
                description 'Leaf AD list information.' ;
                list leaf-list {
                  description 'Leaf AD list information.' ;
                  key 'tunnel-label origin-ip' ;
                  leaf tunnel-label {
                    description 'Tunnel label.' ;
                    type uint32 ;

                  }

                  leaf origin-ip {
                    description 'Origin IP address.' ;
                    type string {
                      length 1..39 ;

                    }

                  }

                  ncd:select "tunnel-label origin-ip" ;
                }

              }

              ncd:select index ;
            }

          }

          container ad-summary {
            description 'The summary information of AD route.' ;
            leaf intra-as-local {
              description 'Local intra-AS route summary.' ;
              type uint32 ;

            }

            leaf intra-as-remote {
              description 'Remote intra-AS route summary.' ;
              type uint32 ;

            }

            leaf intra-as-all {
              description 'Intra-AS route summary.' ;
              type uint32 ;

            }

            leaf inter-as-local {
              description 'Local inter-AS route summary.' ;
              type uint32 ;

            }

            leaf inter-as-remote {
              description 'Remote inter-AS route summary.' ;
              type uint32 ;

            }

            leaf inter-as-all {
              description 'Inter-AS route summary.' ;
              type uint32 ;

            }

            leaf spmsi-ad-local {
              description 'Local spmsi-AD route summary.' ;
              type uint32 ;

            }

            leaf spmsi-ad-remote {
              description 'Remote spmsi-AD route summary.' ;
              type uint32 ;

            }

            leaf spmsi-ad-all {
              description 'Spmsi-AD route summary.' ;
              type uint32 ;

            }

            leaf leaf-ad-local {
              description 'Local leaf-AD route summary.' ;
              type uint32 ;

            }

            leaf leaf-ad-remote {
              description 'Remote leaf-AD route summary.' ;
              type uint32 ;

            }

            leaf leaf-ad-all {
              description 'Leaf-AD route summary.' ;
              type uint32 ;

            }

            leaf source-active-local {
              description 'Local source active route summary.' ;
              type uint32 ;

            }

            leaf source-active-remote {
              description 'Remote source active route summary.' ;
              type uint32 ;

            }

            leaf source-active-all {
              description 'Source active route summary.' ;
              type uint32 ;

            }

            leaf xg-join-local {
              description 'Local XG join route summary.' ;
              type uint32 ;

            }

            leaf xg-join-remote {
              description 'Remote XG join route summary.' ;
              type uint32 ;

            }

            leaf xg-join-all {
              description 'XG join route summary.' ;
              type uint32 ;

            }

            leaf sg-join-local {
              description 'Local SG join route summary.' ;
              type uint32 ;

            }

            leaf sg-join-remote {
              description 'Remote SG join route summary.' ;
              type uint32 ;

            }

            leaf sg-join-all {
              description 'SG join route summary.' ;
              type uint32 ;

            }

            leaf local-ad-all {
              description 'Local AD route summary.' ;
              type uint32 ;

            }

            leaf remote-ad-all {
              description 'Remote AD route summary.' ;
              type uint32 ;

            }

            leaf ad-all {
              description 'AD route summary.' ;
              type uint32 ;

            }

          }

          container public-ad-summary {
            description 'The summary information of AD route of public instance.' ;
            leaf intra-as-local {
              description 'Local intra-AS route summary.' ;
              type uint32 ;

            }

            leaf intra-as-remote {
              description 'Remote intra-AS route summary.' ;
              type uint32 ;

            }

            leaf intra-as-all {
              description 'Intra-AS route summary.' ;
              type uint32 ;

            }

            leaf inter-as-local {
              description 'Local inter-AS route summary.' ;
              type uint32 ;

            }

            leaf inter-as-remote {
              description 'Remote inter-AS route summary.' ;
              type uint32 ;

            }

            leaf inter-as-all {
              description 'Inter-AS route summary.' ;
              type uint32 ;

            }

            leaf spmsi-ad-local {
              description 'Local spmsi-AD route summary.' ;
              type uint32 ;

            }

            leaf spmsi-ad-remote {
              description 'Remote spmsi-AD route summary.' ;
              type uint32 ;

            }

            leaf spmsi-ad-all {
              description 'Spmsi-AD route summary.' ;
              type uint32 ;

            }

            leaf leaf-ad-local {
              description 'Local leaf-AD route summary.' ;
              type uint32 ;

            }

            leaf leaf-ad-remote {
              description 'Remote leaf-AD route summary.' ;
              type uint32 ;

            }

            leaf leaf-ad-all {
              description 'Leaf-AD route summary.' ;
              type uint32 ;

            }

            leaf source-active-local {
              description 'Local source active route summary.' ;
              type uint32 ;

            }

            leaf source-active-remote {
              description 'Remote source active route summary.' ;
              type uint32 ;

            }

            leaf source-active-all {
              description 'Source active route summary.' ;
              type uint32 ;

            }

            leaf xg-join-local {
              description 'Local XG join route summary.' ;
              type uint32 ;

            }

            leaf xg-join-remote {
              description 'Remote XG join route summary.' ;
              type uint32 ;

            }

            leaf xg-join-all {
              description 'XG join route summary.' ;
              type uint32 ;

            }

            leaf sg-join-local {
              description 'Local SG join route summary.' ;
              type uint32 ;

            }

            leaf sg-join-remote {
              description 'Remote SG join route summary.' ;
              type uint32 ;

            }

            leaf sg-join-all {
              description 'SG join route summary.' ;
              type uint32 ;

            }

            leaf local-ad-all {
              description 'Local AD route summary.' ;
              type uint32 ;

            }

            leaf remote-ad-all {
              description 'Remote AD route summary.' ;
              type uint32 ;

            }

            leaf ad-all {
              description 'AD route summary.' ;
              type uint32 ;

            }

            ncd:revise-date 2020-06-20 ;
          }

          container mtunnels {
            description 'MVPN tunnel information.' ;
            list mtunnel {
              description 'MVPN tunnel information.' ;
              key 'tunnel-id tunnel-type' ;
              leaf tunnel-id {
                description 'Tunnel ID.' ;
                type uint32 ;

              }

              leaf tunnel-type {
                description 'Tunnel type.
0:No-Tunnel
1:TE-P2MP
2:mLDP-P2MP
3:PIM-SSM
4:PIM-SM
5:PIM-BIDIR
6:INGRESS-RPL
7:mLDP-MP2MP
11:BIER' ;
                type enumeration {
                  enum No-Tunnel {
                    value 0 ;
                  }

                  enum TE-P2MP {
                    value 1 ;
                  }

                  enum mLDP-P2MP {
                    value 2 ;
                  }

                  enum PIM-SSM {
                    value 3 ;
                  }

                  enum PIM-SM {
                    value 4 ;
                  }

                  enum PIM-BIDIR {
                    value 5 ;
                  }

                  enum INGRESS-RPL {
                    value 6 ;
                  }

                  enum mLDP-MP2MP {
                    value 7 ;
                  }

                  enum BIER {
                    value 11 ;
                  }

                }

              }

              leaf tunnel-state {
                description 'Tunnel state.
0:Root
1:Leaf' ;
                type enumeration {
                  enum Root {
                    value 0 ;
                  }

                  enum Leaf {
                    value 1 ;
                  }

                }

              }

              leaf vrf-name {
                description 'The VRF name of MVPN mtunnel.If the instance of MVPN is public, the value of the node is "", else is VRF name.' ;
                type ncd:string-all {
                  length 0..32 ;

                }

              }

              container mrts {
                description 'Attach mroute information.' ;
                list mrt {
                  description 'Attach mroute information.' ;
                  key 'sub-vrf-name source group' ;
                  leaf sub-vrf-name {
                    description 'VPN Routing/Forwarding instance name.' ;
                    type ncd:string-all {
                      length 1..32 ;

                    }

                  }

                  leaf source {
                    description 'Source address.' ;
                    type ncd:ipv4-address ;

                  }

                  leaf group {
                    description 'Group address.' ;
                    type ncd:ipv4-address ;

                  }

                  ncd:select sub-vrf-name ;
                }

              }

              ncd:select tunnel-type ;
              ncd:select "tunnel-id tunnel-type" ;
            }

            ncd:revise-date 2019-07-15 ;
          }

          container protect-groups {
            description 'MVPN protect group information.' ;
            list protect-group {
              description 'MVPN protect group information.' ;
              key 'protect-group-id m-subdomain-id m-bfir-id m-vpn-label s-subdomain-id s-bfir-id s-vpn-label' ;
              leaf protect-group-id {
                description 'MVPN group ID.' ;
                type uint32 ;

              }

              leaf m-subdomain-id {
                description 'Master subdomain ID.' ;
                type uint8 {
                  range 0..255 ;

                }

              }

              leaf m-bfir-id {
                description 'Master BFIR ID.' ;
                type uint16 {
                  range 1..65535 ;

                }

              }

              leaf m-vpn-label {
                description 'Master VPN Label.' ;
                type uint32 ;

              }

              leaf s-subdomain-id {
                description 'Slave subdomain ID.' ;
                type uint8 {
                  range 0..255 ;

                }

              }

              leaf s-bfir-id {
                description 'Slave BFIR ID.' ;
                type uint16 {
                  range 1..65535 ;

                }

              }

              leaf s-vpn-label {
                description 'Slave VPN label.' ;
                type uint32 ;

              }

              leaf master-state {
                description 'Master tunnel state.' ;
                type ncd:string-all {
                  length 0..23 ;

                }

              }

              leaf egress-wtr {
                description 'Egress WTR delay.' ;
                type ncd:string-all {
                  length 0..15 ;

                }

              }

              leaf vrf-name {
                description 'VRF name.' ;
                type ncd:string-all {
                  length 0..32 ;

                }

              }

              container mrts {
                description 'Attach mroute information.' ;
                list mrt {
                  description 'Attach mroute information.' ;
                  key 'source group' ;
                  leaf source {
                    description 'Source address.' ;
                    type ncd:ipv4-address ;

                  }

                  leaf group {
                    description 'Group address.' ;
                    type ncd:ipv4-address ;

                  }

                  ncd:select "source group" ;
                }

              }

              ncd:select protect-group-id ;
            }

            ncd:revise-date 2020-06-20 ;
          }

          ncd:revise-date 2016-11-29 ;
        }

      }

      container private {
        description 'Private mode of multicast' ;
        container mroutes {
          description 'Multicast route information.' ;
          list mroute {
            description 'Multicast route information.' ;
            key 'vrf-name group-addr source-addr' ;
            leaf vrf-name {
              description 'VRF name' ;
              type string {
                length 1..32 ;

              }

            }

            leaf group-addr {
              description 'Group address' ;
              type ncd:ipv4-address ;

            }

            leaf source-addr {
              description 'Source address' ;
              type ncd:ipv4-address ;

            }

            leaf rp-addr {
              description 'RP address' ;
              type ncd:ipv4-address ;

            }

            leaf iif-name {
              description 'Incoming interface name' ;
              type ncd:string-all {
                length 0..31 ;

              }

            }

            leaf secondary-rpf-intf {
              description 'Secondary RPF interface name' ;
              type ncd:string-all {
                length 0..31 ;

              }

            }

            leaf mrt-flag {
              description 'Mroute flag.
NS:SPT upsend,RT:Reg upsend,MT:Tunnel,NTP:NTP join,B:Bidir,SU:Slave in use.' ;
              type ncd:string-all {
                length 0..31 ;

              }

            }

            leaf mrt-type {
              description 'Mroute type:"STATIC","DYNAMIC".' ;
              type ncd:string-all {
                length 0..19 ;

              }

            }

            leaf iif-flag {
              description 'Incoming interface flag.
NS:SPT upsend,MT:Tunnel.' ;
              type ncd:string-all {
                length 0..31 ;

              }

            }

            leaf fallback-vrf {
              description 'The upstream instance name of mroute.If the instance of upstream is public, the value of the node is IP global, else is VRF name.' ;
              type ncd:string-all {
                length 0..32 ;

              }

              ncd:revise-date 2015-12-09 ;
            }

            list oif-list {
              description 'Downstream interface list' ;
              key 'oif-name type' ;
              leaf oif-name {
                description 'Downstream interface name' ;
                type ncd:string-all {
                  length 0..31 ;

                }

              }

              leaf type {
                description 'Save the breakpoint types of the outcoming interface, not used for the query criteria.
For xg, 1:mroute outcoming interface,2:outcoming interface added by xg filter,3:outcoming interface added by xg global filter. 
For sg, 1:mroute outcoming interface,2:outcoming interface added by sg filter,3:outcoming interface added by xg filter,4:outcoming interface added by sg global filter.' ;
                type int32 ;

              }

              leaf oif-flag {
                description 'Downstream interface flag.
F:Forward,RT:Reg upsend,MT:Tunnel,S:Syn mrt,DF:DF,FLT:Flt add, FD:Flt del.' ;
                type ncd:string-all {
                  length 0..31 ;

                }

              }

              ncd:select oif-name ;
            }

            list fallback-extranet {
              description 'Fallback extranet receiver info.' ;
              key vrf-name ;
              leaf vrf-name {
                description 'The downstream instance name of mroute.If the instance of downstream is public, the value of the node is IP global, else is VRF name.' ;
                type ncd:string-all {
                  length 1..32 ;

                }

              }

              ncd:revise-date 2015-12-09 ;
            }

            list vpn-extranet {
              description 'MVPN multi-import receiver info.' ;
              key vrf-name ;
              leaf vrf-name {
                description 'VRF name.' ;
                type ncd:string-all {
                  length 1..32 ;

                }

              }

              ncd:revise-date 2015-12-09 ;
            }

            list bier-info {
              description 'Bit index explicit replication information.' ;
              key 'subdomain-id bfer-prefix' ;
              leaf subdomain-id {
                description 'Subdomain ID.' ;
                type uint8 {
                  range 0..255 ;

                }

              }

              leaf bfer-prefix {
                description 'BFER prefix.' ;
                type string {
                  length 1..39 ;

                }

              }

              leaf bfr-id {
                description 'BFR ID.' ;
                type uint16 {
                  range 0..65535 ;

                }

              }

              ncd:revise-date 2020-06-20 ;
              ncd:select bfer-prefix ;
            }

            ncd:select "vrf-name group-addr source-addr iif-name" ;
            ncd:select "vrf-name group-addr source-addr" ;
            ncd:select "vrf-name group-addr iif-name" ;
            ncd:select "vrf-name source-addr iif-name" ;
            ncd:select "vrf-name group-addr" ;
            ncd:select "vrf-name source-addr" ;
            ncd:select "vrf-name iif-name" ;
            ncd:select "group-addr source-addr iif-name" ;
            ncd:select "group-addr source-addr" ;
            ncd:select "group-addr iif-name" ;
            ncd:select group-addr ;
            ncd:select "source-addr iif-name" ;
            ncd:select source-addr ;
            ncd:select iif-name ;
            ncd:select vrf-name ;
          }

        }

        container summarys {
          description 'The summary information of mroute.' ;
          list summary {
            description 'The summary information of mroute.' ;
            key vrf-name ;
            leaf vrf-name {
              description 'VRF name' ;
              type string {
                length 1..32 ;

              }

            }

            leaf xg-count {
              description 'XG summary' ;
              type uint32 ;

            }

            leaf sg-count {
              description 'SG summary' ;
              type uint32 ;

            }

            leaf mroute-count {
              description 'XG and SG mroute summary' ;
              type uint32 ;

            }

            ncd:select vrf-name ;
          }

        }

        container briefs {
          description 'The brief information of mroute' ;
          list brief {
            description 'The brief information of mroute' ;
            key 'vrf-name group source' ;
            leaf vrf-name {
              description 'VRF name' ;
              type string {
                length 1..32 ;

              }

            }

            leaf group {
              description 'Group address' ;
              type ncd:ipv4-address ;

            }

            leaf source {
              description 'Source address' ;
              type ncd:ipv4-address ;

            }

            leaf type {
              description 'Mroute type:"STATIC","DYNAMIC".' ;
              type string {
                length 1..11 ;

              }

            }

            ncd:select vrf-name ;
            ncd:select source ;
            ncd:select group ;
            ncd:select "vrf-name source" ;
            ncd:select "vrf-name group" ;
            ncd:select "group source" ;
            ncd:select "vrf-name group source" ;
          }

        }

        container nexthops {
          description 'The nexthop information of mroute' ;
          list nexthop {
            description 'The nexthop information of mroute' ;
            key 'vrf-name dest-addr type' ;
            leaf vrf-name {
              description 'VRF name' ;
              type string {
                length 1..32 ;

              }

            }

            leaf dest-addr {
              description 'Destination address' ;
              type ncd:ipv4-address ;

            }

            leaf type {
              description 'Type:"Mstatic nexthop","Mdt nexthop","Mbgp nexthop","Migp nexthop","Rtm nexthop"' ;
              type ncd:string-all {
                length 0..31 ;

              }

              ncd:revise-date 2015-08-28 ;
            }

            leaf time {
              description 'Nexthop create time' ;
              type ncd:string-all {
                length 0..31 ;

              }

            }

            leaf user {
              description 'Nexthop user:"PIM","DM","MSDP","MSN","MVPN"' ;
              type ncd:string-all {
                length 0..31 ;

              }

            }

            leaf metric {
              description 'Metric' ;
              type uint32 ;

            }

            leaf preference {
              description 'Preference' ;
              type uint32 ;

            }

            leaf mask-len {
              description 'Mask length' ;
              type uint16 ;

            }

            leaf flag {
              description 'Flag.
L:Local,C:Connect,UNR:Unreachable unicast,CTOP:Across the backbone' ;
              type ncd:string-all {
                length 0..31 ;

              }

            }

            leaf fallback-vrf {
              description 'The instance name of fallback nexthop.If the instance of nexthop is public, the value of the node is IP global, else is VRF name.' ;
              type ncd:string-all {
                length 0..32 ;

              }

              ncd:revise-date 2015-12-09 ;
            }

            list ecmp {
              description 'Ecmp information' ;
              key 'nexthop oif-name' ;
              leaf nexthop {
                description 'Nexthop address' ;
                type string {
                  length 1..39 ;

                }

              }

              leaf oif-name {
                description 'Downstream interface name' ;
                type ncd:string-all {
                  length 0..31 ;

                }

              }

              leaf oif-flag {
                description 'Downstream interface flag.
Mdt:Mdt nexthop
Down:Interface down
S:Slave  
M:Master' ;
                type ncd:string-all {
                  length 0..31 ;

                }

              }

              leaf remote-pe {
                description 'Remote PE address.' ;
                type string {
                  length 0..39 ;

                }

              }

              leaf real-nexthop {
                description 'Real nexthop address.' ;
                type string {
                  length 0..39 ;

                }

              }

              ncd:select "nexthop oif-name" ;
            }

            ncd:select vrf-name ;
            ncd:select dest-addr ;
            ncd:select "vrf-name dest-addr" ;
          }

        }

        container mvpn {
          description 'MVPN module show info.' ;
          container mdts {
            description 'MDT information.' ;
            list mdt {
              description 'MDT information.' ;
              key vrf-name ;
              leaf vrf-name {
                description 'VPN Routing/Forwarding instance name.' ;
                type string {
                  length 1..32 ;

                }

              }

              leaf default-mode {
                description 'MDT default mode.
0:NO-MDT
1:GRE
2:MLDP' ;
                type enumeration {
                  enum NO-MDT {
                    value 0 ;
                    description 'NO-MDT mode.' ;
                  }

                  enum GRE {
                    value 1 ;
                    description 'GRE default mode.' ;
                  }

                  enum MLDP {
                    value 2 ;
                    description 'MLDP default mode.' ;
                  }

                }

              }

              leaf data-mode {
                description 'MDT data mode.
0:NO-MDT
1:GRE
2:MLDP' ;
                type enumeration {
                  enum NO-MDT {
                    value 0 ;
                    description 'NO-MDT mode.' ;
                  }

                  enum GRE {
                    value 1 ;
                    description 'GRE data mode.' ;
                  }

                  enum MLDP {
                    value 2 ;
                    description 'MLDP data mode.' ;
                  }

                }

              }

              leaf root-id {
                description 'Root ID.' ;
                type ncd:ipv4-address ;

              }

              leaf global-vpn-id {
                description 'Global VPN ID.' ;
                type string {
                  length 0..15 ;

                }

              }

              leaf data-tree-num {
                description 'MLDP data tree number.' ;
                type uint16 {
                  range 1..5000 ;

                }

              }

              leaf next-spmsi-index {
                description 'MLDP next spmsi index.' ;
                type uint16 {
                  range 1..5000 ;

                }

              }

              leaf mtunnel-addr {
                description 'Mtunnel address.' ;
                type ncd:ipv4-address ;

              }

              leaf mtunnel-name {
                description 'Mtunnel name.' ;
                type ncd:ifname {
                  length 0..31 ;

                }

              }

              leaf mtunnel-state {
                description 'Mtunnel state.
"PIM-MDT disable"
"PIM ok"' ;
                type ncd:string-all {
                  length 0..15 ;

                }

              }

              leaf default-group {
                description 'MDT default group address.' ;
                type ncd:ipv4-address ;

              }

              leaf data-group {
                description 'MDT data group address.' ;
                type ncd:ipv4-address ;

              }

              leaf data-group-mask-len {
                description 'MDT data group mask length.' ;
                type uint8 {
                  range 0..32 ;

                }

              }

              leaf data-acl-name {
                description 'MDT data ACL name.' ;
                type string {
                  length 0..31 ;

                }

              }

              ncd:select vrf-name ;
            }

          }

          container mdt-tlvs {
            description 'MDT TLV information.' ;
            list mdt-tlv {
              description 'MDT TLV information.' ;
              key 'vrf-name source group mdt-sender mdt-data' ;
              leaf vrf-name {
                description 'VPN Routing/Forwarding instance name.' ;
                type string {
                  length 1..32 ;

                }

              }

              leaf source {
                description 'Source address.' ;
                type ncd:ipv4-address ;

              }

              leaf group {
                description 'Group address.' ;
                type ncd:ipv4-address ;

              }

              leaf mdt-sender {
                description 'MDT TLV sender information.' ;
                type ncd:string-with-blank {
                  length 1..99 ;

                }

              }

              leaf mdt-data {
                description 'MDT TLV data information.' ;
                type ncd:string-with-blank {
                  length 1..99 ;

                }

              }

              leaf expire-time {
                description 'MDT TLV expire time.' ;
                type string {
                  length 1..31 ;

                }

              }

              ncd:select vrf-name ;
              ncd:select "vrf-name source" ;
              ncd:select "vrf-name group" ;
              ncd:select "vrf-name source group" ;
            }

            ncd:revise-date 2019-07-15 ;
          }

          container instances {
            description 'MVPN instance information.' ;
            list instance {
              description 'MVPN instance information.' ;
              key vrf-name ;
              leaf vrf-name {
                description 'VPN Routing/Forwarding instance name.' ;
                type string {
                  length 1..32 ;

                }

              }

              leaf rd {
                description 'RD.' ;
                type string {
                  length 0..23 ;

                }

              }

              leaf import-rt {
                description 'MVPN import RT.' ;
                type string {
                  length 0..63 ;

                }

              }

              leaf origin-ip {
                description 'Origin IP address.' ;
                type string {
                  length 0..39 ;

                }

              }

              leaf te-id {
                description 'TE root ID.' ;
                type string {
                  length 0..39 ;

                }

              }

              leaf origin-state {
                description 'Origin state.
"Un-routable"
"Routable,Local"
"Routable,Not Local"' ;
                type ncd:string-all {
                  length 0..23 ;

                }

              }

              leaf te-state {
                description 'TE state.
"in-use"
"Not in-use"' ;
                type ncd:string-all {
                  length 0..15 ;

                }

              }

              leaf mtunnel-type {
                description 'Mtunnel type.
0:No-Tunnel
1:TE-P2MP
2:mLDP-P2MP
3:PIM-SSM
4:PIM-SM
5:PIM-BIDIR
6:INGRESS-RPL
7:mLDP-MP2MP
8:PIM-MDT
11:BIER
126:Static-VXLAN' ;
                type enumeration {
                  enum No-Tunnel {
                    value 0 ;
                  }

                  enum TE-P2MP {
                    value 1 ;
                  }

                  enum mLDP-P2MP {
                    value 2 ;
                  }

                  enum PIM-SSM {
                    value 3 ;
                  }

                  enum PIM-SM {
                    value 4 ;
                  }

                  enum PIM-BIDIR {
                    value 5 ;
                  }

                  enum INGRESS-RPL {
                    value 6 ;
                  }

                  enum mLDP-MP2MP {
                    value 7 ;
                  }

                  enum PIM-MDT {
                    value 8 ;
                  }

                  enum BIER {
                    value 11 ;
                  }

                  enum Static-VXLAN {
                    value 126 ;
                  }

                }

              }

              leaf route-state {
                description 'Route state.
0:Disable
1:Enable' ;
                type enumeration {
                  enum Disable {
                    value 0 ;
                  }

                  enum Enable {
                    value 1 ;
                  }

                }

              }

              leaf mldp-state {
                description 'MLDP state.
0:Disable
1:Enable' ;
                type enumeration {
                  enum Disable {
                    value 0 ;
                  }

                  enum Enable {
                    value 1 ;
                  }

                }

              }

              leaf p-pim-state {
                description 'P-PIM state.
0:Disable
1:Enable' ;
                type enumeration {
                  enum Disable {
                    value 0 ;
                  }

                  enum Enable {
                    value 1 ;
                  }

                }

              }

              leaf c-pim-state {
                description 'C-PIM state.
0:Disable
1:Enable' ;
                type enumeration {
                  enum Disable {
                    value 0 ;
                  }

                  enum Enable {
                    value 1 ;
                  }

                }

              }

              leaf us-protocol {
                description 'Upstream Protocol.
0:Unknown
1:BGP
2:PIM' ;
                type enumeration {
                  enum Unknown {
                    value 0 ;
                  }

                  enum BGP {
                    value 1 ;
                  }

                  enum PIM {
                    value 2 ;
                  }

                }

              }

              leaf mtunnel-name {
                description 'Mtunnel name.' ;
                type ncd:ifname {
                  length 0..31 ;

                }

              }

              leaf mtunnel-state {
                description 'Mtunnel state.
"up / PIM enable"
"down / PIM enable"
"up / PIM disable"
"down / PIM disable"' ;
                type ncd:string-all {
                  length 0..23 ;

                }

              }

              leaf mtunnel-addr {
                description 'Mtunnel address.' ;
                type ncd:ipv4-address ;

              }

              leaf default-group {
                description 'MDT default group address.' ;
                type ncd:ipv4-address ;

              }

              leaf data-group {
                description 'MDT data group address.' ;
                type ncd:ipv4-address ;

              }

              leaf data-group-mask-len {
                description 'MDT data group mask length.' ;
                type uint8 {
                  range 0..32 ;

                }

              }

              leaf data-acl-name {
                description 'MDT data ACL name.' ;
                type string {
                  length 0..31 ;

                }

              }

              ncd:select vrf-name ;
            }

          }

          container ad-routes {
            status obsolete {
              ncd:revise-date 2016-11-29 ;
            }

            description 'MVPN auto discovery route information.' ;
            list ad-route {
              description 'MVPN auto discovery route information.' ;
              key 'vrf-name pe-addr' ;
              leaf vrf-name {
                description 'VPN Routing/Forwarding instance name.' ;
                type string {
                  length 1..32 ;

                }

              }

              leaf pe-addr {
                description 'PE address.' ;
                type ncd:ipv4-address ;

              }

              container intra-ases {
                description 'Intra-AS auto discovery route.' ;
                list intra-as {
                  description 'Intra-AS auto discovery route.' ;
                  key 'ad-state rd origin-ip' ;
                  leaf ad-state {
                    description 'AD route state.
0:Remote
1:Local' ;
                    type enumeration {
                      enum Remote {
                        value 0 ;
                      }

                      enum Local {
                        value 1 ;
                      }

                    }

                  }

                  leaf rd {
                    description 'RD.' ;
                    type string {
                      length 0..23 ;

                    }

                  }

                  leaf origin-ip {
                    description 'Origin IP address.' ;
                    type ncd:ipv4-address ;

                  }

                  leaf tunnel-label {
                    description 'Tunnel label.' ;
                    type uint32 ;

                  }

                  leaf tunnel-type {
                    description 'Tunnel type.
0:No-Tunnel
1:TE-P2MP
2:mLDP-P2MP
3:PIM-SSM
4:PIM-SM
5:PIM-BIDIR
6:INGRESS-RPL
7:mLDP-MP2MP' ;
                    type enumeration {
                      enum No-Tunnel {
                        value 0 ;
                      }

                      enum TE-P2MP {
                        value 1 ;
                      }

                      enum mLDP-P2MP {
                        value 2 ;
                      }

                      enum PIM-SSM {
                        value 3 ;
                      }

                      enum PIM-SM {
                        value 4 ;
                      }

                      enum PIM-BIDIR {
                        value 5 ;
                      }

                      enum INGRESS-RPL {
                        value 6 ;
                      }

                      enum mLDP-MP2MP {
                        value 7 ;
                      }

                    }

                  }

                  leaf tunnel-state {
                    description 'Tunnel state.
1:Leave
2:Join' ;
                    type enumeration {
                      enum Leave {
                        value 1 ;
                      }

                      enum Join {
                        value 2 ;
                      }

                    }

                  }

                  leaf tunnel-id {
                    description 'Tunnel ID.' ;
                    type string {
                      length 0..31 ;

                    }

                  }

                  ncd:select origin-ip ;
                }

              }

              container spmsi-ads {
                description 'Spmsi-AD auto discovery route.' ;
                list spmsi-ad {
                  description 'Spmsi-AD auto discovery route.' ;
                  key 'ad-state rd source group origin-ip' ;
                  leaf ad-state {
                    description 'AD route state.
0:Remote
1:Local' ;
                    type enumeration {
                      enum Remote {
                        value 0 ;
                      }

                      enum Local {
                        value 1 ;
                      }

                    }

                  }

                  leaf rd {
                    description 'RD.' ;
                    type string {
                      length 0..23 ;

                    }

                  }

                  leaf source {
                    description 'Source address.' ;
                    type ncd:ipv4-address ;

                  }

                  leaf group {
                    description 'Group address.' ;
                    type ncd:ipv4-address ;

                  }

                  leaf origin-ip {
                    description 'Origin IP address.' ;
                    type ncd:ipv4-address ;

                  }

                  leaf tunnel-label {
                    description 'Tunnel label.' ;
                    type uint32 ;

                  }

                  leaf tunnel-type {
                    description 'Tunnel type.
0:No-Tunnel
1:TE-P2MP
2:mLDP-P2MP
3:PIM-SSM
4:PIM-SM
5:PIM-BIDIR
6:INGRESS-RPL
7:mLDP-MP2MP' ;
                    type enumeration {
                      enum No-Tunnel {
                        value 0 ;
                      }

                      enum TE-P2MP {
                        value 1 ;
                      }

                      enum mLDP-P2MP {
                        value 2 ;
                      }

                      enum PIM-SSM {
                        value 3 ;
                      }

                      enum PIM-SM {
                        value 4 ;
                      }

                      enum PIM-BIDIR {
                        value 5 ;
                      }

                      enum INGRESS-RPL {
                        value 6 ;
                      }

                      enum mLDP-MP2MP {
                        value 7 ;
                      }

                    }

                  }

                  leaf tunnel-state {
                    description 'Tunnel state.
1:Leave
2:Join' ;
                    type enumeration {
                      enum Leave {
                        value 1 ;
                      }

                      enum Join {
                        value 2 ;
                      }

                    }

                  }

                  leaf leaf-require {
                    description 'Leaf require.
0:N
1:Y' ;
                    type enumeration {
                      enum N {
                        value 0 ;
                      }

                      enum Y {
                        value 1 ;
                      }

                    }

                  }

                  leaf tunnel-id {
                    description 'Tunnel ID.' ;
                    type string {
                      length 0..31 ;

                    }

                  }

                  ncd:select source ;
                  ncd:select group ;
                  ncd:select origin-ip ;
                  ncd:select "source group" ;
                  ncd:select "source origin-ip" ;
                  ncd:select "group origin-ip" ;
                  ncd:select "source group origin-ip" ;
                }

              }

              container leaf-ads {
                description 'Leaf-AD auto discovery route.' ;
                list leaf-ad {
                  description 'Leaf-AD auto discovery route.' ;
                  key 'ad-state type spmsi-rd spmsi-source spmsi-group spmsi-origin-ip origin-ip' ;
                  leaf ad-state {
                    description 'AD route state.
0:Remote
1:Local' ;
                    type enumeration {
                      enum Remote {
                        value 0 ;
                      }

                      enum Local {
                        value 1 ;
                      }

                    }

                  }

                  leaf type {
                    description 'AD route type.
2:Inter-AS
3:Spmsi-AD' ;
                    type enumeration {
                      enum Inter-AS {
                        value 2 ;
                      }

                      enum Spmsi-AD {
                        value 3 ;
                      }

                    }

                  }

                  leaf spmsi-rd {
                    description 'Spmsi-AD RD.' ;
                    type string {
                      length 0..23 ;

                    }

                  }

                  leaf spmsi-source {
                    description 'Spmsi-AD source address.' ;
                    type ncd:ipv4-address ;

                  }

                  leaf spmsi-group {
                    description 'Spmsi-AD group address.' ;
                    type ncd:ipv4-address ;

                  }

                  leaf spmsi-origin-ip {
                    description 'Spmsi-AD origin IP address.' ;
                    type ncd:ipv4-address ;

                  }

                  leaf origin-ip {
                    description 'Origin IP address.' ;
                    type ncd:ipv4-address ;

                  }

                  leaf nexthop {
                    description 'Nexthop address.' ;
                    type ncd:ipv4-address ;

                  }

                  ncd:select spmsi-source ;
                  ncd:select spmsi-group ;
                  ncd:select origin-ip ;
                  ncd:select "spmsi-source spmsi-group" ;
                  ncd:select "spmsi-source origin-ip" ;
                  ncd:select "spmsi-group origin-ip" ;
                  ncd:select "spmsi-source spmsi-group origin-ip" ;
                }

              }

              container source-actives {
                description 'Source-active auto discovery route.' ;
                list source-active {
                  description 'Source-active auto discovery route.' ;
                  key 'ad-state rd source group' ;
                  leaf ad-state {
                    description 'AD route state.
0:Remote
1:Local' ;
                    type enumeration {
                      enum Remote {
                        value 0 ;
                      }

                      enum Local {
                        value 1 ;
                      }

                    }

                  }

                  leaf rd {
                    description 'RD.' ;
                    type string {
                      length 0..23 ;

                    }

                  }

                  leaf source {
                    description 'Source address.' ;
                    type ncd:ipv4-address ;

                  }

                  leaf group {
                    description 'Group address.' ;
                    type ncd:ipv4-address ;

                  }

                  leaf nexthop {
                    description 'Nexthop address.' ;
                    type ncd:ipv4-address ;

                  }

                  ncd:select source ;
                  ncd:select group ;
                  ncd:select "source group" ;
                }

              }

              container xg-joins {
                description 'XG-join route.' ;
                list xg-join {
                  description 'XG-join route.' ;
                  key 'ad-state rd source-as rp-addr group' ;
                  leaf ad-state {
                    description 'AD route state.
0:Remote
1:Local' ;
                    type enumeration {
                      enum Remote {
                        value 0 ;
                      }

                      enum Local {
                        value 1 ;
                      }

                    }

                  }

                  leaf rd {
                    description 'RD.' ;
                    type string {
                      length 0..23 ;

                    }

                  }

                  leaf source-as {
                    description 'Source autonomous system number.' ;
                    type uint32 ;

                  }

                  leaf rp-addr {
                    description 'RP address.' ;
                    type ncd:ipv4-address ;

                  }

                  leaf group {
                    description 'Group address.' ;
                    type ncd:ipv4-address ;

                  }

                  leaf nexthop {
                    description 'Nexthop address.' ;
                    type ncd:ipv4-address ;

                  }

                  ncd:select rp-addr ;
                  ncd:select group ;
                  ncd:select "rp-addr group" ;
                }

                ncd:revise-date 2015-08-12 ;
              }

              container sg-joins {
                description 'SG-join route.' ;
                list sg-join {
                  description 'SG-join route.' ;
                  key 'ad-state rd source-as source group' ;
                  leaf ad-state {
                    description 'AD route state.
0:Remote
1:Local' ;
                    type enumeration {
                      enum Remote {
                        value 0 ;
                      }

                      enum Local {
                        value 1 ;
                      }

                    }

                  }

                  leaf rd {
                    description 'RD.' ;
                    type string {
                      length 0..23 ;

                    }

                  }

                  leaf source-as {
                    description 'Source autonomous system number.' ;
                    type uint32 ;

                  }

                  leaf source {
                    description 'Source address.' ;
                    type ncd:ipv4-address ;

                  }

                  leaf group {
                    description 'Group address.' ;
                    type ncd:ipv4-address ;

                  }

                  leaf nexthop {
                    description 'Nexthop address.' ;
                    type ncd:ipv4-address ;

                  }

                  ncd:select source ;
                  ncd:select group ;
                  ncd:select "source group" ;
                }

              }

              ncd:select vrf-name ;
            }

          }

          container auto-discovery-routes {
            description 'MVPN auto discovery route information.' ;
            list auto-discovery-route {
              description 'MVPN auto discovery route information.' ;
              key vrf-name ;
              leaf vrf-name {
                description 'VPN Routing/Forwarding instance name.' ;
                type string {
                  length 1..32 ;

                }

              }

              container intra-ases {
                description 'Intra-AS auto discovery route.' ;
                list intra-as {
                  description 'Intra-AS auto discovery route.' ;
                  key 'rd origin-ip' ;
                  leaf rd {
                    description 'RD.' ;
                    type string {
                      length 0..23 ;

                    }

                  }

                  leaf origin-ip {
                    description 'Origin IP address.' ;
                    type string {
                      length 1..39 ;

                    }

                  }

                  leaf root-tunnel {
                    description 'Root Tunnel.
Flags: L- Local,R- Remote,J- Join Ptnl,S- Start Ptnl,T0- No Ptnl 
       T1- RSVP-TE,T2- mLDP-P2MP,T3- PIM-SSM,T4- PIM-SM,T5- PIM-Bidir
       T6- Ingress-Replication,T7- mLDP-MP2MP,T11- BIER
(flags:type:label:id)/Flags' ;
                    type ncd:string-all {
                      length 0..119 ;

                    }

                  }

                  leaf leaf-tunnel {
                    description 'Leaf Tunnel.
Flags: L- Local,R- Remote,J- Join Ptnl,S- Start Ptnl,T0- No Ptnl 
       T1- RSVP-TE,T2- mLDP-P2MP,T3- PIM-SSM,T4- PIM-SM,T5- PIM-Bidir
       T6- Ingress-Replication,T7- mLDP-MP2MP,T11- BIER
(flags:type:label:id)/Flags' ;
                    type ncd:string-all {
                      length 0..119 ;

                    }

                  }

                  leaf ir-tunnel {
                    description 'Ingress replication tunnel.
Flags: L- Local,R- Remote,J- Join Ptnl,S- Start Ptnl,T0- No Ptnl 
       T1- RSVP-TE,T2- mLDP-P2MP,T3- PIM-SSM,T4- PIM-SM,T5- PIM-Bidir
       T6- Ingress-Replication,T7- mLDP-MP2MP,T11- BIER
(flags:type:label:id)/Flags' ;
                    type ncd:string-all {
                      length 0..119 ;

                    }

                  }

                  ncd:select origin-ip ;
                }

              }

              container inter-ases {
                description 'Inter-AS auto discovery route.' ;
                list inter-as {
                  description 'Inter-AS auto discovery route.' ;
                  key 'rd source-as' ;
                  leaf rd {
                    description 'RD.' ;
                    type string {
                      length 0..23 ;

                    }

                  }

                  leaf source-as {
                    description 'Source autonomous system number.' ;
                    type uint32 ;

                  }

                  leaf root-tunnel {
                    description 'Root Tunnel.
Flags: L- Local,R- Remote,J- Join Ptnl,S- Start Ptnl,T0- No Ptnl 
       T1- RSVP-TE,T2- mLDP-P2MP,T3- PIM-SSM,T4- PIM-SM,T5- PIM-Bidir
       T6- Ingress-Replication,T7- mLDP-MP2MP,T11- BIER
(flags:type:label:id)/Flags' ;
                    type ncd:string-all {
                      length 0..119 ;

                    }

                  }

                  leaf leaf-tunnel {
                    description 'Leaf tunnel.
Flags: L- Local,R- Remote,J- Join Ptnl,S- Start Ptnl,T0- No Ptnl 
       T1- RSVP-TE,T2- mLDP-P2MP,T3- PIM-SSM,T4- PIM-SM,T5- PIM-Bidir
       T6- Ingress-Replication,T7- mLDP-MP2MP,T11- BIER
(flags:type:label:id)/Flags' ;
                    type ncd:string-all {
                      length 0..119 ;

                    }

                  }

                  leaf ir-tunnel {
                    description 'Ingress replication tunnel.
Flags: L- Local,R- Remote,J- Join Ptnl,S- Start Ptnl,T0- No Ptnl 
       T1- RSVP-TE,T2- mLDP-P2MP,T3- PIM-SSM,T4- PIM-SM,T5- PIM-Bidir
       T6- Ingress-Replication,T7- mLDP-MP2MP,T11- BIER
(flags:type:label:id)/Flags' ;
                    type ncd:string-all {
                      length 0..119 ;

                    }

                  }

                  ncd:select source-as ;
                }

              }

              container spmsi-ads {
                description 'Spmsi-AD auto discovery route.' ;
                list spmsi-ad {
                  description 'Spmsi-AD auto discovery route.' ;
                  key 'rd source group origin-ip' ;
                  leaf rd {
                    description 'RD.' ;
                    type string {
                      length 0..23 ;

                    }

                  }

                  leaf source {
                    description 'Source address.' ;
                    type ncd:ipv4-address ;

                  }

                  leaf group {
                    description 'Group address.' ;
                    type ncd:ipv4-address ;

                  }

                  leaf origin-ip {
                    description 'Origin IP address.' ;
                    type string {
                      length 1..39 ;

                    }

                  }

                  leaf root-tunnel {
                    description 'Root tunnel.
Flags: L- Local,R- Remote,J- Join Ptnl,S- Start Ptnl,T0- No Ptnl 
       T1- RSVP-TE,T2- mLDP-P2MP,T3- PIM-SSM,T4- PIM-SM,T5- PIM-Bidir
       T6- Ingress-Replication,T7- mLDP-MP2MP,T11- BIER
(flags:type:label:id)/Flags' ;
                    type ncd:string-all {
                      length 0..119 ;

                    }

                  }

                  leaf leaf-tunnel {
                    description 'Leaf tunnel.
Flags: L- Local,R- Remote,J- Join Ptnl,S- Start Ptnl,T0- No Ptnl 
       T1- RSVP-TE,T2- mLDP-P2MP,T3- PIM-SSM,T4- PIM-SM,T5- PIM-Bidir
       T6- Ingress-Replication,T7- mLDP-MP2MP,T11- BIER
(flags:type:label:id)/Flags' ;
                    type ncd:string-all {
                      length 0..119 ;

                    }

                  }

                  leaf ir-tunnel {
                    description 'Ingress replication tunnel.
Flags: L- Local,R- Remote,J- Join Ptnl,S- Start Ptnl,T0- No Ptnl 
       T1- RSVP-TE,T2- mLDP-P2MP,T3- PIM-SSM,T4- PIM-SM,T5- PIM-Bidir
       T6- Ingress-Replication,T7- mLDP-MP2MP,T11- BIER
(flags:type:label:id)/Flags' ;
                    type ncd:string-all {
                      length 0..119 ;

                    }

                  }

                  ncd:select source ;
                  ncd:select group ;
                  ncd:select origin-ip ;
                  ncd:select "source group" ;
                  ncd:select "source origin-ip" ;
                  ncd:select "group origin-ip" ;
                  ncd:select "source group origin-ip" ;
                }

              }

              container leaf-ads {
                description 'Leaf-AD auto discovery route.' ;
                list leaf-ad {
                  description 'Leaf-AD auto discovery route.' ;
                  key 'type sub-rd sub-source sub-group sub-origin-ip sub-source-as origin-ip' ;
                  leaf type {
                    description 'AD route type.
1:Intra-AS
2:Inter-AS
3:Spmsi-AD' ;
                    type enumeration {
                      enum Intra-AS {
                        value 1 ;
                      }

                      enum Inter-AS {
                        value 2 ;
                      }

                      enum Spmsi-AD {
                        value 3 ;
                      }

                    }

                  }

                  leaf sub-rd {
                    description 'RD.' ;
                    type string {
                      length 0..23 ;

                    }

                  }

                  leaf sub-source {
                    description 'Source address.' ;
                    type ncd:ipv4-address ;

                  }

                  leaf sub-group {
                    description 'Group address.' ;
                    type ncd:ipv4-address ;

                  }

                  leaf sub-origin-ip {
                    description 'Origin IP address.' ;
                    type string {
                      length 1..39 ;

                    }

                  }

                  leaf sub-source-as {
                    description 'Source autonomous system number.' ;
                    type uint32 ;

                  }

                  leaf origin-ip {
                    description 'Origin IP address.' ;
                    type string {
                      length 1..39 ;

                    }

                  }

                  leaf p-tunnel {
                    description 'Public tunnel.
Flags: L- Local,R- Remote,J- Join Ptnl,S- Start Ptnl,T0- No Ptnl 
       T1- RSVP-TE,T2- mLDP-P2MP,T3- PIM-SSM,T4- PIM-SM,T5- PIM-Bidir
       T6- Ingress-Replication,T7- mLDP-MP2MP,T11- BIER
(flags:type:label:id)/Flags' ;
                    type ncd:string-all {
                      length 0..119 ;

                    }

                  }

                  ncd:select origin-ip ;
                }

              }

              container source-actives {
                description 'Source active auto discovery route.' ;
                list source-active {
                  description 'Source active auto discovery route.' ;
                  key 'ad-state rd source group' ;
                  leaf ad-state {
                    description 'AD route state.
0:Remote
1:Local' ;
                    type enumeration {
                      enum Remote {
                        value 0 ;
                      }

                      enum Local {
                        value 1 ;
                      }

                    }

                  }

                  leaf rd {
                    description 'RD.' ;
                    type string {
                      length 0..23 ;

                    }

                  }

                  leaf source {
                    description 'Source address.' ;
                    type ncd:ipv4-address ;

                  }

                  leaf group {
                    description 'Group address.' ;
                    type ncd:ipv4-address ;

                  }

                  leaf nexthop {
                    description 'Nexthop address.' ;
                    type string {
                      length 0..39 ;

                    }

                  }

                  ncd:select source ;
                  ncd:select group ;
                  ncd:select "source group" ;
                }

              }

              container xg-joins {
                description 'XG join route.' ;
                list xg-join {
                  description 'XG join route.' ;
                  key 'ad-state rd source-as rp-addr group' ;
                  leaf ad-state {
                    description 'AD route state.
0:Remote
1:Local' ;
                    type enumeration {
                      enum Remote {
                        value 0 ;
                      }

                      enum Local {
                        value 1 ;
                      }

                    }

                  }

                  leaf rd {
                    description 'RD.' ;
                    type string {
                      length 0..23 ;

                    }

                  }

                  leaf source-as {
                    description 'Source autonomous system number.' ;
                    type uint32 ;

                  }

                  leaf rp-addr {
                    description 'RP address.' ;
                    type ncd:ipv4-address ;

                  }

                  leaf group {
                    description 'Group address.' ;
                    type ncd:ipv4-address ;

                  }

                  leaf nexthop {
                    description 'Nexthop address.' ;
                    type string {
                      length 0..39 ;

                    }

                  }

                  ncd:select rp-addr ;
                  ncd:select group ;
                  ncd:select "rp-addr group" ;
                }

              }

              container sg-joins {
                description 'SG join route.' ;
                list sg-join {
                  description 'SG join route.' ;
                  key 'ad-state rd source-as source group' ;
                  leaf ad-state {
                    description 'AD route state.
0:Remote
1:Local' ;
                    type enumeration {
                      enum Remote {
                        value 0 ;
                      }

                      enum Local {
                        value 1 ;
                      }

                    }

                  }

                  leaf rd {
                    description 'RD.' ;
                    type string {
                      length 0..23 ;

                    }

                  }

                  leaf source-as {
                    description 'Source autonomous system number.' ;
                    type uint32 ;

                  }

                  leaf source {
                    description 'Source address.' ;
                    type ncd:ipv4-address ;

                  }

                  leaf group {
                    description 'Group address.' ;
                    type ncd:ipv4-address ;

                  }

                  leaf nexthop {
                    description 'Nexthop address.' ;
                    type string {
                      length 0..39 ;

                    }

                  }

                  ncd:select source ;
                  ncd:select group ;
                  ncd:select "source group" ;
                }

              }

              ncd:select vrf-name ;
            }

            ncd:revise-date 2016-11-29 ;
          }

          container mtibs {
            description 'MVPN tunnel information.' ;
            list mtib {
              description 'MVPN tunnel information.' ;
              key 'vrf-name tunnel-id tunnel-type' ;
              leaf vrf-name {
                description 'VPN Routing/Forwarding instance name.' ;
                type string {
                  length 1..32 ;

                }

              }

              leaf tunnel-id {
                description 'Tunnel ID.' ;
                type uint32 ;

              }

              leaf tunnel-type {
                description 'Tunnel type.
0:No-Tunnel
1:TE-P2MP
2:mLDP-P2MP
3:PIM-SSM
4:PIM-SM
5:PIM-BIDIR
6:INGRESS-RPL
7:mLDP-MP2MP
11:BIER' ;
                type enumeration {
                  enum No-Tunnel {
                    value 0 ;
                  }

                  enum TE-P2MP {
                    value 1 ;
                  }

                  enum mLDP-P2MP {
                    value 2 ;
                  }

                  enum PIM-SSM {
                    value 3 ;
                  }

                  enum PIM-SM {
                    value 4 ;
                  }

                  enum PIM-BIDIR {
                    value 5 ;
                  }

                  enum INGRESS-RPL {
                    value 6 ;
                  }

                  enum mLDP-MP2MP {
                    value 7 ;
                  }

                  enum BIER {
                    value 11 ;
                  }

                }

              }

              leaf tunnel-state {
                description 'Tunnel state.
0:Root
1:Leaf' ;
                type enumeration {
                  enum Root {
                    value 0 ;
                  }

                  enum Leaf {
                    value 1 ;
                  }

                }

              }

              leaf leaf-require {
                description 'Leaf require.
0:N
1:Y' ;
                type enumeration {
                  enum N {
                    value 0 ;
                  }

                  enum Y {
                    value 1 ;
                  }

                }

              }

              leaf protocol-state {
                description 'Protocol state.
0:Up
1:Down
2:Join
3:Leave' ;
                type enumeration {
                  enum Up {
                    value 0 ;
                  }

                  enum Down {
                    value 1 ;
                  }

                  enum Join {
                    value 2 ;
                  }

                  enum Leave {
                    value 3 ;
                  }

                }

              }

              leaf tunnel-label {
                description 'Tunnel label.' ;
                type uint32 ;

              }

              leaf tunnel-attr {
                description 'Tunnel attribute.' ;
                type ncd:string-all {
                  length 0..119 ;

                }

              }

              leaf leave-delay {
                description 'Leave delay.' ;
                type string {
                  length 0..15 ;

                }

              }

              container multi-imports {
                description 'Multi-import VPN information.' ;
                list multi-import {
                  description 'Multi-import VPN information.' ;
                  key sub-vrf-name ;
                  leaf sub-vrf-name {
                    description 'Multi-import VPN Routing/Forwarding instance name.
If the instance is public, the value of the node is IP global, else is VRF name.' ;
                    type ncd:string-all {
                      length 1..32 ;

                    }

                  }

                  leaf sub-tunnel-state {
                    description 'Tunnel state.' ;
                    type ncd:string-all {
                      length 0..15 ;

                    }

                    ncd:revise-date 2016-11-29 ;
                  }

                  ncd:select sub-vrf-name ;
                }

              }

              ncd:select vrf-name ;
              ncd:select "vrf-name tunnel-id tunnel-type" ;
            }

          }

          container ipmsi-infos {
            description 'MVPN IPMSI information.' ;
            list ipmsi-info {
              description 'MVPN IPMSI information.' ;
              key 'vrf-name tunnel-id tunnel-type' ;
              leaf vrf-name {
                description 'VPN Routing/Forwarding instance name.' ;
                type string {
                  length 1..32 ;

                }

              }

              leaf tunnel-id {
                description 'Tunnel ID.' ;
                type uint32 ;

              }

              leaf tunnel-type {
                description 'Tunnel type.
0:No-Tunnel
1:TE-P2MP
2:mLDP-P2MP
3:PIM-SSM
4:PIM-SM
5:PIM-BIDIR
6:INGRESS-RPL
7:mLDP-MP2MP
11:BIER' ;
                type enumeration {
                  enum No-Tunnel {
                    value 0 ;
                  }

                  enum TE-P2MP {
                    value 1 ;
                  }

                  enum mLDP-P2MP {
                    value 2 ;
                  }

                  enum PIM-SSM {
                    value 3 ;
                  }

                  enum PIM-SM {
                    value 4 ;
                  }

                  enum PIM-BIDIR {
                    value 5 ;
                  }

                  enum INGRESS-RPL {
                    value 6 ;
                  }

                  enum mLDP-MP2MP {
                    value 7 ;
                  }

                  enum BIER {
                    value 11 ;
                  }

                }

              }

              leaf tunnel-state {
                description 'Tunnel state.' ;
                type ncd:string-all {
                  length 0..15 ;

                }

              }

              leaf tunnel-attr {
                description 'Tunnel attribute.' ;
                type ncd:string-all {
                  length 0..119 ;

                }

              }

              leaf gbier-info {
                description 'GBIER information.' ;
                type ncd:string-all {
                  length 0..119 ;

                }

              }

              leaf root-info {
                description 'Root information.' ;
                type ncd:string-all {
                  length 0..79 ;

                }

              }

              container leaf-infos {
                description 'Leaf information.' ;
                list leaf-info {
                  description 'Leaf information.' ;
                  key 'egress-pe mpls-label' ;
                  leaf egress-pe {
                    description 'Egress PE.' ;
                    type ncd:string-all {
                      length 1..39 ;

                    }

                  }

                  leaf mpls-label {
                    description 'MPLS label.' ;
                    type uint32 ;

                  }

                  leaf bier-prefix {
                    description 'BIER prefix address..' ;
                    type ncd:string-all {
                      length 0..39 ;

                    }

                  }

                  leaf bier-bfr-id {
                    description 'BIER BFR ID.' ;
                    type uint16 ;

                  }

                  ncd:select egress-pe ;
                }

              }

              ncd:select vrf-name ;
              ncd:select "vrf-name tunnel-id tunnel-type" ;
            }

            ncd:revise-date 2023-10-12 ;
          }

          container spmsi-infos {
            description 'MVPN SPMSI information.' ;
            list spmsi-info {
              description 'MVPN SPMSI information.' ;
              key 'vrf-name tunnel-id tunnel-type' ;
              leaf vrf-name {
                description 'VPN Routing/Forwarding instance name.' ;
                type string {
                  length 1..32 ;

                }

              }

              leaf tunnel-id {
                description 'Tunnel ID.' ;
                type uint32 ;

              }

              leaf tunnel-type {
                description 'Tunnel type.
0:No-Tunnel
1:TE-P2MP
2:mLDP-P2MP
3:PIM-SSM
4:PIM-SM
5:PIM-BIDIR
6:INGRESS-RPL
7:mLDP-MP2MP
11:BIER' ;
                type enumeration {
                  enum No-Tunnel {
                    value 0 ;
                  }

                  enum TE-P2MP {
                    value 1 ;
                  }

                  enum mLDP-P2MP {
                    value 2 ;
                  }

                  enum PIM-SSM {
                    value 3 ;
                  }

                  enum PIM-SM {
                    value 4 ;
                  }

                  enum PIM-BIDIR {
                    value 5 ;
                  }

                  enum INGRESS-RPL {
                    value 6 ;
                  }

                  enum mLDP-MP2MP {
                    value 7 ;
                  }

                  enum BIER {
                    value 11 ;
                  }

                }

              }

              leaf tunnel-state {
                description 'Tunnel state.' ;
                type ncd:string-all {
                  length 0..15 ;

                }

              }

              leaf tunnel-attr {
                description 'Tunnel attribute.' ;
                type ncd:string-all {
                  length 0..119 ;

                }

              }

              leaf gbier-info {
                description 'GBIER information.' ;
                type ncd:string-all {
                  length 0..119 ;

                }

              }

              leaf root-info {
                description 'Root information.' ;
                type ncd:string-all {
                  length 0..79 ;

                }

              }

              container leaf-infos {
                description 'Leaf information.' ;
                list leaf-info {
                  description 'Leaf information.' ;
                  key 'egress-pe mpls-label' ;
                  leaf egress-pe {
                    description 'Egress PE.' ;
                    type ncd:string-all {
                      length 1..39 ;

                    }

                  }

                  leaf mpls-label {
                    description 'MPLS label.' ;
                    type uint32 ;

                  }

                  leaf bier-prefix {
                    description 'BIER prefix address..' ;
                    type ncd:string-all {
                      length 0..39 ;

                    }

                  }

                  leaf bier-bfr-id {
                    description 'BIER BFR ID.' ;
                    type uint16 ;

                  }

                  ncd:select egress-pe ;
                }

              }

              ncd:select vrf-name ;
              ncd:select "vrf-name tunnel-id tunnel-type" ;
            }

            ncd:revise-date 2023-10-12 ;
          }

          container pmsi-summarys {
            description 'The summary information of PMSI tunnel.' ;
            list pmsi-summary {
              description 'The summary information of PMSI tunnel.' ;
              key vrf-name ;
              leaf vrf-name {
                type string {
                  length 1..32 ;

                }

              }

              leaf ipmsi-number {
                description 'IPMSI tunnel summary.' ;
                type uint32 ;

              }

              leaf spmsi-number {
                description 'SPMSI tunnel summary.' ;
                type uint32 ;

              }

              ncd:select vrf-name ;
            }

            ncd:revise-date 2023-10-12 ;
          }

          container mribs {
            description 'MVPN route information.' ;
            list mrib {
              description 'MVPN route information.' ;
              key 'vrf-name source group' ;
              leaf vrf-name {
                description 'VPN Routing/Forwarding instance name.' ;
                type string {
                  length 1..32 ;

                }

              }

              leaf source {
                description 'Source address.' ;
                type ncd:ipv4-address ;

              }

              leaf group {
                description 'Group address.' ;
                type ncd:ipv4-address ;

              }

              leaf intf-state {
                description 'Interface state.
IFT - Receive from P-tunnel
OFT - Send to P-tunnel
OFNL - Downstream join state' ;
                type string {
                  length 0..15 ;

                }

              }

              leaf upstream-tunnel {
                description 'Upstream tunnel.' ;
                type ncd:string-all {
                  length 0..79 ;

                }

              }

              leaf upstream-pe {
                description 'Upstream PE address.' ;
                type string {
                  length 0..39 ;

                }

              }

              leaf rpf-tunnel-id {
                description 'RPF tunnel ID.' ;
                type uint32 ;

              }

              leaf rpf-vrf-name {
                description 'RPF VPN Routing/Forwarding instance name.' ;
                type string {
                  length 0..32 ;

                }

              }

              leaf downstream-tunnel {
                description 'Downstream tunnel.' ;
                type ncd:string-all {
                  length 0..79 ;

                }

              }

              leaf switch-tunnel {
                description 'Switch tunnel.' ;
                type ncd:string-all {
                  length 0..79 ;

                }

              }

              leaf switch-time {
                description 'Switch time.' ;
                type string {
                  length 0..15 ;

                }

              }

              container spmsi-ads {
                status obsolete {
                  ncd:revise-date 2016-11-29 ;
                }

                description 'Spmsi-AD auto discovery route.' ;
                list spmsi-ad {
                  description 'Spmsi-AD auto discovery route.' ;
                  key 'ad-state rd source group origin-ip' ;
                  leaf ad-state {
                    description 'AD route state.
0:Remote
1:Local' ;
                    type enumeration {
                      enum Remote {
                        value 0 ;
                      }

                      enum Local {
                        value 1 ;
                      }

                    }

                  }

                  leaf rd {
                    description 'RD.' ;
                    type string {
                      length 0..23 ;

                    }

                  }

                  leaf source {
                    description 'Source address.' ;
                    type ncd:ipv4-address ;

                  }

                  leaf group {
                    description 'Group address.' ;
                    type ncd:ipv4-address ;

                  }

                  leaf origin-ip {
                    description 'Origin IP address.' ;
                    type ncd:ipv4-address ;

                  }

                  leaf spmsi-tunnel {
                    description 'Spmsi tunnel.' ;
                    type ncd:string-all {
                      length 0..79 ;

                    }

                  }

                  leaf uptime {
                    description 'Uptime.' ;
                    type string {
                      length 0..15 ;

                    }

                  }

                  ncd:select origin-ip ;
                }

              }

              container spmsi-auto-discoveries {
                description 'Spmsi-AD auto discovery route.' ;
                list spmsi-auto-discovery {
                  description 'Spmsi-AD auto discovery route.' ;
                  key 'rd source group origin-ip' ;
                  leaf rd {
                    description 'RD.' ;
                    type string {
                      length 0..23 ;

                    }

                  }

                  leaf source {
                    description 'Source address.' ;
                    type ncd:ipv4-address ;

                  }

                  leaf group {
                    description 'Group address.' ;
                    type ncd:ipv4-address ;

                  }

                  leaf origin-ip {
                    description 'Origin IP address.' ;
                    type string {
                      length 1..39 ;

                    }

                  }

                  leaf root-tunnel {
                    description 'Root tunnel.' ;
                    type ncd:string-all {
                      length 0..79 ;

                    }

                  }

                  leaf ad-state {
                    description 'AD route state.
0:Remote
1:Local
2:Local/Remote' ;
                    type enumeration {
                      enum Remote {
                        value 0 ;
                      }

                      enum Local {
                        value 1 ;
                      }

                      enum "Local/Remote" {
                        value 2 ;
                      }

                    }

                  }

                  leaf leaf-tunnel {
                    description 'Leaf tunnel.' ;
                    type ncd:string-all {
                      length 0..79 ;

                    }

                  }

                  leaf ir-tunnel {
                    description 'Ingress replication tunnel.' ;
                    type ncd:string-all {
                      length 0..79 ;

                    }

                  }

                  leaf uptime {
                    description 'Uptime.' ;
                    type string {
                      length 0..15 ;

                    }

                  }

                  ncd:select origin-ip ;
                }

                ncd:revise-date 2016-11-29 ;
              }

              container leaf-ads {
                status obsolete {
                  ncd:revise-date 2016-11-29 ;
                }

                description 'Leaf-AD auto discovery route.' ;
                list leaf-ad {
                  description 'Leaf-AD auto discovery route.' ;
                  key 'ad-state type spmsi-rd spmsi-source spmsi-group spmsi-origin-ip origin-ip' ;
                  leaf ad-state {
                    description 'AD route state.
0:Remote
1:Local' ;
                    type enumeration {
                      enum Remote {
                        value 0 ;
                      }

                      enum Local {
                        value 1 ;
                      }

                    }

                  }

                  leaf type {
                    description 'AD route type.
2:Inter-AS
3:Spmsi-AD' ;
                    type enumeration {
                      enum Inter-AS {
                        value 2 ;
                      }

                      enum Spmsi-AD {
                        value 3 ;
                      }

                    }

                  }

                  leaf spmsi-rd {
                    description 'Spmsi-AD RD.' ;
                    type string {
                      length 0..23 ;

                    }

                  }

                  leaf spmsi-source {
                    description 'Spmsi-AD source address.' ;
                    type ncd:ipv4-address ;

                  }

                  leaf spmsi-group {
                    description 'Spmsi-AD group address.' ;
                    type ncd:ipv4-address ;

                  }

                  leaf spmsi-origin-ip {
                    description 'Spmsi-AD origin IP address.' ;
                    type ncd:ipv4-address ;

                  }

                  leaf origin-ip {
                    description 'Origin IP address.' ;
                    type ncd:ipv4-address ;

                  }

                  leaf uptime {
                    description 'Uptime.' ;
                    type string {
                      length 0..15 ;

                    }

                  }

                  ncd:select origin-ip ;
                }

              }

              container leaf-auto-discoveries {
                description 'Leaf-AD auto discovery route.' ;
                list leaf-auto-discovery {
                  description 'Leaf-AD auto discovery route.' ;
                  key 'type sub-rd sub-source sub-group sub-origin-ip origin-ip' ;
                  leaf type {
                    description 'AD route type.
1:Intra-AS
2:Inter-AS
3:Spmsi-AD' ;
                    type enumeration {
                      enum Intra-AS {
                        value 1 ;
                      }

                      enum Inter-AS {
                        value 2 ;
                      }

                      enum Spmsi-AD {
                        value 3 ;
                      }

                    }

                  }

                  leaf sub-rd {
                    description 'Sub RD.' ;
                    type string {
                      length 0..23 ;

                    }

                  }

                  leaf sub-source {
                    description 'Sub source address.' ;
                    type ncd:ipv4-address ;

                  }

                  leaf sub-group {
                    description 'Sub group address.' ;
                    type ncd:ipv4-address ;

                  }

                  leaf sub-origin-ip {
                    description 'Sub origin IP address.' ;
                    type string {
                      length 1..39 ;

                    }

                  }

                  leaf origin-ip {
                    description 'Origin IP address.' ;
                    type string {
                      length 1..39 ;

                    }

                  }

                  leaf ad-state {
                    description 'AD route state.
0:Remote
1:Local
2:Local/Remote' ;
                    type enumeration {
                      enum Remote {
                        value 0 ;
                      }

                      enum Local {
                        value 1 ;
                      }

                      enum "Local/Remote" {
                        value 2 ;
                      }

                    }

                  }

                  leaf uptime {
                    description 'Uptime.' ;
                    type string {
                      length 0..15 ;

                    }

                  }

                  ncd:select origin-ip ;
                }

                ncd:revise-date 2016-11-29 ;
              }

              container source-actives {
                description 'Source active auto discovery route.' ;
                list source-active {
                  description 'Source active auto discovery route.' ;
                  key 'ad-state rd source group' ;
                  leaf ad-state {
                    description 'AD route state.
0:Remote
1:Local' ;
                    type enumeration {
                      enum Remote {
                        value 0 ;
                      }

                      enum Local {
                        value 1 ;
                      }

                    }

                  }

                  leaf rd {
                    description 'RD.' ;
                    type string {
                      length 0..23 ;

                    }

                  }

                  leaf source {
                    description 'Source address.' ;
                    type ncd:ipv4-address ;

                  }

                  leaf group {
                    description 'Group address.' ;
                    type ncd:ipv4-address ;

                  }

                  leaf uptime {
                    description 'Uptime.' ;
                    type string {
                      length 0..15 ;

                    }

                  }

                  ncd:select ad-state ;
                }

              }

              container xg-joins {
                description 'XG join route.' ;
                list xg-join {
                  description 'XG join route.' ;
                  key 'ad-state rd source-as rp-addr group' ;
                  leaf ad-state {
                    description 'AD route state.
0:Remote
1:Local' ;
                    type enumeration {
                      enum Remote {
                        value 0 ;
                      }

                      enum Local {
                        value 1 ;
                      }

                    }

                  }

                  leaf rd {
                    description 'RD.' ;
                    type string {
                      length 0..23 ;

                    }

                  }

                  leaf source-as {
                    description 'Source autonomous system number.' ;
                    type uint32 ;

                  }

                  leaf rp-addr {
                    description 'RP address.' ;
                    type ncd:ipv4-address ;

                  }

                  leaf group {
                    description 'Group address.' ;
                    type ncd:ipv4-address ;

                  }

                  leaf uptime {
                    description 'Uptime.' ;
                    type string {
                      length 0..15 ;

                    }

                  }

                  ncd:select ad-state ;
                }

                ncd:revise-date 2015-08-12 ;
              }

              container sg-joins {
                description 'SG join route.' ;
                list sg-join {
                  description 'SG join route.' ;
                  key 'ad-state rd source-as source group' ;
                  leaf ad-state {
                    description 'AD route state.
0:Remote
1:Local' ;
                    type enumeration {
                      enum Remote {
                        value 0 ;
                      }

                      enum Local {
                        value 1 ;
                      }

                    }

                  }

                  leaf rd {
                    description 'RD.' ;
                    type string {
                      length 0..23 ;

                    }

                  }

                  leaf source-as {
                    description 'Source autonomous system number.' ;
                    type uint32 ;

                  }

                  leaf source {
                    description 'Source address.' ;
                    type ncd:ipv4-address ;

                  }

                  leaf group {
                    description 'Group address.' ;
                    type ncd:ipv4-address ;

                  }

                  leaf uptime {
                    description 'Uptime.' ;
                    type string {
                      length 0..15 ;

                    }

                  }

                  ncd:select ad-state ;
                }

              }

              ncd:select vrf-name ;
              ncd:select source ;
              ncd:select group ;
              ncd:select "vrf-name source" ;
              ncd:select "vrf-name group" ;
              ncd:select "source group" ;
              ncd:select "vrf-name source group" ;
            }

          }

          container ad-summarys {
            description 'The summary information of AD route.' ;
            list ad-summary {
              description 'The summary information of AD route.' ;
              key vrf-name ;
              leaf vrf-name {
                type string {
                  length 1..32 ;

                }

              }

              leaf intra-as-local {
                description 'Local intra-AS route summary.' ;
                type uint32 ;

              }

              leaf intra-as-remote {
                description 'Remote intra-AS route summary.' ;
                type uint32 ;

              }

              leaf intra-as-all {
                description 'Intra-AS route summary.' ;
                type uint32 ;

              }

              leaf inter-as-local {
                description 'Local inter-AS route summary.' ;
                type uint32 ;

              }

              leaf inter-as-remote {
                description 'Remote inter-AS route summary.' ;
                type uint32 ;

              }

              leaf inter-as-all {
                description 'Inter-AS route summary.' ;
                type uint32 ;

              }

              leaf spmsi-ad-local {
                description 'Local spmsi-AD route summary.' ;
                type uint32 ;

              }

              leaf spmsi-ad-remote {
                description 'Remote spmsi-AD route summary.' ;
                type uint32 ;

              }

              leaf spmsi-ad-all {
                description 'Spmsi-AD route summary.' ;
                type uint32 ;

              }

              leaf leaf-ad-local {
                description 'Local leaf-AD route summary.' ;
                type uint32 ;

              }

              leaf leaf-ad-remote {
                description 'Remote leaf-AD route summary.' ;
                type uint32 ;

              }

              leaf leaf-ad-all {
                description 'Leaf-AD route summary.' ;
                type uint32 ;

              }

              leaf source-active-local {
                description 'Local source active route summary.' ;
                type uint32 ;

              }

              leaf source-active-remote {
                description 'Remote source active route summary.' ;
                type uint32 ;

              }

              leaf source-active-all {
                description 'Source active route summary.' ;
                type uint32 ;

              }

              leaf xg-join-local {
                description 'Local XG join route summary.' ;
                type uint32 ;

              }

              leaf xg-join-remote {
                description 'Remote XG join route summary.' ;
                type uint32 ;

              }

              leaf xg-join-all {
                description 'XG join route summary.' ;
                type uint32 ;

              }

              leaf sg-join-local {
                description 'Local SG join route summary.' ;
                type uint32 ;

              }

              leaf sg-join-remote {
                description 'Remote SG join route summary.' ;
                type uint32 ;

              }

              leaf sg-join-all {
                description 'SG join route summary.' ;
                type uint32 ;

              }

              leaf local-ad-all {
                description 'Local AD route summary.' ;
                type uint32 ;

              }

              leaf remote-ad-all {
                description 'Remote AD route summary.' ;
                type uint32 ;

              }

              leaf ad-all {
                description 'AD route summary.' ;
                type uint32 ;

              }

              ncd:select vrf-name ;
            }

            ncd:revise-date 2016-11-29 ;
          }

        }

      }

    }

    ncd:revise-date 2015-03-31 ;
  }

  container operation {
    config false ;
    description 'Operation module.' ;
    container multicast {
      description 'Multicast' ;
      container public {
        description 'Public mode of multicast' ;
        container clear {
          description 'Clear node' ;
          container mroutes {
            description 'Multicast route.' ;
            list source-group {
              description 'Clear mroute of the designed source and group address.' ;
              key 'group source' ;
              leaf group {
                description 'Group address' ;
                type ncd:ipv4-address ;

              }

              leaf source {
                description 'Source address' ;
                type ncd:ipv4-address ;

              }

            }

            list group {
              description 'Clear mroute of the designed group address.' ;
              key group ;
              leaf group {
                description 'Group address' ;
                type ncd:ipv4-address ;

              }

            }

            container mroute {
              description 'Clear multicast public route.' ;
              leaf public {
                description 'Public' ;
                type empty ;

              }

            }

          }

        }

      }

      container private {
        description 'Private mode of multicast' ;
        container clear {
          description 'Clear node' ;
          container mroutes {
            description 'Multicast route.' ;
            list source-group {
              description 'Clear mroute of the designed vrf name,source and group address.' ;
              key 'vrf-name group source' ;
              leaf vrf-name {
                description 'VRF name' ;
                type string {
                  length 1..32 ;

                }

              }

              leaf group {
                description 'Group address' ;
                type ncd:ipv4-address ;

              }

              leaf source {
                description 'Source address' ;
                type ncd:ipv4-address ;

              }

            }

            list group {
              description 'Clear mroute of the designed vrf name and group address.' ;
              key 'vrf-name group' ;
              leaf vrf-name {
                description 'VRF name' ;
                type string {
                  length 1..32 ;

                }

              }

              leaf group {
                description 'Group address' ;
                type ncd:ipv4-address ;

              }

            }

            list mroute {
              description 'Clear mroute of the designed vrf name.' ;
              key vrf-name ;
              leaf vrf-name {
                description 'VRF name' ;
                type string {
                  length 1..32 ;

                }

              }

            }

          }

        }

      }

    }

    ncd:revise-date 2015-03-31 ;
  }

  notification mroute-summary {
    container all {
      config false ;
      description 'global and vrf mroute summary' ;
      leaf xg-count {
        description 'Total number of XG routes' ;
        type uint32 ;

      }

      leaf sg-count {
        description 'Total number of SG routes' ;
        type uint32 ;

      }

      leaf total-count {
        description 'Total number of multicast routes' ;
        type uint32 ;

      }

    }

    list specific {
      config false ;
      key vrf-name ;
      leaf vrf-name {
        description 'VRF name' ;
        type ncd:string-quesiton-mark ;

      }

      leaf xg-count {
        description 'Total number of XG routes' ;
        type uint32 ;

      }

      leaf sg-count {
        description 'Total number of SG routes' ;
        type uint32 ;

      }

      leaf total-count {
        description 'Total number of multicast routes' ;
        type uint32 ;

      }

    }

    ncd:revise-date 2021-12-08 ;
  }

}
