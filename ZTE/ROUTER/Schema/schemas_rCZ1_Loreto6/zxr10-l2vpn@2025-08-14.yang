module zxr10-l2vpn {
  namespace "http://www.zte.com.cn/zxr10/netconf/schema/rosng/l2vpn" ;
  prefix l2vpn ;
  yang-version 1 ;
  import zxr10-netconf-defs {
    prefix ncd ;
  }

  organization "ZTE Corporation" ;
  contact "ZTE Corporation
  Nanjing Institute of ZTE Corporation
  No.68 Zijinghua Rd. Yuhuatai District, Nanjing, China
  Tel: +86-25-52870000" ;
  description 'The netconf module to describe L2VPN services info.It contains state and configuration info.' ;
  revision 2025-08-14 {
    description '1.Add the mtu and mtu-mismatch-ignore leaf node which in configuration/l2vpn/service-instances/admin-vpls-instances/admin-vpls-instance.
2.Add the mtu and mtu-mismatch-ignore leaf node which in configuration/l2vpn/service-instances/remote-monitor-instance/remote-monitor-instance.' ;
  }

  revision 2025-07-16 {
    description '1.Add the enumeration of bgp and be which in state/l2vpn/pw-info/tunnel-policy-result/result-type.
2.Add the enumeration of bgp and be which in state/l2vpn/kompella-pw/kompella-pw-info/tunnel-policy-result/result-type.' ;
  }

  revision 2025-06-19 {
    description '1.Add the lst-holdoff leaf node which in configuration/l2vpn/service-instances/vpws-instances/vpws-instance/vpws-ac-bind/ac-instance-bind/ac-type/ethernet/ethernet-params.' ;
  }

  revision 2025-06-09 {
    description '1.Add label 5960x in feature l2cp-drop.
2.Add the feature of l2cp-drop-subset.' ;
  }

  revision 2025-06-03 {
    description '1.Add the mtu-mismatch-ignore leaf node which in configuration/l2vpn/service-instances/vlss-instances/vlss-instance.' ;
  }

  revision 2025-04-14 {
    description '1.Add outlabel5-outlabel24 leaf in state/l2vpn/pw-info.
2.Add outlabel5-outlabel24 leaf in state/l2vpn/kompella-pw/kompella-pw-info' ;
  }

  revision 2024-12-27 {
    description '1.Add the pfs-bits-tracked-ignore-remote-status leaf which in configuration/l2vpn/pw-specification/pw-entry.' ;
  }

  revision 2024-11-11 {
    description '1.After the auto-discovery martini is configured in VPLS instance or EVPN VPLS instance, the martini-discovery container is changed from cannot get to can get.
2.After the auto-discovery kompella is configured in VPLS instance or EVPN VPLS instance, the kompella-discovery container is changed from cannot get to can get.' ;
  }

  revision 2024-10-29 {
    description '1.The cir and pir nodes which in vpls-instance or evpn-vpls-instance cannot get when not config broadcast-traffic-rate.
2.The cir and pir nodes which in vpls-instance or evpn-vpls-instance cannot get when not config unknown-multicast-traffic-rate.
3.The cir and pir nodes which in vpls-instance or evpn-vpls-instance cannot get when not config unknown-unicast-traffic-rate.
4.The separate-in-signal nodes which in vpls-instance kompella kompella cannot get when not config encapsulation.
5.The separate-in-signal nodes which in evpn-vpls-instance kompella cannot get when not config encapsulation.' ;
  }

  revision 2024-10-11 {
    description '1.Add the l2vpn-evpn-prefix-sid container , delete-delay and delay-time leaf which in configuration/l2vpn/l2vpn-global' ;
  }

  revision 2024-08-13 {
    description '1.Delete the wtr-params choice and add the wtr , wtr-second-with-minute , wtr-second leaf which in configuration/l2vpn/service-instances/evpn-vpls-instances/evpn-vpls-instance.
2.Delete the wtr-params choice and add the wtr , wtr-second-with-minute , wtr-second leaf which in configuration/l2vpn/service-instances/vpws-community-instances/vpws-community-instance/auto-discovery-type/type/mpls-evpn/mpls-evpn-params.
3.Delete the wtr-params choice and add the wtr , wtr-second-with-minute , wtr-second leaf which in configuration/l2vpn/service-instances/vpws-community-instances/vpws-community-instance/auto-discovery-type/type/srv6-evpn/srv6-evpn-params.
4.Delete the wtr-params choice and add the wtr , wtr-second-with-minute , wtr-second leaf which in configuration/l2vpn/service-instances/vpws-community-instances/vpws-community-instance/auto-discovery-type/type/vxlan-evpn/vxlan-evpn-params.
5.Delete the wtr-params choice and add the wtr , wtr-second-with-minute , wtr-second leaf which in configuration/l2vpn/service-instances/ring-tree-instances/ring-tree-instance/revertive-mode-params.
6.Delete the wtr-params choice and add the wtr , wtr-second-with-minute , wtr-second leaf which in configuration/l2vpn/service-instances/l2vpn-p2p-services/l2vpn-p2p-service/static-srv6-evpn/srv6-remote-sid-params/srv6-remote-sid-param.' ;
  }

  revision 2024-07-15 {
    description '1.Add the FN.C89E and PC.SWITCH label on the feature of l2cp-drop.' ;
  }

  revision 2024-07-10 {
    description '1.Add the unknown-mac-withdraw-mode leaf which in configuration/l2vpn/service-instances/b-vpls-instances/b-vpls-instance.
2.Add the mac-withdraw-optimized-options leaf which in configuration/l2vpn/service-instances/b-vpls-instances/b-vpls-instance.' ;
  }

  revision 2024-07-09 {
    description '1.Modify the second node range from 0-3600 to 0-720 which in configuration/l2vpn/service-instances/evpn-vpls-instances/evpn-vpls-instance.
2.Modify the second node range from 0-3600 to 0-720 which in configuration/l2vpn/service-instances/vpws-community-instances/vpws-community-instance/auto-discovery-type/vxlan-evpn-params.
3.Modify the second node range from 0-3600 to 0-720 which in configuration/l2vpn/service-instances/vpws-community-instances/vpws-community-instance/auto-discovery-type/srv6-evpn-params.
4.Modify the second node range from 0-3600 to 0-720 which in configuration/l2vpn/service-instances/vpws-community-instances/vpws-community-instance/auto-discovery-type/mpls-evpn-params.
5.Modify the second node range from 0-3600 to 0-720 which in configuration/l2vpn/service-instances/l2vpn-p2p-services/l2vpn-p2p-service/static-srv6-evpn/srv6-remote-sid-params/srv6-remote-sid-param.' ;
  }

  revision 2024-07-02 {
    description '1.Remove the PC.MSE,PC.switch label from the feature of bridge-mapping.' ;
  }

  revision 2024-06-28 {
    description '1.Modify the description of CBP PBB and I-SID.
2.ADD the traffic-statistics-params container in configuration/l2vpn/service-instances/i-vpls-instances/i-vpls-instance.
3.Add the traffic-enable node in configuration/l2vpn/service-instances/i-vpls-instances/i-vpls-instance/i-vpls-ac-bind/ac-instance-bind/ac-type/ethernet/ethernet-params.' ;
  }

  revision 2024-06-19 {
    description '1.Modify the description of the yang node.' ;
  }

  revision 2024-06-01 {
    description '1.Add the encapsulation container in configuration/l2vpn:configuration/l2vpn:l2vpn/l2vpn:service-instances/l2vpn:vpws-community-instances/l2vpn:vpws-community-instance/l2vpn:auto-discovery-type/l2vpn:type/l2vpn:mpls-evpn/l2vpn:mpls-evpn-params/l2vpn:mpls-evpn-ac-bind/l2vpn:ac-instance-bind/l2vpn:ac-type/l2vpn:ethernet/l2vpn:ethernet-params
2.Add the encapsulation container in configuration/l2vpn:configuration/l2vpn:l2vpn/l2vpn:service-instances/l2vpn:vpws-community-instances/l2vpn:vpws-community-instance/l2vpn:auto-discovery-type/l2vpn:type/l2vpn:srv6-evpn/l2vpn:srv6-evpn-params/l2vpn:srv6-evpn-ac-bind/l2vpn:ac-instance-bind/l2vpn:ac-type/l2vpn:ethernet/l2vpn:ethernet-params
3.Add the encapsulation container in configuration/l2vpn:configuration/l2vpn:l2vpn/l2vpn:service-instances/l2vpn:vpws-community-instances/l2vpn:vpws-community-instance/l2vpn:auto-discovery-type/l2vpn:type/l2vpn:vxlan-evpn/l2vpn:vxlan-evpn-params/l2vpn:vxlan-evpn-ac-bind/l2vpn:ac-instance-bind/l2vpn:ac-type/l2vpn:ethernet/l2vpn:ethernet-params' ;
  }

  revision 2024-05-09 {
    description '1.Modify the mtu leaf maximum value range from 9216  to 65535 which in service-instances/vpws-instances/vpws-instance.
2.Modify the mtu leaf maximum value range from 9216  to 65535 which in service-instances/vpls-instances/vpls-instance.
3.Modify the mtu leaf maximum value range from 9216  to 65535 which in service-instances/mspw-instances/mspw-instance/remote-parameters.
4.Modify the mtu leaf maximum value range from 9216  to 65535 which in service-instances/evpn-vpls-instances/evpn-vpls-instance.
5.Modify the mtu leaf maximum value range from 9216  to 65535 which in service-instances/l2vpn:ring-tree-instances.
6.Modify the mtu leaf maximum value range from 9216  to 65535 which in service-instances/vlss-instances/vlss-instance.
7.Modify the mtu leaf maximum value range from 9216  to 65535 which in service-instances/b-vpls-instances/b-vpls-instance.' ;
  }

  revision 2024-04-15 {
    description '1.Add SWITCH.5960X and PC.SWITCH product label in flow-label feature.
2.Add SWITCH.5960X and PC.SWITCH product label in ac-traffic-statistics.
3.Add SWITCH.5960X and PC.SWITCH product label in pw-traffic-statistics.
4.Add SWITCH.5960X and PC.SWITCH product label in vlss-instances.
5.Add SWITCH.5960X product label in martini-discovery.
6.Add SWITCH.5960X and PC.SWITCH product label in kompella-discovery.' ;
  }

  revision 2024-04-01 {
    description '1.Add the l2vpn-usid-fib leaf which in configuration/l2vpn/l2vpn-global.' ;
  }

  revision 2024-01-23 {
    description '1.Add the vpls-irb-track-state leaf node which in configuration/l2vpn/l2vpn-global.' ;
  }

  revision 2024-01-18 {
    description '1.Add the encap-type leaf node which in configuration/l2vpn/service-instances/vpws-community-instances/vpws-community-instances/auto-discovery-type/type/srv6-evpn/srv6-evpn-params/srv6-evpn-ac-bind/ac-instance-bind/ac-type/ethernet-params/bfd-params.' ;
  }

  revision 2024-01-02 {
    description '1.Add the vlss-protect-rules container node which in configuration/l2vpn/service-instances/vlss-instances/vlss-instance/vlss-ac-bind.
2.Modify the range of the pw-group-id leaf from 1-4000 to 1-8192 which in state/l2vpn/pw-group-info.
3.Modify the range of the pw-list-id leaf from 1-1024 to 1-4096 which in state/l2vpn/pw-list.
4.Modify the range of the pw-group-id leaf from 1-4000 to 1-8192 which in state/l2vpn/access-pw-group.' ;
  }

  revision 2023-12-23 {
    description '1.Obsolete the vpls-irb-track-vpls-state container node which in configuration/l2vpn/l2vpn-global.' ;
  }

  revision 2023-12-12 {
    description '1.Add the wtr-params choice and wtr-minute case wtr-second case wtr-time node second node which in configuration/l2vpn/service-instances/evpn-vpls-instances/evpn-vpls-instance.
2.Add the wtr-params choice and wtr-minute case wtr-second case wtr-time node second node which in configuration/l2vpn/service-instances/vpws-community-instances/vpws-community-instance/auto-discovery-type/type/mpls-evpn/mpls-evpn-params.
3.Add the wtr-params choice and wtr-minute case wtr-second case wtr-time node second node which in configuration/l2vpn/service-instances/vpws-community-instances/vpws-community-instance/auto-discovery-type/type/srv6-evpn/srv6-evpn-params.
4.Add the wtr-params choice and wtr-minute case wtr-second case wtr-time node second node which in configuration/l2vpn/service-instances/vpws-community-instances/vpws-community-instance/auto-discovery-type/type/vxlan-evpn/vxlan-evpn-params.
5.Add the wtr-params choice and wtr-minute case wtr-second case wtr-time node second node which in configuration/l2vpn/service-instances/ring-tree-instances/ring-tree-instance/revertive-mode-params.
6.Add the wtr-params choice and wtr-minute case wtr-second case wtr-time node second node which in configuration/l2vpn/service-instances/l2vpn-p2p-services/l2vpn-p2p-service/static-srv6-evpn/srv6-remote-sid-params/srv6-remote-sid-param.' ;
  }

  revision 2023-12-11 {
    description '1.Add the traffic-enable leaf node which in configuration/l2vpn/service-instances/vpws-community-instances/vpws-community-instances/auto-discovery-type/type/srv6-evpn/srv6-evpn-params.
2.Add the traffic-enable leaf node which in configuration/l2vpn/service-instances/vpws-community-instances/vpws-community-instances/auto-discovery-type/type/mpls-evpn/mpls-evpn-params.
3.Add the traffic-enable leaf node which in configuration/l2vpn/service-instances/evpn-vpls-instances/evpn-vpls-instance/evpn-vpls-mpls-evpn.
4.Add the traffic-enable leaf node which in configuration/l2vpn/service-instances/evpn-vpls-instances/evpn-vpls-instance/evpn-vpls-srv6-evpn.
5.Add the traffic-enable leaf node which in configuration/l2vpn/service-instances/l2vpn-p2p-services/l2vpn-p2p-service/static-srv6-evpn.
6.Add the vpws-evpn-instance-statistics list which in state/l2vpn/statistics.
7.Add the in-traffic-rate,in-packet-rate,out-traffic-rate,out-packet-rate leaf nodes which in state/l2vpn/statistics/instance-statistics.' ;
  }

  revision 2023-11-09 {
    description '1.Add the lamp leaf node and the lacp-tagged leaf node which in configuration/l2vpn/service-instances/vpws-community-instances/vpws-community-instances/auto-discovery-type/type/vxlan-evpn/vxlan-evpn-params/vxlan-evpn-ac-bind/ac-instance-bind/ac-type/ethernet/ethernet-params/l2protocol-control-policy
2.Add the lamp leaf node and the lacp-tagged leaf node which in configuration/l2vpn/service-instances/vpws-community-instances/vpws-community-instances/auto-discovery-type/type/srv6-evpn/srv6-evpn-params/srv6-evpn-ac-bind/ac-instance-bind/ac-type/ethernet/ethernet-params/l2protocol-control-policy
3.Add the lamp leaf node and the lacp-tagged leaf node which in configuration/l2vpn/service-instances/vpws-community-instances/vpws-community-instances/auto-discovery-type/type/mpls-evpn/mpls-evpn-params/mpls-evpn-ac-bind/ac-instance-bind/ac-type/ethernet/ethernet-params/l2protocol-control-policy' ;
  }

  revision 2023-10-16 {
    description '1.Modify the range of the unicast-inrate-bps leaf from 0-18446744073709551615 to 1-18446744073709551615.
2.Modify the range of the broadcast-inrate-bps leaf from 0-18446744073709551615 to 1-18446744073709551615.
3.Modify the range of the drop-inrate-bps leaf from 0-18446744073709551615 to 1-18446744073709551615.' ;
  }

  revision 2023-09-21 {
    description '1.Add the vpls-irb-track-vpls-state leaf node which in configuration/l2vpn/l2vpn-global/vpls-irb-track-vpls-state.' ;
  }

  revision 2023-09-09 {
    description '1.Obsolete the global-session-selectors container node which in configuration/l2vpn/l2vpn-global.
2.Obsolete the specify-session-selectors container node which in configuration/l2vn/l2vpn-global.
3.Obsolete the pwe3-signal-session rpc.' ;
  }

  revision 2023-09-02 {
    description '1.Add the cword-usage-forced leaf node which in configuration/l2vpn/service-instances/evpn-vpls-instances/evpn-vpls-instance/evpn-vpls-mpls-evpn/cword-usage-forced.' ;
  }

  revision 2023-08-24 {
    description 'Add the feature of separated-bum-label.' ;
  }

  revision 2023-08-16 {
    description '1.Obsolete the container of b-vpls-rd which in configuration/b-vpls-instances/b-vpls-instance.
2.Obsolete the container of auto-discovery-type which in configuration/b-vpls-instances/b-vpls-instance.
3.Obsolete the container of bum-bmac which in configuration/b-vpls-instances/b-vpls-instance.
4.Obsolete the leaf of df-election which in configuration/i-vpls-instances/i-vpls-instance.
5.Obsolete the container of i-vpls-smart-vlan-bind which in configuration/i-vpls-instances/i-vpls-instance.' ;
  }

  revision 2023-06-05 {
    description '1.Add the split-horizon-scope-params container node which in configuration/l2vpn/vpls-instances/vpls-instance/martini-discovery/pw-details-params/split-horizon-scope-params.
2.Add the split-horizon-scope-params container node which in configuration/l2vpn/evpn-vpls-instances/evpn-vpls-instance/martini-discovery/pw-details-params/split-horizon-scope-params.' ;
  }

  revision 2023-05-09 {
    description '1.Add the evi-rt-flag leaf node which in configuration/l2vpn/service-instances/evpn-vpls-instances/evpn-vpls-instance/evpn-vpls-dynamic-vxlan/route-target-params/route-target.
2.Add the signal-mld-proxy leaf node which in configuration/l2vpn/service-instances/evpn-vpls-instances/evpn-vpls-instance/evpn-multicast.' ;
  }

  revision 2023-04-26 {
    description '1.Add the evi-rt-flag leaf node which in configuration/l2vpn/service-instances/evpn-vpls-instances/evpn-vpls-instance/evpn-vpls-srv6-evpn/route-target-params/route-target.' ;
  }

  revision 2023-03-25 {
    description '1.Add the mac-control leaf node which in configuration/service-instances/vpws-instance/ac-instance-bind/ethernet-params/l2protocol-control-policy.
2.Add the mac-control leaf node which in configuration/service-instances/vlss-instance/ac-instance-bind/ethernet-params/l2protocol-control-policy.
3.Add the mac-control leaf node which in configuration/service-instances/vpws-community-instance/vxlan-evpn-ac-bind/auto-discovery-type/ac-instance-bind/ethernet-params/l2protocol-control-policy.
4.Add the mac-control leaf node which in configuration/service-instances/vpws-community-instance/srv6-evpn-ac-bind/auto-discovery-type/ac-instance-bind/ethernet-params/l2protocol-control-policy.
5.Add the mac-control leaf node which in configuration/service-instances/vpws-community-instance/mpls-evpn-ac-bind/auto-discovery-type/ac-instance-bind/ethernet-params/l2protocol-control-policy.
6.Add the mac-control leaf node which in configuration/service-instances/vpws-vxlan-instance/ac-instance-bind/ethernet-params/l2protocol-control-policy.
7.Add the mac-control leaf node which in configuration/service-instances/l2vpn-p2p-service/ac-instance-bind/ethernet-params/l2protocol-control-policy.' ;
  }

  revision 2023-03-10 {
    description '1.Add the ingress-adjust-drop-tagged-frames leaf nodes which in ethernet access modes of all instances.' ;
  }

  revision 2023-02-14 {
    description '1.Add the vpws-id leaf node which in configuration/l2vpn/service-instances/vlss-instances/vlss-instance/vlss-ac-bind/ac-instance-bind.
2.Add the srv6-evpn-evpl-bind container node which in configuration/l2vpn/service-instances/vpws-community-instances/vpws-community-instance/auto-discovery-type/srv6-evpn-params.
3.Add the mpls-evpn-evpl-bind container node which in configuration/l2vpn/service-instances/vpws-community-instances/vpws-community-instance/auto-discovery-type/mpls-evpn-params.' ;
  }

  revision 2023-02-10 {
    description '1.Add the work-path-status and protect-path-status leaf nodes which in state/l2vpn/pw-group-info.' ;
  }

  revision 2023-01-31 {
    description '1.Add the shared-flood-list leaf node which in configuration/l2vpn/service-instances/evpn-vpls-instances/evpn-vpls-instance.' ;
  }

  revision 2023-01-10 {
    description '1.Add the originate leaf node which in configuration/l2vpn/service-instances/evpn-vpls-instances/evpn-vpls-instance/rt-2.' ;
  }

  revision 2022-12-20 {
    description '1.Add the evpn-vpls-evpn-pw-bind container node which in configuration/l2vpn/service-instances/evpn-vpls-instances/evpn-vpls-instance.' ;
  }

  revision 2022-12-05 {
    description '1.Add the default-vcid,mtu,default-cword and mtu-mismatch-ignore leaf nodes which in configuration/l2vpn/service-instances/b-vpls-instances/b-vpls-instance.
2.Add the b-vpls-ds-mode and traffic-statistics-params container which in configuration/l2vpn/service-instances/b-vpls-instances/b-vpls-instance.
3.Add the sspw-target-differ-from-ldp leaf node which in configuration/l2vpn/service-instances/vpls-instances/vpls-instance/martini-discovery/martini-vpls-params.
4.Add the sspw-target-differ-from-ldp leaf node which in configuration/l2vpn/service-instances/evpn-vpls-instances/evpn-vpls-instance/martini-discovery/martini-vpls-params.
5.Add the enumeration of outer-tpid inner-tpid nodes which in configuration/l2vpn/pw-specification/pw-entry/required-vlan-parameters.' ;
  }

  revision 2022-10-10 {
    description '1.Add the esi-proxy leaf node which in configuration/l2vpn/service-instances/evpn-vpls-instances/evpn-vpls-instance.' ;
  }

  revision 2022-09-19 {
    description '1.Add the evpn-redundancy-adjust container node which in configuration/service-instances/evpn-vpls-instances/evpn-vpls-instance.
2.Add the evpn-redundancy-adjust container node which in configuration/service-instances/vpws-community-instances/vpws-community-instance.
3.Add the wtr-time leaf node which in configuration/service-instances/vpws-community-instances/vpws-community-instance/auto-discovery-type/vxlan-evpn-params.' ;
  }

  revision 2022-09-13 {
    description '1.Add the mtu-mismatch-ignore leaf node which in service-instances/vpws-instances/vpws-instance.
2.Add the mtu-mismatch-ignore leaf node which in service-instances/vpls-instances/vpls-instance.
3.Add the mtu-mismatch-ignore leaf node which in service-instances/mspw-instances/mspw-instance/remote-parameters.
4.Add the mtu-mismatch-ignore leaf node which in service-instances/evpn-vpls-instances/evpn-vpls-instance.
5.Add the mtu-mismatch-ignore leaf node which in service-instances/vpws-community-instances/vpws-community-instance.' ;
  }

  revision 2022-08-13 {
    description '1.Add the choice case branch in configuration/l2vpn/pw-specification/pw-entry/track-fast-notified.
2.Add the track-notified leaf node in configuration/l2vpn/pw-specification/pw-entry.' ;
  }

  revision 2022-07-26 {
    description '1. Add the default-encapsulation leaf which in configuration/l2vpn/service-instances/i-vpls-instances/i-vpls-instance.
2. Add the description leaf which in configuration/l2vpn/service-instances/i-vpls-instances/i-vpls-instance.
3. Add the i-vpls-service-delimiter container which in configuration/l2vpn/service-instances/i-vpls-instances/i-vpls-instance.
4. Add the description leaf which in configuration/l2vpn/service-instances/b-vpls-instances/b-vpls-instance.
5. Add the customer-backbone-point container which in configuration/l2vpn/service-instances/b-vpls-instances/b-vpls-instance.
6. Add the vpls-pw-bind container which in configuration/l2vpn/service-instances/b-vpls-instances/b-vpls-instance.
7. Add 15K label to the feature of vpws-community-mpls-duplicate.
8. Add the push-vlan-id leaf which in configuration/l2vpn/service-instances/i-vpls-instances/i-vpls-instance/i-vpls-ac-bind/ac-instance-bind/ac-type/ethernet/ethernet-params.
9. Add the rewrite-vlan-id leaf which in configuration/l2vpn/service-instances/i-vpls-instances/i-vpls-instance/i-vpls-ac-bind/ac-instance-bind/ac-type/ethernet/ethernet-params.
10. Add the ingress-adjust-push leaf which in configuration/l2vpn/service-instances/i-vpls-instances/i-vpls-instance/i-vpls-ac-bind/ac-instance-bind/ac-type/ethernet/ethernet-params.
11. Add the ingress-adjust-rewrite leaf which in configuration/l2vpn/service-instances/i-vpls-instances/i-vpls-instance/i-vpls-ac-bind/ac-instance-bind/ac-type/ethernet/ethernet-params.' ;
  }

  revision 2022-06-30 {
    description '1.Add the rt-2-single-label container node which in configuration/service-instances/evpn-vpls-instances/evpn-vpls-instance/evpn-vpls-mpls-evpn.
2.Add the rt-2-single-label container node which in configuration/service-instances/evpn-vpls-instances/evpn-vpls-instance/evpn-vpls-srv6-evpn.' ;
  }

  revision 2022-06-09 {
    description '1.Add the circuit-status-vector leaf node which in configuration/l2vpn/vpws-community-instances/auto-discovery-type/kompella-params.' ;
  }

  revision 2022-05-12 {
    description '1.Add the rt-2 container node which in configuration/l2vpn/service-instances/evpn-vpls-instances/evpn-vpls-instance.' ;
  }

  revision 2022-04-27 {
    description 'Add the bfd-params container which in configuration/l2vpn/service-instances/vpws-community-instances/vpws-community-instance/auto-discovery-type/type/srv6-evpn/srv6-evpn-params/srv6-evpn-ac-bind/ac-instance-bind/ac-type/ethernet/ethernet-params.' ;
  }

  revision 2022-04-20 {
    description '1.Add the evpn-irb container which in configuration/l2vpn/l2vpn-global.
2.Add the l2vpn-rd-template container which in configuration/l2vpn/l2vpn-global.
3.Add the template-based leaf node which in configuration/l2vpn/service-instances/evpn-vpls-instances/evpn-vpls-instance/evpn-vpls-rd.
4.Add the template-based leaf node which in configuration/l2vpn/service-instances/vpws-community-instances/vpws-community-instance/vpws-community-rd.' ;
  }

  revision 2022-03-28 {
    description '1.Add the srv6-evpn-next-header leaf which in configuration/l2vpn/l2vpn-global.' ;
  }

  revision 2022-03-24 {
    description '1.Add the best-path-sr leaf node which in configuration/service-instances/evpn-vpls-instances/evpn-vpls-instance.
2.Add the best-path-sr leaf node which in configuration/service-instances/vpws-community-instances/vpws-community-instance.' ;
  }

  revision 2022-03-15 {
    description '1.Add the split-horizon-params container node which in configuration/service-instances/evpn-vpls-instances/evpn-vpls-instance/evpn-vpls-srv6-evpn.
2.Add the srv6-tunnel-params container node which in configuration/service-instances/evpn-vpls-instances/evpn-vpls-instance/evpn-vpls-srv6-evpn.
3.Add the srv6-tunnel-params container node which in configuration/l2vpn/service-instances/vpws-community-instances/vpws-community-instance.
4.Add the srv6-tunnel-params container node which in configuration/l2vpn/service-instances/l2vpn-p2p-services/l2vpn-p2p-service.
5.Add the vccv-flow-label leaf node and flow-label container node which in configuration/service-instances/evpn-vpls-instances/evpn-vpls-instance/martini-discovery/pw-details-params/pw-details.
6.Add the vccv-flow-label leaf node and flow-label container node which in configuration/service-instances/vpls-instances/vpls-instance/martini-discovery/pw-details-params/pw-details.' ;
  }

  revision 2022-03-12 {
    description '1.Add the multi-chassis-protection container which in configuration/l2vpn/l2vpn-global.' ;
  }

  revision 2022-03-07 {
    description '1.Add the vccv-flow-label leaf node which in configuration/l2vpn/pw-specification/pw-entry.' ;
  }

  revision 2022-02-15 {
    description '1.Add the neighbour-ipv4 container which in configuration/l2vpn/service-instances/evpn-vpls-instances/evpn-vpls-instance.
2.Add the neighbour-ipv6 container which in configuration/l2vpn/service-instances/evpn-vpls-instances/evpn-vpls-instance.
3.Add the split-horizon-params container which in configuration/l2vpn/service-instances/evpn-vpls-instances/evpn-vpls-instance.
4.Add the split-horizon-params container which in configuration/l2vpn/service-instances/evpn-vpls-instances/evpn-vpls-instance/evpn-vpls-mpls-evpn.
5.4.Add the flow-label container which in configuration/l2vpn/service-instances/evpn-vpls-instances/evpn-vpls-instance/evpn-vpls-mpls-evpn.
6.1.Add the flow-label container which in configuration/l2vpn/service-instances/vpws-community-instances/vpws-community-instance/auto-discovery-type/mpls-evpn-params.
7.Add the split-horizon-scope-params container node which in configuration/l2vpn/vpls-instances/vpls-instance/kompella-discovery/kompella-params/kompella-vpls-params.
8.Add the split-horizon-scope-params container node which in configuration/l2vpn/evpn-vpls-instances/evpn-vpls-instance/kompella-discovery/kompella-params/kompella-vpls-params.
9.Obsolete split-horizon-scope leaf node which in configuration/l2vpn/evpn-vpls-instances/evpn-vpls-instance/kompella-discovery/kompella-params/kompella-vpls-params.
10.Obsolete split-horizon-scope leaf node which in configuration/l2vpn/vpls-instances/vpls-instance/kompella-discovery/kompella-params/kompella-vpls-params.
11.Add the multi-homed-ce-pool container which in configuration/l2vpn/service-instances/vpls-instances/vpls-instance.
12.Add the ac-fault-associate container which in configuration/l2vpn/service-instances/evpn-vpls-instances/evpn-vpls-instance.
13.Add the ce-pool container which in configuration/l2vpn/service-instances/evpn-vpls-instances/evpn-vpls-instance.' ;
  }

  revision 2021-12-22 {
    description '1.Add the site-preference-params container node which in configuration/l2vpn/vpws-community-instances/auto-discovery-type/kompella-params.
2.Add the site-preference-params container node which in configuration/l2vpn/vpls-instances/vpls-instance/kompella-discovery/kompella-params/kompella-vpls-params.
3.Add the site-preference-params container node which in configuration/l2vpn/evpn-vpls-instances/evpn-vpls-instance/kompella-discovery/kompella-params/kompella-vpls-params.
4.Delete the site-preference leaf node which in configuration/l2vpn/vpws-community-instances/auto-discovery-type/kompella-params.
5.Delete the site-preference leaf node which in configuration/l2vpn/vpls-instances/vpls-instance/kompella-discovery/kompella-params/kompella-vpls-params.
6.Delete the site-preference leaf node which in configuration/l2vpn/evpn-vpls-instances/evpn-vpls-instance/kompella-discovery/kompella-params/kompella-vpls-params.
7.Add the flow-label container node which in configuration/l2vpn/vpws-community-instances/auto-discovery-type/kompella-params.
8.Add the flow-label container node which in configuration/l2vpn/vpls-instances/vpls-instance/kompella-discovery/kompella-params/kompella-vpls-params.
9.Add the flow-label container node which in configuration/l2vpn/evpn-vpls-instances/evpn-vpls-instance/kompella-discovery/kompella-params/kompella-vpls-params.' ;
  }

  revision 2021-12-13 {
    description '1.Add the multi-chassis-pw-params container node which in configuration/l2vpn/vpls-instances/vpls-instance/kompella-discovery/kompella-params/kompella-vpls-params/multi-chassis-pw-params.
2.Add the multi-chassis-pw-params container node which in configuration/l2vpn/evpn-vpls-instances/evpn-vpls-instance/kompella-discovery/kompella-params/kompella-vpls-params/multi-chassis-pw-params.
3.Add the multi-chassis-pw-params container node which in configuration/l2vpn/vpls-instances/vpls-instance/kompella-discovery/kompella-params/kompella-vpls-params/multi-chassis-pw-params.
4.Add the proactive-remote-standby container which in configuration/l2vpn/pw-specification/pw-entry.' ;
  }

  revision 2021-11-25 {
    description '1.Add the default-color leaf node which in configuration/l2vpn/vpws-community-instances.
2.Add the default-color leaf node which in configuration/l2vpn/evpn-vpls-instances/evpn-vpls-instance.
3.Add the proactive-remote-standby container node which in configuration/pw-specification/pw-entry.' ;
  }

  revision 2021-11-23 {
    description '1.Add the site-preference leaf node which in configuration/l2vpn/vpls-instances/vpls-instance/kompella-discovery/kompella-params/kompella-vpls-params/site-preference.
2.Add the site-preference leaf node which in configuration/l2vpn/evpn-vpls-instances/evpn-vpls-instance/kompella-discovery/kompella-params/kompella-vpls-params/site-preference.' ;
  }

  revision 2021-11-01 {
    description '1.Add the oam-mapping node which in configuration/l2vpn/service-instances/l2vpn-p2p-services/p2p-ac-bind.
2.Add the track-name node which in configuration/l2vpn/service-instances/l2vpn-p2p-services/p2p-ac-bind.
3.Obsolete the leaf node local-wtr-time which in configuration/l2vpn/service-instances/l2vpn-p2p-services/l2vpn-p2p-service/static-srv6-evpn/srv6-remote-sid-params/srv6-remote-sid-param.
4.Add the leaf node wtr-time which in configuration/l2vpn/service-instances/l2vpn-p2p-services/l2vpn-p2p-service/static-srv6-evpn/srv6-remote-sid-params/srv6-remote-sid-param.
5.Add the mtu leaf node which in configuration/l2vpn/service-instances/evpn-vpls-instances/evpn-vpls-instance.' ;
  }

  revision 2021-10-12 {
    description '1.Add the site-preference leaf node which in configuration/l2vpn/vpws-community-instances/auto-discovery-type/kompella-params/site-params.
2.Add the ingress-adjust-rewrite-params container node which in configuration/l2vpn/vpws-community-instances/auto-discovery-type/kompella-params/site-params/remote-ce-ranges/ac-instance-bind/ethernet-params.
3.Add the enum value of  ingress-adjust-tag-as-payload node which in configuration/l2vpn/vpws-community-instances/auto-discovery-type/kompella-params/site-params/remote-ce-ranges/ac-instance-bind/ethernet-params.' ;
  }

  revision 2021-09-15 {
    description '1.Change the default value of revertive-mode leaf node which in configuration/l2vpn/service-instances/ring-tree-instances/ring-tree-instance.' ;
  }

  revision 2021-09-09 {
    description 'change configuration/l2vpn/evpn-vpls-instances/evpn-vpls-instance/evpn-vpls-static-vni/split-horizon to support configue lists of split-horizon groups.' ;
  }

  revision 2021-09-08 {
    description '1.Add the eti-redundancy leaf node which in configuration/l2vpn/vpws-community-instances/vpws-community-instance.' ;
  }

  revision 2021-09-04 {
    description '1.Add the rt-2-params container which in configuration/service-instances/evpn-vpls-instances/evpn-vpls-instance/evpn-vpls-mpls-evpn.
2.Add the rt-2-params container which in configuration/service-instances/evpn-vpls-instances/evpn-vpls-instance/evpn-vpls-srv6-evpn.' ;
  }

  revision 2021-07-14 {
    description '1.Add the evpn-evi-specific-sub-interfaces container which in configuration/l2vpn/l2vpn-global.' ;
  }

  revision 2021-07-09 {
    description '1.The split-horizon range changed from 1-1 to 1-51 of EVPN instance.' ;
  }

  revision 2021-06-24 {
    description '1.Add the dcb container which in configuration/l2vpn/service-instances/evpn-vpls-instances/evpn-vpls-instance/evpn-vpls-mpls-evpn.' ;
  }

  revision 2021-06-16 {
    description '1.Add the evpn-multicast container node which in configuration/l2vpn/evpn-vpls-instances/evpn-vpls-instance.
2.Add the evi-rt-flag leaf node which in configuration/l2vpn/evpn-vpls-instances/evpn-vpls-instance/evpn-vpls-mpls-evpn/route-target-params.' ;
  }

  revision 2021-06-07 {
    description '1.Add the l2protocol-control-policy container which in configuration/l2vpn/service-instances/vlss-instances/vlss-instance.
2.Add the l2protocol-control-policy container which in configuration/l2vpn/service-instances/vpws-community-instances/vpws-community-instance/auto-discovery-type/vxlan-evpn-params/vxlan-evpn-ac-bind/ac-instance-bind.
3.Add the l2protocol-control-policy container which in configuration/l2vpn/service-instances/vpws-community-instances/vpws-community-instance/auto-discovery-type/srv6-evpn-params/srv6-evpn-ac-bind/ac-instance-bind.
4.Add the l2protocol-control-policy container which in configuration/l2vpn/service-instances/vpws-community-instances/vpws-community-instance/auto-discovery-type/mpls-evpn-params/mpls-evpn-ac-bind/ac-instance-bind.
5.Add the l2protocol-control-policy container which in configuration/l2vpn/service-instances/vpws-vxlan-instances/vpws-vxlan-instance/vpws-vxlan-ac-bind.
6.Add the l2protocol-control-policy container which in configuration/l2vpn/service-instances/l2vpn-p2p-services/l2vpn-p2p-service/p2p-ac-bind.
7.Add the traffic-enable node which in configuration/l2vpn/service-instances/vpls-evpn-instances/vpls-evpn-instance.
8.Add the traffic-enable node which in configuration/l2vpn/service-instances/vpws-community-instances/vpws-community-instance.
9.Add the traffic-enable node which in configuration/l2vpn/service-instances/l2vpn-p2p-services/l2vpn-p2p-service and p2p-ac-bind.' ;
  }

  revision 2021-05-27 {
    description '1.Add the link-acl-name node which in configuration/l2vpn/service-instances/vpls-instances/vpls-instance.
2.Add the link-acl-name node which in configuration/l2vpn/service-instances/evpn-vpls-instances/evpn-vpls-instance.
3.Add the seamless-integrated node which in configuration/l2vpn/service-instances/evpn-vpls-instances/evpn-vpls-instance/evpn-vpls-srv6-evpn.' ;
  }

  revision 2021-05-20 {
    description '1.Add the ignore-remote-pfs-bits node which in configuration/l2vpn/protect-rules/protect-group.' ;
  }

  revision 2021-04-27 {
    description '1.Add the best-path leaf node which in configuration/service-instances/evpn-vpls-instances/evpn-vpls-instance.
2.Add the best-path leaf node which in configuration/service-instances/vpws-community-instances/vpws-community-instance.
3.Add the enumeration of native for umr leaf node which in configuration/service-instances/evpn-vpls-instances/evpn-vpls-instance.' ;
  }

  revision 2021-04-22 {
    description '1.Add the ingress-adjust-tag-as-endpoint leaf node which in configuration/service-instances/evpn-vpls-instance/evpn-vpls-ac-bind/ethernet-params.' ;
  }

  revision 2021-04-02 {
    description '1.Add the lst-for-etree node which in configuation/service-instances/vpls-instances/vpls-instance/vpls-ac-bind/ac-instance-bind/ethernet-params.
2.Add the lst-for-etree node which in configuation/service-instances/vpws-instances/vpws-instance/vpws-ac-bind/ac-instance-bind/ethernet-params.' ;
  }

  revision 2021-03-23 {
    description '1.Add the seamless-integrated node which in configuration/l2vpn/service-instances/evpn-vpls-instances/evpn-vpls-instance/evpn-vpls-mpls-evpn.' ;
  }

  revision 2021-03-04 {
    description '1.Add the vccv-bfd-template-name in configuration/l2vpn/service-instances/vpls-instances/vpls-instance/martini-discovery/pw-details-params/pw-details/vccv-bfd-params.
2.Add the vccv-bfd-template-name in configuration/l2vpn/service-instances/evpn-vpls-instances/evpn-vpls-instance/martini-discovery/pw-details-params/pw-details/vccv-bfd-params.' ;
  }

  revision 2021-02-27 {
    description '1.Change the range of bandwidth and ratelimit parameters from 0-4294967295 to 0|1-4294967295 which in configuration/l2vpn/pw-specification/qos-parameters.' ;
  }

  revision 2021-01-30 {
    description '1.Add the etree-advertise-leaf leaf node which in configuration/service-instances/evpn-vpls-instances/evpn-vpls-instance/evpn-vpls-srv6-evpn.' ;
  }

  revision 2021-01-20 {
    description '1.Add the tunnel-srv6-sid node which in configuration/l2vpn/pw-specification/pw-entry.' ;
  }

  revision 2021-01-18 {
    description '1.Add enum value of SRv6 TE and SR policy group in state/l2vpn/kompella-pw/kompella-pw-info/tunnel-policy-result/result-type.
2.Add enum value of SRv6 TE and SR policy group in state/l2vpn/pw-info/tunnel-policy-result/result-type.' ;
  }

  revision 2021-01-07 {
    description '1.Obsolete the max-traffic-rate-params container which in configuration/l2vpn/service-instances/evpn-vpls-instances/evpn-vpls-instance.' ;
  }

  revision 2021-01-05 {
    description '1.Add the egress-keep-normalized-tag and rewrite-outer-vlanid-flag leaves which in configuration/l2vpn/service-instances/vpws-community-instances/vpws-community-instance/auto-discovery-type/type/srv6-evpn/srv6-evpn-params/srv6-evpn-ac-bind/ac-instance-bind/ac-type/ethernet/ethernet-params.
2.Add the egress-keep-normalized-tag and rewrite-outer-vlanid-flag leaves which in configuration/l2vpn/service-instances/vpws-community-instances/vpws-community-instance/auto-discovery-type/type/mpls-evpn/mpls-evpn-params/mpls-evpn-ac-bind/ac-instance-bind/ac-type/ethernet/ethernet-params.
3.Add the egress-keep-normalized-tag and rewrite-outer-vlanid-flag leaves which in configuration/l2vpn/service-instances/vpws-instances/vpws-instance/vpws-ac-bind/ac-instance-bind/ethernet-params.
4.Add the egress-keep-normalized-tag and rewrite-outer-vlanid-flag leaves which in configuration/l2vpn/service-instances/vpls-instances/vpls-instance/vpls-ac-bind/ac-instance-bind/ethernet-params.
5.Add the egress-keep-normalized-tag and rewrite-outer-vlanid-flag leaves which in configuration/l2vpn/service-instances/evpn-vpls-instances/evpn-vpls-instance/evpn-vpls-ac-bind/ac-instance-bind/ethernet-params.
6.Add the mac-limit-params container in configuration/l2vpn/service-instances/vpls-instances/vpls-instance/martini-discovery/pw-details-params/pw-details.
7.Add the mac-limit-params container in configuration/l2vpn/service-instances/evpn-vpls-instances/evpn-vpls-instance/martini-discovery/pw-details-params/pw-details.' ;
  }

  revision 2020-12-25 {
    description '1.Add the broadcast-traffic-rate-params,unknown-multicast-traffic-rate-params and unknown-unicast-traffic-rate-params containers which in configuration/l2vpn/service-instances/vpls-instances/vpls-instance.
2.Add the broadcast-traffic-rate-params,unknown-multicast-traffic-rate-params and unknown-unicast-traffic-rate-params containers which in configuration/l2vpn/service-instances/vpls-instances/evpn-vpls-instance.' ;
  }

  revision 2020-12-18 {
    description '1.Add the l2vpn-p2p-services container which in configuration/l2vpn/service-instances.' ;
  }

  revision 2020-12-14 {
    description '1.Add the umr leaf node which in configuration/service-instances/evpn-vpls-instances/evpn-vpls-instance.' ;
  }

  revision 2020-12-08 {
    description '1.Add the srv6-local-sid-params container which in configuration/service-instances/evpn-vpls-instances/evpn-vpls-instance/evpn-vpls-srv6-evpn.
2.Add the srv6-equivalent-sid-params container which in configuration/service-instances/evpn-vpls-instances/evpn-vpls-instance/evpn-vpls-srv6-evpn.
3.Add the split-horizon leaf node which in configuration/service-instances/evpn-vpls-instances/evpn-vpls-instance/evpn-vpls-srv6-evpn/route-target-params/route-target.' ;
  }

  revision 2020-10-21 {
    description '1.Add the tunnel-policy-result container in state/l2vpn/kompella-pw/kompella-pw-info.
2.Add the tunnel-policy-result container in state/l2vpn/pw-info.' ;
  }

  revision 2020-09-21 {
    description '1.Add the duplicate container in configuration/l2vpn/service-instances/vpws-community-instances/vpws-community-instance/auto-discovery-type/type/srv6-evpn/srv6-evpn-params/srv6-evpn-ac-bind/ac-instance-bind/ac-type/ethernet/ethernet-params.
2.Add the nd-enable leaf in configuration/l2vpn/service-instances/vpws-community-instances/vpws-community-instance/auto-discovery-type/type/srv6-evpn/srv6-evpn-params/srv6-evpn-ac-bind/ac-instance-bind/ac-type/ethernet/ethernet-params/duplicate.
3.Add the arp-enable leaf in configuration/l2vpn/service-instances/vpws-community-instances/vpws-community-instance/auto-discovery-type/type/srv6-evpn/srv6-evpn-params/srv6-evpn-ac-bind/ac-instance-bind/ac-type/ethernet/ethernet-params/duplicate.
4.Add the send-arp-enable leaf in configuration/l2vpn/service-instances/vpws-community-instances/vpws-community-instance/auto-discovery-type/type/srv6-evpn/srv6-evpn-params/srv6-evpn-ac-bind/ac-instance-bind/ac-type/ethernet/ethernet-params/duplicate.
5.Add the send-nd-enable leaf in configuration/l2vpn/service-instances/vpws-community-instances/vpws-community-instance/auto-discovery-type/type/srv6-evpn/srv6-evpn-params/srv6-evpn-ac-bind/ac-instance-bind/ac-type/ethernet/ethernet-params/duplicate.
6.Add the send-periodic-arp leaf in configuration/l2vpn/service-instances/vpws-community-instances/vpws-community-instance/auto-discovery-type/type/srv6-evpn/srv6-evpn-params/srv6-evpn-ac-bind/ac-instance-bind/ac-type/ethernet/ethernet-params/duplicate.
7.Add the send-periodic-nd leaf in configuration/l2vpn/service-instances/vpws-community-instances/vpws-community-instance/auto-discovery-type/type/srv6-evpn/srv6-evpn-params/srv6-evpn-ac-bind/ac-instance-bind/ac-type/ethernet/ethernet-params/duplicate.' ;
  }

  revision 2020-08-11 {
    description '1.Add the srv6-evpn-ds-mode container which in configuration/l2vpn/service-instances/vpws-community-instances/vpws-community-instance/auto-discovery-type/srv6-evpn-params.' ;
  }

  revision 2020-08-06 {
    description '1.Add the in-traffic-rate,in-packet-rate,out-traffic-rate,out-packet-rate nodes for telemetry fun which in state/l2vpn/statistics.' ;
  }

  revision 2020-07-29 {
    description '1.Add the bgp-multi-homing container which in configuration/l2vpn/service-instances/vpls-instances/vpls-instance/vpls-ac-bind/ac-instance-bind/ethernet-params.' ;
  }

  revision 2020-07-23 {
    description '1.Add asnd-nn type in rd node which in configuration/l2vpn/service-instances/evpn-vpls-instances/evpn-vpls-instance/evpn-vpls-rd.
2.Add asnd-nn type in rt-value node which in configuration/l2vpn/service-instances/evpn-vpls-instances/evpn-vpls-instance/evpn-vpls-mpls-evpn/route-target-params/route-target.
3.Add asnd-nn type in rt-value node which in configuration/l2vpn/service-instances/evpn-vpls-instances/evpn-vpls-instance/evpn-vpls-srv6-evpn/route-target-params/route-target.
4.Add asnd-nn type in rd node which in configuration/l2vpn/service-instances/vpws-community-instances/vpws-community-instance/vpws-community-rd.
5.Add asnd-nn type in rd node which in configuration/l2vpn/service-instances/vpws-community-instances/vpws-community-instance/auto-discovery-type/srv6-evpn-params/route-target-params/route-target.
6.Add asnd-nn type in rd node which in configuration/l2vpn/service-instances/vpws-community-instances/vpws-community-instance/auto-discovery-type/mpls-evpn-params/route-target-params/route-target.' ;
  }

  revision 2020-07-18 {
    description '1.Obsolete the srv6-sid-params container node which in configuration/l2vpn/service-instances/evpn-vpls-instances/evpn-vpls-instance/evpn-vpls-srv6-evpn.
2.Obsolete the srv6-sid-params container node which in configuration/l2vpn/service-instances/vpws-community-instances/vpws-community-instance/auto-discovery-type/srv6-evpn-params/srv6-evpn-ac-bind/ac-instance-bind.
3.Obsolete the srv6-sid-params container node which in configuration/l2vpn/service-instances/vpws-community-instances/vpws-community-instance/auto-discovery-type/srv6-evpn-params/srv6-evpn-access-pw-bind/pw-instance-bind.
4.Obsolete the srv6-sid-params container node which in configuration/l2vpn/service-instances/vpws-community-instances/vpws-community-instance/auto-discovery-type/srv6-evpn-params/srv6-evpn-bridge-if-bind/bridge-if-instance-bind.' ;
  }

  revision 2020-07-13 {
    description '1.Add the leaf node mac-withdraw-optimized-options which in configuration/l2vpn/service-instances/vpls-instances/vpls-instance.' ;
  }

  revision 2020-07-08 {
    description '1.Add the srv6-evpn-bridge-if-bind container which in configuration/l2vpn/service-instances/vpws-community-instances/vpws-community-instance/auto-discovery-type/srv6-evpn-params.' ;
  }

  revision 2020-07-03 {
    description '1.Add the ingress-adjust-push-params and ingress-adjust-rewrite-params containers which in configuration/l2vpn/service-instances/vpws-community-instances/vpws-community-instance/auto-discovery-type/srv6-evpn-params/srv6-evpn-ac-bind/ethernet-params.
2.Add the ingress-adjust-push-params and ingress-adjust-rewrite-params containers which in configuration/l2vpn/service-instances/vpws-community-instances/vpws-community-instance/auto-discovery-type/mpls-evpn-params/mpls-evpn-ac-bind/ethernet-params.' ;
  }

  revision 2020-06-24 {
    description '1.The length of export-map-name and import-map-name leaves which in configuration/l2vpn/service-instances/vpws-community-instances/vpws-community-instance changed from 1-31 to 1-200.
2.The length of export-map-name and import-map-name leaves which in configuration/l2vpn/service-instances/evpn-vpls-instances/evpn-vpls-instance changed from 1-31 to 1-200.' ;
  }

  revision 2020-06-19 {
    description '1.Add the srv6-evpn-access-pw-bind container which in configuration/l2vpn/service-instances/vpws-community-instances/vpws-community-instance/auto-discovery-type/srv6-evpn-params.' ;
  }

  revision 2020-06-08 {
    description '1.Add the srv6-locator-params container which in configuration/l2vpn/service-instances/vpws-community-instances/vpws-community-instance/auto-discovery-type/srv6-evpn-params/srv6-evpn-ac-bind/ac-instance-bind.
2.Add the srv6-locator-params container which in configuration/l2vpn/service-instances/evpn-vpls-instances/evpn-vpls-instance/evpn-vpls-srv6-evpn.
3.Add the wtr-time leaf node which in configuration/l2vpn/service-instances/vpws-community-instances/vpws-community-instance/auto-discovery-type/srv6-evpn-params.' ;
  }

  revision 2020-03-27 {
    description '1.Add the df-election leaf node which in /configuration/l2vpn/service-instances/vpws-community-instances/vpws-community-instance/auto-discovery-type/srv6-evpn-params/df-election.
2.Add the route-map-params container which in configuration/l2vpn/service-instances/vpws-community-instances/vpws-community-instance.' ;
  }

  revision 2020-03-25 {
    description '1.Add leaf unknown-unicast in configuration/l2vpn/service-instances/evpn-vpls-instances/evpn-vpls-instance.
2.Add leaf unknown-unicast in configuration/l2vpn/service-instances/vpls-instances/vpls-instance.
3.Add the global-session-selectors container node which in configuration/l2vpn-global.
4.Add the specify-session-selectors container node which in configuration/l2vpn-global.
5.Add the pwe3-signal-session rpc.' ;
  }

  revision 2020-03-17 {
    description 'Create the vpws-community-mpls-duplicate node.
Add the vpws-community-mpls-duplicate node on configuration/l2vpn/vpws-community-instances/vpws-community-instance/auto-descovery-type/mpls-evpn-params/mpls-evpn-ac-bind/ac-instance-bind/ethernet-params/duplicate node.' ;
  }

  revision 2020-03-09 {
    description '1.Obsolete the sid-auto leaf node which in configuration/l2vpn/service-instances/vpws-community-instances/vpws-community-instance/auto-discovery-type/srv6-evpn-params/srv6-evpn-ac-bind/ac-instance-bind/srv6-sid-params.' ;
  }

  revision 2020-03-02 {
    description '1.Add the evpn-vpls-srv6-evpn container in configuration/l2vpn/service-instances/evpn-vpls-instances/evpn-vpls-instance for srv6-evpn function.' ;
  }

  revision 2020-02-22 {
    description '1.The entropy-label node default value changed from enable to disable which in configuration/l2vpn/service-instances/evpn-vpls-instances/evpn-vpls-instance.
2.The entropy-label node default value changed from enable to disable which in configuration/l2vpn/service-instances/vpws-community-instances/vpws-community-instance/auto-discovery-type/mpls-evpn-params.' ;
  }

  revision 2020-02-13 {
    description '1.Add the color node which in configuration/l2vpn/pw-specification/pw-entry.' ;
  }

  revision 2019-12-18 {
    description '1.Add the ip-move-dampening container which in configuration/service-instances/evpn-vpls-instances/evpn-vpls-instance.' ;
  }

  revision 2019-11-19 {
    description '1.Add the vpws-bridge-if-bind container which in configuration/l2vpn/service-instances/vpws-instances/vpws-instance.' ;
  }

  revision 2019-10-29 {
    description '1.Add the evpn-vpws-evi-labels container which in configuration/l2vpn/service-instances/vpws-community-instances/vpws-community-instance/auto-discovery-type/mpls-evpn-params/mpls-evpn-ac-bind/ac-instance-bind/ethernet-params.
2.Add the 6100 project in remote-monitor-instances feature.
3.Add the cac-flag node which in configuration/l2vpn/pw-specification/pw-entry.
4.Modify the explaination of evi-label node.
5.Add the broadcast-tunnel container node which in configuration/l2vpn/service-instances/evpn-vpls-instances/evpn-vpls-instance/evpn-vpls-mpls-evpn.
6.Obsolete the vtep-interface container node which in configuration/l2vpn/service-instances/evpn-vpls-instances/evpn-vpls-instance/evpn-vpls-dynamic-vxlan.' ;
  }

  revision 2019-10-23 {
    description '1.Obsolete the control-word leaf node which in /configuration/l2vpn/service-instances/vpws-community-instances/vpws-community-instance/auto-discovery-type/vxlan-evpn-params/control-word
2.Obsolete the control-word leaf node which in /configuration/l2vpn/service-instances/vpws-community-instances/vpws-community-instance/auto-discovery-type/srv6-evpn-params/control-word' ;
  }

  revision 2019-09-29 {
    description '1.Add the ingress-adjust-pop-uni-tag leaf node in /configuration/l2vpn/service-instances/vpls-instances/vpls-instance/vpls-ac-bind/ac-instance-bind/ethernet-params;
2.Add the ingress-adjust-pop-uni-tag leaf node in /configuration/l2vpn/service-instances/vlss-instances/vlss-instance/vlss-ac-bind/ac-instance-bind/ethernet-params;
3.Obsolete the uni-egress-adjust-keep-nni-inner-vlan leaf node in /configuration/l2vpn/service-instances/vpls-instances/vpls-instance;
4.Obsolete the uni-egress-adjust-keep-nni-inner-vlan leaf node in /configuration/l2vpn/service-instances/vlss-instances/vlss-instance;
5.Add the uni-egress-adjust-nni-inner-vlan leaf node in /configuration/l2vpn/service-instances/vpls-instances/vpls-instance;
6.Add the uni-egress-adjust-nni-inner-vlan leaf node in /configuration/l2vpn/service-instances/vlss-instances/vlss-instance;
7.Add the instance-description node leaf in configuration/l2vpn/service-instances/evpn-vpls-instances/evpn-vpls-instance;
8.Add the instance-description node leaf in configuration/l2vpn/service-instances/vpws-community-instances/vpws-community-instance;
9.Add the if-description node leaf in configuration/l2vpn/service-instances/vpws-community-instances/vpws-community-instance/auto-discovery-type/vxlan-evpn-params/vxlan-evpn-ac-bind;
10.Add the if-description node leaf in configuration/l2vpn/service-instances/vpws-community-instances/vpws-community-instance/auto-discovery-type/srv6-evpn-params/srv6-evpn-ac-bind;
11.Add the if-description node leaf in configuration/l2vpn/service-instances/vpws-community-instances/vpws-community-instance/auto-discovery-type/mpls-evpn-params/mpls-evpn-ac-bind.' ;
  }

  revision 2019-09-17 {
    description '1.Add the encapsulation leaf node in configuration/service-instances/evpn-vpls-instances/evpn-vpls-instance.' ;
  }

  revision 2019-09-02 {
    description '1.Add the split-horizon leaf which in configuration/l2vpn/service-instances/evpn-vpls-instances/evpn-vpls-instance/evpn-vpls-mpls-evpn/route-target-params/route-target.
2.Add the evpn-vpls-evi-labels container which in configuration/l2vpn/service-instances/evpn-vpls-instances/evpn-vpls-instance/evpn-vpls-mpls-evpn.
3.Add the evpn-vpls-equivalent-evi-labels container which in configuration/l2vpn/service-instances/evpn-vpls-instances/evpn-vpls-instance/evpn-vpls-mpls-evpn.
4.Add the switch-cmd leaf node in configuration/l2vpn/service-instances/ring-tree-instances/ring-tree-instance.' ;
  }

  revision 2019-08-12 {
    description '1.Add the duplicate container in configuration/l2vpn/service-instances/vpws-community-instances/vpws-community-instance/auto-discovery-type/type/mpls-evpn/mpls-evpn-params/mpls-evpn-ac-bind/ac-instance-bind/ac-type/ethernet/ethernet-params.
2.Add the nd-enable leaf in configuration/l2vpn/service-instances/vpws-community-instances/vpws-community-instance/auto-discovery-type/type/mpls-evpn/mpls-evpn-params/mpls-evpn-ac-bind/ac-instance-bind/ac-type/ethernet/ethernet-params/duplicate.
3.Add the arp-enable leaf in configuration/l2vpn/service-instances/vpws-community-instances/vpws-community-instance/auto-discovery-type/type/mpls-evpn/mpls-evpn-params/mpls-evpn-ac-bind/ac-instance-bind/ac-type/ethernet/ethernet-params/duplicate.
4.Add the send-arp-enable leaf in configuration/l2vpn/service-instances/vpws-community-instances/vpws-community-instance/auto-discovery-type/type/mpls-evpn/mpls-evpn-params/mpls-evpn-ac-bind/ac-instance-bind/ac-type/ethernet/ethernet-params/duplicate.
5.Add the send-nd-enable leaf in configuration/l2vpn/service-instances/vpws-community-instances/vpws-community-instance/auto-discovery-type/type/mpls-evpn/mpls-evpn-params/mpls-evpn-ac-bind/ac-instance-bind/ac-type/ethernet/ethernet-params/duplicate.
6.Add the send-periodic-arp leaf in configuration/l2vpn/service-instances/vpws-community-instances/vpws-community-instance/auto-discovery-type/type/mpls-evpn/mpls-evpn-params/mpls-evpn-ac-bind/ac-instance-bind/ac-type/ethernet/ethernet-params/duplicate.
7.Add the send-periodic-nd leaf in configuration/l2vpn/service-instances/vpws-community-instances/vpws-community-instance/auto-discovery-type/type/mpls-evpn/mpls-evpn-params/mpls-evpn-ac-bind/ac-instance-bind/ac-type/ethernet/ethernet-params/duplicate.' ;
  }

  revision 2019-08-10 {
    description '1.Add the entropy-label leaf node in configuration/service-instances/evpn-vpls-instances/evpn-vpls-instance.
2.Add the entropy-label leaf node in configuration/service-instances/vpws-community-instances/vpws-community-instance/auto-discovery-type/mpls-evpn-params.
3.Add the set-traffic-class leaf node in configuration/pw-specification/pw-entry.' ;
  }

  revision 2019-08-06 {
    description '1.Add the push-tpid leaf node in configuration/l2vpn/vlss-instances/vlss-instance/vlss-ac-bind/ac-instance-bind/ethernet/ethernet-params.
2.Add the rewrite-tpid leaf node in configuration/l2vpn/vlss-instances/vlss-instance/vlss-ac-bind/ac-instance-bind/ethernet/ethernet-params.
3.Add the push-tpid leaf node in configuration/l2vpn/vpls-instances/vpls-instance/vpls-ac-bind/ac-instance-bind/ethernet/ethernet-params.
4.Add the rewrite-tpid leaf node in configuration/l2vpn/vpls-instances/vpls-instance/vpls-ac-bind/ac-instance-bind/ethernet/ethernet-params.
5.Add the lst-flag leaf in configuration/l2vpn/vlss-instances/vlss-instance/vlss-ac-bind/ac-instance-bind/ethernet/ethernet-params.
6.Add the lst-holdoff leaf in configuration/l2vpn/vlss-instances/vlss-instance/vlss-ac-bind/ac-instance-bind/ethernet/ethernet-params.' ;
  }

  revision 2019-07-11 {
    description '1.Add the max-traffic-rate-params container in configuration/l2vpn/service-instances/evpn-vpls-instances/evpn-vpls-instance;
2.Add the entropy-label leaf in configuration/l2vpn/pw-specification/pw-entry.' ;
  }

  revision 2019-06-29 {
    description '1.Add the originator-ip leaf in configuration/l2vpn/service-instances/evpn-vpls-instances/evpn-vpls-instance.' ;
  }

  revision 2019-06-13 {
    description '1.Add the in-bandwidth-utilization leaf in state/l2vpn/statistic/pw-statistics.
2.Add the out-bandwidth-utilization leaf in state/l2vpn/statistic/pw-statistics.
3.Add the uni-egress-adjust-keep-nni-inner-vlan leaf node in configuration/l2vpn/vlss-instances/vlss-instance.
4.Add the nni-egress-adjust-uni-rewrite container node in configuration/l2vpn/vlss-instances/vlss-instance/vlss-ac-bind/ac-instance-bind/ethernet/ethernet-params.
5.Add the nni-egress-adjust-uni-tpid container node in configuration/l2vpn/vlss-instances/vlss-instance/vlss-ac-bind/ac-instance-bind/ethernet/ethernet-params.
6.Add the ingress-adjust-serve-as-pvid leaf node in configuration/l2vpn/vlss-instances/vlss-instance/vlss-ac-bind/ac-instance-bind/ethernet/ethernet-params.
7.Add the uni-egress-adjust-keep-nni-inner-vlan leaf node in configuration/l2vpn/vpls-instances/vpls-instance.
8.Add the nni-egress-adjust-uni-rewrite container node in configuration/l2vpn/vpls-instances/vpls-instance/vpls-ac-bind/ac-instance-bind/ethernet/ethernet-params.
9.Add the nni-egress-adjust-uni-tpid container node in configuration/l2vpn/vpls-instances/vpls-instance/vpls-ac-bind/ac-instance-bind/ethernet/ethernet-params.
10.Add the ingress-adjust-serve-as-pvid leaf node in configuration/l2vpn/vpls-instances/vpls-instance/vpls-ac-bind/ac-instance-bind/ethernet/ethernet-params.
11.Add the pw-rate-statistics-period leaf node in configuration/l2vpn/l2vpn-global.
12.The qualified leaf node delete mandatory true attribute which in /configuration/l2vpn/service-instances/evpn-vpls-instances/evpn-vpls-instance.' ;
  }

  revision 2019-06-10 {
    description '1.Add the evpn-vpls-ds-mode container in configuration/l2vpn/evpn-vpls-instances/evpn-vpls-instance.
2.Add the mpls-evpn-ds-mode container in configuration/l2vpn/vpws-community-instances/vpws-community-instance/auto-discovery-type/mpls-evpn.
3.Add the traffic-enable leaf node in configuration/l2vpn/vpws-community-instances/vpws-community-instance/auto-discovery-type/mpls-evpn/mpls-evpn-params/mpls-evpn-ac-bind/ethernet.
4.Add the traffic-enable leaf node in configuration/l2vpn/vpws-community-instances/vpws-community-instance/auto-discovery-type/srv6-evpn/srv6-evpn-params/srv6-evpn-ac-bind/ethernet.
5.Add the traffic-enable leaf node in configuration/l2vpn/vpws-community-instances/vpws-community-instance/auto-discovery-type/vxlan-evpn/vxlan-evpn-params/vxlan-evpn-ac-bind/ethernet.' ;
  }

  revision 2019-04-30 {
    description '1.Add the seperated-bum-label leaf in configuration/l2vpn/service-instances/evpn-vpls-instances/evpn-vpls-instance/evpn-vpls-mpls-evpn;
2.Add the qualified leaf node in /configuration/l2vpn/service-instances/evpn-vpls-instances/evpn-vpls-instance.' ;
  }

  revision 2019-04-09 {
    description '1.Add the idle-code-new leaf node in configuration/service-instances/vpws-instances/vpws-instance/vpws-ac-bind/ac-instance-bind/tdm/tdm-params;
2.Add the idle-code-new leaf node in configuration/service-instances/vlss-instances/vlss-instance/vlss-ac-bind/ac-instance-bind/tdm/tdm-params;
3.Add the mpls-evpn-access-pw-bind container in configuration/l2vpn/service-instances/vpws-community-instances/vpws-community-instance/auto-discovery-type/mpls-evpn-params;
4.Add the evpn-vpls-pw-bind container node in /configuration/l2vpn/service-instances/evpn-vpls-instances/evpn-vpls-instance;
5.Add the martini-discovery container node in /configuration/l2vpn/service-instances/evpn-vpls-instances/evpn-vpls-instance;
6.Add the kompella-discovery container node in /configuration/l2vpn/service-instances/evpn-vpls-instances/evpn-vpls-instance.' ;
  }

  revision 2019-03-25 {
    description '1.Add the rt-2-router-mac leaf in configuration/l2vpn/service-instances/evpn-vpls-instances/evpn-vpls-instance/evpn-vpls-dynamic-vxlan/rt-2-params;
2.Add the red leaf node in configuration/pw-specification/pw-entry/qos-parameters/rate-limit-params/rate-limit.' ;
  }

  revision 2019-03-22 {
    description 'Add feature clear-ac-statistic.' ;
  }

  revision 2019-02-15 {
    description '1)Add the pfs-bits-tracked leaf in configuration/l2vpn/pw-specification/pw-entry;
2)Add the mpls-evpn-bridge-if-bind container in configuration/l2vpn/service-instances/vpws-community-instances/vpws-community-instance/auto-discovery-type/mpls-evpn-params
3)Add the wtr-time leaf in configuration/l2vpn/service-instances/evpn-vpls-instances/evpn-vpls-instance
4)Add the wtr-time leaf in configuration/l2vpn/service-instances/vpws-community-instances/vpws-community-instance/auto-discovery-type/mpls-evpn-params;
5)Add the df-shortcut-params container in configuration/l2vpn/service-instances/evpn-vpls-instances/evpn-vpls-instance.' ;
  }

  revision 2019-01-16 {
    description '1)Add the etree-advertise-leaf leaf in configuration/l2vpn/service-instances/evpn-vpls-instances/evpn-vpls-instance/evpn-vpls-mpls-evpn;
2)Add the leaf-role leaf in configuration/l2vpn/service-instances/evpn-vpls-instances/evpn-vpls-instance/evpn-vpls-ac-bind/ac-instance-bind/ac-type/ethernet/ethernet-params;' ;
  }

  revision 2018-12-17 {
    description '1)Add the route-map-params container in configuration/l2vpn/service-instances/evpn-vpls-instances/evpn-vpls-instance;
2)Add the vni-symmetric-params container in configuration/l2vpn/service-instances/evpn-vpls-instances/evpn-vpls-instance/evpn-vpls-dynamic-vxlan;
3)Add the rt-2-params container in configuration/l2vpn/service-instances/evpn-vpls-instances/evpn-vpls-instance/evpn-vpls-dynamic-vxlan;' ;
  }

  revision 2018-12-07 {
    description '1.Add the ingress-adjust-tag-as-endpoint leaf in configuration/l2vpn/service-instances/vpls-instances/vpls-instance/vpls-ac-bind/ac-instance-bind/ac-type/ethernet/ethernet-params/ingress-adjust-params/tag-as-endpoint.' ;
  }

  revision 2018-10-31 {
    description '1.Add the ingress-adjust-push-params container in configuration/l2vpn/service-instances/evpn-vpls-instances/evpn-vpls-instance/evpn-vpls-ac-bind/evpn-vpls-instance-bind/ethernet-params;
2.Add the ingress-adjust-rewrite-params container in configuration/l2vpn/service-instances/evpn-vpls-instances/evpn-vpls-instance/evpn-vpls-ac-bind/evpn-vpls-instance-bind/ethernet-params;' ;
  }

  revision 2018-10-29 {
    description '1.Adjust the containers order which in configuration/l2vpn from service-instances,pw-specification,protect-rules to protect-rules,pw-specification,service-instances.' ;
  }

  revision 2018-09-07 {
    description '1.Add the nni leaf in configuration/l2vpn/service-instances/vlss-instances/vlss-instance/vlss-ac-bind/ac-instance-bind;
2.Add the ingress-adjust-uni-proxy leaf in configuration/l2vpn/service-instances/vlss-instances/vlss-instance/vlss-ac-bind/ac-instance-bind/ethernet/ethernet-params
3.Add the nni leaf in configuration/l2vpn/service-instances/vpls-instances/vpls-instance/vpls-ac-bind/ac-instance-bind;
4.Add the ingress-adjust-uni-proxy leaf in configuration/l2vpn/service-instances/vpls-instances/vpls-instance/vpls-ac-bind/ac-instance-bind/ethernet/ethernet-params;
5.Add the ring-tree-instances container in configuration/l2vpn/service-instances;
6.Add the one-by-one enumeration for helper leaf which in configuration/protect-rules/protect-group/protect-strategy/single-dni-pwgroup container.
7.Add the node-role leaf in configuration/l2vpn/pw-specification/pw-entry.' ;
  }

  revision 2018-08-27 {
    description '1.Delete the dropped value of l2bfd node which in configuraion/service-instances/vpws-instances/vpws-instance/vpws-ac-bind/ethernet-params/l2protocol-control-policy;
2.Delete the encapsulation node of VPWS-VXLAN which in configuraion/service-instances/vpws-vxlan-instances/vpws-vxlan-instance;
3.Add the static-vxlan list in configuraion/service-instances/vpws-vxlan-instances/vpws-vxlan-instance/vpws-vxlan-static-vxlans.' ;
  }

  revision 2018-07-25 {
    description '1.Add the track-fast-notified leaf in configuration/l2vpn/pw-specification/pw-entry.
2.Add the track-group-flag leaf in configuration/l2vpn/pw-specification/pw-entry.
3.Add the i-vpls-instances container in configuration/l2vpn/service-instances.
4.Add the b-vpls-instances container in configuration/l2vpn/service-instances' ;
  }

  revision 2018-07-08 {
    description '1.Delete the tunnel-policy-params container which in configuration/l2vpn/service-instances/evpn-vpls-instances/evpn-vpls-mpls-evpn.
2.Add the peer-ipv4 and peer-ipv6 containers in configuration/l2vpn/service-instances/evpn-vpls-instances.
3.Add the peer-ipv4 and peer-ipv6 containers in configuration/l2vpn/service-instances/vpws-community-instances.
4.Add the vpws-vxlan-instances container in configuration/l2vpn/service-instances.
5.Add the max-traffic-rate-params in configuration/l2vpn/service-instances/vpls-instances/vpls-instance/martini-discovery/pw-details-params/pw-details.' ;
  }

  revision 2018-01-26 {
    description '1.Add the equivalent-vxlan-id leaf in configuration/l2vpn/service-instances/evpn-vpls-instances/evpn-vpls-instance
2.Modify the rang of the unicast-inrate-pps leaf from <0,4294967295> to <1,4294967295>, which in configuration/l2vpn/service-instances/vpws-instances/vpws-instance/traffic-statistics-params
3.Modify the rang of the broadcast-inrate-pps leaf from <0,4294967295> to <1,4294967295>, which in configuration/l2vpn/service-instances/vpws-instances/vpws-instance/traffic-statistics-params
4.Modify the rang of the drop-inrate-pps leaf from <0,4294967295> to <1,4294967295>, which in configuration/l2vpn/service-instances/vpws-instances/vpws-instance/traffic-statistics-params
5.Modify the rang of the unicast-inrate-pps leaf from <0,4294967295> to <1,4294967295>, which in configuration/l2vpn/service-instances/vpws-instances/vpws-instance/vpws-ac-bind/ac-instance-bind/ac-type/ethernet/ethernet-params/traffic-statistics-params
6.Modify the rang of the broadcast-inrate-pps leaf from <0,4294967295> to <1,4294967295>, which in configuration/l2vpn/service-instances/vpws-instances/vpws-instance/vpws-ac-bind/ac-instance-bind/ac-type/ethernet/ethernet-params/traffic-statistics-params
7.Modify the rang of the drop-inrate-pps leaf from <0,4294967295> to <1,4294967295>, which in configuration/l2vpn/service-instances/vpws-instances/vpws-instance/vpws-ac-bind/ac-instance-bind/ac-type/ethernet/ethernet-params/traffic-statistics-params
8.Modify the rang of the unicast-inrate-pps leaf from <0,4294967295> to <1,4294967295>, which in configuration/l2vpn/service-instances/vpws-instances/vpws-instance/vpws-ac-bind/ac-instance-bind/ac-type/tdm/tdm-params/traffic-statistics-params
9.Modify the rang of the broadcast-inrate-pps leaf from <0,4294967295> to <1,4294967295>, which in configuration/l2vpn/service-instances/vpws-instances/vpws-instance/vpws-ac-bind/ac-instance-bind/ac-type/tdm/tdm-params/traffic-statistics-params
10.Modify the rang of the drop-inrate-pps leaf from <0,4294967295> to <1,4294967295>, which in configuration/l2vpn/service-instances/vpws-instances/vpws-instance/vpws-ac-bind/ac-instance-bind/ac-type/tdm/tdm-params/traffic-statistics-params
11.Modify the rang of the unicast-inrate-pps leaf from <0,4294967295> to <1,4294967295>, which in configuration/l2vpn/service-instances/vpws-instances/vpws-instance/vpws-ac-bind/ac-instance-bind/ac-type/atm/atm-params/traffic-statistics-params
12.Modify the rang of the broadcast-inrate-pps leaf from <0,4294967295> to <1,4294967295>, which in configuration/l2vpn/service-instances/vpws-instances/vpws-instance/vpws-ac-bind/ac-instance-bind/ac-type/atm/atm-params/traffic-statistics-params
13.Modify the rang of the drop-inrate-pps leaf from <0,4294967295> to <1,4294967295>, which in configuration/l2vpn/service-instances/vpws-instances/vpws-instance/vpws-ac-bind/ac-instance-bind/ac-type/atm/atm-params/traffic-statistics-params
14.Modify the rang of the unicast-inrate-pps leaf from <0,4294967295> to <1,4294967295>, which in configuration/l2vpn/service-instances/vpws-instances/vpws-instance/vpws-ac-bind/ac-instance-bind/ac-type/ppp/ppp-params/traffic-statistics-params
15.Modify the rang of the broadcast-inrate-pps leaf from <0,4294967295> to <1,4294967295>, which in configuration/l2vpn/service-instances/vpws-instances/vpws-instance/vpws-ac-bind/ac-instance-bind/ac-type/ppp/ppp-params/traffic-statistics-params
16.Modify the rang of the drop-inrate-pps leaf from <0,4294967295> to <1,4294967295>, which in configuration/l2vpn/service-instances/vpws-instances/vpws-instance/vpws-ac-bind/ac-instance-bind/ac-type/ppp/ppp-params/traffic-statistics-params
17.Modify the rang of the unicast-inrate-pps leaf from <0,4294967295> to <1,4294967295>, which in configuration/l2vpn/service-instances/vpws-instances/vpws-instance/vpws-ac-bind/ac-instance-bind/ac-type/hdlc/hdlc-params/traffic-statistics-params
18.Modify the rang of the broadcast-inrate-pps leaf from <0,4294967295> to <1,4294967295>, which in configuration/l2vpn/service-instances/vpws-instances/vpws-instance/vpws-ac-bind/ac-instance-bind/ac-type/hdlc/hdlc-params/traffic-statistics-params
19.Modify the rang of the drop-inrate-pps leaf from <0,4294967295> to <1,4294967295>, which in configuration/l2vpn/service-instances/vpws-instances/vpws-instance/vpws-ac-bind/ac-instance-bind/ac-type/hdlc/hdlc-params/traffic-statistics-params
20.Modify the rang of the unicast-inrate-pps leaf from <0,4294967295> to <1,4294967295>, which in configuration/l2vpn/service-instances/vpws-instances/vpws-instance/vpws-ac-bind/ac-instance-bind/ac-type/fr/fr-params/traffic-statistics-params
21.Modify the rang of the broadcast-inrate-pps leaf from <0,4294967295> to <1,4294967295>, which in configuration/l2vpn/service-instances/vpws-instances/vpws-instance/vpws-ac-bind/ac-instance-bind/ac-type/fr/fr-params/traffic-statistics-params
22.Modify the rang of the drop-inrate-pps leaf from <0,4294967295> to <1,4294967295>, which in configuration/l2vpn/service-instances/vpws-instances/vpws-instance/vpws-ac-bind/ac-instance-bind/ac-type/fr/fr-params/traffic-statistics-params
23.Modify the rang of the unicast-inrate-pps leaf from <0,4294967295> to <1,4294967295>, which in configuration/l2vpn/service-instances/vpws-instances/vpws-instance/vpws-ac-bind/ac-instance-bind/ac-type/iwf-ip/iwf-ip-params/traffic-statistics-params
24.Modify the rang of the broadcast-inrate-pps leaf from <0,4294967295> to <1,4294967295>, which in configuration/l2vpn/service-instances/vpws-instances/vpws-instance/vpws-ac-bind/ac-instance-bind/ac-type/iwf-ip/iwf-ip-params/traffic-statistics-params
25.Modify the rang of the drop-inrate-pps leaf from <0,4294967295> to <1,4294967295>, which in configuration/l2vpn/service-instances/vpws-instances/vpws-instance/vpws-ac-bind/ac-instance-bind/ac-type/iwf-ip/iwf-ip-params/traffic-statistics-params
26.Modify the rang of the unicast-inrate-pps leaf from <0,4294967295> to <1,4294967295>, which in configuration/l2vpn/service-instances/vpws-instances/vpws-instance/vpws-ac-bind/ac-instance-bind/ac-type/iwf-eth/iwf-eth-params/traffic-statistics-params
27.Modify the rang of the broadcast-inrate-pps leaf from <0,4294967295> to <1,4294967295>, which in configuration/l2vpn/service-instances/vpws-instances/vpws-instance/vpws-ac-bind/ac-instance-bind/ac-type/iwf-eth/iwf-eth-params/traffic-statistics-params
28.Modify the rang of the drop-inrate-pps leaf from <0,4294967295> to <1,4294967295>, which in configuration/l2vpn/service-instances/vpws-instances/vpws-instance/vpws-ac-bind/ac-instance-bind/ac-type/iwf-eth/iwf-eth-params/traffic-statistics-params
29.Modify the rang of the unicast-inrate-pps leaf from <0,4294967295> to <1,4294967295>, which in configuration/l2vpn/service-instances/vpls-instances/vpls-instance/traffic-statistics-params
30.Modify the rang of the broadcast-inrate-pps leaf from <0,4294967295> to <1,4294967295>, which in configuration/l2vpn/service-instances/vpls-instances/vpls-instance/traffic-statistics-params
31.Modify the rang of the drop-inrate-pps leaf from <0,4294967295> to <1,4294967295>, which in configuration/l2vpn/service-instances/vpls-instances/vpls-instance/traffic-statistics-params
32.Modify the rang of the unicast-inrate-pps leaf from <0,4294967295> to <1,4294967295>, which in configuration/l2vpn/service-instances/vpls-instances/vpls-instance/vpls-ac-bind/ac-instance-bind/ac-type/ethernet/ethernet-params/traffic-statistics-params
33.Modify the rang of the broadcast-inrate-pps leaf from <0,4294967295> to <1,4294967295>, which in configuration/l2vpn/service-instances/vpls-instances/vpls-instance/vpls-ac-bind/ac-instance-bind/ac-type/ethernet/ethernet-params/traffic-statistics-params
34.Modify the rang of the drop-inrate-pps leaf from <0,4294967295> to <1,4294967295>, which in configuration/l2vpn/service-instances/vpls-instances/vpls-instance/vpls-ac-bind/ac-instance-bind/ac-type/ethernet/ethernet-params/traffic-statistics-params
35.Modify the rang of the unicast-inrate-pps leaf from <0,4294967295> to <1,4294967295>, which in configuration/l2vpn/service-instances/mspw-instances/mspw-instance/traffic-statistics-params
36.Modify the rang of the broadcast-inrate-pps leaf from <0,4294967295> to <1,4294967295>, which in configuration/l2vpn/service-instances/mspw-instances/mspw-instance/traffic-statistics-params
37.Modify the rang of the drop-inrate-pps leaf from <0,4294967295> to <1,4294967295>, which in configuration/l2vpn/service-instances/mspw-instances/mspw-instance/traffic-statistics-params
38.Modify the rang of the unicast-inrate-pps leaf from <0,4294967295> to <1,4294967295>, which in configuration/l2vpn/service-instances/vlss-instances/vlss-instance/traffic-statistics-params
39.Modify the rang of the broadcast-inrate-pps leaf from <0,4294967295> to <1,4294967295>, which in configuration/l2vpn/service-instances/vlss-instances/vlss-instance/traffic-statistics-params
40.Modify the rang of the drop-inrate-pps leaf from <0,4294967295> to <1,4294967295>, which in configuration/l2vpn/service-instances/vlss-instances/vlss-instance/traffic-statistics-params
41.Modify the rang of the unicast-inrate-pps leaf from <0,4294967295> to <1,4294967295>, which in configuration/l2vpn/service-instances/vlss-instances/vlss-instance/vlss-ac-bind/ac-instance-bind/ac-type/ethernet/ethernet-params/traffic-statistics-params
42.Modify the rang of the broadcast-inrate-pps leaf from <0,4294967295> to <1,4294967295>, which in configuration/l2vpn/service-instances/vlss-instances/vlss-instance/vlss-ac-bind/ac-instance-bind/ac-type/ethernet/ethernet-params/traffic-statistics-params
43.Modify the rang of the drop-inrate-pps leaf from <0,4294967295> to <1,4294967295>, which in configuration/l2vpn/service-instances/vlss-instances/vlss-instance/vlss-ac-bind/ac-instance-bind/ac-type/ethernet/ethernet-params/traffic-statistics-params
44.Modify the rang of the unicast-inrate-pps leaf from <0,4294967295> to <1,4294967295>, which in configuration/l2vpn/service-instances/vlss-instances/vlss-instance/vlss-ac-bind/ac-instance-bind/ac-type/tdm/tdm-params/traffic-statistics-params
45.Modify the rang of the broadcast-inrate-pps leaf from <0,4294967295> to <1,4294967295>, which in configuration/l2vpn/service-instances/vlss-instances/vlss-instance/vlss-ac-bind/ac-instance-bind/ac-type/tdm/tdm-params/traffic-statistics-params
46.Modify the rang of the drop-inrate-pps leaf from <0,4294967295> to <1,4294967295>, which in configuration/l2vpn/service-instances/vlss-instances/vlss-instance/vlss-ac-bind/ac-instance-bind/ac-type/tdm/tdm-params/traffic-statistics-params
47.Modify the rang of the unicast-inrate-pps leaf from <0,4294967295> to <1,4294967295>, which in configuration/l2vpn/service-instances/vlss-instances/vlss-instance/vlss-ac-bind/ac-instance-bind/ac-type/atm/atm-params/traffic-statistics-params
48.Modify the rang of the broadcast-inrate-pps leaf from <0,4294967295> to <1,4294967295>, which in configuration/l2vpn/service-instances/vlss-instances/vlss-instance/vlss-ac-bind/ac-instance-bind/ac-type/atm/atm-params/traffic-statistics-params
49.Modify the rang of the drop-inrate-pps leaf from <0,4294967295> to <1,4294967295>, which in configuration/l2vpn/service-instances/vlss-instances/vlss-instance/vlss-ac-bind/ac-instance-bind/ac-type/atm/atm-params/traffic-statistics-params
50.Modify the rang of the unicast-inrate-pps leaf from <0,4294967295> to <1,4294967295>, which in configuration/l2vpn/service-instances/vlss-instances/vlss-instance/vlss-ac-bind/ac-instance-bind/ac-type/ppp/ppp-params/traffic-statistics-params
51.Modify the rang of the broadcast-inrate-pps leaf from <0,4294967295> to <1,4294967295>, which in configuration/l2vpn/service-instances/vlss-instances/vlss-instance/vlss-ac-bind/ac-instance-bind/ac-type/ppp/ppp-params/traffic-statistics-params
52.Modify the rang of the drop-inrate-pps leaf from <0,4294967295> to <1,4294967295>, which in configuration/l2vpn/service-instances/vlss-instances/vlss-instance/vlss-ac-bind/ac-instance-bind/ac-type/ppp/ppp-params/traffic-statistics-params
53.Modify the rang of the unicast-inrate-pps leaf from <0,4294967295> to <1,4294967295>, which in configuration/l2vpn/service-instances/vlss-instances/vlss-instance/vlss-ac-bind/ac-instance-bind/ac-type/hdlc/hdlc-params/traffic-statistics-params
54.Modify the rang of the broadcast-inrate-pps leaf from <0,4294967295> to <1,4294967295>, which in configuration/l2vpn/service-instances/vlss-instances/vlss-instance/vlss-ac-bind/ac-instance-bind/ac-type/hdlc/hdlc-params/traffic-statistics-params
55.Modify the rang of the drop-inrate-pps leaf from <0,4294967295> to <1,4294967295>, which in configuration/l2vpn/service-instances/vlss-instances/vlss-instance/vlss-ac-bind/ac-instance-bind/ac-type/hdlc/hdlc-params/traffic-statistics-params
56.Modify the rang of the unicast-inrate-pps leaf from <0,4294967295> to <1,4294967295>, which in configuration/l2vpn/service-instances/vlss-instances/vlss-instance/vlss-ac-bind/ac-instance-bind/ac-type/fr/fr-params/traffic-statistics-params
57.Modify the rang of the broadcast-inrate-pps leaf from <0,4294967295> to <1,4294967295>, which in configuration/l2vpn/service-instances/vlss-instances/vlss-instance/vlss-ac-bind/ac-instance-bind/ac-type/fr/fr-params/traffic-statistics-params
58.Modify the rang of the drop-inrate-pps leaf from <0,4294967295> to <1,4294967295>, which in configuration/l2vpn/service-instances/vlss-instances/vlss-instance/vlss-ac-bind/ac-instance-bind/ac-type/fr/fr-params/traffic-statistics-params
59.Modify the rang of the unicast-inrate-pps leaf from <0,4294967295> to <1,4294967295>, which in configuration/l2vpn/service-instances/vlss-instances/vlss-instance/vlss-ac-bind/ac-instance-bind/ac-type/iwf-ip/iwf-ip-params/traffic-statistics-params
60.Modify the rang of the broadcast-inrate-pps leaf from <0,4294967295> to <1,4294967295>, which in configuration/l2vpn/service-instances/vlss-instances/vlss-instance/vlss-ac-bind/ac-instance-bind/ac-type/iwf-ip/iwf-ip-params/traffic-statistics-params
61.Modify the rang of the drop-inrate-pps leaf from <0,4294967295> to <1,4294967295>, which in configuration/l2vpn/service-instances/vlss-instances/vlss-instance/vlss-ac-bind/ac-instance-bind/ac-type/iwf-ip/iwf-ip-params/traffic-statistics-params
62.Modify the rang of the unicast-inrate-pps leaf from <0,4294967295> to <1,4294967295>, which in configuration/l2vpn/service-instances/vlss-instances/vlss-instance/vlss-ac-bind/ac-instance-bind/ac-type/iwf-eth/iwf-eth-params/traffic-statistics-params
63.Modify the rang of the broadcast-inrate-pps leaf from <0,4294967295> to <1,4294967295>, which in configuration/l2vpn/service-instances/vlss-instances/vlss-instance/vlss-ac-bind/ac-instance-bind/ac-type/iwf-eth/iwf-eth-params/traffic-statistics-params
64.Modify the rang of the drop-inrate-pps leaf from <0,4294967295> to <1,4294967295>, which in configuration/l2vpn/service-instances/vlss-instances/vlss-instance/vlss-ac-bind/ac-instance-bind/ac-type/iwf-eth/iwf-eth-params/traffic-statistics-params
65.Modify the rang of the unicast-inrate-pps leaf from <0,4294967295> to <1,4294967295>, which in configuration/l2vpn/service-instances/evpn-vpls-instances/evpn-vpls-instance/evpn-vpls-ac-bind/ac-instance-bind/ac-type/ethernet/ethernet-params/traffic-statistics-params
66.Modify the rang of the broadcast-inrate-pps leaf from <0,4294967295> to <1,4294967295>, which in configuration/l2vpn/service-instances/evpn-vpls-instances/evpn-vpls-instance/evpn-vpls-ac-bind/ac-instance-bind/ac-type/ethernet/ethernet-params/traffic-statistics-params
67.Modify the rang of the drop-inrate-pps leaf from <0,4294967295> to <1,4294967295>, which in configuration/l2vpn/service-instances/evpn-vpls-instances/evpn-vpls-instance/evpn-vpls-ac-bind/ac-instance-bind/ac-type/ethernet/ethernet-params/traffic-statistics-params
68.Modify the rang of the unicast-inrate-pps leaf from <0,4294967295> to <1,4294967295>, which in configuration/l2vpn/pw-specification/pw-entry/traffic-statistics-params
69.Modify the rang of the broadcast-inrate-pps leaf from <0,4294967295> to <1,4294967295>, which in configuration/l2vpn/pw-specification/pw-entry/traffic-statistics-params
70.Modify the rang of the drop-inrate-pps leaf from <0,4294967295> to <1,4294967295>, which in configuration/l2vpn/pw-specification/pw-entry/traffic-statistics-params
71.Modify the rang of the cir leaf from <0,4294967295> to <1,4294967295>, which in configuration/l2vpn/pw-specification/pw-entry/qos-parameters/qos-params-type/bandwidth-params/bandwidth
72.Modify the rang of the pir leaf from <0,4294967295> to <1,4294967295>, which in configuration/l2vpn/pw-specification/pw-entry/qos-parameters/qos-params-type/bandwidth-params/bandwidth' ;
  }

  revision 2018-01-24 {
    description '1.Add the unknown-mac-withdraw-mode leaf in configuration/l2vpn/service-instances/vpls-instances/vpls-instance.' ;
  }

  revision 2018-01-19 {
    description '1.Add the fault-spread leaf in configuration/l2vpn/service-instances/vpws-instances/vpws-instance/vpws-ac-bind/ac-instance-bind/ac-type/sonet-sdh/sonet-sdh-params
2.Add the oam-mapping leaf in configuration/l2vpn/service-instances/vpws-instances/vpws-instance/vpws-ac-bind/ac-instance-bind/ac-type/sonet-sdh/sonet-sdh-params
3.Add the track-name leaf in configuration/l2vpn/service-instances/vpws-instances/vpws-instance/vpws-ac-bind/ac-instance-bind/ac-type/sonet-sdh/sonet-sdh-params
4.Add the mpls-exp-value leaf in configuration/l2vpn/service-instances/vpws-instances/vpws-instance/vpws-ac-bind/ac-instance-bind/ac-type/sonet-sdh/sonet-sdh-params
5.Add the mpls-exp-value leaf in configuration/l2vpn/service-instances/vlss-instances/vlss-instance/vlss-ac-bind/ac-instance-bind/ac-type/sonet-sdh/sonet-sdh-params
6.Add label PTN6100 in feature martini-discovery
7.Add label PTN6100 in feature kompella-discovery
8.Add label PTN6100 in feature pw-list
9.Add label PTN6100 in feature operation-re-negotiate
10.Modify the rang of the distribute-period leaf from <2,64> to <1,64>, which in configuration/l2vpn/service-instances/vlss-instances/vlss-instance/vlss-ac-bind/ac-instance-bind/ac-type/tdm/tdm-params
11.Modify the rang of the cir leaf from <8,20000000> to <0,4294967295>, which in configuration/l2vpn/pw-specification/pw-entry/qos-parameters/qos-params-type/rate-limit-params/rate-limit
12.Modify the rang of the cbs leaf from <1,5120000> to <1,4294967295>, which in configuration/l2vpn/pw-specification/pw-entry/qos-parameters/qos-params-type/rate-limit-params/rate-limit
13.Modify the rang of the pir leaf from <8,20000000> to <0,4294967295>, which in configuration/l2vpn/pw-specification/pw-entry/qos-parameters/qos-params-type/rate-limit-params/rate-limit
14.Modify the rang of the pbs leaf from <1,5120000> to <1,4294967295>, which in configuration/l2vpn/pw-specification/pw-entry/qos-parameters/qos-params-type/rate-limit-params/rate-limit
15.Modify the rang of the cir leaf from <1,4294967295> to <0,4294967295>, which in configuration/l2vpn/pw-specification/pw-entry/qos-parameters/qos-params-type/bandwidth-params/bandwidth
16.Modify the rang of the pir leaf from <1,4294967295> to <0,4294967295>, which in configuration/l2vpn/pw-specification/pw-entry/qos-parameters/qos-params-type/bandwidth-params/bandwidth' ;
  }

  revision 2017-12-13 {
    description '1.Add the bridge-interface container in configuration/l2vpn/service-instances/vpls-instances/vpls-instance.' ;
  }

  revision 2017-12-01 {
    description '1.Add the vpws-community-instances container in configuration/l2vpn/service-instances.' ;
  }

  revision 2017-11-17 {
    description '1.In order to distinguish switch and other projects add the features of bridge-interface and bridge-mapping,The bridge-mapping feature is for switch project and th bridge-interface feature is for other projects.
2.Add the bridge-mapping container in configuration/l2vpn/service-instances/evpn-vpls-instances/evpn-vpls-instance. 
3.Add the feature for bridge-interface container which in configuration/l2vpn/service-instances/evpn-vpls-instances/evpn-vpls-instance.' ;
  }

  revision 2017-11-15 {
    description '1.Add the service-id leaf in configuration/l2vpn/service-instances/vpls-instances/vpls-instance.
2.Add the service-id leaf in configuration/l2vpn/service-instances/evpn-vpls-instances/evpn-vpls-instance.' ;
  }

  revision 2017-11-07 {
    description '1. Delete the evpn-vpls-instances feature,EVPN VPLS function modified to support all projects.' ;
  }

  revision 2017-09-20 {
    description '1.Add the l2bfd leaf in configuration/l2vpn/service-instances/vpws-instances/vpws-instance/vpws-ac-bind/ac-instance-bind/ac-type/ethernet/ethernet-params/l2protocol-control-policy/l2bfd.' ;
  }

  revision 2017-09-07 {
    description '1.Add the vtep-interface container in configuration/l2vpn/service-instances/evpn-vpls-instances/evpn-vpls-instance/evpn-vpls-dynamic-vxlan.' ;
  }

  revision 2017-08-25 {
    description '1.Add the description leaf node which in configuration/l2vpn/service-instances/vpws-instances/vpws-instance/vpws-ac-bind/ac-instance-bind.
2.Add the description leaf node which in configuration/l2vpn/service-instances/vpls-instances/vpls-instance/vpls-ac-bind/ac-instance-bind.
3.Add the description leaf node which in configuration/l2vpn/service-instances/vlss-instances/vlss-instance/vlss-ac-bind/ac-instance-bind.
4.Add the description leaf node which in configuration/l2vpn/service-instances/evpn-vpls-instances/evpn-vpls-instance/evpn-vpls-ac-bind/ac-instance-bind.' ;
  }

  revision 2017-07-26 {
    description '1.ZSR added support the l2protocol-control-policy function.
2.V6000(vBRAS-C)added support the VPLS EVPN function.
3. L2VPN netconf module modified to support all projects.' ;
  }

  revision 2017-07-13 {
    description '1.T8000 added support the l2protocol-control-policy function.' ;
  }

  revision 2017-07-05 {
    description '1.Add the ac-fault-associate leaf which in configuration/l2vpn/service-instances/vpws-instances/vpws-instance;
2.Add the ac-fault-associate container which in configuration/l2vpn/service-instances/vpls-instances/vpls-instance.' ;
  }

  revision 2017-06-28 {
    description '1. Add the split-horizon-scope leaf which in configuration/l2vpn/service-instances/vpls-instances/vpls-instance/martini-discovery/pw-details-params.' ;
  }

  revision 2017-06-20 {
    description '1.Add the evpn-vpls-mpls-evpn container in configuration/service-instances/evpn-vpls-instance for mpls-evpn function.' ;
  }

  revision 2017-06-13 {
    description '1.T8000 added support EVPN VPLS funtion.' ;
  }

  revision 2017-06-08 {
    description '1.Add the equivalent-vxlan-id leaf in configuration/l2vpn/vpls-instances/vpls-instance.' ;
  }

  revision 2017-03-31 {
    description '1.Add the split-horizon and split-horizon-scopes leaves in configuration/service-instances/evpn-vpls-instances/evpn-vpls-instance/evpn-vpls-ac-bind/ac-instance-bind.' ;
  }

  revision 2017-03-07 {
    description '1.Add leaf configuration/l2vpn/service-instances/evpn-vpls-instances/evpn-vpls-instance/evpn-vpls-static-vxlans/evpn-vpls-static-vxlan/split-horizon.' ;
  }

  revision 2017-02-24 {
    description '1.MCG-5000 and MSR(ASR,ZSRV2) added support EVPN VPLS funtion.
2.PTN(6100) added support admin-vpls funtion.' ;
  }

  revision 2016-12-26 {
    description '1.Add the split-horizon leaf which in configuration/l2vpn/service-instances/evpn-vpls-instances/evpn-vpls-instance/evpn-vpls-dynamic-vxlan/route-target-params.
2.Add the split-horizon leaf which in configuration/l2vpn/service-instances/evpn-vpls-instances/evpn-vpls-instance/evpn-vpls-dynamic-vxlan/evpn-vpls-vni-labels.
3.Add the evpn-vpls-equivalent-vni-label list which in configuration/l2vpn/service-instances/evpn-vpls-instances/evpn-vpls-instance/evpn-vpls-dynamic-vxlan/evpn-vpls-vni-labels.' ;
  }

  revision 2016-12-15 {
    description '1. Add the hard-pipe containers which in configuration/l2vpn/service-instances/vpws-instances/vpws-instance/vpws-ac-bind/ethernet-params,tdm-params,atm-params,ppp-params,hdlc-params,fr-params,sonet-sdh-params.
2. Add the hard-pipe containers which in configuration/l2vpn/service-instances/vlss-instances/vlss-instance/vlss-ac-bind/ethernet-params,tdm-params,atm-params,ppp-params,hdlc-params,fr-params,sonet-sdh-params.
3. Add the leaf of hard-pipe which in configuration/l2vpn/pw-specification/pw-entry.' ;
  }

  revision 2016-10-14 {
    description '1.Add the user-protocol-template container in configuration/vpws-instances/vpws-instance/vpws-ac-bind/ac-instance-bind/ethernet-params/l2protocol-control-policy.' ;
  }

  revision 2016-09-27 {
    description '1.Add the control-word and split-horizon-scope leafs in configuration/l2vpn/service-instances/vpls-instances/vpls-instance/kompella-discovery/kompella-params.
2.Add the encapulation container in configuration/l2vpn/service-instances/vpls-instances/vpls-instance/kompella-discovery/kompella-params.' ;
  }

  revision 2016-09-23 {
    description '1.Obsolete the tunnel-destination-ipv6 node which in l2vpn/configuration/pw-specification/pw-entry.
2.Add the tunnel-destination container in l2vpn/configuration/pw-specification/pw-entry.' ;
  }

  revision 2016-08-12 {
    description '1.Delete the ingress-ajust-push-params container which in configuration/l2vpn/service-instances/evpn-vpls-instances/evpn-vpls-instance/evpn-vpls-ac-bind/ac-instance-bind/ethernet-params.' ;
  }

  revision 2016-07-22 {
    description '1.Add the evpn-vpls-instances container in configuration/l2vpn/service-instances.' ;
  }

  revision 2016-07-13 {
    description '1.Add the dni-detect feature for DNI detect function.
2.Add the vpws-receiving-pw-bind and enhanced-dni-pwgroup features for enhanced DNI-PW protect group function.
3.Add the flow-label feature for flow label function.
4.Apply the dni-detect feature on dni-detect container which in configuration/l2vpn/l2vpn-global.
5.Apply the vpws-receiving-pw-bind feature on vpws-receiving-pw-bind container which in configuration/l2vpn/service-instances/vpws-instances/vpws-instance.
6.Apply the enhanced-dni-pwgroup feature on enhanced-dni-pwgroup choice which in configuration/l2vpn/protect-rules/protect-group/protect-strategy.
7.Apply the flow-label feature on flow-label container which in configuration/l2vpn/pw-specification/pw-entry.' ;
  }

  revision 2016-03-30 {
    description '1.Add the vpws-receiving-pw-bind container in configuration/l2vpn/service-instances/vpws-instance.
2.Add a choice of enhanced-dni-pwgroup in configuration/l2vpn/protect-rules/protect-group/protect-strategy.' ;
  }

  revision 2016-02-22 {
    description '1.Add the dni-detect container in configuration/l2vpn/l2vpn-global for DNI assosiate peer BFD function.' ;
  }

  revision 2016-01-14 {
    description '1.Add the enumeration for abm,cfm,cisco,dldp,dot1x,dot3x,efm,garp,gmrp,gvrp,pvst,zdp,erps,
udld,vtp,zesr leafs which in configuration/l2vpn/service-instances/vpws-instances/vpws-ac-bind/ac-instance-bind/l2protocol-control-policy.
2.Add the erps,udld,vtp,zesr leafs which in configuration/l2vpn/service-instances/vpws-instances/vpws-ac-bind/ac-instance-bind/l2protocol-control-policy.' ;
  }

  revision 2015-11-10 {
    description '1.Delete the l2cp-drop container in configuration/l2vpn/service-instances/vpws-instances/vpws-ac-bind/ac-instance-bind.
2.Add the l2protocol-control-policy container in configuration/l2vpn/service-instances/vpws-instances/vpws-ac-bind/ac-instance-bind.
3.Delete the T8000 project label on l2cp-drop feature.' ;
  }

  revision 2015-10-30 {
    description '1.Add the pw-name leaf node in state/l2vpn/kompella-pw/kompella-pw-info.' ;
  }

  revision 2015-10-15 {
    description '1.Revert the modify of 2015-09-14,the default value of fault-spread node reverted to disable and add the explaination of enum value which in configuration/l2vpn/service-instances/vpws-instance/vpws-ac-bind/ac-instance-bind/ethernet-params,configuration/l2vpn/service-instances/vpws-instance/vpws-ac-bind/ac-instance-bind/tdm-params,configuration/l2vpn/service-instances/vpws-instance/vpws-ac-bind/ac-instance-bind/atm-params,configuration/l2vpn/service-instances/vpws-instance/vpws-ac-bind/ac-instance-bind/ppp-params,configuration/l2vpn/service-instances/vpws-instance/vpws-ac-bind/ac-instance-bind/hdlc-params,configuration/l2vpn/service-instances/vpws-instance/vpws-ac-bind/ac-instance-bind/fr-params,configuration/l2vpn/service-instances/vpws-instance/vpws-ac-bind/ac-instance-bind/iwf-ip-params,configuration/l2vpn/service-instances/vpws-instance/vpws-ac-bind/ac-instance-bind/iwf-eth-params.' ;
  }

  revision 2015-10-08 {
    description '1.Modify the remote-veid node range from 0-65534 to 0-65535 which in state/l2vpn/kompella-pw/kompella-pw-info.' ;
  }

  revision 2015-09-14 {
    description '1.The default value of fault-spread node changed from disable to enable which in configuration/l2vpn/service-instances/vpws-instance/vpws-ac-bind/ac-instance-bind/ethernet-params,configuration/l2vpn/service-instances/vpws-instance/vpws-ac-bind/ac-instance-bind/tdm-params,configuration/l2vpn/service-instances/vpws-instance/vpws-ac-bind/ac-instance-bind/atm-params,configuration/l2vpn/service-instances/vpws-instance/vpws-ac-bind/ac-instance-bind/ppp-params,configuration/l2vpn/service-instances/vpws-instance/vpws-ac-bind/ac-instance-bind/hdlc-params,configuration/l2vpn/service-instances/vpws-instance/vpws-ac-bind/ac-instance-bind/fr-params,configuration/l2vpn/service-instances/vpws-instance/vpws-ac-bind/ac-instance-bind/iwf-ip-params,configuration/l2vpn/service-instances/vpws-instance/vpws-ac-bind/ac-instance-bind/iwf-eth-params.
2.The list name of outtter-fwd modified to outter-fwd which in state/l2vpn/pw-info/outter-fwd-info.' ;
  }

  revision 2015-08-21 {
    description '1.The following nodes data type modified from ipv4-address to ipv4-address-none-zero:
1)state/l2vpn/pw-info/peer-address;
2)state/l2vpn/kompella-pw/peer-address;
2.Modify the service-vlan node range from 1-4094 to 0-4094 which in configuration/l2vpn/service-instances/vpws-instance/vpws-ac-bind/ac-instance-bind/iwf-eth-params;
3.Add the service-vlan node in configuration/l2vpn/service-instances/vlss-instance/vlss-ac-bind/ac-instance-bind/iwf-eth-params.' ;
  }

  revision 2015-08-14 {
    description '1.Add the unknown value in status node which in state/l2vpn/pw-list.' ;
  }

  revision 2015-08-04 {
    description '1. Delete the outter-depth,outlabel1,outlabel2,outlabel3,tunnel-id and out-interface leafs which in state/l2vpn/pw-info;
2. Delete the outter-depth,outlabel1,outlabel2,outlabel3,tunnel-id and out-interface leafs which in state/l2vpn/kompella-pw;
3. Add the outter-fwd-info container in state/l2vpn/pw-info;
4. Add the outter-fwd-info container in state/l2vpn/kompella-pw/kompella-pw-info;' ;
  }

  revision 2015-07-27 {
    description '1.Delete the config flag which on operation node.' ;
  }

  revision 2015-07-15 {
    description '1. Add the default-encapsulation leaf node in configuration/vpls-instances/vpls-instance.' ;
  }

  revision 2015-07-03 {
    description '1. In order to remove the ipv6 zero address,add the patterns in tunnel-destination-ipv6 node which in configuration/pw-specification/pw-entry.' ;
  }

  revision 2015-06-23 {
    description '1.The following nodes data type modified from mac-address to mac-address-none-zero:
1)configuration/l2vpn/service-instances/vpws-instances/vpws-ac-bind/ethernet/l2cp-drop/drop-wildcard;
2)configuration/l2vpn/service-instances/vpws-instances/vpws-ac-bind/iwf-ip/local-ce-mac;
3)configuration/l2vpn/service-instances/vlss-instances/vlss-ac-bind/iwf-ip/local-ce-mac;
4)configuration/l2vpn/service-instances/vpws-instances/vpws-ac-bind/iwf-eth/proxy-mac and remote-mac;
5)configuration/l2vpn/service-instances/vlss-instances/vlss-ac-bind/iwf-eth/proxy-mac and remote-mac;
6)configuration/l2vpn/service-instances/vpws-instances/vpws-ac-bind/tdm-relay/access-source/dmac;
2.The following nodes data type modified from ipv4-address to ipv4-address-none-zero:
1)configuration/l2vpn/service-instances/vpws-instances/vpws-ac-bind/iwf-ip/remote-ip;
2)configuration/l2vpn/service-instances/vlss-instances/vlss-ac-bind/iwf-ip/remote-ip;
3)configuration/l2vpn/service-instances/vpws-instances/vpws-ac-bind/iwf-eth/local-ip and remote-ip;
4)configuration/l2vpn/service-instances/vlss-instances/vlss-ac-bind/iwf-eth/local-ip and remote-ip;
5)configuration/l2vpn/service-instances/vpls-instances/martini-discovery/pw-details-params/peer-address;
3.The ingress-adjust-drop-tagged-frames nodes delete the null enum value which in the flowing paths.The null enum value is not necessary.
1)configuration/l2vpn/service-instances/vpws-instances/vpws-ac-bind/ethernet/ethernet-params;
2)configuration/l2vpn/service-instances/vpls-instances/vpls-ac-bind/ethernet/ethernet-params;
3)configuration/l2vpn/service-instances/vlss-instances/vlss-ac-bind/ethernet/ethernet-params;
4. The traffic-enable node which in configuration/l2vpn/l2vpn-global delete th  mim map 2 to 0,The code modify so it is not necessary.' ;
  }

  revision 2015-04-28 {
    description "1. Add the traffic-enable leaf node in configuration/vpls-instances/martini-discovery/pw-details-params and configuration/vpls-instances/kompella-discovery/kompella-params.
    2. Add the requested-vlan-parameters in configuration/pw-specification/pw-entry.
    3. Add the feature of requested-vlan-pw for requested vlan function.
    4. Modify the pw-name's if filter-id from 919 to 925 which in operation/l2vpn/pw-statistics/pw-info." ;
  }

  revision 2015-04-20 {
    description '1. Add the oam-mapping leaf node in configuration/l2vpn/service-instances/mspw-instances/mspw-instance.' ;
  }

  revision 2015-02-06 {
    description '1.The enumeration value of negotiated-cword leaf changed from notPreferred to not-preferred which in state/l2vpn/pw-info.
2.The date type of description leaf changed from string to string-with-blank which in configuration/l2vpn/admin-vpls-instance.
3. The range of service-vlan leaf changed from 0-4094 to 1-4094 which in configuration/l2vpn/vpws-instance/vpws-ac-bind/iwf-eth.
4.Delete the service-vlan leaf which in configuration/l2vpn/vlss-instance/vlss-ac-bind/iwf-eth.
5.Modify the mode of vccv-bfd-params which in configuration/l2vpn/service-instances/vpls-instances/martini-discovery/pw-details.
6.Modify the slot-number prefix value which in configuration/l2vpn/service-instances/vpls-instances/vpls-ac-bind/ethernet-cip/slot-params and configuration/l2vpn/service-instances/vpws-instances/vpws-ac-bind/ethernet-cip/slot-params.
7.The enumeration value of fr-dlci-header-length leaf changed from dlciheadlengthThree to dlciHeadlengthThree, from dlciheadlengthFour to dlciHeadlengthFour.' ;
  }

  revision 2015-01-28 {
    description '1.Add the remaining-pw leaf node in state/l2vpn/pw-count.
2.Add the remaining-vpls,remaining-vpws leaf nodes in state/l2vpn/inst-count.
3.Add the default value on vpws-instances/vpws-ac-bind/ac-instance-bind/ethernet-params/l2cp-drop/drop-dldp leaf.' ;
  }

  revision 2015-01-07 {
    description '1.Add the flow-label container in configuration/l2vpn/pw-specification.' ;
  }

  revision 2014-11-20 {
    description '1.Add the udp-echo container in configuration/l2vpn/service-instances/vpws-instance/vpws-ac-bind/ethernet-params for monitor-ip udp-echo function.
2.Add the udp-echo container in configuration/l2vpn/service-instances/vlss-instance/vlss-ac-bind/ethernet-params for monitor-ip udp-echo function.' ;
  }

  revision 2014-10-22 {
    description "1. The working-interface node's if filter-id modified from 936 to 919 which in state/l2vpn/pw-group-info;
    2. Add the access-pw-group container in state/l2vpn for access PW query information;
    3. Modify the protect-rules container which in configuration/l2vpn,add three choice branches for common-group,single-dni-pwgroup and dual-dni-pwgroup." ;
  }

  revision 2014-10-17 {
    description '1.Add the choice of ethernet-cip and tdm-relay in configuration/l2vpn/vpws-instances/vpws-instance/vpws-ac-bind.
2.Add the choice of ethernet-cip in configuration/l2vpn/vpls-instances/vpls-instance/vpls-ac-bind.
3.Add the features of ethernet-cip and tdm-relay.' ;
  }

  revision 2014-10-13 {
    description '1.Modify the pw-list-id node range from 1-256 to 1-1024 which in state/l2vpn/pw-list.
2.Modify the list-id node range from 1-256 to 1-1024 which in configuration/l2vpn/protect-rules/pw-list-params/pw-list.' ;
  }

  revision 2014-09-22 {
    description "1. Because the PW's bandwidth and rate-limit is mutually-exclusive,so add a choice branch for them. Modify the configuration/pw-specification/qos-parameters." ;
  }

  revision 2014-08-22 {
    description '1.Add the dlciheadlengthThree value of fr-dlci-header-length node which in configuration/service-instances/mspw-instances/mspw-instance/remote-parameters.' ;
  }

  revision 2014-08-14 {
    description '1.Add the admin-vpls-instances container in configuration/l2vpn/service-instances for VPLS STP function.
2.Add the admin-vpls-instances feature for admin-vpls-instances container.' ;
  }

  revision 2014-07-28 {
    description "1.Delete the auto-discovery container which in operation/l2vpn;
    2.Delete the name and lifespan-permanent nodes which in configuration/l2vpn/service-instances/vpls-instance/martini-discovery/pw-details-params/pw-details;
    3.The out-interface node's range changed from 1-31 to 0-31,which in state/l2vpn/pw-info;
    4. Additional the description of remote-status node,which in state/l2vpn/pw-info." ;
  }

  revision 2014-07-17 {
    description '1.Add the traffic-enable-pw leaf in state/l2vpn/pw-count for traffic enable pw count function.
2.Add the tunnel-destination-ipv6 leaf in configuration/l2vpn/pw-specification/pw-entry.' ;
  }

  revision 2014-07-04 {
    description "1. Add the range limit of create-time,last-status-change-time and out-interface which in state/l2vpn/pw-info.
    2. Modify  the leaf of monitor-ip's date type from ipv4-address to ipv4-address-without-all-zero,which in configuration/vpws-instance/vpws-ac-bind/ethernet-params and configuration/vlss-instance/vlss-ac-bind/ethernet-params.
    3.Modify  the leaf of monitor-mac's date type from mac-address to mac-address-without-all-zero,which in configuration/vpws-instance/vpws-ac-bind/ethernet-params and configuration/vlss-instance/vlss-ac-bind/ethernet-params." ;
  }

  revision 2014-06-26 {
    description '1.Modify the following leaf nodes name which in state/statistics/instance-statistics,state/statistics/pw-statistics and state/statistics/ac-statistics:recvpkts changed to in-packets,recvbytes changed to in-bytes,recvpkts-rate changed to in-packets-rate,recvbytes-rate changed to in-bytes-rate,sndpkts changed to out-packets,sndbytes changed to out-bytes,sndpkts-rate changed to out-packets-rate,sndbytes-rate changed to out-bytes-rate,in-drop-pkts changed to in-drop-packets,out-drop-pkts changed to out-drop-packets,indrop-bytes-rate changed to in-drop-bytes-rate,indrop-packets-rate changed to in-drop-packets-rate,inbroadcast-bytes-rate changed to in-broadcast-bytes-rate,inbroadcast-packets-rate changed to in-broadcast-packets-rate,inunicast-bytes-rate changed to in-unknown-unicast-bytes-rate,inunicast-packets-rate changed to in-unknown-unicast-packets-rate.
2.Add the following leaf nodes in state/statistics/instance-statistics,state/statistics/pw-statistics and state/statistics/ac-statistics:in-unknown-unicast-bytes,in-unknown-unicast-packets,in-multicast-bytes,in-multicast-packets,out-broadcast-bytes,out-broadcast-packets,out-multicast-bytes,out-multicast-packets.
3.Delete the in-bandwidth,in-bandwidth-usage,out-bandwidth and out-bandwidth-usage nodes which in state/statistics/pw-statistics.
4.Adjust the leaf nodes sequence of state/statistics/instance-statistics,state/statistics/pw-statistics and state/statistics/ac-statistics.' ;
  }

  revision 2014-05-29 {
    description '1. Add the pw-count container in state/l2vpn for pw count function.' ;
  }

  revision 2014-05-28 {
    description '1. The pw-info which in state/l2vpn table add three query conditions:vpn-name,peer-address and vpn-name+peer-address.
2. The ac-statistics which in state/l2vpn/statistics table modify the key from interface-index to ac-name,because the interface-index is not visible to the user.
3. Add the kompella-pw query info in state/l2vpn table.
4. Add the rtp-header node and delete the rtp-timestamp node default value,which in configuration/l2vpn/service-instances/vpws-ac-bind/ac-instance-bind/sonet-sdh and configuration/l2vpn/service-instances/vpws-ac-bind/ac-instance-bind/sonet-sdh.
5. The node name of vcc-bfd-capability changed to vccv-bfd-capability which in configuration/pw-specification/pw-entry/vccv-bfd-params.
6. The create-time and last-status-change-time nodes data type changed from time to string-with-blank which in state/pw-info list.
7. Add the range limitation 1-256 for pw-list-id node which in state/pw-list list.
8. Add the string length limitation 1-31 for PW and AC name which in state/l2vpn.' ;
  }

  revision 2014-02-11 {
    description '1. Add the inst-count container for L2VPN instance count.
2. Add the l2cp-drop container in ethernet of vpws-ac-bind and the feature of l2cp-drop.
3. Add the monitor-ip,monitor-mac,monitor-mode nodes in ethernet of vpws-ac-bind and vlss-ac-bind.
4. Modify the data type and range of iccp-group-roid leaf.
5. Add the presence for containers which have mandatory.
6. Add the rtp-header node in tdm of vpws-ac-bind and vlss-ac-bind,and delete the rtp-timestamp node default value.' ;
  }

  revision 2014-01-09 {
    description '1.Add the case of sonet-sdh in ac-instance-bind of VPWS/VLSS instances.
2.Delete the sdh-sonet,sdh-payload-compression, payload-bytes and payload-units nodes which in tdm-params of VPWS/VLSS instances.
3.The node name of l2vpn-enable changed to l2vpn-global.
4.Add the traffic-enable node in ac-instance-bind of VPWS/VLSS instances.
5.Add the root-leaf node in ethernet-params of vpls-ac-bind.
6.Add the structure node in tdm-params of vlss-ac-bind.
7.Add the rate-limit-red-flag node in qos-parameters of pw-specification.
8.Delete the required-vlan-tag node in required-vlan-parameters of pw-specification.
9.Add the operation-re-negotiate,operation-control-word and operation-auto-discovery features.
10.The description node date type of instances changed from string to string-with-blank.' ;
  }

  revision 2013-12-11 {
    description '1. The tdm-time-slots node range changed from 1-1000 to 1-400 which in mspw-instances/remote-parameters/tdm-parameters.
2. Add max-cells node in vpws-instances/vpws-ac-bind/atm-params and vlss-instances/vlss-ac-bind/atm-params.
3. The push-vlan-id node range changed from 0-4094 to 1-4094,and delete the default value.
4. Add the if-fliter function.It include:pw-info/pw-name,pw-group-info/working-interface,pw-statistics/pw-name,mc-protect-group/local-pw-name of state node;vpws-pw-bind/pw-name,vpws-ac-bind/ac-name,vpls-pw-bind/pw-name,vpls-ac-bind/ac-name,mspw-pw-bind/pw-name,vlss-ac-bind/ac-name,monitor-pw-bind/pw-name,pw-entry/pw-name,protect-group/interface-name,pw-protect-group/protect-pw/protect-pwname,ac-protect-group/protect-pw/protect-pwname,pw-list/master-pw-info/pw-name,pw-list/slave-pw-info/pw-name of configuration node;negotiate-pw/pw-name,control-lbit/pw-name,clear/pw-info/pw-name,clear/ac-info/ac-name of operation node.' ;
  }

  revision 2013-11-21 {
    description '1. Add the split-horizon-scopes node in vpls-pw-bind and vpls-ac-bind.
2. Add the status-terminal node in mspw-instance.' ;
  }

  revision 2013-10-23 {
    description '1. Add the revision of 2013-10-23.
2. Modify the features in according with function.
3. Add the container of l2vpn-enable and delete the global-enable nodes enumeration value of disable.
4. The qos-mode service-class and colour nodes delete the enumeration value of null.
5. The minimum of traffic-statistics related nodes is changed from 1 to 0,for example,unicast-inrate-bps,unicast-inrate-pps,broadcast-inrate-bps,drop-inrate-bps.
6. The value of sdh-sonet node is changed from boolean to enumeration.
7. Delete the cell-concatenation node,because this version does not have this function.
8. The value of split-horizon node which in vpls-ac-bind container is changed from spoke/hub to server/client.
9. The name of ingress-tag-as-payload changed to ingress-adjust-tag-as-payload.
10. The name of begin-ve-block changed to begin-ve-id,The name of end-ve-block changed to end-ve-id.
11. fcs-retention-headlength-flag,fr-dlci-header-length,cas-trunk-type,async-type and cword-usage-forced nodes delete the enumeration value of null.
12. Add the container of tdm-parameters.
13. Add the leaf nodes of oam-mapping-ignoring-frr and abort-mapping-to-ac.
14. Delete the leaf nodes of coworker-proxy-ac.
15. Add the container of l2vpn-statistics for clear the L2VPN all statistics.' ;
  }

  revision 2013-08-14 {
    description "The second version.The changes are as follows:
    1.Increasing the operation object model;
    2.In order to use the MIB object,modify the following object ID:
    status/l2vpn/statistics/instance-statistics's object ID modified from 14572 to 14339;
    status/l2vpn/statistics/pw-statistics's object ID modified from 14573 to 14340;     status/l2vpn/statistics/ac-statistics-s object ID modified from 14574 to 14341;
    3. The configuration attribute removed of status/l2vpn/statistics node." ;
  }

  revision 2013-06-20 {
    description 'Initial version.' ;
  }

  feature instances-traffic-statistics {
    description 'The VPLS/VPWS/MSPW/VLSS instances traffic statistics function.' ;
  }

  feature ac-traffic-statistics {
    description 'The AC traffic statistics function.' ;
  }

  feature pw-traffic-statistics {
    description 'The PW traffic statistics function.' ;
  }

  feature tdm {
    description 'The TDM function.' ;
  }

  feature atm {
    description 'The ATM function.' ;
  }

  feature ppp {
    description 'The PPP function.' ;
  }

  feature fr {
    description 'The FR function.' ;
  }

  feature hdlc {
    description 'The HDLC function.' ;
  }

  feature inter-working-ip {
    description 'The inter-working IP function.' ;
  }

  feature inter-working-ethernet {
    description 'The inter-working ethernet function.' ;
  }

  feature vlss-instances {
    description 'The VLSS instances function.' ;
  }

  feature remote-monitor-instances {
    description 'The remote monitor instances function.' ;
  }

  feature ac-protect-group {
    description 'The AC protect group function.' ;
  }

  feature pw-list {
    description 'The PW list function.' ;
  }

  feature required-vlan-pw ;

  feature martini-discovery {
    description 'The martini-discovery function.' ;
  }

  feature kompella-discovery {
    description 'The kompella-discovery function.' ;
  }

  feature mspw-remote-parameters {
    description 'The MSPW remote interface parameters.' ;
  }

  feature sonet-sdh {
    description 'The SONET/SDH function.' ;
  }

  feature operation-re-negotiate {
    description 'The re-negotiate function in operation node.' ;
  }

  feature operation-control-word {
    description 'The control word relation function of operation node.' ;
  }

  feature operation-auto-discovery {
    description 'The auto discovery function in operation node.' ;
  }

  feature l2cp-drop {
    description 'The l2cp-drop function.' ;
  }

  feature l2cp-drop-subset {
    description 'The l2cp-drop function.' ;
    ncd:revise-date 2025-06-09 ;
  }

  feature admin-vpls-instances {
    description 'The administrator VPLS instances function.' ;
  }

  feature ethernet-cip {
    description 'The ethernet-cip function.' ;
  }

  feature tdm-relay {
    description 'The TDM relay function.' ;
  }

  feature requested-vlan-pw {
    description 'The requested VLAN value function.' ;
  }

  feature dni-detect {
    description 'The DNI detect function.' ;
  }

  feature vpws-receiving-pw-bind {
    description 'The receiving PW which bind to VPWS service.' ;
  }

  feature enhanced-dni-pwgroup {
    description 'The enhanced DNI-PW protect group function.' ;
  }

  feature flow-label {
    description 'The flow label function.' ;
  }

  feature bridge-interface {
    description 'The bridge interface function for EVPN VPLS.' ;
  }

  feature bridge-mapping {
    description 'The bridge mapping function for EVPN VPLS.' ;
  }

  feature clear-ac-statistic {
    description 'Clear the AC traffic statistics.' ;
  }

  feature idle-code-enum {
    description 'The idle code value is enumeration.' ;
  }

  feature idle-code-range {
    description 'The idle code value is range of 0-255.' ;
  }

  feature vpws-community-mpls-duplicate {
    description 'The duplicate feature of VPWS community MPLS EVPN.' ;
  }

  feature vpws-community-srv6-duplicate {
    description 'The duplicate feature of VPWS community SRv6 EVPN.' ;
  }

  feature separated-bum-label {
    description 'Separated BUM label.' ;
    ncd:revise-date 2023-08-24 ;
  }

  feature vpls-irb-track-vpls-state {
    description 'VPLS IRB interface track the VPLS instance state.' ;
    ncd:revise-date 2023-09-21 ;
  }

  feature wtr-second {
    description 'Set WTR in second.' ;
    ncd:revise-date 2023-12-12 ;
  }

  feature vlss-access-pw-group {
    description 'VLSS access PW group.' ;
    ncd:revise-date 2024-01-02 ;
  }

  container state {
    config false ;
    description 'L2VPN module state info.' ;
    container l2vpn {
      description 'L2VPN module query root node.It contains PW,PW group,traffic statistics,PW track and PW list info.' ;
      list pw-info {
        description 'PW forwarding table query info.' ;
        key pw-name ;
        leaf pw-name {
          description 'The name of the PW.' ;
          type ncd:ifname {
            length 1..31 {
              description 'The length of PW name.' ;
            }

          }

        }

        leaf vpn-name {
          description 'The name of the L2VPN instance.' ;
          type string {
            length 1..32 {
              description 'The length of instance name.' ;
            }

          }

        }

        leaf peer-address {
          description "The remote peer's IP address of the PW." ;
          type ncd:ipv4-address-none-zero ;

        }

        leaf vcid {
          description 'The VCID of the PW.' ;
          type uint32 ;

        }

        leaf pw-type {
          description 'L2VPN PW type. Assigned values are specified in IANA Allocations for Pseudowire Edge to Edge Emulation (PWE3).' ;
          type enumeration {
            enum unknown {
              value 0 ;
              description 'The PW type is unknown.' ;
            }

            enum dlciOld {
              value 1 ;
              description 'The PW type is FR-DLCI old.' ;
            }

            enum atmSdu {
              value 2 ;
              description 'The PW type is ATM-AAL5-SDU.' ;
            }

            enum atmCell {
              value 3 ;
              description 'The PW type is ATM-CELL.' ;
            }

            enum vlan {
              value 4 ;
              description 'The PW type is VLAN.' ;
            }

            enum ethernet {
              value 5 ;
              description 'The PW type is ethernet.' ;
            }

            enum hdlc {
              value 6 ;
              description 'The PW type is HDLC.' ;
            }

            enum ppp {
              value 7 ;
              description 'The PW type is PPP.' ;
            }

            enum sdhCESoM {
              value 8 ;
              description 'The PW type is SONET/SDH Circuit Emulation Service over MPLS.' ;
            }

            enum atmVCCn {
              value 9 ;
              description 'The PW type is ATM n-to-one VCC.' ;
            }

            enum atmVPCn {
              value 10 ;
              description 'The PW type is ATM n-to-one VPC.' ;
            }

            enum ipL2 {
              value 11 ;
              description 'The PW type is IP-L2.' ;
            }

            enum atmVCC1 {
              value 12 ;
              description 'The PW type is ATM one-to-one VCC.' ;
            }

            enum atmVPC1 {
              value 13 ;
              description 'The PW type is ATM one-to-one VPC.' ;
            }

            enum atmPDU {
              value 14 ;
              description 'The PW type is ATM AAL5 PDU VCC.' ;
            }

            enum frPort {
              value 15 ;
              description 'The PW type is FR port.' ;
            }

            enum sdhCEoP {
              value 16 ;
              description 'The PW type is SONET/SDH Circuit Emulation over Packet.' ;
            }

            enum saTopE1 {
              value 17 ;
              description 'The PW type is Structure-agnostic E1 over Packet.' ;
            }

            enum saTopT1 {
              value 18 ;
              description 'The PW type is Structure-agnostic T1 (DS1) over Packet.' ;
            }

            enum saTopE3 {
              value 19 ;
              description 'The PW type is Structure-agnostic E3 over Packet.' ;
            }

            enum saTopT3 {
              value 20 ;
              description 'The PW type is Structure-agnostic T3 (DS3) over Packet.' ;
            }

            enum ceSoPSNB {
              value 21 ;
              description 'The PW type is CESoPSN basic.' ;
            }

            enum tdmAAL1 {
              value 22 ;
              description 'The PW type is TDMoIP AAL1.' ;
            }

            enum ceSoPSNC {
              value 23 ;
              description 'The PW type is CESoPSN TDM with CAS.' ;
            }

            enum tdmAAL2 {
              value 24 ;
              description 'The PW type is TDMoIP AAL2.' ;
            }

            enum dlciNew {
              value 25 ;
              description 'The PW type is FR-DLCI.' ;
            }

          }

        }

        leaf local-label {
          description 'The local label of the PW.' ;
          type uint32 ;

        }

        leaf remote-label {
          description 'The remote label of the PW.' ;
          type uint32 ;

        }

        leaf pw-state {
          description 'The state of the PW.' ;
          type enumeration {
            enum down {
              value 1 ;
              description 'The state of the PW is down.' ;
            }

            enum up {
              value 2 ;
              description 'The state of the PW is up.' ;
            }

          }

        }

        leaf remote-status {
          description 'The remote status of the PW.Contain:ALLOK,PWNF,AR,AT,PSNR,PSNT,PWFS,RS,PWSA.
ALLOK - Pseudo Wire Forwarding(hex:0x00,dec:0)
PWNF  - Pseudo Wire Not Forwarding(hex:0x01,dec:1)
AR    - Local AC (ingress) Receive Fault(hex:0x02,dec:2)
AT    - Local AC (egress) Transmit Fault(hex:0x04,dec:4)
PSNR  - Local PSN-facing PW (ingress) Receive Fault(hex:0x08,dec:8)
PSNT  - Local PSN-facing PW (egress) Transmit Fault(hex:0x10,dec:16) 
PWFS  - Pseudo Wire Forwarding Standby(hex:0x20,dec:32)
RS    - Request Switchover to this PW(hex:0x40,dec:64)
PWSA  - Pseudo Wire Status All Fault(hex:0x01|0x02|0x04|0x08|0x10,dec:1|2|4|8|16)' ;
          type uint32 ;

        }

        leaf negotiated-cword {
          description 'The negotiated cword of the PW(0:not-preferred;1:preferred).' ;
          type enumeration {
            enum not-preferred {
              value 0 ;
              description 'The negotiated cword of the PW is not preferred.' ;
            }

            enum preferred {
              value 1 ;
              description 'The negotiated cword of the PW is preferred.' ;
            }

          }

        }

        leaf negotiated-vccv {
          description 'The negotiated VCCV of the PW.
When the PW state is down the negotiated-vccv is 0;When the PW state is up,the negotiated-vccv value meaning is below:
1.CC type is CWORD:if(1==negotiated-vccv & 0x01);
2.CC type is ALERT_LABEL:if(1==negotiated-vccv & 0x02);
3.CC type is TTL:if(1==negotiated-vccv & 0x04);
4.CV type is ICMP:if(1==negotiated-vccv & (0x01 << 8));
5.CV type is LSP:if(1==negotiated-vccv & (0x02 << 8));
6.CV type is BFD_BASIC_HEAD:if(1==negotiated-vccv & (0x04 << 8));
7.CV type is BFD_STATUS_HEAD:if(1==negotiated-vccv & (0x08 << 8));
8.CV type is BFD_BASIC_RAW:if(1==negotiated-vccv & (0x10 << 8));
9.CV type is BFD_STATUS_RAW:if(1==negotiated-vccv & (0x20 << 8)).' ;
          type uint16 ;

        }

        leaf create-time {
          description 'The create time of the PW.' ;
          type ncd:string-with-blank {
            length 1..64 {
              description 'The string length of create-time.' ;
            }

          }

        }

        leaf last-status-change-time {
          description 'The last status change time of the PW.' ;
          type ncd:string-with-blank {
            length 1..64 {
              description 'The string length of last-status-change-time.' ;
            }

          }

        }

        leaf track-name {
          description 'The name of PW track.' ;
          type string {
            length 1..31 {
              description 'The length of track name.' ;
            }

          }

        }

        leaf track-status {
          description 'The state of PW track.' ;
          type enumeration {
            enum unknown {
              value 0 ;
              description 'The PW track status is unknown.' ;
            }

            enum down {
              value 1 ;
              description 'The PW track status is down.' ;
            }

            enum up {
              value 2 ;
              description 'The PW track status is up.' ;
            }

          }

        }

        container outter-fwd-info {
          description 'The outer forwarding info of PW.' ;
          list outter-fwd {
            description 'The outer forwarding info of PW.' ;
            key number ;
            leaf number {
              description 'The PSN outer forwarding number of the PW.' ;
              type uint32 {
                range 1..64 {
                  description 'The range of outer forwarding number.' ;
                }

              }

            }

            leaf outlabel1 {
              description 'The PSN outer label 1 of the PW.' ;
              type uint32 ;

            }

            leaf outlabel2 {
              description 'The PSN outer label 2 of the PW.' ;
              type uint32 ;

            }

            leaf outlabel3 {
              description 'The PSN outer label 3 of the PW.' ;
              type uint32 ;

            }

            leaf outlabel4 {
              description 'The PSN outer label 4 of the PW.' ;
              type uint32 ;

            }

            leaf outlabel5 {
              type uint32 ;

              description 'The PSN outer label 5 of the PW.' ;
              ncd:revise-date 2025-04-14 ;
            }

            leaf outlabel6 {
              type uint32 ;

              description 'The PSN outer label 6 of the PW.' ;
              ncd:revise-date 2025-04-14 ;
            }

            leaf outlabel7 {
              type uint32 ;

              description 'The PSN outer label 7 of the PW.' ;
              ncd:revise-date 2025-04-14 ;
            }

            leaf outlabel8 {
              type uint32 ;

              description 'The PSN outer label 8 of the PW.' ;
              ncd:revise-date 2025-04-14 ;
            }

            leaf outlabel9 {
              type uint32 ;

              description 'The PSN outer label 9 of the PW.' ;
              ncd:revise-date 2025-04-14 ;
            }

            leaf outlabel10 {
              type uint32 ;

              description 'The PSN outer label 10 of the PW.' ;
              ncd:revise-date 2025-04-14 ;
            }

            leaf outlabel11 {
              type uint32 ;

              description 'The PSN outer label 11 of the PW.' ;
              ncd:revise-date 2025-04-14 ;
            }

            leaf outlabel12 {
              type uint32 ;

              description 'The PSN outer label 12 of the PW.' ;
              ncd:revise-date 2025-04-14 ;
            }

            leaf outlabel13 {
              type uint32 ;

              description 'The PSN outer label 13 of the PW.' ;
              ncd:revise-date 2025-04-14 ;
            }

            leaf outlabel14 {
              type uint32 ;

              description 'The PSN outer label 14 of the PW.' ;
              ncd:revise-date 2025-04-14 ;
            }

            leaf outlabel15 {
              type uint32 ;

              description 'The PSN outer label 15 of the PW.' ;
              ncd:revise-date 2025-04-14 ;
            }

            leaf outlabel16 {
              type uint32 ;

              description 'The PSN outer label 16 of the PW.' ;
              ncd:revise-date 2025-04-14 ;
            }

            leaf outlabel17 {
              type uint32 ;

              description 'The PSN outer label 17 of the PW.' ;
              ncd:revise-date 2025-04-14 ;
            }

            leaf outlabel18 {
              type uint32 ;

              description 'The PSN outer label 18 of the PW.' ;
              ncd:revise-date 2025-04-14 ;
            }

            leaf outlabel19 {
              type uint32 ;

              description 'The PSN outer label 19 of the PW.' ;
              ncd:revise-date 2025-04-14 ;
            }

            leaf outlabel20 {
              type uint32 ;

              description 'The PSN outer label 20 of the PW.' ;
              ncd:revise-date 2025-04-14 ;
            }

            leaf outlabel21 {
              type uint32 ;

              description 'The PSN outer label 21 of the PW.' ;
              ncd:revise-date 2025-04-14 ;
            }

            leaf outlabel22 {
              type uint32 ;

              description 'The PSN outer label 22 of the PW.' ;
              ncd:revise-date 2025-04-14 ;
            }

            leaf outlabel23 {
              type uint32 ;

              description 'The PSN outer label 23 of the PW.' ;
              ncd:revise-date 2025-04-14 ;
            }

            leaf outlabel24 {
              type uint32 ;

              description 'The PSN outer label 24 of the PW.' ;
              ncd:revise-date 2025-04-14 ;
            }

            leaf out-interface {
              description 'The name of the PSN out interface.' ;
              type string {
                length 0..31 {
                  description 'The length of interface name.' ;
                }

              }

            }

            leaf tunnel-id {
              description 'PSN tunnel ID.' ;
              type uint32 ;

            }

            ncd:revise-date 2015-09-14 ;
          }

          ncd:revise-date 2015-08-04 ;
        }

        container tunnel-policy-result {
          description 'The result of the tunnel policy.' ;
          leaf result-type {
            description 'The result type of the tunnel policy.' ;
            type enumeration {
              enum te-tunnel {
                value 1 ;
                description 'The select result is TE tunnel.' ;
              }

              enum te-ecmp {
                value 2 ;
                description 'The select result is TE ECMP.' ;
              }

              enum te-ldsh {
                value 3 ;
                description 'The select result is TE LDSH.' ;
              }

              enum te-ldshv6 {
                value 4 ;
                description 'The select result is TE LDSHv6.' ;
              }

              enum ldp-lsp {
                value 5 ;
                description 'The select result is LDP LSP.' ;
              }

              enum sr-be {
                value 6 ;
                description 'The select result is SR BE.' ;
              }

              enum gre-tunnel {
                value 7 ;
                description 'The select result is GRE tunnel.' ;
              }

              enum unsupported-type {
                value 8 ;
                description 'The select result is not supported.' ;
              }

              enum srv6-te-tunnel {
                value 9 ;
                description 'The select result is SRv6 TE tunnel.' ;
              }

              enum sr-policy-group {
                value 10 ;
                description 'The select result is SR policy group.' ;
              }

              enum bgp {
                value 11 ;
                description 'The select result is BGP.' ;
              }

              enum be {
                value 12 ;
                description 'The select result is BE.' ;
              }

            }

          }

          leaf result-id {
            description 'The forward table ID of the tunnel policy selection result.' ;
            type uint32 ;

          }

          ncd:revise-date 2020-10-21 ;
        }

        ncd:select vpn-name ;
        ncd:select peer-address ;
        ncd:select "vpn-name peer-address" ;
        ncd:select pw-name ;
      }

      list pw-group-info {
        description 'PW group query info.' ;
        key working-interface ;
        leaf working-interface {
          description 'The working PW/AC name of the PW protect.' ;
          type ncd:ifname {
            length 1..31 {
              description 'The length of working interface name.' ;
            }

          }

        }

        leaf pw-group-id {
          description 'The PW protect group identification.' ;
          type uint32 {
            range 1..8192 {
              description 'The range of PW group identification.' ;
            }

          }

        }

        leaf protected-pw {
          description 'The protection PW name of the PW protect strategy.' ;
          type string {
            length 1..31 {
              description 'The length of protection PW name.' ;
            }

          }

        }

        leaf switch-flag {
          description 'The switch flag of the PW protect group.' ;
          type enumeration {
            enum yes {
              value 1 ;
              description 'The switch flag of the PW protect group is no.' ;
            }

            enum no {
              value 2 ;
              description 'The switch flag of the PW protect group is yes.' ;
            }

          }

        }

        leaf work-path-status {
          description 'Working path status.' ;
          type enumeration {
            enum no-defect {
              value 0 ;
              description 'Working PW status is signal OK.' ;
            }

            enum defect {
              value 1 ;
              description 'Working PW status is signal fail.' ;
            }

            enum defect-sd {
              value 2 ;
              description 'Working PW status is signal degrade.' ;
            }

          }

          ncd:revise-date 2023-02-10 ;
        }

        leaf protect-path-status {
          description 'Protection path status.' ;
          type enumeration {
            enum no-defect {
              value 0 ;
              description 'Protect PW status is signal OK.' ;
            }

            enum defect {
              value 1 ;
              description 'Protect PW status is signal fail.' ;
            }

            enum defect-sd {
              value 2 ;
              description 'Protect PW status is signal degrade.' ;
            }

          }

          ncd:revise-date 2023-02-10 ;
        }

        container dni-pw-peer-info {
          description 'The DNI-PW peer information in common protect group.' ;
          leaf peer-useable {
            description 'The DNI-PW peer chassis useable flag.' ;
            type enumeration {
              enum unknown {
                value 0 ;
                description 'Peer chassis is unknown.' ;
              }

              enum unuseable {
                value 1 ;
                description 'Peer chassis is unuseable.' ;
              }

              enum useable {
                value 2 ;
                description 'Peer chassis is useable.' ;
              }

            }

          }

          leaf peer-protect-type {
            description 'The DNI-PW peer PW protect type.' ;
            type enumeration {
              enum unknown {
                value 0 ;
                description 'The DNI-PW peer protect type is unknown.' ;
              }

              enum 1:1-unidirectional-receiving-selective {
                value 1 ;
                description 'The DNI-PW peer protect type is 1:1 unidirectional receiving selective.' ;
              }

              enum 1:1-bidirectional-receiving-selective {
                value 2 ;
                description 'The DNI-PW peer protect type is 1:1 bidirectional receiving selective.' ;
              }

              enum 1:1-unidirectional-receiving-both {
                value 3 ;
                description 'The DNI-PW peer protect type is 1:1 unidirectional receiving both.' ;
              }

              enum 1:1-bidirectional-receiving-both {
                value 4 ;
                description 'The DNI-PW peer protect type is 1:1 bidirectional receiving both.' ;
              }

              enum "1+1-unidirectional-receiving-selective" {
                value 5 ;
                description 'The DNI-PW peer protect type is 1+1 unidirectional receiving selective.' ;
              }

              enum "1+1-bidirectional-receiving-selective" {
                value 6 ;
                description 'The DNI-PW peer protect type is 1+1 bidirectional receiving selective.' ;
              }

              enum "1+1-unidirectional-receiving-both" {
                value 7 ;
                description 'The DNI-PW peer protect type is 1+1 unidirectional receiving both.' ;
              }

              enum "1+1-bidirectional-receiving-both" {
                value 8 ;
                description 'The DNI-PW peer protect type is 1+1 bidirectional receiving both.' ;
              }

            }

          }

          leaf peer-mc-role {
            description 'The DNI-PW peer PW MC role.' ;
            type enumeration {
              enum unknown {
                value 0 ;
                description 'The DNI-PW peer MC role is unknown.' ;
              }

              enum master {
                value 1 ;
                description 'The DNI-PW peer MC role is master.' ;
              }

              enum slave {
                value 2 ;
                description 'The DNI-PW peer MC role is slave.' ;
              }

            }

          }

          leaf peer-iccp-id {
            description 'The DNI-PW peer ICCP ID.' ;
            type uint32 {
              range 0..4294967295 {
                description 'The ICCP identification range.' ;
              }

            }

          }

          leaf peer-pw-state {
            description 'The DNI-PW peer PW state.' ;
            type enumeration {
              enum unknown {
                value 0 ;
                description 'The DNI-PW peer PW state is unknown.' ;
              }

              enum down {
                value 1 ;
                description 'The DNI-PW peer PW state is down.' ;
              }

              enum up {
                value 2 ;
                description 'The DNI-PW peer PW state is up.' ;
              }

            }

          }

        }

      }

      container statistics {
        description 'Traffic statistics state info.It contains instance statistics,PW statistics and AC statistics.' ;
        list instance-statistics {
          description 'Instance statistics query info.It contains the following attributes:instance-name,recvpkts,recvbytes,recvpkts-rate,recvbytes-rate,sendpkts,sndbytes,sndpkts-rate,sndbytes-rate.' ;
          key instance-name ;
          leaf instance-name {
            description 'The name of the instance.' ;
            type string {
              length 1..32 {
                description 'The length of instance name.' ;
              }

            }

          }

          leaf in-bytes {
            description 'The input bytes count of the instance.' ;
            type uint64 ;

            units bytes ;
          }

          leaf in-packets {
            description 'The input packets count of the instance.' ;
            type uint64 ;

            units packets ;
          }

          leaf in-drop-bytes {
            description 'The input drop bytes.' ;
            type uint64 ;

            units bytes ;
          }

          leaf in-drop-packets {
            description 'The input drop packets.' ;
            type uint64 ;

            units packets ;
          }

          leaf in-broadcast-bytes {
            description 'The input broadcast bytes.' ;
            type uint64 ;

            units bytes ;
          }

          leaf in-broadcast-packets {
            description 'The input broadcast packets.' ;
            type uint64 ;

            units packets ;
          }

          leaf in-unicast-bytes {
            description 'The input unicast bytes.' ;
            type uint64 ;

            units bytes ;
          }

          leaf in-unicast-packets {
            description 'The input unicast packets.' ;
            type uint64 ;

            units packets ;
          }

          leaf in-unknown-unicast-bytes {
            description 'The input unknown unicast bytes.' ;
            type uint64 ;

            units bytes ;
          }

          leaf in-unknown-unicast-packets {
            description 'The input unknown unicast packets.' ;
            type uint64 ;

            units packets ;
          }

          leaf in-multicast-bytes {
            description 'The input multicast bytes.' ;
            type uint64 ;

            units bytes ;
          }

          leaf in-multicast-packets {
            description 'The input multicast packets.' ;
            type uint64 ;

            units packets ;
          }

          leaf out-bytes {
            description 'The output bytes count of the instance.' ;
            type uint64 ;

            units bytes ;
          }

          leaf out-packets {
            description 'The output packets count of the instance.' ;
            type uint64 ;

            units packets ;
          }

          leaf out-drop-bytes {
            description 'The output drop bytes.' ;
            type uint64 ;

            units bytes ;
          }

          leaf out-drop-packets {
            description 'The output drop packets.' ;
            type uint64 ;

            units packets ;
          }

          leaf out-broadcast-bytes {
            description 'The output broadcast bytes.' ;
            type uint64 ;

            units bytes ;
          }

          leaf out-broadcast-packets {
            description 'The output broadcast packets.' ;
            type uint64 ;

            units packets ;
          }

          leaf out-multicast-bytes {
            description 'The output multicast bytes.' ;
            type uint64 ;

            units bytes ;
          }

          leaf out-multicast-packets {
            description 'The output multicast packets.' ;
            type uint64 ;

            units packets ;
          }

          leaf in-bytes-rate {
            description 'The input bytes rate of the instance.' ;
            type uint64 ;

            units bps ;
          }

          leaf in-packets-rate {
            description 'The input packets rate of the instance.' ;
            type uint64 ;

            units pbs ;
          }

          leaf in-drop-bytes-rate {
            description 'The input drop bytes rate.' ;
            type uint64 ;

            units bps ;
          }

          leaf in-drop-packets-rate {
            description 'The input drop packets rate.' ;
            type uint64 ;

            units pps ;
          }

          leaf in-broadcast-bytes-rate {
            description 'The input broadcast bytes rate.' ;
            type uint64 ;

            units bps ;
          }

          leaf in-broadcast-packets-rate {
            description 'The input broadcast packets rate.' ;
            type uint64 ;

            units pps ;
          }

          leaf in-unknown-unicast-bytes-rate {
            description 'The input unknown unicast bytes rate.' ;
            type uint64 ;

            units bps ;
          }

          leaf in-unknown-unicast-packets-rate {
            description 'The input unknown unicast packets rate.' ;
            type uint64 ;

            units pps ;
          }

          leaf out-packets-rate {
            description 'The output packets rate of the instance.' ;
            type uint64 ;

            units pbs ;
          }

          leaf out-bytes-rate {
            description 'The output bytes rate of the instance.' ;
            type uint64 ;

            units bps ;
          }

          leaf in-traffic-rate {
            type decimal64 {
              fraction-digits 4 ;
            }

            description 'The input traffic rate(unit:Mbps). The node does not support query.' ;
            units Mbps ;
            ncd:revise-date 2023-12-11 ;
          }

          leaf in-packet-rate {
            type decimal64 {
              fraction-digits 4 ;
            }

            description 'The input packet rate(unit:Kfps). ' ;
            units Kfps ;
            ncd:revise-date 2023-12-11 ;
          }

          leaf out-traffic-rate {
            type decimal64 {
              fraction-digits 4 ;
            }

            description 'The output traffic rate(unit:Mbps). ' ;
            units Mbps ;
            ncd:revise-date 2023-12-11 ;
          }

          leaf out-packet-rate {
            type decimal64 {
              fraction-digits 4 ;
            }

            description 'The output packet rate(unit:Kfps). The node does not support query.' ;
            units Kfps ;
            ncd:revise-date 2023-12-11 ;
          }

        }

        list pw-statistics {
          description 'PW statistics query info.It contains the following attributes:instance-name,recvpkts,recvbytes,recvpkts-rate,recvbytes-rate,sendpkts,sndbytes,sndpkts-rate,sndbytes-rate,in-drop-pkts,in-drop-bytes,out-drop-pkts,out-drop-bytes,in-bandwidth,in-bandwidth-usage,out-bandwidth,out-bandwidth-usage.' ;
          key pw-name ;
          leaf pw-name {
            description 'The name of the PW.' ;
            type ncd:ifname {
              length 1..31 {
                description 'The length of PW name.' ;
              }

            }

          }

          leaf in-bytes {
            description 'The input bytes count of the PW.' ;
            type uint64 ;

            units bytes ;
          }

          leaf in-packets {
            description 'The input packets count of the PW.' ;
            type uint64 ;

            units packets ;
          }

          leaf in-drop-bytes {
            description 'The input dropped bytes of the PW.' ;
            type uint64 ;

            units bytes ;
          }

          leaf in-drop-packets {
            description 'The input dropped packets of the PW.' ;
            type uint64 ;

            units packets ;
          }

          leaf in-broadcast-bytes {
            description 'The input broadcast bytes.' ;
            type uint64 ;

            units bytes ;
          }

          leaf in-broadcast-packets {
            description 'The input broadcast packets.' ;
            type uint64 ;

            units packets ;
          }

          leaf in-unicast-bytes {
            description 'The input unicast bytes.' ;
            type uint64 ;

            units bytes ;
          }

          leaf in-unicast-packets {
            description 'The input unicast packets.' ;
            type uint64 ;

            units packets ;
          }

          leaf in-unknown-unicast-bytes {
            description 'The input unknown unicast bytes.' ;
            type uint64 ;

            units bytes ;
          }

          leaf in-unknown-unicast-packets {
            description 'The input unknown unicast packets.' ;
            type uint64 ;

          }

          leaf in-multicast-bytes {
            description 'The input multicast bytes.' ;
            type uint64 ;

          }

          leaf in-multicast-packets {
            description 'The input multicast packets.' ;
            type uint64 ;

          }

          leaf out-bytes {
            description 'The output bytes count of the PW.' ;
            type uint64 ;

            units bytes ;
          }

          leaf out-packets {
            description 'The output packets count of the PW.' ;
            type uint64 ;

            units packets ;
          }

          leaf out-drop-bytes {
            description 'The output dropped bytes of the PW.' ;
            type uint64 ;

            units bytes ;
          }

          leaf out-drop-packets {
            description 'The output dropped packets of the PW.' ;
            type uint64 ;

            units packets ;
          }

          leaf out-broadcast-bytes {
            description 'The output broadcast bytes.' ;
            type uint64 ;

          }

          leaf out-broadcast-packets {
            description 'The output broadcast packets.' ;
            type uint64 ;

          }

          leaf out-multicast-bytes {
            description 'The output multicast bytes.' ;
            type uint64 ;

          }

          leaf out-multicast-packets {
            description 'The output multicast packets.' ;
            type uint64 ;

          }

          leaf in-bytes-rate {
            description "The received bytes rate of the PW.This node's unit is not standard, in order to according with the standard,add the in-traffic-rate node." ;
            type uint64 ;

            units bps ;
          }

          leaf in-packets-rate {
            description "The input packets rate of the PW.This node's unit is not standard, in order to according with the standard,add the in-packet-rate node." ;
            type uint64 ;

            units pbs ;
          }

          leaf in-drop-bytes-rate {
            description 'The input dropped bytes rate.' ;
            type uint64 ;

            units bps ;
          }

          leaf in-drop-packets-rate {
            description 'The input dropped packets rate.' ;
            type uint64 ;

            units pps ;
          }

          leaf in-broadcast-bytes-rate {
            description 'The input broadcast bytes rate.' ;
            type uint64 ;

            units bps ;
          }

          leaf in-broadcast-packets-rate {
            description 'The input broadcast packets rate.' ;
            type uint64 ;

            units pps ;
          }

          leaf in-unknown-unicast-bytes-rate {
            description 'The input unknown unicast bytes rate.' ;
            type uint64 ;

            units bps ;
          }

          leaf in-unknown-unicast-packets-rate {
            description 'The input unknown unicast packets rate.' ;
            type uint64 ;

            units pps ;
          }

          leaf out-bytes-rate {
            description "The output bytes rate of the PW.This node's unit is not standard, in order to according with the standard,add the out-traffic-rate node." ;
            type uint64 ;

            units bps ;
          }

          leaf out-packets-rate {
            description "The output packets rate of the PW.This node's unit is not standard, in order to according with the standard,add the out-packet-rate node." ;
            type uint64 ;

            units pbs ;
          }

          leaf in-bandwidth-utilization {
            description 'The input bandwidth utilization of the PW.' ;
            type uint64 ;

            ncd:revise-date 2019-06-13 ;
          }

          leaf out-bandwidth-utilization {
            description 'The output bandwidth utilization of the PW.' ;
            type uint64 ;

            ncd:revise-date 2019-06-13 ;
          }

          leaf in-traffic-rate {
            description 'The input traffic rate(unit:Mbps).' ;
            type decimal64 {
              fraction-digits 4 ;
            }

            units Mbps ;
            ncd:revise-date 2020-08-06 ;
          }

          leaf in-packet-rate {
            description 'The input packet rate(unit:Kfps).' ;
            type decimal64 {
              fraction-digits 4 ;
            }

            units Kfps ;
            ncd:revise-date 2020-08-06 ;
          }

          leaf out-traffic-rate {
            description 'The output traffic rate(unit:Mbps).' ;
            type decimal64 {
              fraction-digits 4 ;
            }

            units Mbps ;
            ncd:revise-date 2020-08-06 ;
          }

          leaf out-packet-rate {
            description 'The output packet rate(unit:Kfps).' ;
            type decimal64 {
              fraction-digits 4 ;
            }

            units Kfps ;
            ncd:revise-date 2020-08-06 ;
          }

        }

        list ac-statistics {
          description 'AC statistics query info.It contains the following attributes:interface-index,recvpkts,recvbytes,recvpkts-rate,recvbytes-rate,sendpkts,sndbytes,sndpkts-rate,sndbytes-rate,in-drop-pkts,out-drop-pkts.' ;
          key ac-name ;
          leaf ac-name {
            description 'The interface name of the AC.' ;
            type ncd:ifname {
              length 1..31 {
                description 'The length of AC name.' ;
              }

            }

          }

          leaf in-bytes {
            description 'The input bytes count of the AC.' ;
            type uint64 ;

            units bytes ;
          }

          leaf in-packets {
            description 'The input packets count of the AC.' ;
            type uint64 ;

            units packets ;
          }

          leaf in-drop-bytes {
            description 'The input dropped bytes count of the AC.' ;
            type uint64 ;

            units bytes ;
          }

          leaf in-drop-packets {
            description 'The input dropped packets count of the AC.' ;
            type uint64 ;

            units packets ;
          }

          leaf in-broadcast-bytes {
            description 'The input broadcast bytes.' ;
            type uint64 ;

            units bytes ;
          }

          leaf in-broadcast-packets {
            description 'The input broadcast packets.' ;
            type uint64 ;

            units packets ;
          }

          leaf in-unicast-bytes {
            description 'The input unicast bytes.' ;
            type uint64 ;

            units bytes ;
          }

          leaf in-unicast-packets {
            description 'The input unicast packets.' ;
            type uint64 ;

            units packets ;
          }

          leaf in-unknown-unicast-bytes {
            description 'The input unknown unicast bytes.' ;
            type uint64 ;

          }

          leaf in-unknown-unicast-packets {
            description 'The input unknown unicast packets.' ;
            type uint64 ;

          }

          leaf in-multicast-bytes {
            description 'The input multicast bytes.' ;
            type uint64 ;

          }

          leaf in-multicast-packets {
            description 'The input multicast packets.' ;
            type uint64 ;

          }

          leaf out-bytes {
            description 'The output bytes count of the AC.' ;
            type uint64 ;

            units bytes ;
          }

          leaf out-packets {
            description 'The output packets count of the AC.' ;
            type uint64 ;

            units packets ;
          }

          leaf out-drop-bytes {
            description 'The output dropped bytes count of the AC.' ;
            type uint64 ;

            units bytes ;
          }

          leaf out-drop-packets {
            description 'The output dropped packets count of the AC.' ;
            type uint64 ;

            units packets ;
          }

          leaf out-broadcast-bytes {
            description 'The output broadcast bytes.' ;
            type uint64 ;

          }

          leaf out-broadcast-packets {
            description 'The output broadcast packets.' ;
            type uint64 ;

          }

          leaf out-multicast-bytes {
            description 'The output multicast bytes.' ;
            type uint64 ;

          }

          leaf out-multicast-packets {
            description 'The output multicast packets.' ;
            type uint64 ;

          }

          leaf in-bytes-rate {
            description 'The input bytes rate of the AC.' ;
            type uint64 ;

            units bps ;
          }

          leaf in-packets-rate {
            description 'The input packets rate of the AC.' ;
            type uint64 ;

            units pbs ;
          }

          leaf in-drop-bytes-rate {
            description 'The input drop bytes rate.' ;
            type uint64 ;

            units bps ;
          }

          leaf in-drop-packets-rate {
            description 'The input drop packets rate.' ;
            type uint64 ;

            units pps ;
          }

          leaf in-broadcast-bytes-rate {
            description 'The input broadcast bytes rate.' ;
            type uint64 ;

            units bps ;
          }

          leaf in-broadcast-packets-rate {
            description 'The input broadcast packets rate.' ;
            type uint64 ;

            units pps ;
          }

          leaf in-unknown-unicast-bytes-rate {
            description 'The input unknown unicast bytes rate.' ;
            type uint64 ;

            units bps ;
          }

          leaf in-unknown-unicast-packets-rate {
            description 'The input unknown unicast packets rate.' ;
            type uint64 ;

            units pps ;
          }

          leaf out-bytes-rate {
            description 'The output bytes rate of the AC.' ;
            type uint64 ;

            units bps ;
          }

          leaf out-packets-rate {
            description 'The output packets rate of the AC.' ;
            type uint64 ;

            units pbs ;
          }

        }

        list vpws-evpn-instance-statistics {
          description 'VPWS EVPN instance statistics query info. It contains the following attributes:instance-name,local-vpws-id,interface-name,in-bytes,in-packets,out-bytes,out-packets,in-traffic-rate,in-packet-rate,out-traffic-rate,out-packet-rate. Neither the list nor its leaf nodes support query.' ;
          key 'instance-name local-vpws-id' ;
          leaf instance-name {
            type string {
              length 1..32 {
                description 'The length of instance name.' ;
              }

            }

            description 'The name of the instance.' ;
          }

          leaf local-vpws-id {
            type uint32 {
              range 1..4294967294 ;

            }

            description 'Local VPWS ID.' ;
          }

          leaf interface-name {
            type string {
              length 1..31 ;

            }

            description 'The name of the AC interface.' ;
          }

          leaf in-bytes {
            type uint64 ;

            description 'The input bytes count of the instance.' ;
            units bytes ;
          }

          leaf in-packets {
            type uint64 ;

            description 'The input packets count of the instance.' ;
            units packets ;
          }

          leaf out-bytes {
            type uint64 ;

            description 'The output bytes count of the instance.' ;
            units bytes ;
          }

          leaf out-packets {
            type uint64 ;

            description 'The output packets count of the instance.' ;
            units packets ;
          }

          leaf in-traffic-rate {
            type decimal64 {
              fraction-digits 4 ;
            }

            description 'The input traffic rate(unit:Mbps).' ;
            units Mbps ;
          }

          leaf in-packet-rate {
            type decimal64 {
              fraction-digits 4 ;
            }

            description 'The input packet rate(unit:Kfps).' ;
            units Kfps ;
          }

          leaf out-traffic-rate {
            type decimal64 {
              fraction-digits 4 ;
            }

            description 'The output traffic rate(unit:Mbps).' ;
            units Mbps ;
          }

          leaf out-packet-rate {
            type decimal64 {
              fraction-digits 4 ;
            }

            description 'The output packet rate(unit:Kfps).' ;
            units Kfps ;
          }

          ncd:revise-date 2023-12-11 ;
          ncd:select instance-name ;
        }

      }

      list pw-list {
        description 'PW list query info.It contains the following attributes:PW list ID and status.' ;
        key pw-list-id ;
        leaf pw-list-id {
          description 'The identification of PW list.' ;
          type uint32 {
            range 1..4096 {
              description 'The range of PW list ID.' ;
            }

          }

        }

        leaf status {
          description 'The status of PW list.' ;
          type enumeration {
            enum unknown {
              value 0 ;
              description 'PW list state is unknown.' ;
            }

            enum down {
              value 1 ;
              description 'PW list state is down.' ;
            }

            enum up {
              value 2 ;
              description 'PW list state is up.' ;
            }

          }

        }

      }

      list mc-protect-group {
        description 'The multiple chassis protect group query info.' ;
        key local-pw-name ;
        leaf local-pw-name {
          description 'The local PW name of multiple chassis protect group.' ;
          type ncd:ifname {
            length 1..31 {
              description 'The length of local PW name.' ;
            }

          }

        }

        leaf group-id {
          description 'The multiple chassis protect group identification.' ;
          type uint32 {
            range 1..8192 {
              description 'The range of multiple chassis protect group identification.' ;
            }

          }

        }

        leaf switch-flag {
          description 'The switch flag of the multiple chassis protect group.' ;
          type enumeration {
            enum yes {
              value 1 ;
              description 'The switch flag of the multiple chassis protect group is yes.' ;
            }

            enum no {
              value 2 ;
              description 'The switch flag of the multiple chassis protect group is no.' ;
            }

          }

        }

        container dni-pw-peer-info {
          description 'The DNI-PW peer information in mc protect group.' ;
          leaf peer-useable {
            description 'The DNI-PW peer chassis useable flag.' ;
            type enumeration {
              enum unknown {
                value 0 ;
                description 'Peer chassis is unknown.' ;
              }

              enum unuseable {
                value 1 ;
                description 'Peer chassis is unuseable.' ;
              }

              enum useable {
                value 2 ;
                description 'Peer chassis is useable.' ;
              }

            }

          }

          leaf peer-protect-type {
            description 'The DNI-PW peer PW protect type.' ;
            type enumeration {
              enum unknown {
                value 0 ;
                description 'The DNI-PW peer protect type is unknown.' ;
              }

              enum 1:1-unidirectional-receiving-selective {
                value 1 ;
                description 'The DNI-PW peer protect type is 1:1 unidirectional receiving selective.' ;
              }

              enum 1:1-bidirectional-receiving-selective {
                value 2 ;
                description 'The DNI-PW peer protect type is 1:1 bidirectional receiving selective.' ;
              }

              enum 1:1-unidirectional-receiving-both {
                value 3 ;
                description 'The DNI-PW peer protect type is 1:1 unidirectional receiving both.' ;
              }

              enum 1:1-bidirectional-receiving-both {
                value 4 ;
                description 'The DNI-PW peer protect type is 1:1 bidirectional receiving both.' ;
              }

              enum "1+1-unidirectional-receiving-selective" {
                value 5 ;
                description 'The DNI-PW peer protect type is 1+1 unidirectional receiving selective.' ;
              }

              enum "1+1-bidirectional-receiving-selective" {
                value 6 ;
                description 'The DNI-PW peer protect type is 1+1 bidirectional receiving selective.' ;
              }

              enum "1+1-unidirectional-receiving-both" {
                value 7 ;
                description 'The DNI-PW peer protect type is 1+1 unidirectional receiving both.' ;
              }

              enum "1+1-bidirectional-receiving-both" {
                value 8 ;
                description 'The DNI-PW peer protect type is 1+1 bidirectional receiving both.' ;
              }

            }

          }

          leaf peer-mc-role {
            description 'The DNI-PW peer PW MC role.' ;
            type enumeration {
              enum unknown {
                value 0 ;
                description 'The DNI-PW peer MC role is unknown.' ;
              }

              enum master {
                value 1 ;
                description 'The DNI-PW peer MC role is master.' ;
              }

              enum slave {
                value 2 ;
                description 'The DNI-PW peer MC role is slave.' ;
              }

            }

          }

          leaf peer-iccp-id {
            description 'The DNI-PW peer ICCP ID.' ;
            type uint32 {
              range 0..4294967295 {
                description 'The ICCP identification range.' ;
              }

            }

          }

          leaf peer-pw-state {
            description 'The DNI-PW peer PW state.' ;
            type enumeration {
              enum unknown {
                value 0 ;
                description 'The DNI-PW peer PW state is unknown.' ;
              }

              enum down {
                value 1 ;
                description 'The DNI-PW peer PW state is down.' ;
              }

              enum up {
                value 2 ;
                description 'The DNI-PW peer PW state is up.' ;
              }

            }

          }

        }

      }

      container inst-count {
        description 'L2VPN instances count.' ;
        leaf configured-vpls {
          description 'The number of VPLS instances which has been configured.' ;
          type uint32 ;

          default 0 ;
        }

        leaf configured-vpws {
          description 'The number of VPWS instances which has been configured.' ;
          type uint32 ;

          default 0 ;
        }

        leaf configured-vlss {
          description 'The number of VLSS instances which has been configured.' ;
          type uint32 ;

          default 0 ;
        }

        leaf configured-mspw {
          description 'The number of MSPW instances which has been configured.' ;
          type uint32 ;

          default 0 ;
        }

        leaf maximum-vpls {
          description 'The maximum number of VPLS instances which can be configured.' ;
          type uint32 ;

        }

        leaf maximum-vpws {
          description 'The maximum number of VPWS instances which can be configured.' ;
          type uint32 ;

        }

        leaf maximum-vlss {
          description 'The maximum number of VLSS instances which can be configured.' ;
          type uint32 ;

        }

        leaf maximum-mspw {
          description 'The maximum number of MSPW instances which can be configured.' ;
          type uint32 ;

        }

        leaf remaining-vpls {
          description 'The number of remaining VPLS which has not been configured.' ;
          type uint32 ;

          default 0 ;
        }

        leaf remaining-vpws {
          description 'The number of remaining VPWS which has not been configured.' ;
          type uint32 ;

          default 0 ;
        }

      }

      container kompella-pw {
        description 'Kompella PW forwarding table query info.' ;
        list kompella-pw-info {
          description 'Kompella PW forwarding table query info.' ;
          key 'rd remote-veid' ;
          leaf rd {
            description 'The route distinguisher parameter.' ;
            type union {
              type ncd:asn-nn ;

              type ncd:ipadd-nn ;

            }

          }

          leaf remote-veid {
            description 'The remote VE identification for the VPLS instance.' ;
            type uint16 {
              range 0..65535 {
                description 'The VE ID value.' ;
              }

            }

          }

          leaf vpn-name {
            description 'The name of the L2VPN instance.' ;
            type string {
              length 1..32 {
                description 'The length of instance name.' ;
              }

            }

          }

          leaf pw-name {
            description 'The name of the auto PW.' ;
            type ncd:ifname {
              length 1..31 {
                description 'The length of auto PW name.' ;
              }

            }

            ncd:revise-date 2015-10-30 ;
          }

          leaf peer-address {
            description "The remote peer's IP address of the Kompella PW." ;
            type ncd:ipv4-address-none-zero ;

          }

          leaf mtu {
            description 'The MTU value of the Kompella PW.' ;
            type uint16 ;

            default 1500 ;
          }

          leaf protocol-type {
            description 'Protocol type of Kompella PW.' ;
            type enumeration {
              enum bgp {
                value 0 ;
                description 'The protocol type is BGP.' ;
              }

            }

          }

          leaf pw-type {
            description 'L2VPN PW type. Assigned values are specified in IANA Allocations for Pseudowire Edge to Edge Emulation (PWE3).' ;
            type enumeration {
              enum unknown {
                value 0 ;
                description 'The PW type is unknown.' ;
              }

              enum dlciOld {
                value 1 ;
                description 'The PW type is FR-DLCI old.' ;
              }

              enum atmSdu {
                value 2 ;
                description 'The PW type is ATM-AAL5-SDU.' ;
              }

              enum atmCell {
                value 3 ;
                description 'The PW type is ATM-CELL.' ;
              }

              enum vlan {
                value 4 ;
                description 'The PW type is VLAN.' ;
              }

              enum ethernet {
                value 5 ;
                description 'The PW type is ethernet.' ;
              }

              enum hdlc {
                value 6 ;
                description 'The PW type is HDLC.' ;
              }

              enum ppp {
                value 7 ;
                description 'The PW type is PPP.' ;
              }

              enum sdhCESoM {
                value 8 ;
                description 'The PW type is SONET/SDH Circuit Emulation Service over MPLS.' ;
              }

              enum atmVCCn {
                value 9 ;
                description 'The PW type is ATM n-to-one VCC.' ;
              }

              enum atmVPCn {
                value 10 ;
                description 'The PW type is ATM n-to-one VPC.' ;
              }

              enum ipL2 {
                value 11 ;
                description 'The PW type is IP-L2.' ;
              }

              enum atmVCC1 {
                value 12 ;
                description 'The PW type is ATM one-to-one VCC.' ;
              }

              enum atmVPC1 {
                value 13 ;
                description 'The PW type is ATM one-to-one VPC.' ;
              }

              enum atmPDU {
                value 14 ;
                description 'The PW type is ATM AAL5 PDU VCC.' ;
              }

              enum frPort {
                value 15 ;
                description 'The PW type is FR port.' ;
              }

              enum sdhCEoP {
                value 16 ;
                description 'The PW type is SONET/SDH Circuit Emulation over Packet.' ;
              }

              enum saTopE1 {
                value 17 ;
                description 'The PW type is Structure-agnostic E1 over Packet.' ;
              }

              enum saTopT1 {
                value 18 ;
                description 'The PW type is Structure-agnostic T1 (DS1) over Packet.' ;
              }

              enum saTopE3 {
                value 19 ;
                description 'The PW type is Structure-agnostic E3 over Packet.' ;
              }

              enum saTopT3 {
                value 20 ;
                description 'The PW type is Structure-agnostic T3 (DS3) over Packet.' ;
              }

              enum ceSoPSNB {
                value 21 ;
                description 'The PW type is CESoPSN basic.' ;
              }

              enum tdmAAL1 {
                value 22 ;
                description 'The PW type is TDMoIP AAL1.' ;
              }

              enum ceSoPSNC {
                value 23 ;
                description 'The PW type is CESoPSN TDM with CAS.' ;
              }

              enum tdmAAL2 {
                value 24 ;
                description 'The PW type is TDMoIP AAL2.' ;
              }

              enum dlciNew {
                value 25 ;
                description 'The PW type is FR-DLCI.' ;
              }

            }

          }

          leaf create-time {
            description 'The create time of the Kompella PW.' ;
            type ncd:string-with-blank ;

          }

          leaf last-status-change-time {
            description 'The last status change time of the Kompella PW.' ;
            type ncd:string-with-blank ;

          }

          leaf local-label {
            description 'The local label of the Kompella PW.' ;
            type uint32 ;

          }

          leaf remote-label {
            description 'The remote label of the Kompella PW.' ;
            type uint32 ;

          }

          leaf auto-pwname {
            description 'The interface name of the auto PW.' ;
            type ncd:ifname {
              length 1..31 {
                description 'The length of auto PW interface name.' ;
              }

            }

          }

          leaf negotiated-cword {
            description 'The negotiated control word of the Kompella PW (0:notPreferred;1:preferred).' ;
            type enumeration {
              enum notPreferred {
                value 0 ;
                description 'The negotiated cword of the PW is not preferred.' ;
              }

              enum preferred {
                value 1 ;
                description 'The negotiated cword of the PW is preferred.' ;
              }

            }

          }

          leaf relation-pwname {
            description 'The relation PW name when have Kompella PW FRR.' ;
            type ncd:ifname {
              length 0..31 {
                description 'The length of relation PW name.It may be null.' ;
              }

            }

          }

          leaf frr-type {
            description 'The type of Kompella PW FRR.' ;
            type enumeration {
              enum null {
                value 0 ;
                description 'The FRR type is null.' ;
              }

              enum frr_primary {
                value 1 ;
                description 'The FRR type is primary.' ;
              }

              enum frr_secondary {
                value 2 ;
                description 'The FRR type is secondary.' ;
              }

            }

          }

          leaf pw-state {
            description 'The state of the Kompella PW.' ;
            type enumeration {
              enum down {
                value 1 ;
                description 'The state of the Kompella PW is down.' ;
              }

              enum up {
                value 2 ;
                description 'The state of the Kompella PW is up.' ;
              }

            }

          }

          leaf pw-sequence {
            description 'The sequence status of Kompella PW.' ;
            type enumeration {
              enum disable {
                value 0 ;
                description 'The PW sequence is disable.' ;
              }

              enum enable {
                value 1 ;
                description 'The PW sequence is enable.' ;
              }

            }

            default disable ;
          }

          leaf active-status {
            description 'The Kompella PW active state.' ;
            type enumeration {
              enum enable {
                value 0 ;
                description 'The Kompella PW active state is enable.' ;
              }

              enum disable {
                value 1 ;
                description 'The Kompella PW active state is disable.' ;
              }

            }

            default enable ;
          }

          leaf bandwidth {
            description 'The bandwidth value of Kompella PW.' ;
            type uint32 {
              range 0..4294967295 {
                description 'The range of the bandwidth value.' ;
              }

            }

            units kbps ;
          }

          container outter-fwd-info {
            description 'The outer forwarding info of Kompella PW.' ;
            list outter-fwd {
              description 'The outer forwarding info of Kompella PW.' ;
              key number ;
              leaf number {
                description 'The PSN outer forwarding number of the Kompella PW.' ;
                type uint32 {
                  range 1..64 {
                    description 'The range of outer forwarding number.' ;
                  }

                }

              }

              leaf outlabel1 {
                description 'The PSN outer label 1 of the Kompella PW.' ;
                type uint32 ;

              }

              leaf outlabel2 {
                description 'The PSN outer label 2 of the Kompella PW.' ;
                type uint32 ;

              }

              leaf outlabel3 {
                description 'The PSN outer label 3 of the Kompella PW.' ;
                type uint32 ;

              }

              leaf outlabel4 {
                description 'The PSN outer label 4 of the Kompella PW.' ;
                type uint32 ;

              }

              leaf outlabel5 {
                type uint32 ;

                description 'The PSN outer label 5 of the Kompella PW.' ;
                ncd:revise-date 2025-04-14 ;
              }

              leaf outlabel6 {
                type uint32 ;

                description 'The PSN outer label 6 of the Kompella PW.' ;
                ncd:revise-date 2025-04-14 ;
              }

              leaf outlabel7 {
                type uint32 ;

                description 'The PSN outer label 7 of the Kompella PW.' ;
                ncd:revise-date 2025-04-14 ;
              }

              leaf outlabel8 {
                type uint32 ;

                description 'The PSN outer label 8 of the Kompella PW.' ;
                ncd:revise-date 2025-04-14 ;
              }

              leaf outlabel9 {
                type uint32 ;

                description 'The PSN outer label 9 of the Kompella PW.' ;
                ncd:revise-date 2025-04-14 ;
              }

              leaf outlabel10 {
                type uint32 ;

                description 'The PSN outer label 10 of the Kompella PW.' ;
                ncd:revise-date 2025-04-14 ;
              }

              leaf outlabel11 {
                type uint32 ;

                description 'The PSN outer label 11 of the Kompella PW.' ;
                ncd:revise-date 2025-04-14 ;
              }

              leaf outlabel12 {
                type uint32 ;

                description 'The PSN outer label 12 of the Kompella PW.' ;
                ncd:revise-date 2025-04-14 ;
              }

              leaf outlabel13 {
                type uint32 ;

                description 'The PSN outer label 13 of the Kompella PW.' ;
                ncd:revise-date 2025-04-14 ;
              }

              leaf outlabel14 {
                type uint32 ;

                description 'The PSN outer label 14 of the Kompella PW.' ;
                ncd:revise-date 2025-04-14 ;
              }

              leaf outlabel15 {
                type uint32 ;

                description 'The PSN outer label 15 of the Kompella PW.' ;
                ncd:revise-date 2025-04-14 ;
              }

              leaf outlabel16 {
                type uint32 ;

                description 'The PSN outer label 16 of the Kompella PW.' ;
                ncd:revise-date 2025-04-14 ;
              }

              leaf outlabel17 {
                type uint32 ;

                description 'The PSN outer label 17 of the Kompella PW.' ;
                ncd:revise-date 2025-04-14 ;
              }

              leaf outlabel18 {
                type uint32 ;

                description 'The PSN outer label 18 of the Kompella PW.' ;
                ncd:revise-date 2025-04-14 ;
              }

              leaf outlabel19 {
                type uint32 ;

                description 'The PSN outer label 19 of the Kompella PW.' ;
                ncd:revise-date 2025-04-14 ;
              }

              leaf outlabel20 {
                type uint32 ;

                description 'The PSN outer label 20 of the Kompella PW.' ;
                ncd:revise-date 2025-04-14 ;
              }

              leaf outlabel21 {
                type uint32 ;

                description 'The PSN outer label 21 of the Kompella PW.' ;
                ncd:revise-date 2025-04-14 ;
              }

              leaf outlabel22 {
                type uint32 ;

                description 'The PSN outer label 22 of the Kompella PW.' ;
                ncd:revise-date 2025-04-14 ;
              }

              leaf outlabel23 {
                type uint32 ;

                description 'The PSN outer label 23 of the Kompella PW.' ;
                ncd:revise-date 2025-04-14 ;
              }

              leaf outlabel24 {
                type uint32 ;

                description 'The PSN outer label 24 of the Kompella PW.' ;
                ncd:revise-date 2025-04-14 ;
              }

              leaf out-interface {
                description 'The name of the PSN outer interface.' ;
                type string {
                  length 0..31 {
                    description 'The length of interface name.' ;
                  }

                }

              }

              leaf tunnel-id {
                description 'PSN tunnel ID.' ;
                type uint32 ;

              }

            }

            ncd:revise-date 2015-08-04 ;
          }

          container tunnel-policy-result {
            description 'The result of the tunnel policy.' ;
            leaf result-type {
              description 'The result type of the tunnel policy.' ;
              type enumeration {
                enum te-tunnel {
                  value 1 ;
                  description 'The select result is TE tunnel.' ;
                }

                enum te-ecmp {
                  value 2 ;
                  description 'The select result is TE ECMP.' ;
                }

                enum te-ldsh {
                  value 3 ;
                  description 'The select result is TE LDSH.' ;
                }

                enum te-ldshv6 {
                  value 4 ;
                  description 'The select result is TE LDSHv6.' ;
                }

                enum ldp-lsp {
                  value 5 ;
                  description 'The select result is LDP LSP.' ;
                }

                enum sr-be {
                  value 6 ;
                  description 'The select result is SR BE.' ;
                }

                enum gre-tunnel {
                  value 7 ;
                  description 'The select result is GRE tunnel.' ;
                }

                enum unsupported-type {
                  value 8 ;
                  description 'The select result is not supported.' ;
                }

                enum srv6-te-tunnel {
                  value 9 ;
                  description 'The select result is SRv6 TE tunnel.' ;
                }

                enum sr-policy-group {
                  value 10 ;
                  description 'The select result is SR policy group.' ;
                }

                enum bgp {
                  value 11 ;
                  description 'The select result is BGP.' ;
                }

                enum be {
                  value 12 ;
                  description 'The select result is BE.' ;
                }

              }

            }

            leaf result-id {
              description 'The forward table ID of the tunnel policy selection result.' ;
              type uint32 ;

            }

            ncd:revise-date 2020-10-21 ;
          }

          ncd:select vpn-name ;
          ncd:select remote-veid ;
          ncd:select "remote-veid vpn-name" ;
        }

      }

      container pw-count {
        description 'The PW count query table.' ;
        leaf configured-pw {
          description 'The number of PW which has been configured.' ;
          type uint32 ;

          default 0 ;
        }

        leaf maximum-pw {
          description 'The maximum number of PW which can be configured.' ;
          type uint32 ;

          default 0 ;
        }

        leaf traffic-enable-pw {
          description 'The number of PW which enabled traffic statistics.' ;
          type uint32 ;

          default 0 ;
        }

        leaf remaining-pw {
          description 'The number of remaining PW which has not been configured.' ;
          type uint32 ;

          default 0 ;
        }

      }

      container access-pw-group {
        description 'Access PW group query table.' ;
        list access-pw-group-info {
          description 'Access PW protect group query info.' ;
          key redirect-pw-name ;
          leaf redirect-pw-name {
            description 'The PW name which access PW group redirect to.' ;
            type ncd:ifname {
              length 1..31 {
                description 'The length of redirect PW name.' ;
              }

            }

          }

          leaf pw-group-id {
            description 'The access protect group identification.' ;
            type uint32 {
              range 1..8192 {
                description 'The range of access protect group identification.' ;
              }

            }

          }

          leaf local-ac-name {
            description 'The local access interface name.' ;
            type ncd:ifname {
              length 1..31 {
                description 'The length of local AC name.' ;
              }

            }

          }

          leaf access-pw-name {
            description 'The access PW name of access PW protect group.' ;
            type ncd:ifname {
              length 1..31 {
                description 'The length of access PW name.' ;
              }

            }

          }

          leaf switch-flag {
            description 'The switch flag of access protect group.' ;
            type enumeration {
              enum yes {
                value 1 ;
                description 'The switch flag of the access protect group is yes.' ;
              }

              enum no {
                value 2 ;
                description 'The switch flag of the access protect group is no.' ;
              }

            }

          }

        }

      }

      container ac-protect-group {
        list ac-protect-group-info {
          leaf local-ac-name {
            type ncd:ifname {
              length 1..31 {
                description 'The length of redirect PW name.' ;
              }

            }

            description 'The local AC interface name.' ;
          }

          leaf pw-group-id {
            type uint32 {
              range 1..8192 {
                description 'The range of access protect group identification.' ;
              }

            }

            description 'The AC protect group identification.' ;
          }

          leaf access-pw-name {
            type ncd:ifname {
              length 1..31 {
                description 'The length of access PW name.' ;
              }

            }

            description 'The access PW name of AC protect group.' ;
          }

          leaf switch-flag {
            type enumeration {
              enum yes {
                value 1 ;
                description 'The switch flag of the AC protect group is yes.' ;
              }

              enum no {
                value 2 ;
                description 'The switch flag of the AC protect group is no.' ;
              }

            }

            description 'The switch flag of AC protect group.' ;
          }

          key local-ac-name ;
          description 'AC protect group query info.' ;
        }

        description 'AC protect group query table.' ;
        ncd:revise-date 2024-01-02 ;
      }

    }

  }

  container configuration {
    description 'L2VPN module configuration info.' ;
    container l2vpn {
      description 'L2VPN module configure root node.It contains service instances,PW specification,protect-rules.' ;
      container l2vpn-global {
        description 'L2VPN enable flag.' ;
        presence l2vpn-global ;
        leaf global-enable {
          description 'The enable status of L2VPN service.' ;
          type enumeration {
            enum enable {
              value 1 ;
              description 'The enable status of L2VPN service is enable.' ;
            }

          }

          mandatory true ;
        }

        leaf traffic-enable {
          description 'The enable status of PW statistics.' ;
          type enumeration {
            enum disable {
              value 0 ;
              description 'The enable status of L2VPN service statistics is disable.' ;
            }

            enum enable {
              value 1 ;
              description 'The enable status of L2VPN service statistics is enable.' ;
            }

          }

          default disable ;
        }

        leaf pw-rate-statistics-period {
          description 'PW rate period set.' ;
          type uint32 {
            range 10..600 {
              description 'The range of PW rate statistics period.' ;
            }

          }

          units second ;
          default 120 ;
          ncd:revise-date 2019-06-13 ;
        }

        leaf srv6-evpn-next-header {
          description 'Specify SRv6 next header type.' ;
          type enumeration {
            enum ethernet-143 {
              value 0 ;
              description 'The SRv6 next header type field is 143(Ethernet).' ;
            }

            enum compatible-59 {
              value 1 ;
              description 'The SRv6 next header type field is 59(IPv6-NoNxt).' ;
            }

          }

          default ethernet-143 ;
          ncd:revise-date 2022-03-28 ;
        }

        leaf vpls-irb-track-state {
          status current ;

          type enumeration {
            enum track-vpls-state {
              value 1 ;
              description 'VPLS IRB interface track the VPLS instance state.' ;
            }

          }

          if-feature vpls-irb-track-vpls-state ;

          description 'VPLS IRB interface track the VPLS instance state.' ;
          ncd:revise-date 2024-01-23 ;
        }

        leaf vpls-irb-track-vpls-state {
          description 'VPLS IRB interface track the VPLS instance state.' ;
          status obsolete {
            ncd:revise-date 2023-12-23 ;
          }

          type enumeration {
            enum track-vpls-state {
              value 1 ;
              description 'VPLS IRB interface track the VPLS instance state.' ;
            }

          }

          if-feature vpls-irb-track-vpls-state ;

          ncd:revise-date 2023-09-21 ;
        }

        container dni-detect {
          if-feature dni-detect ;

          description 'Config DNI-PW associate peer BFD.' ;
          presence dni-detect ;
          leaf peer {
            description 'Specify remote IPv4 address.' ;
            type ncd:ipv4-address-none-zero ;

            mandatory true ;
          }

          leaf source {
            description 'Specify local IPv4 address.' ;
            type ncd:ipv4-address-none-zero ;

            mandatory true ;
          }

          ncd:revise-date 2016-02-22 ;
        }

        container multi-chassis-protection {
          description 'Global multiple chassis protection time.' ;
          presence multi-chassis-protection ;
          leaf suspicious-time {
            description "The temporary suspicion on the AC's recovery." ;
            type uint16 {
              range 10..5000 {
                description 'Suspicious time(ms).' ;
              }

            }

            units ms ;
            mandatory true ;
          }

          leaf protection-scenario {
            description 'Configure protection scenario.' ;
            type enumeration {
              enum kompella-pw {
                value 1 ;
                description 'Configure Kompella PW.' ;
              }

            }

            mandatory true ;
          }

          ncd:revise-date 2022-03-12 ;
        }

        container global-session-selectors {
          status obsolete {
            ncd:revise-date 2023-09-09 ;
          }

          description 'The global session selector.' ;
          leaf global-session-selector {
            description 'The global session selector.' ;
            type enumeration {
              enum target-session-only {
                value 1 ;
                description 'The global session selector is target-session-only.' ;
              }

            }

          }

          ncd:revise-date 2020-03-25 ;
        }

        container specify-session-selectors {
          status obsolete {
            ncd:revise-date 2023-09-09 ;
          }

          description 'Specify the session selector.' ;
          list specify-session-selector {
            description 'Specify the session selector.' ;
            key peer ;
            leaf peer {
              description 'Specify the session peer address.' ;
              type ncd:ipv4-address-none-zero ;

            }

            leaf local-router-id {
              description 'Specify the session local router ID.' ;
              type ncd:ipv4-address-none-zero ;

              mandatory true ;
            }

          }

          ncd:revise-date 2020-03-25 ;
        }

        container evpn-evi-specific-sub-interfaces {
          description 'Specify the IRB interface attach the EVPN VPWS as subinterface.' ;
          list evpn-evi-specific-sub-interface {
            description 'Specify the IRB interface attach the EVPN VPWS as subinterface.' ;
            key bridge-interface-name ;
            leaf bridge-interface-name {
              description 'The name of the bridge interface name.' ;
              type ncd:ifname ;

            }

          }

          ncd:revise-date 2021-07-14 ;
        }

        container evpn-irb {
          description 'EVPN IRB parameters.' ;
          presence evpn-irb ;
          leaf signal-default-gateway {
            description 'Signal default gateway extended community.' ;
            type empty ;

            mandatory true ;
          }

          leaf strict {
            description 'No sticky flag carried along with default gateway.' ;
            type empty ;

          }

          ncd:revise-date 2022-04-20 ;
        }

        container l2vpn-rd-template {
          description 'L2VPN RD template.' ;
          leaf evpn-rd {
            description 'RD of EVPN type.' ;
            type union {
              type ncd:asn-nn ;

              type ncd:ipadd-nn ;

              type ncd:asnd-nn ;

            }

          }

          ncd:revise-date 2022-04-20 ;
        }

        container l2vpn-evpn-prefix-sid {
          description 'Config L2VPN EVPN prefix-sid delete-delay.' ;
          presence l2vpn-evpn-prefix-sid ;
          leaf delete-delay {
            type empty ;

            description 'Delay to delete.' ;
            mandatory true ;
          }

          leaf delay-time {
            type uint8 {
              range 1..30 ;

            }

            description 'Delay time(min).' ;
            units min ;
          }

          ncd:revise-date 2024-10-11 ;
        }

        leaf l2vpn-usid-fib {
          type enumeration {
            enum short-sid-only {
              description 'Install short SID only.' ;
              value 0 ;
            }

            enum long-sid-only {
              description 'Install long SID only.' ;
              value 1 ;
            }

            enum long-and-short-sid {
              description 'Install both long and short SID.' ;
              value 2 ;
            }

          }

          description 'Configure the L2VPN SRv6 uSID FIB installation mode.' ;
          default short-sid-only ;
          ncd:revise-date 2024-04-01 ;
        }

      }

      container protect-rules {
        description 'The PW protect rules configuration info.' ;
        list protect-group {
          description 'The protect group configuration info.It contains common protect-group,single-dni-pwgroup,dual-dni-pwgroup.' ;
          key interface-name ;
          leaf interface-name {
            description 'The PW name of protect group.' ;
            type ncd:ifname {
              length 1..31 {
                description 'The length of PW or redirect PW name.' ;
              }

            }

          }

          leaf mc-pw-role {
            description 'The MC-PW role which is configured with the PW protectable.' ;
            type enumeration {
              enum null {
                value 0 ;
                description 'The MC-PW role is null.' ;
              }

              enum mc-master {
                value 1 ;
                description 'The MC-PW role is MC-master.' ;
              }

              enum mc-slave {
                value 2 ;
                description 'The MC-PW role is MC-slave.' ;
              }

            }

            mandatory true ;
          }

          leaf pfs-bits {
            description 'The negotiation mode of the PW protectable.' ;
            type enumeration {
              enum null {
                value 0 ;
                description 'The negotiation mode is null.' ;
              }

              enum independent {
                value 1 ;
                description 'The negotiation mode is independent.' ;
              }

              enum master {
                value 2 ;
                description 'The negotiation mode is master.' ;
              }

              enum slave {
                value 3 ;
                description 'The negotiation mode is slave.' ;
              }

            }

            default null ;
          }

          leaf regard-of-ac {
            description 'The advertise type of the PW protectable.' ;
            type enumeration {
              enum regard-of-ac {
                value 0 ;
                description 'The advertise type is regard of AC.' ;
              }

              enum regardless-of-ac {
                value 1 ;
                description 'The advertise type is regardless of AC.' ;
              }

            }

            default regard-of-ac ;
          }

          leaf ignore-remote-pfs-bits {
            description 'Ignore or not remote pfs-bits status,(1:ignore,0:not-ignore).' ;
            type enumeration {
              enum not-ignore-remote-pfs-bits {
                value 0 ;
                description 'Not ignore remote pfs-bits.' ;
              }

              enum ignore-remote-pfs-bits {
                value 1 ;
                description 'Ignore remote pfs-bits.' ;
              }

            }

            default not-ignore-remote-pfs-bits ;
            ncd:revise-date 2021-05-20 ;
          }

          container protect-strategy {
            description 'The PW protect strategy configuration info.' ;
            presence protect-strategy ;
            choice group-type {
              description 'The PW protect group type.It contains common protect-group,single-dni-pwgroup,dual-dni-pwgroup.' ;
              case common-group {
                description 'Common PW protect group.' ;
                container common-group-params {
                  description 'The common PW protect group parameters.' ;
                  presence common-group-params ;
                  leaf protect-type {
                    description 'The protect type of the PW protect strategy.' ;
                    type enumeration {
                      enum one-by-one {
                        value 1 ;
                        description 'The protect type of the PW protect strategy is one by one.' ;
                      }

                      enum one-plus-one {
                        value 2 ;
                        description 'The protect type of the PW protect strategy is one plus one.' ;
                      }

                    }

                    mandatory true ;
                  }

                  leaf direction {
                    description 'The protected direction of the PW protect strategy.' ;
                    type enumeration {
                      enum unidirectional {
                        value 1 ;
                        description 'The protected direction of the PW protect strategy is unidirectional.' ;
                      }

                      enum bidirectional {
                        value 2 ;
                        description 'The protected direction of the PW protect strategy is bidirectional.' ;
                      }

                    }

                    default unidirectional ;
                  }

                  leaf receiver-parameters {
                    description 'The protected receiver of the PW protect strategy.' ;
                    type enumeration {
                      enum selective {
                        value 1 ;
                        description 'The protected receiver of the PW protect strategy is selective.' ;
                      }

                      enum both {
                        value 2 ;
                        description 'The protected receiver of the PW protect strategy is both.' ;
                      }

                    }

                    default selective ;
                  }

                  leaf aps-mode {
                    description 'The APS mode of the PW protect strategy.' ;
                    type enumeration {
                      enum null {
                        value 0 ;
                        description 'The APS mode of the PW protect strategy is null.' ;
                      }

                      enum aps {
                        value 1 ;
                        description 'The APS mode of the PW protect strategy is APS.' ;
                      }

                    }

                    mandatory true ;
                  }

                  container backup-pw-params {
                    description 'The protect PW configuration parameters info.' ;
                    list protect-pw {
                      description 'The protect PW configuration info.' ;
                      key protect-pwname ;
                      leaf protect-pwname {
                        description 'The protect PW name.' ;
                        type ncd:ifname {
                          length 1..31 {
                            description 'The length of protect PW name.' ;
                          }

                        }

                      }

                      leaf protect-distance {
                        description 'The distance between back-up PW and protected PW.' ;
                        type uint16 {
                          range 1..255 {
                            description 'The value of distance between back-up PW and protected PW.' ;
                          }

                        }

                      }

                    }

                  }

                }

              }

              case single-dni-pwgroup {
                description 'Single DNI-PW protect group.' ;
                container single-dni-pwgroup-params {
                  description 'The single DNI-PW protect group parameters.' ;
                  presence single-dni-pwgroup-params ;
                  leaf mc-protect-type {
                    description 'The MC protect type of the PW protect strategy.' ;
                    type enumeration {
                      enum mc-protection {
                        value 2 ;
                      }

                    }

                    mandatory true ;
                  }

                  leaf helper {
                    description 'The protect strategy of the single DNI-PW.' ;
                    type enumeration {
                      enum one-by-one {
                        value 1 ;
                        description 'The protect strategy of the single DNI-PW is one-by-one.' ;
                      }

                      enum one-puls-one {
                        value 2 ;
                        description 'The protect strategy of the single DNI-PW is one-plus-one.' ;
                      }

                    }

                  }

                  leaf direction {
                    description 'The protected direction of the PW protect strategy.' ;
                    type enumeration {
                      enum unidirectional {
                        value 1 ;
                        description 'The protected direction of the PW protect strategy is unidirectional.' ;
                      }

                      enum bidirectional {
                        value 2 ;
                        description 'The protected direction of the PW protect strategy is bidirectional.' ;
                      }

                    }

                  }

                  leaf receiver-parameters {
                    description 'The protected receiver of the PW protect strategy.' ;
                    type enumeration {
                      enum selective {
                        value 1 ;
                        description 'The protected receiver of the PW protect strategy is selective.' ;
                      }

                      enum both {
                        value 2 ;
                        description 'The protected receiver of the PW protect strategy is both.' ;
                      }

                    }

                  }

                  container inter-chassis-params {
                    description 'Inter chassis protect PW configure parameters.' ;
                    list inter-chassis-protect-pw {
                      description 'Inter chassis protect PW configure info.' ;
                      key inter-chassis-protect-pwname ;
                      leaf inter-chassis-protect-pwname {
                        description 'Inter chassis protect PW name.' ;
                        type ncd:ifname {
                          length 1..31 {
                            description 'The length of inter-chassis protect PW name.' ;
                          }

                        }

                      }

                    }

                  }

                }

              }

              case dual-dni-pwgroup {
                description 'Dual DNI-PW protect group.' ;
                container dual-dni-pwgroup-params {
                  description 'The dual DNI-PW protect group parameters.' ;
                  presence dual-dni-pwgroup-params ;
                  leaf dual-dni-protect-type {
                    description 'The protect type of dual DNI-PW.' ;
                    type enumeration {
                      enum mc-and-access-pw {
                        value 3 ;
                        description 'The value of the MC protect type is mc-and-access-pw.' ;
                      }

                    }

                    mandatory true ;
                  }

                  container backup-mc-pw-params {
                    description 'The backup MC-PW parameters of dual DNI-PW.' ;
                    presence backup-mc-pw-params ;
                    list backup-mc-pw {
                      description 'Backup MC-PW configure info.' ;
                      key backup-mc-pwname ;
                      leaf backup-mc-pwname {
                        description 'Backup MC-PW name.' ;
                        type ncd:ifname {
                          length 1..31 {
                            description 'The length of backup MC-PW name.' ;
                          }

                        }

                      }

                    }

                  }

                  container access-pw-params {
                    description 'The access protect PW parameters of dual DNI-PW.' ;
                    presence access-pw-params ;
                    list access-protect-pw {
                      description 'Access protect PW configure info.' ;
                      key access-protect-pwname ;
                      leaf access-protect-pwname {
                        description 'Access protect PW name.' ;
                        type ncd:ifname {
                          length 1..31 {
                            description 'The length of access PW name.' ;
                          }

                        }

                      }

                      container ce-side-params {
                        description 'The CE side parameters of access protect PW.' ;
                        presence ce-side-params ;
                        leaf ce-side {
                          description 'The CE side configuration of access protect PW.' ;
                          type enumeration {
                            enum "1+1" {
                              value 1 ;
                              description 'The CE decides to 1+1 between two nodes.' ;
                            }

                            enum 1:1 {
                              value 2 ;
                              description 'The CE decides to 1:1 between two nodes.' ;
                            }

                            enum load-balance {
                              value 3 ;
                              description 'The CE decides to load-balance between two nodes.' ;
                            }

                          }

                          mandatory true ;
                        }

                      }

                    }

                  }

                }

              }

              case enhanced-dni-pwgroup {
                if-feature enhanced-dni-pwgroup ;

                description 'Enhanced DNI-PW protect group.' ;
                container enhanced-dni-pwgroup-params {
                  description 'The enhanced DNI-PW protect group parameters.' ;
                  presence enhanced-dni-pwgroup-params ;
                  leaf enhanced-dni-protect-type {
                    description 'The protect type of enhanced DNI-PW.' ;
                    type enumeration {
                      enum enhanced-mc-and-access-pw {
                        value 5 ;
                        description 'The value of the enhanced MC-PW protect type is enhanced-mc-and-access-pw.' ;
                      }

                    }

                    mandatory true ;
                  }

                  container backup-mc-pw-shortcut-params {
                    description 'The shortcut backup MC-PW parameters of enhanced DNI-PW.' ;
                    presence backup-mc-pw-shortcut-params ;
                    list backup-mc-pw-shortcut {
                      description 'The shortcut backup MC-PW configure info.' ;
                      key backup-mc-shortcut-pwname ;
                      leaf backup-mc-shortcut-pwname {
                        description 'The shortcut backup MC-PW name.' ;
                        type ncd:ifname ;

                      }

                    }

                  }

                  container access-pw-params {
                    description 'The access protect PW parameters of enhanced DNI-PW.' ;
                    presence access-pw-params ;
                    list access-protect-pw {
                      description 'Access protect PW configure info.' ;
                      key access-protect-pwname ;
                      leaf access-protect-pwname {
                        description 'Access protect PW name.' ;
                        type ncd:ifname ;

                      }

                      container ce-side-params {
                        description 'The CE side parameters of access protect PW.' ;
                        presence ce-side-params ;
                        leaf ce-side {
                          description 'The CE side configuration of access protect PW.' ;
                          type enumeration {
                            enum "1+1" {
                              value 1 ;
                              description 'The CE decides to 1+1 between two nodes.' ;
                            }

                            enum 1:1 {
                              value 2 ;
                              description 'The CE decides to 1:1 between two nodes.' ;
                            }

                            enum load-balance {
                              value 3 ;
                              description 'The CE decides to load-balance between two nodes.' ;
                            }

                          }

                          mandatory true ;
                        }

                      }

                    }

                  }

                }

                ncd:revise-date 2016-03-30 ;
              }

            }

          }

          container iccp-connection {
            description 'Inter-Chassis Communication Protocol(ICCP)configuration info.' ;
            presence iccp-connection ;
            leaf iccp-groupid {
              description 'Inter-Chassis Communication Protocol(ICCP) group ID.The maximum value is determined by the parameters of performance.' ;
              type uint32 {
                range 1..4294967295 {
                  description 'The value of ICCP group identification.' ;
                }

              }

              mandatory true ;
            }

            leaf iccp-group-roid {
              description 'Inter-Chassis Communication Protocol(ICCP) ROID.' ;
              type uint64 {
                range 1..18446744073709551615 {
                  description 'The value of ICCP group ROID.' ;
                }

              }

              mandatory true ;
            }

          }

          container mc-selection {
            description 'To select a single active PW from the two MC-PWs.' ;
            presence mc-selection ;
            leaf mc-selection-type {
              description 'The multiple chassis selection type of the PW protect strategy.' ;
              type enumeration {
                enum mc-selection {
                  value 0 ;
                  description 'The MC selection type is mc-selection.' ;
                }

                enum oam-mapping {
                  value 1 ;
                  description 'The MC selection type is oam-mapping.' ;
                }

              }

              mandatory true ;
            }

          }

        }

      }

      container pw-specification {
        description 'PW specification configuration info.' ;
        list pw-entry {
          description 'PW entry configuration info.' ;
          key pw-name ;
          leaf pw-name {
            description 'The name of the PW.' ;
            type ncd:ifname ;

          }

          leaf neighbour {
            description "The remote peer's IP address of the PW." ;
            type ncd:ipv4-address ;

            mandatory true ;
          }

          leaf vcid {
            description 'The VC identification of the PW.' ;
            type uint32 {
              range 1..4294967295 {
                description 'The VC identification value.' ;
              }

            }

            mandatory true ;
          }

          leaf pw-type {
            description 'The PW type of the PW.' ;
            type enumeration {
              enum unknown {
                value 0 ;
                description 'The PW type is unknown.' ;
              }

              enum dlciOld {
                value 1 ;
                description 'The PW type is FR-DLCI old.' ;
              }

              enum atmSdu {
                value 2 ;
                description 'The PW type is ATM-AAL5-SDU.' ;
              }

              enum atmCell {
                value 3 ;
                description 'The PW type is ATM-CELL.' ;
              }

              enum vlan {
                value 4 ;
                description 'The PW type is VLAN.' ;
              }

              enum ethernet {
                value 5 ;
                description 'The PW type is ethernet.' ;
              }

              enum hdlc {
                value 6 ;
                description 'The PW type is HDLC.' ;
              }

              enum ppp {
                value 7 ;
                description 'The PW type is PPP.' ;
              }

              enum sdhCESoM {
                value 8 ;
                description 'The PW type is SONET/SDH Circuit Emulation Service over MPLS.' ;
              }

              enum atmVCCn {
                value 9 ;
                description 'The PW type is ATM n-to-one VCC.' ;
              }

              enum atmVPCn {
                value 10 ;
                description 'The PW type is ATM n-to-one VPC.' ;
              }

              enum ipL2 {
                value 11 ;
                description 'The PW type is IP-L2.' ;
              }

              enum atmVCC1 {
                value 12 ;
                description 'The PW type is ATM one-to-one VCC.' ;
              }

              enum atmVPC1 {
                value 13 ;
                description 'The PW type is ATM one-to-one VPC.' ;
              }

              enum atmPDU {
                value 14 ;
                description 'The PW type is ATM AAL5 PDU VCC.' ;
              }

              enum frPort {
                value 15 ;
                description 'The PW type is FR port.' ;
              }

              enum sdhCEoP {
                value 16 ;
                description 'The PW type is SONET/SDH Circuit Emulation over Packet.' ;
              }

              enum saTopE1 {
                value 17 ;
                description 'The PW type is Structure-agnostic E1 over Packet.' ;
              }

              enum saTopT1 {
                value 18 ;
                description 'The PW type is Structure-agnostic T1 (DS1) over Packet.' ;
              }

              enum saTopE3 {
                value 19 ;
                description 'The PW type is Structure-agnostic E3 over Packet.' ;
              }

              enum saTopT3 {
                value 20 ;
                description 'The PW type is Structure-agnostic T3 (DS3) over Packet.' ;
              }

              enum ceSoPSNB {
                value 21 ;
                description 'The PW type is CESoPSN basic.' ;
              }

              enum tdmAAL1 {
                value 22 ;
                description 'The PW type is TDMoIP AAL1.' ;
              }

              enum ceSoPSNC {
                value 23 ;
                description 'The PW type is CESoPSN TDM with CAS.' ;
              }

              enum tdmAAL2 {
                value 24 ;
                description 'The PW type is TDMoIP AAL2.' ;
              }

              enum dlciNew {
                value 25 ;
                description 'The PW type is FR-DLCI.' ;
              }

            }

            mandatory true ;
          }

          leaf control-word {
            description 'The control-word capability of the PW.' ;
            type enumeration {
              enum not-preferred {
                value 0 ;
                description 'The control-word capability is not preferred.' ;
              }

              enum preferred {
                value 1 ;
                description 'The control-word capability is preferred.' ;
              }

            }

            default not-preferred ;
          }

          leaf signal-type {
            description 'The signal type of the PW.' ;
            type enumeration {
              enum static {
                value 0 ;
                description 'The signal type is static.' ;
              }

              enum dynamic {
                value 1 ;
                description 'The signal type is dynamic.' ;
              }

            }

            default dynamic ;
          }

          leaf local-label {
            description 'The local label of the PW.' ;
            type uint32 {
              range 16..1048575 {
                description 'The range of local label.' ;
              }

            }

          }

          leaf remote-label {
            description 'The remote label of the PW.' ;
            type uint32 {
              range 16..1048575 {
                description 'The range of remote label.' ;
              }

            }

          }

          leaf tunnel-policy-name {
            description 'The PSN tunnel policy name of the PW.' ;
            type string {
              length 1..63 {
                description 'The length of tunnel policy name.' ;
              }

            }

          }

          leaf track-name {
            description 'The name of track object that bind to the PW.' ;
            type string {
              length 1..31 {
                description 'The length of track name.' ;
              }

            }

          }

          leaf track-group-flag {
            description 'The track group flag.' ;
            type empty ;

            ncd:revise-date 2018-07-25 ;
          }

          choice track-group-notify {
            description 'Track group notify.' ;
            case fast-notify {
              description 'Track group notify fast.' ;
              leaf track-fast-notified {
                description 'Notify LDP to send messages fast.' ;
                type empty ;

              }

            }

            case notify {
              description 'Track group notify.' ;
              leaf track-notified {
                description 'Notify LDP to send messages.' ;
                type empty ;

              }

              ncd:revise-date 2022-08-13 ;
            }

            ncd:revise-date 2018-07-25 ;
          }

          leaf shutdown {
            description 'The enable status of the PW.' ;
            type enumeration {
              enum disable {
                value 0 ;
                description 'The enable status of the PW is disable.' ;
              }

              enum enable {
                value 1 ;
                description 'The enable status of the PW is enable.' ;
              }

            }

            default enable ;
          }

          leaf cword-sequencing {
            description 'The cword sequencing enable status of the PW.' ;
            type enumeration {
              enum disable {
                value 0 ;
                description 'The cword sequencing enable status is disable.' ;
              }

              enum enable {
                value 1 ;
                description 'The cword sequencing enable status is enable.' ;
              }

            }

            default disable ;
          }

          leaf cw-lbit {
            description 'The control-word L-bit capability of the PW.' ;
            type enumeration {
              enum disable {
                value 0 ;
                description 'The control-word L-bit is disable.' ;
              }

              enum enable {
                value 1 ;
                description 'The control-word L-bit is enable.' ;
              }

            }

            default enable ;
          }

          leaf sd-enable {
            description 'The enable status of the PW SD propagation.' ;
            type enumeration {
              enum disable {
                value 0 ;
                description 'The enable status of the PW SD propagation is disable.' ;
              }

              enum enable {
                value 1 ;
                description 'The enable status of the PW SD propagation is enable.' ;
              }

            }

            default disable ;
          }

          leaf raw-tag-reversed {
            description 'Raw or tagged reversed flag of the PW.' ;
            type enumeration {
              enum disable {
                value 0 ;
                description 'Raw or tagged reversed flag is disable.' ;
              }

              enum enable {
                value 1 ;
                description 'Raw or tagged reversed flag is enable' ;
              }

            }

            default disable ;
          }

          leaf cword-usage-forced {
            description 'Control-word usage forced flag of the PW.' ;
            type enumeration {
              enum force-unused {
                value 1 ;
                description 'Control-word usage forced flag is force unused.' ;
              }

              enum force-used {
                value 2 ;
                description 'Control-word usage forced flag is force used.' ;
              }

            }

          }

          leaf oam-mapping-ignoring-frr {
            description 'Oam mapping ignoring FRR or not.' ;
            type enumeration {
              enum disable {
                value 0 ;
                description 'Oam mapping not ignoring FRR.' ;
              }

              enum enable {
                value 1 ;
                description 'Oam mapping ignoring FRR.' ;
              }

            }

            default disable ;
          }

          leaf abort-mapping-to-ac {
            description 'Abort mapping to AC or not.' ;
            type enumeration {
              enum disable {
                value 0 ;
                description 'Mapping to AC normal.' ;
              }

              enum enable {
                value 1 ;
                description 'Abort mapping to AC.' ;
              }

            }

            default disable ;
          }

          leaf hard-pipe {
            description 'The hard pipe of the PW.' ;
            type enumeration {
              enum disable {
                value 0 ;
                description 'The hard pipe of the PW is disable.' ;
              }

              enum enable {
                value 1 ;
                description 'The hard pipe of the PW is enable.' ;
              }

            }

            default disable ;
            ncd:revise-date 2016-12-15 ;
          }

          leaf pfs-bits-tracked {
            description 'Preferential forwarding status bits is tracked.' ;
            type enumeration {
              enum not-tracked {
                value 0 ;
                description 'Preferential forwarding status bits is not tracked.' ;
              }

              enum tracked {
                value 1 ;
                description 'Preferential forwarding status bits is tracked.' ;
              }

            }

            default not-tracked ;
            ncd:revise-date 2019-02-15 ;
          }

          leaf pfs-bits-tracked-ignore-remote-status {
            type empty ;

            description 'Ignore remote PSN/AC status.' ;
            ncd:revise-date 2024-12-27 ;
          }

          leaf entropy-label {
            description 'Enable/Disable PW entropy label.' ;
            type enumeration {
              enum disable {
                value 0 ;
                description 'PW entropy label is disable.' ;
              }

              enum enable {
                value 1 ;
                description 'PW entropy label is enable.' ;
              }

            }

            default disable ;
            ncd:revise-date 2019-07-11 ;
          }

          leaf node-role {
            description 'The node-role of ring-tree instance.' ;
            type enumeration {
              enum common-leaf {
                value 0 ;
                description 'The node-role of ring-tree is common-leaf.' ;
              }

              enum work-root {
                value 1 ;
                description 'The node-role of ring-tree is work-root.' ;
              }

              enum protect-root {
                value 2 ;
                description 'The node-role of ring-tree is protect-root.' ;
              }

              enum work-leaf {
                value 3 ;
                description 'The node-role of ring-tree is work-leaf.' ;
              }

              enum protect-leaf {
                value 4 ;
                description 'The node-role of ring-tree is protect-leaf.' ;
              }

            }

            default common-leaf ;
            ncd:revise-date 2018-09-07 ;
          }

          leaf set-traffic-class {
            description 'Set traffic-class of PW.' ;
            type uint32 {
              range 0..7 {
                description 'The range of traffic-class.' ;
              }

            }

            ncd:revise-date 2019-08-10 ;
          }

          leaf cac-flag {
            description 'The CAC flag of PW.' ;
            type enumeration {
              enum disable {
                value 0 ;
                description 'The CAC flag is OFF.' ;
              }

              enum enable {
                value 1 ;
                description 'The CAC flag is ON.' ;
              }

            }

            default enable ;
            ncd:revise-date 2019-10-29 ;
          }

          leaf tunnel-destination-ipv6 {
            status obsolete {
              ncd:revise-date 2016-09-23 ;
            }

            description 'IPv6 address as tunnel destination.' ;
            type ncd:ipv6-address {
              pattern "([0-9a-fA-F]{1,4}:){7}([0-9a-fA-F]{0,4})$|^([0-9a-fA-F]{1,4}:){1,6}(:[0-9a-fA-F]{0,4}){1,6}$|^([:]{2})(([0-9a-fA-F]{1,4}:){0,6})([0-9a-fA-F]{1,4})$|^([0-9a-fA-F]{1,4}:){6}([0-9]{1,3}.){3}([0-9]{1,3})$|^([0-9a-fA-F]{1,4}:){1,5}(:[0-9a-fA-F]{0,4}){1,5}([0-9]{1,3}.){3}([0-9]{1,3})$|^([:]{2})(([0-9a-fA-F]{1,4}:){0,5})([0-9]{1,3}.){3}([0-9]{1,3})" ;

            }

          }

          leaf color {
            description 'The color of PW.' ;
            type uint32 {
              range 1..4294967295 {
                description 'The range of PW color.' ;
              }

            }

            ncd:revise-date 2020-02-13 ;
          }

          leaf tunnel-srv6-sid {
            description 'The SRv6 SID of the outer tunnel.' ;
            type ncd:ipv6-address-none-zero ;

            ncd:revise-date 2021-01-20 ;
          }

          leaf vccv-flow-label {
            description 'The flow-label for VCCV packets without standard flow-labels.' ;
            type empty ;

            ncd:revise-date 2022-03-07 ;
          }

          container tunnel-destination {
            description 'The address as tunnel destination.' ;
            choice destination-type {
              description 'The tunnel destination type.' ;
              case ipv6 {
                description 'The tunnel destination type is IPv6.' ;
                leaf tunnel-destination-ipv6 {
                  description 'IPv6 address as tunnel destination.' ;
                  type ncd:ipv6-address {
                    pattern "([0-9a-fA-F]{1,4}:){7}([0-9a-fA-F]{0,4})$|^([0-9a-fA-F]{1,4}:){1,6}(:[0-9a-fA-F]{0,4}){1,6}$|^([:]{2})(([0-9a-fA-F]{1,4}:){0,6})([0-9a-fA-F]{1,4})$|^([0-9a-fA-F]{1,4}:){6}([0-9]{1,3}.){3}([0-9]{1,3})$|^([0-9a-fA-F]{1,4}:){1,5}(:[0-9a-fA-F]{0,4}){1,5}([0-9]{1,3}.){3}([0-9]{1,3})$|^([:]{2})(([0-9a-fA-F]{1,4}:){0,5})([0-9]{1,3}.){3}([0-9]{1,3})" ;

                  }

                }

              }

              case ipv4 {
                description 'The tunnel destination type is IPv4.' ;
                leaf tunnel-destination-ipv4 {
                  description 'IPv4 address as tunnel destination.' ;
                  type ncd:ipv4-address-none-zero ;

                }

              }

            }

            ncd:revise-date 2016-09-23 ;
          }

          container required-vlan-parameters {
            if-feature required-vlan-pw ;

            description 'Required VLAN parameters configuration info of PW.' ;
            leaf outer-vlan-id {
              description 'Outer VLAN value of remote required.' ;
              type uint16 {
                range 1..4094 {
                  description 'The outer VLAN ID value.' ;
                }

              }

            }

            leaf inner-vlan-id {
              description 'Inner VLAN value of remote required.' ;
              type uint16 {
                range 1..4094 {
                  description 'The inner VLAN ID value.' ;
                }

              }

            }

            leaf keep-ingress-tag {
              description 'The keep ingress tag of the PW.' ;
              type enumeration {
                enum disable {
                  value 0 ;
                  description 'The keep ingress tag of the PW is disable.' ;
                }

                enum enable {
                  value 1 ;
                  description 'The keep ingress tag of the PW is enable.' ;
                }

              }

              default disable ;
            }

            leaf outer-tpid {
              description 'Outer ether-type of remote required.' ;
              type enumeration {
                enum 8100 {
                  value 0 ;
                  description 'Outer ether-type of remote required is 8100.' ;
                }

                enum 9100 {
                  value 1 ;
                  description 'Outer ether-type of remote required is 9100.' ;
                }

                enum 9200 {
                  value 2 ;
                  description 'Outer ether-type of remote required is 9200.' ;
                }

                enum 88a8 {
                  value 3 ;
                  description 'Outer ether-type of remote required is 88a8.' ;
                }

                enum 88e7 {
                  value 4 ;
                  description 'Outer ether-type of remote required is 88e7.' ;
                }

                enum 9300 {
                  value 5 ;
                  description 'Outer ether-type of remote required is 9300.' ;
                }

              }

            }

            leaf inner-tpid {
              description 'Inner ether-type of remote required.' ;
              type enumeration {
                enum 8100 {
                  value 0 ;
                  description 'Inner ether-type of remote required is 8100.' ;
                }

                enum 9100 {
                  value 1 ;
                  description 'Inner ether-type of remote required is 9100.' ;
                }

                enum 9200 {
                  value 2 ;
                  description 'Inner ether-type of remote required is 9200.' ;
                }

                enum 88a8 {
                  value 3 ;
                  description 'Inner ether-type of remote required is 88a8.' ;
                }

                enum 88e7 {
                  value 4 ;
                  description 'Inner ether-type of remote required is 88e7.' ;
                }

                enum 9300 {
                  value 5 ;
                  description 'Inner ether-type of remote required is 9300.' ;
                }

              }

            }

          }

          container traffic-statistics-params {
            if-feature pw-traffic-statistics ;

            description 'The traffic statistics parameters info of PW.' ;
            leaf statistics-enable {
              description 'The traffic statistics status of PW.' ;
              type enumeration {
                enum disable {
                  value 0 ;
                  description 'The traffic statistics status of PW is disable.' ;
                }

                enum enable {
                  value 1 ;
                  description 'The traffic statistics status of PW is enable.' ;
                }

              }

              default disable ;
            }

            leaf in-bytes-rate-low {
              description 'The low threshold of warning for input bytes rate.' ;
              type uint32 {
                range 0..4294967294 {
                  description 'The input bytes rate low threshold value.' ;
                }

              }

              default 0 ;
            }

            leaf in-bytes-rate-high {
              description 'The high threshold of warning for input bytes rate.' ;
              type uint32 {
                range 1..4294967295 {
                  description 'The input bytes rate high threshold value.' ;
                }

              }

              default 4294967295 ;
            }

            leaf out-bytes-rate-low {
              description 'The low threshold of warning for output bytes rate.' ;
              type uint32 {
                range 0..4294967294 {
                  description 'The output bytes rate low threshold value.' ;
                }

              }

              default 0 ;
            }

            leaf out-bytes-rate-high {
              description 'The high threshold of warning for output bytes rate.' ;
              type uint32 {
                range 1..4294967295 {
                  description 'The output bytes rate high threshold value.' ;
                }

              }

              default 4294967295 ;
            }

            leaf unicast-inrate-bps {
              description 'The unicast input bytes rate.' ;
              type uint64 {
                range 1..18446744073709551615 {
                  description 'The range of unicast input packets rate.' ;
                }

              }

              units bps ;
            }

            leaf unicast-inrate-pps {
              description 'The unicast input packets rate.' ;
              type uint32 {
                range 1..4294967295 {
                  description 'The range of unicast input packets rate.' ;
                }

              }

              units pps ;
            }

            leaf broadcast-inrate-bps {
              description 'The broadcast input bytes rate.' ;
              type uint64 {
                range 1..18446744073709551615 {
                  description 'The range of broadcast input packets rate.' ;
                }

              }

              units bps ;
            }

            leaf broadcast-inrate-pps {
              description 'The broadcast input packets rate.' ;
              type uint32 {
                range 1..4294967295 {
                  description 'The range of broadcast input packets rate.' ;
                }

              }

              units pps ;
            }

            leaf drop-inrate-bps {
              description 'The drop input bytes rate.' ;
              type uint64 {
                range 1..18446744073709551615 {
                  description 'The range of drop input packets rate.' ;
                }

              }

              units bps ;
            }

            leaf drop-inrate-pps {
              description 'The drop input packets rate.' ;
              type uint32 {
                range 1..4294967295 {
                  description 'The range of drop input packets rate.' ;
                }

              }

              units pps ;
            }

          }

          container qos-parameters {
            description 'The QoS parameters of PW.' ;
            choice qos-params-type {
              description 'The QoS parameters type of PW.' ;
              case bandwidth-params {
                description 'The bandwidth parameters of PW.' ;
                container bandwidth {
                  description 'The bandwidth of PW.' ;
                  presence bandwidth ;
                  leaf cir {
                    description 'The committed bandwidth value of the PW.' ;
                    type uint32 {
                      range "0 | 1..4294967295" {
                        description 'The range of the committed bandwidth value.' ;
                      }

                    }

                    units kbps ;
                    mandatory true ;
                  }

                  leaf cbs {
                    description 'The committed burst size value of the PW.' ;
                    type uint32 {
                      range 1..4294967295 {
                        description 'The range of committed burst size value.' ;
                      }

                    }

                    units KB ;
                  }

                  leaf pir {
                    description 'The peak bandwidth value of the PW.' ;
                    type uint32 {
                      range "0 | 1..4294967295" {
                        description 'The range of peak bandwidth value.' ;
                      }

                    }

                    units kbps ;
                  }

                  leaf pbs {
                    description 'The excess burst size value of the PW.' ;
                    type uint32 {
                      range 1..4294967295 {
                        description 'The range of excess burst size value.' ;
                      }

                    }

                    units KB ;
                  }

                }

              }

              case rate-limit-params {
                description 'The rate limit parameters of PW.' ;
                container rate-limit {
                  description 'The rate limit of PW.' ;
                  presence rate-limit ;
                  leaf mode {
                    description 'The mode of PW rate limit.' ;
                    type enumeration {
                      enum blind {
                        value 1 ;
                        description 'The mode of PW rate limit is blind.' ;
                      }

                      enum aware {
                        value 2 ;
                        description 'The mode of PW rate limit is aware.' ;
                      }

                    }

                    mandatory true ;
                  }

                  leaf cir {
                    description 'The committed information rate value of PW rate limit.' ;
                    type uint32 {
                      range "0 | 1..4294967295" {
                        description 'The range of committed information rate value.' ;
                      }

                    }

                    units kbps ;
                    mandatory true ;
                  }

                  leaf cbs {
                    description 'The committed burst size value of PW rate limit.' ;
                    type uint32 {
                      range 1..4294967295 {
                        description 'The range of committed burst size value.' ;
                      }

                    }

                    units KB ;
                    mandatory true ;
                  }

                  leaf pir {
                    description 'The peak information rate value of PW rate limit.' ;
                    type uint32 {
                      range "0 | 1..4294967295" {
                        description 'The range of peak information rate value.' ;
                      }

                    }

                    units kbps ;
                    mandatory true ;
                  }

                  leaf pbs {
                    description 'The peak burst size value of PW rate limit.' ;
                    type uint32 {
                      range 1..4294967295 {
                        description 'The range of peak burst size value.' ;
                      }

                    }

                    units KB ;
                    mandatory true ;
                  }

                  leaf red {
                    description 'The packet color parameter.' ;
                    type enumeration {
                      enum forward {
                        value 1 ;
                        description 'The packet action is forward.' ;
                      }

                      enum discard {
                        value 2 ;
                        description 'The packet action is discard.' ;
                      }

                    }

                    ncd:revise-date 2019-03-25 ;
                  }

                }

              }

            }

          }

          container vccv-bfd-params {
            description 'The VCCV BFD parameters info of PW.' ;
            leaf vccv-bfd {
              description 'The BFD capability of the PW.' ;
              type enumeration {
                enum disable {
                  value 0 ;
                  description 'The BFD capability is disable.' ;
                }

                enum enable {
                  value 1 ;
                  description 'The BFD capability is enable.' ;
                }

              }

              default disable ;
            }

            leaf vccv-bfd-encapsulation {
              description 'The BFD raw encapsulation capability of the PW.' ;
              type enumeration {
                enum ip {
                  value 0 ;
                  description 'The BFD raw encapsulation capability is IP.' ;
                }

                enum raw {
                  value 1 ;
                  description 'The BFD raw encapsulation capability is raw.' ;
                }

              }

              default ip ;
            }

            leaf vccv-bfd-capability {
              description 'The BFD signal status capability of the PW.' ;
              type enumeration {
                enum basic {
                  value 0 ;
                  description 'The BFD signal status capability is basic.' ;
                }

                enum status {
                  value 1 ;
                  description 'The BFD signal status capability is status.' ;
                }

              }

              default basic ;
            }

            leaf static-vccv-cc {
              description "The static VCCV's CC type of the PW." ;
              type enumeration {
                enum null {
                  value 0 ;
                  description "The static VCCV's CC type is null." ;
                }

                enum ttl {
                  value 1 ;
                  description "The static VCCV's CC type is TTL." ;
                }

                enum alert-label {
                  value 2 ;
                  description "The static VCCV's CC type is alert label." ;
                }

                enum control-word {
                  value 3 ;
                  description "The static VCCV's CC type is control word." ;
                }

              }

              default null ;
            }

          }

          container flow-label {
            if-feature flow-label ;

            description 'PW support flow label function.' ;
            leaf push {
              description 'Flow label transmit capability.' ;
              type enumeration {
                enum disable {
                  value 0 ;
                  description 'Flow label transmit capability is disable.' ;
                }

                enum enable {
                  value 1 ;
                  description 'Flow label transmit capability is enable.' ;
                }

              }

              default disable ;
            }

            leaf pop {
              description 'Flow label receive capability.' ;
              type enumeration {
                enum disable {
                  value 0 ;
                  description 'Flow label receive capability is disable.' ;
                }

                enum enable {
                  value 1 ;
                  description 'Flow label receive capability is enable.' ;
                }

              }

              default disable ;
            }

          }

          container requested-vlan-parameters {
            if-feature requested-vlan-pw ;

            description 'Requested VLAN parameters configuration info of PW.' ;
            leaf requested-vlan-id {
              description 'The requested VLAN value of PW.' ;
              type uint16 {
                range 1..4094 {
                  description 'The range of requested VLAN ID.' ;
                }

              }

            }

            ncd:revise-date 2015-04-28 ;
          }

          container proactive-remote-standby {
            description 'Treat remote standby flag as not forwarding.' ;
            leaf enable-flag {
              description 'Treat remote standby as not forwarding enable flag.' ;
              type enumeration {
                enum disable {
                  value 0 ;
                  description 'Treat remote standby as not forwarding is disable.' ;
                }

                enum enable {
                  value 1 ;
                  description 'Treat remote standby as not forwarding is enable.' ;
                }

              }

              default disable ;
            }

            leaf smoothly {
              description 'Standby drops flows smoothly in temporary state.' ;
              type empty ;

              ncd:revise-date 2021-12-13 ;
            }

            ncd:revise-date 2021-11-25 ;
          }

        }

      }

      container service-instances {
        description 'The L2VPN service instances configuration info.It contains VPLS,VPWS,MSPW,VLSS,remote-monitor instance and the instance name is unique.' ;
        container vpws-instances {
          description 'The VPWS instances configuration info.' ;
          list vpws-instance {
            description 'The VPWS instance configuration info.' ;
            key instance-name ;
            leaf instance-name {
              description 'The name of the VPWS instance.' ;
              type string {
                length 1..32 {
                  description 'The length of instance name.' ;
                }

              }

            }

            leaf description {
              description 'The description of the VPWS instance.' ;
              type ncd:string-with-blank {
                length 1..104 {
                  description 'The description range of instance.' ;
                }

              }

            }

            leaf mtu {
              description 'The MTU value of the VPWS instance.' ;
              type uint16 {
                range 60..65535 {
                  description 'The range of MTU.' ;
                }

              }

            }

            leaf shutdown {
              description 'The enable status of the VPWS instance.' ;
              type enumeration {
                enum disable {
                  value 0 ;
                  description 'The status of the VPWS instance is disable.' ;
                }

                enum enable {
                  value 1 ;
                  description 'The status of the VPWS instance is enable.' ;
                }

              }

              default enable ;
            }

            leaf default-cword {
              description 'The default control-word capability of the VPWS instance.' ;
              type enumeration {
                enum not-preferred {
                  value 0 ;
                  description 'Default cword is not preferred.' ;
                }

                enum preferred {
                  value 1 ;
                  description 'Default cword is preferred.' ;
                }

              }

              default not-preferred ;
            }

            leaf qos-mode {
              description 'The QoS service mode of the VPWS instance.' ;
              type enumeration {
                enum uniform {
                  value 1 ;
                  description 'QoS mode is uniform.' ;
                }

                enum pipe {
                  value 2 ;
                  description 'QoS mode is pipe.' ;
                }

                enum shortPipe {
                  value 3 ;
                  description 'QoS mode is shortPipe.' ;
                }

              }

            }

            leaf service-class {
              description 'The QoS service class of the VPWS instance.' ;
              type enumeration {
                enum be {
                  value 1 ;
                  description 'The QoS service class is be.' ;
                }

                enum af1 {
                  value 2 ;
                  description 'The QoS service class is af1.' ;
                }

                enum af2 {
                  value 3 ;
                  description 'The QoS service class is af2.' ;
                }

                enum af3 {
                  value 4 ;
                  description 'The QoS service class is af3.' ;
                }

                enum af4 {
                  value 5 ;
                  description 'The QoS service class is af4.' ;
                }

                enum ef {
                  value 6 ;
                  description 'The QoS service class is ef.' ;
                }

                enum cs6 {
                  value 7 ;
                  description 'The QoS service class is cs6.' ;
                }

                enum cs7 {
                  value 8 ;
                  description 'The QoS service class is cs7.' ;
                }

              }

            }

            leaf colour {
              description 'The QoS packet colour of the VPWS instance.' ;
              type enumeration {
                enum green {
                  value 1 ;
                  description 'The QoS packet colour is green.' ;
                }

                enum yellow {
                  value 2 ;
                  description 'The QoS packet colour is yellow.' ;
                }

                enum red {
                  value 3 ;
                  description 'The QoS packet colour is red.' ;
                }

              }

            }

            leaf ac-fault-associate {
              description 'AC fault associate PW status or not.' ;
              type enumeration {
                enum not-associate-pw {
                  value 0 ;
                  description 'AC fault not associate PW status or signal.' ;
                }

                enum associate-pw-status {
                  value 1 ;
                  description 'AC fault associate PW status notify to PWE3.' ;
                }

                enum associate-pw-signal {
                  value 2 ;
                  description 'AC fault associate PW signal release notify to PWE3.' ;
                }

              }

              default not-associate-pw ;
              ncd:revise-date 2017-07-05 ;
            }

            leaf mtu-mismatch-ignore {
              description 'Ignore the MTU mismatch in the PW negotiation.' ;
              type empty ;

              ncd:revise-date 2022-09-13 ;
            }

            container traffic-statistics-params {
              if-feature instances-traffic-statistics ;

              description 'The traffic statistics parameters of VPWS instance.' ;
              leaf traffic-enable {
                description 'The traffic statistics status of VPWS service.' ;
                type enumeration {
                  enum disable {
                    value 0 ;
                    description 'The traffic statistics status of VPWS service is disable.' ;
                  }

                  enum enable {
                    value 1 ;
                    description 'The traffic statistics status of VPWS service is enable.' ;
                  }

                }

                default disable ;
              }

              leaf unicast-inrate-bps {
                description 'The unicast input bytes rate.' ;
                type uint64 {
                  range 1..18446744073709551615 {
                    description 'The range of unicast input bytes.' ;
                  }

                }

                units bps ;
              }

              leaf unicast-inrate-pps {
                description 'The unicast input packets rate.' ;
                type uint32 {
                  range 1..4294967295 {
                    description 'The range of unicast input packets rate.' ;
                  }

                }

                units pps ;
              }

              leaf broadcast-inrate-bps {
                description 'The broadcast input bytes rate.' ;
                type uint64 {
                  range 1..18446744073709551615 {
                    description 'The range of broadcast input bytes.' ;
                  }

                }

                units bps ;
              }

              leaf broadcast-inrate-pps {
                description 'The broadcast input packets rate.' ;
                type uint32 {
                  range 1..4294967295 {
                    description 'The range of broadcast input packets rate.' ;
                  }

                }

                units pps ;
              }

              leaf drop-inrate-bps {
                description 'The drop input bytes rate.' ;
                type uint64 {
                  range 1..18446744073709551615 {
                    description 'The range of drop input bytes.' ;
                  }

                }

                units bps ;
              }

              leaf drop-inrate-pps {
                description 'The drop input packets rate.' ;
                type uint32 {
                  range 1..4294967295 {
                    description 'The range of drop input packets rate.' ;
                  }

                }

                units pps ;
              }

            }

            container vpws-pw-bind {
              description 'VPWS PW binding configuration info.' ;
              list pw-instance-bind {
                description 'PW binding instance configuration info.' ;
                key pw-name ;
                leaf pw-name {
                  description 'The name of the PW in the bind.' ;
                  type ncd:ifname ;

                }

              }

            }

            container vpws-ac-bind {
              description 'VPWS AC binding configuration info.' ;
              list ac-instance-bind {
                description 'AC binding instance configuration info.' ;
                key ac-name ;
                leaf ac-name {
                  description 'The name of the AC in the bind.' ;
                  type ncd:ifname ;

                }

                leaf description {
                  description 'The description of the interface.' ;
                  type ncd:string-with-blank {
                    length 1..104 {
                      description 'The description range of interface.' ;
                    }

                  }

                  ncd:revise-date 2017-08-25 ;
                }

                choice ac-type {
                  description 'The access type of VPWS instance,All the access type is mutual exclusion.' ;
                  case ethernet {
                    description 'The ethernet access type.' ;
                    container ethernet-params {
                      description 'Ethernet access type parameters.' ;
                      presence ethernet-params ;
                      leaf ethernet {
                        description 'Ethernet access type.' ;
                        type empty ;

                        mandatory true ;
                      }

                      leaf track-name {
                        description 'The name of the track object which bind to the AC.' ;
                        type string {
                          length 1..31 {
                            description 'The length of the track name.' ;
                          }

                        }

                      }

                      leaf oam-mapping {
                        description 'The oam-mapping flag of the ethernet parameter.' ;
                        type enumeration {
                          enum disable {
                            value 0 ;
                            description 'The oam-mapping flag of the ethernet parameter is disable.' ;
                          }

                          enum enable {
                            value 1 ;
                            description 'The oam-mapping flag of the ethernet parameter is enable.' ;
                          }

                        }

                        default disable ;
                      }

                      leaf traffic-enable {
                        description 'The traffic statistics enable flag of the ethernet parameter.' ;
                        type enumeration {
                          enum disable {
                            value 0 ;
                            description 'The traffic statistics flag is disable.' ;
                          }

                          enum enable {
                            value 1 ;
                            description 'The traffic statistics flag is enable.' ;
                          }

                        }

                        default disable ;
                      }

                      leaf lst-flag {
                        description 'The lst flag of the ethernet parameter.' ;
                        type enumeration {
                          enum disable {
                            value 0 ;
                            description 'Lst flag of the ethernet parameter is disable.' ;
                          }

                          enum enable {
                            value 1 ;
                            description 'Lst flag of the ethernet parameter is enable.' ;
                          }

                        }

                        default disable ;
                      }

                      leaf lst-holdoff {
                        type uint16 {
                          range 1..1000 {
                            description 'The range of lst holdoff time.' ;
                          }

                        }

                        description 'Lst holdoff time.' ;
                        units 10ms ;
                        ncd:revise-date 2025-06-19 ;
                      }

                      leaf fault-spread {
                        description 'Fault transfer switch between the AC and the PW (disable: AC is associated with PW status, enable: AC and PW status are not affected by each other).' ;
                        type enumeration {
                          enum disable {
                            value 0 ;
                            description 'The fault is spread.' ;
                          }

                          enum enable {
                            value 1 ;
                            description 'The fault is not spread.' ;
                          }

                        }

                        default disable ;
                      }

                      leaf ingress-adjust-push {
                        description 'The ingress adjust push flag of the ethernet parameter.' ;
                        type enumeration {
                          enum disable {
                            value 0 ;
                            description 'The ingress adjust push flag of the ethernet parameter is disable.' ;
                          }

                          enum enable {
                            value 1 ;
                            description 'The ingress adjust push flag of the ethernet parameter is enable.' ;
                          }

                        }

                        default disable ;
                      }

                      leaf push-vlan-id {
                        description 'The ingress adjust push VLAN ID of the ethernet parameter.' ;
                        type uint16 {
                          range 1..4094 {
                            description 'The range of push VLAN ID is 1-4094.' ;
                          }

                        }

                      }

                      leaf ingress-adjust-rewrite {
                        description 'The ingress adjust rewrite flag of the ethernet parameter.' ;
                        type enumeration {
                          enum disable {
                            value 0 ;
                            description 'The ingress adjust rewrite flag of the ethernet parameter is disable.' ;
                          }

                          enum enable {
                            value 1 ;
                            description 'The ingress adjust rewrite flag of the ethernet parameter is enable.' ;
                          }

                        }

                        default disable ;
                      }

                      leaf rewrite-vlan-id {
                        description 'The ingress adjust rewrite VLAN ID of the ethernet parameter.' ;
                        type uint16 {
                          range 1..4094 {
                            description 'The range of rewrite VLAN ID is 1-4094.' ;
                          }

                        }

                      }

                      leaf rewrite-outer-vlanid-flag {
                        description 'Rewrite outer VLAN ID flag.' ;
                        type enumeration {
                          enum disable {
                            value 0 ;
                            description 'Rewrite outer VLAN ID flag is disable.' ;
                          }

                          enum enable {
                            value 1 ;
                            description 'Rewrite outer VLAN ID flag is enable.' ;
                          }

                        }

                        default disable ;
                        ncd:revise-date 2021-01-05 ;
                      }

                      leaf ingress-adjust-tag-as-payload {
                        description 'The ingress tag as payload flag of the ethernet parameter.' ;
                        type enumeration {
                          enum disable {
                            value 0 ;
                            description 'The ingress tag as payload flag is disable.' ;
                          }

                          enum all {
                            value 1 ;
                            description 'The ingress tag as payload flag is from outer most.' ;
                          }

                          enum from-sub-layer {
                            value 2 ;
                            description 'The ingress tag as payload flag is from sub layer.' ;
                          }

                        }

                        default disable ;
                      }

                      leaf ingress-adjust-drop-tagged-frames {
                        description 'The ingress adjust drop tagged frames flag of the ethernet.' ;
                        type enumeration {
                          enum disable {
                            value 0 ;
                            description 'The ingress adjust drop tagged frames flag is disable.' ;
                          }

                          enum enable {
                            value 1 ;
                            description 'The ingress adjust drop tagged frames flag is enable.' ;
                          }

                        }

                      }

                      leaf egress-keep-normalized-tag {
                        description 'To keep the normalized tag unchanged onto the egress AC.' ;
                        type enumeration {
                          enum disable {
                            value 0 ;
                            description 'To keep the normalized tag unchanged onto the egress AC is disable.' ;
                          }

                          enum enable {
                            value 1 ;
                            description 'To keep the normalized tag unchanged onto the egress AC is enable.' ;
                          }

                        }

                        default disable ;
                        ncd:revise-date 2021-01-05 ;
                      }

                      leaf monitor-ip {
                        description 'The NNI ping monitor IP address.' ;
                        type ncd:ipv4-address-none-zero ;

                      }

                      leaf monitor-mac {
                        description 'The NNI ping monitor MAC address.' ;
                        type ncd:mac-address-none-zero ;

                      }

                      leaf monitor-mode {
                        description 'The NNI ping monitor mode.' ;
                        type enumeration {
                          enum master-slave {
                            value 0 ;
                            description 'The monitor mode is master-slave.' ;
                          }

                          enum load-balance {
                            value 1 ;
                            description 'The monitor mode is load-balance.' ;
                          }

                        }

                        default master-slave ;
                      }

                      leaf lst-for-etree {
                        description 'The lst-for-etree of the ethernet parameter.' ;
                        type enumeration {
                          enum disable {
                            value 0 ;
                            description 'The lst-for-etree is disable.' ;
                          }

                          enum enable {
                            value 1 ;
                            description 'The lst-for-etree is enable.' ;
                          }

                        }

                        default disable ;
                        ncd:revise-date 2021-04-02 ;
                      }

                      container traffic-statistics-params {
                        if-feature ac-traffic-statistics ;

                        description 'The traffic statistics parameters of ethernet access.' ;
                        leaf unicast-inrate-bps {
                          description 'The unicast input bytes rate.' ;
                          type uint64 {
                            range 1..18446744073709551615 {
                              description 'The range of unicast input bytes.' ;
                            }

                          }

                          units bps ;
                        }

                        leaf unicast-inrate-pps {
                          description 'The unicast input packets rate.' ;
                          type uint32 {
                            range 1..4294967295 {
                              description 'The range of unicast input packets rate.' ;
                            }

                          }

                          units pps ;
                        }

                        leaf broadcast-inrate-bps {
                          description 'The broadcast input packets rate.' ;
                          type uint64 {
                            range 1..18446744073709551615 {
                              description 'The range of broadcast input bytes.' ;
                            }

                          }

                          units bps ;
                        }

                        leaf broadcast-inrate-pps {
                          description 'The broadcast input packets rate.' ;
                          type uint32 {
                            range 1..4294967295 {
                              description 'The range of broadcast input packets rate.' ;
                            }

                          }

                          units pps ;
                        }

                        leaf drop-inrate-bps {
                          description 'The drop input bytes rate.' ;
                          type uint64 {
                            range 1..18446744073709551615 {
                              description 'The range of drop input bytes.' ;
                            }

                          }

                          units bps ;
                        }

                        leaf drop-inrate-pps {
                          description 'The drop input packets rate.' ;
                          type uint32 {
                            range 1..4294967295 {
                              description 'The range of drop input packets rate.' ;
                            }

                          }

                          units pps ;
                        }

                      }

                      container udp-echo {
                        description 'Configure UDP echo function.' ;
                        leaf echo-ip {
                          description 'UDP echo IP address.' ;
                          type ncd:ipv4-address-none-zero ;

                        }

                        leaf echo-mac {
                          description 'UDP echo MAC address.' ;
                          type ncd:mac-address-none-zero ;

                        }

                        leaf echo-port-number {
                          description 'UDP echo port number.' ;
                          type uint16 {
                            range 1..65535 {
                              description 'UDP echo port number range.' ;
                            }

                          }

                        }

                      }

                      container l2protocol-control-policy {
                        if-feature l2cp-drop ;

                        description 'L2protocol packet filtering function.' ;
                        leaf wildcard {
                          description 'Configure the wildcard mask filter rules.' ;
                          type ncd:mac-address-none-zero ;

                          if-feature l2cp-drop-subset {
                            ncd:revise-date 2025-06-09 ;
                          }

                        }

                        leaf abm {
                          description 'All bridge multicast frame protocol packet filtering.' ;
                          type enumeration {
                            enum tunnelled {
                              value 0 ;
                              description 'All bridge multicast frame protocol packet filtering is tunnelled.' ;
                            }

                            enum dropped {
                              value 1 ;
                              description 'All bridge multicast frame protocol packet filtering is dropped.' ;
                            }

                            enum terminated {
                              value 2 ;
                              description 'All bridge multicast frame protocol packet filtering is terminated.' ;
                            }

                          }

                          if-feature l2cp-drop-subset {
                            ncd:revise-date 2025-06-09 ;
                          }

                        }

                        leaf dot1x {
                          description '802.1x protocol frame packet filtering.' ;
                          type enumeration {
                            enum tunnelled {
                              value 0 ;
                              description '802.1x protocol frame packet filtering is tunnelled.' ;
                            }

                            enum dropped {
                              value 1 ;
                              description '802.1x protocol frame packet filtering is dropped.' ;
                            }

                            enum terminated {
                              value 2 ;
                              description '802.1x protocol frame packet filtering is terminated.' ;
                            }

                          }

                        }

                        leaf dot3x {
                          description '802.3x protocol frame packet filtering.' ;
                          type enumeration {
                            enum tunnelled {
                              value 0 ;
                              description '802.3x protocol frame packet filtering is tunnelled.' ;
                            }

                            enum dropped {
                              value 1 ;
                              description '802.3x protocol frame packet filtering is dropped.' ;
                            }

                            enum terminated {
                              value 2 ;
                              description '802.3x protocol frame packet filtering is terminated.' ;
                            }

                          }

                          if-feature l2cp-drop-subset {
                            ncd:revise-date 2025-06-09 ;
                          }

                        }

                        leaf garp {
                          description 'GARP protocol packet filtering.' ;
                          type enumeration {
                            enum tunnelled {
                              value 0 ;
                              description 'GARP protocol packet filtering is tunnelled.' ;
                            }

                            enum dropped {
                              value 1 ;
                              description 'GARP protocol packet filtering is dropped.' ;
                            }

                            enum terminated {
                              value 2 ;
                              description 'GARP protocol packet filtering is terminated.' ;
                            }

                          }

                          if-feature l2cp-drop-subset {
                            ncd:revise-date 2025-06-09 ;
                          }

                        }

                        leaf gmrp {
                          description 'GMRP protocol packet filtering.' ;
                          type enumeration {
                            enum tunnelled {
                              value 0 ;
                              description 'GMRP protocol packet filtering is tunnelled.' ;
                            }

                            enum dropped {
                              value 1 ;
                              description 'GMRP protocol packet filtering is dropped.' ;
                            }

                            enum terminated {
                              value 2 ;
                              description 'GMRP protocol packet filtering is terminated.' ;
                            }

                          }

                        }

                        leaf gvrp {
                          description 'GVRP protocol packet filtering.' ;
                          type enumeration {
                            enum tunnelled {
                              value 0 ;
                              description 'GVRP protocol packet filtering is tunnelled.' ;
                            }

                            enum dropped {
                              value 1 ;
                              description 'GVRP protocol packet filtering is dropped.' ;
                            }

                            enum terminated {
                              value 2 ;
                              description 'GVRP protocol packet filtering is terminated.' ;
                            }

                          }

                        }

                        leaf cisco {
                          description 'CISCO protocol packet filtering.' ;
                          type enumeration {
                            enum tunnelled {
                              value 0 ;
                              description 'CISCO protocol packet filtering is tunnelled.' ;
                            }

                            enum dropped {
                              value 1 ;
                              description 'CISCO protocol packet filtering is dropped.' ;
                            }

                            enum terminated {
                              value 2 ;
                              description 'CISCO protocol packet filtering is terminated.' ;
                            }

                          }

                          if-feature l2cp-drop-subset {
                            ncd:revise-date 2025-06-09 ;
                          }

                        }

                        leaf dldp {
                          description 'DLDP protocol packet filtering.' ;
                          type enumeration {
                            enum tunnelled {
                              value 0 ;
                              description 'DLDP protocol packet filtering is tunnelled.' ;
                            }

                            enum dropped {
                              value 1 ;
                              description 'DLDP protocol packet filtering is dropped.' ;
                            }

                            enum terminated {
                              value 2 ;
                              description 'DLDP protocol packet filtering is terminated.' ;
                            }

                          }

                          if-feature l2cp-drop-subset {
                            ncd:revise-date 2025-06-09 ;
                          }

                        }

                        leaf efm {
                          description 'EFM protocol packet filtering.' ;
                          type enumeration {
                            enum tunnelled {
                              value 0 ;
                              description 'EFM protocol packet filtering is tunnelled.' ;
                            }

                            enum dropped {
                              value 1 ;
                              description 'EFM protocol packet filtering is dropped.' ;
                            }

                            enum terminated {
                              value 2 ;
                              description 'EFM protocol packet filtering is terminated.' ;
                            }

                          }

                        }

                        leaf cfm {
                          description 'CFM protocol packet filtering.' ;
                          type enumeration {
                            enum tunnelled {
                              value 0 ;
                              description 'EFM protocol packet filtering is tunnelled.' ;
                            }

                            enum dropped {
                              value 1 ;
                              description 'EFM protocol packet filtering is dropped.' ;
                            }

                            enum terminated {
                              value 2 ;
                              description 'EFM protocol packet filtering is terminated.' ;
                            }

                          }

                          if-feature l2cp-drop-subset {
                            ncd:revise-date 2025-06-09 ;
                          }

                        }

                        leaf pvst {
                          description 'PVST protocol packet filtering.' ;
                          type enumeration {
                            enum tunnelled {
                              value 0 ;
                              description 'PVST protocol packet filtering is tunnelled.' ;
                            }

                            enum dropped {
                              value 1 ;
                              description 'PVST protocol packet filtering is dropped.' ;
                            }

                            enum terminated {
                              value 2 ;
                              description 'PVST protocol packet filtering is terminated.' ;
                            }

                          }

                          if-feature l2cp-drop-subset {
                            ncd:revise-date 2025-06-09 ;
                          }

                        }

                        leaf zdp {
                          description 'ZDP protocol packet filtering.' ;
                          type enumeration {
                            enum tunnelled {
                              value 0 ;
                              description 'ZDP protocol packet filtering is tunnelled.' ;
                            }

                            enum dropped {
                              value 1 ;
                              description 'ZDP protocol packet filtering is dropped.' ;
                            }

                            enum terminated {
                              value 2 ;
                              description 'ZDP protocol packet filtering is terminated.' ;
                            }

                          }

                          if-feature l2cp-drop-subset {
                            ncd:revise-date 2025-06-09 ;
                          }

                        }

                        leaf lacp {
                          description 'LACP protocol packet filtering.' ;
                          type enumeration {
                            enum tunnelled {
                              value 0 ;
                              description 'LACP protocol packet filtering is tunnelled.' ;
                            }

                            enum dropped {
                              value 1 ;
                              description 'LACP protocol packet filtering is dropped.' ;
                            }

                            enum terminated {
                              value 2 ;
                              description 'LACP protocol packet filtering is terminated.' ;
                            }

                          }

                        }

                        leaf lldp {
                          description 'LLDP protocol packet filtering.' ;
                          type enumeration {
                            enum tunnelled {
                              value 0 ;
                              description 'LLDP protocol packet filtering is tunnelled.' ;
                            }

                            enum dropped {
                              value 1 ;
                              description 'LLDP protocol packet filtering is dropped.' ;
                            }

                            enum terminated {
                              value 2 ;
                              description 'LLDP protocol packet filtering is terminated.' ;
                            }

                          }

                        }

                        leaf stp {
                          description 'STP protocol packet filtering.' ;
                          type enumeration {
                            enum tunnelled {
                              value 0 ;
                              description 'STP protocol packet filtering is tunnelled.' ;
                            }

                            enum dropped {
                              value 1 ;
                              description 'STP protocol packet filtering is dropped.' ;
                            }

                            enum terminated {
                              value 2 ;
                              description 'STP protocol packet filtering is terminated.' ;
                            }

                            enum tunnelled-monitored {
                              value 3 ;
                              description 'STP protocol packet filtering is tunnelled-monitored.' ;
                            }

                          }

                        }

                        leaf erps {
                          description 'ERPS protocol packet filtering.' ;
                          type enumeration {
                            enum tunnelled {
                              value 0 ;
                              description 'ERPS protocol packet filtering is tunnelled.' ;
                            }

                            enum dropped {
                              value 1 ;
                              description 'ERPS protocol packet filtering is dropped.' ;
                            }

                            enum terminated {
                              value 2 ;
                              description 'ERPS protocol packet filtering is terminated.' ;
                            }

                          }

                          ncd:revise-date 2016-01-14 ;
                        }

                        leaf udld {
                          description 'UDLD protocol packet filtering.' ;
                          type enumeration {
                            enum tunnelled {
                              value 0 ;
                              description 'UDLD protocol packet filtering is tunnelled.' ;
                            }

                            enum dropped {
                              value 1 ;
                              description 'UDLD protocol packet filtering is dropped.' ;
                            }

                            enum terminated {
                              value 2 ;
                              description 'UDLD protocol packet filtering is terminated.' ;
                            }

                          }

                          if-feature l2cp-drop-subset {
                            ncd:revise-date 2025-06-09 ;
                          }

                          ncd:revise-date 2016-01-14 ;
                        }

                        leaf vtp {
                          description 'VTP protocol packet filtering.' ;
                          type enumeration {
                            enum tunnelled {
                              value 0 ;
                              description 'VTP protocol packet filtering is tunnelled.' ;
                            }

                            enum dropped {
                              value 1 ;
                              description 'VTP protocol packet filtering is dropped.' ;
                            }

                            enum terminated {
                              value 2 ;
                              description 'VTP protocol packet filtering is terminated.' ;
                            }

                          }

                          if-feature l2cp-drop-subset {
                            ncd:revise-date 2025-06-09 ;
                          }

                          ncd:revise-date 2016-01-14 ;
                        }

                        leaf zesr {
                          description 'ZESR protocol packet filtering.' ;
                          type enumeration {
                            enum tunnelled {
                              value 0 ;
                              description 'ZESR protocol packet filtering is tunnelled.' ;
                            }

                            enum dropped {
                              value 1 ;
                              description 'ZESR protocol packet filtering is dropped.' ;
                            }

                            enum terminated {
                              value 2 ;
                              description 'ZESR protocol packet filtering is terminated.' ;
                            }

                          }

                          if-feature l2cp-drop-subset {
                            ncd:revise-date 2025-06-09 ;
                          }

                          ncd:revise-date 2016-01-14 ;
                        }

                        leaf l2bfd {
                          description 'L2BFD protocol packet filtering.' ;
                          type enumeration {
                            enum tunnelled {
                              value 0 ;
                              description 'L2BFD protocol packet filtering is tunnelled.' ;
                            }

                            enum terminated {
                              value 2 ;
                              description 'L2BFD protocol packet filtering is terminated.' ;
                            }

                          }

                          if-feature l2cp-drop-subset {
                            ncd:revise-date 2025-06-09 ;
                          }

                          ncd:revise-date 2017-09-20 ;
                        }

                        leaf mac-control {
                          description 'MAC-control protocol packet filtering.' ;
                          type enumeration {
                            enum tunnelled {
                              value 0 ;
                              description 'MAC-control protocol packet filtering is tunnelled.' ;
                            }

                            enum dropped {
                              value 1 ;
                              description 'MAC-control protocol packet filtering is dropped.' ;
                            }

                            enum terminated {
                              value 2 ;
                              description 'MAC-control protocol packet filtering is terminated.' ;
                            }

                          }

                          if-feature l2cp-drop-subset {
                            ncd:revise-date 2025-06-09 ;
                          }

                          ncd:revise-date 2023-03-25 ;
                        }

                        container user-protocol-template {
                          description 'The template of user protocol.' ;
                          presence user-protocol-template ;
                          leaf user-protocol-name {
                            description 'The class name of user protocol.' ;
                            type string {
                              length 1..31 {
                                description 'The length of user protocol class name.' ;
                              }

                            }

                            mandatory true ;
                          }

                          leaf user-protocol-action {
                            description 'User protocol template action.' ;
                            type enumeration {
                              enum tunnelled {
                                value 0 ;
                                description 'User protocol template action is tunnelled.' ;
                              }

                              enum dropped {
                                value 1 ;
                                description 'User protocol template action is dropped.' ;
                              }

                              enum terminated {
                                value 2 ;
                                description 'User protocol template action is terminated.' ;
                              }

                            }

                            mandatory true ;
                          }

                          if-feature l2cp-drop-subset {
                            ncd:revise-date 2025-06-09 ;
                          }

                          ncd:revise-date 2016-10-14 ;
                        }

                        ncd:revise-date 2015-11-10 ;
                      }

                      container hard-pipe {
                        description 'Configure hard pipe info.' ;
                        presence hard-pipe ;
                        leaf bandwidth {
                          description 'The bandwidth of hard pipe.' ;
                          type uint32 {
                            range 1..4294967295 {
                              description 'The range of bandwidth.' ;
                            }

                          }

                          mandatory true ;
                        }

                        leaf expand-ratio {
                          description 'The expand-ratio of hard pipe.' ;
                          type uint8 {
                            range 1..100 {
                              description 'The range of expand ratio.' ;
                            }

                          }

                          mandatory true ;
                        }

                        ncd:revise-date 2016-12-15 ;
                      }

                    }

                  }

                  case tdm {
                    if-feature tdm ;

                    description 'The TDM access type.' ;
                    container tdm-params {
                      description 'TDM access type parameters.' ;
                      presence tdm-params ;
                      leaf tdm {
                        description 'TDM access type.' ;
                        type empty ;

                        mandatory true ;
                      }

                      leaf track-name {
                        description 'The name of the track object which bind to the AC.' ;
                        type string {
                          length 1..31 {
                            description 'The length of the track name.' ;
                          }

                        }

                      }

                      leaf oam-mapping {
                        description 'The oam-mapping flag of the TDM parameter.' ;
                        type enumeration {
                          enum disable {
                            value 0 ;
                            description 'The oam-mapping flag of the TDM parameter is disable.' ;
                          }

                          enum enable {
                            value 1 ;
                            description 'The oam-mapping flag of the TDM parameter is enable.' ;
                          }

                        }

                        default disable ;
                      }

                      leaf traffic-enable {
                        description 'The traffic statistics enable flag of the TDM parameter.' ;
                        type enumeration {
                          enum disable {
                            value 0 ;
                            description 'The traffic statistics flag is disable.' ;
                          }

                          enum enable {
                            value 1 ;
                            description 'The traffic statistics flag is enable.' ;
                          }

                        }

                        default disable ;
                      }

                      leaf fault-spread {
                        description 'Fault transfer switch between the AC and the PW (disable: AC is associated with PW status, enable: AC and PW status are not affected by each other).' ;
                        type enumeration {
                          enum disable {
                            value 0 ;
                            description 'The fault is spread.' ;
                          }

                          enum enable {
                            value 1 ;
                            description 'The fault is not spread.' ;
                          }

                        }

                        default disable ;
                      }

                      leaf distribute-period {
                        description 'The distribute period value of the TDM parameter.' ;
                        type uint8 {
                          range 1..64 {
                            description 'The distribute period value.' ;
                          }

                        }

                        units 125us ;
                      }

                      leaf jitter-buffer {
                        description 'The jitter buffer value of the TDM parameter.' ;
                        type uint16 {
                          range 1..400 {
                            description 'The jitter buffer value.' ;
                          }

                        }

                        units 125us ;
                        default 20 ;
                      }

                      leaf rtp-header {
                        description 'Configure the RTP header or not.' ;
                        type enumeration {
                          enum disable {
                            value 0 ;
                            description 'The RTP header is disable.' ;
                          }

                          enum enable {
                            value 1 ;
                            description 'The RTP header is enable.' ;
                          }

                        }

                        default disable ;
                      }

                      leaf rtp-timestamp {
                        description 'The RTP timestamp mode of the TDM parameter.' ;
                        type enumeration {
                          enum absolute {
                            value 1 ;
                            description 'RTP timestamp is absolute.' ;
                          }

                          enum differ {
                            value 2 ;
                            description 'RTP timestamp is differ.' ;
                          }

                        }

                      }

                      leaf idle-code {
                        if-feature idle-code-enum ;

                        description 'The idle code value of the TDM parameter.' ;
                        type enumeration {
                          enum 0xff {
                            value 0 ;
                            description 'The idle code is 0xff.' ;
                          }

                          enum 0x7e {
                            value 1 ;
                            description 'The idle code is 0x7e.' ;
                          }

                        }

                        default 0xff ;
                      }

                      leaf idle-code-new {
                        if-feature idle-code-range ;

                        description 'The idle code value of the TDM parameter.' ;
                        type uint8 {
                          range 0..255 {
                            description 'The value of idle code.' ;
                          }

                        }

                        default 255 ;
                        ncd:revise-date 2019-04-09 ;
                      }

                      leaf mpls-exp-value {
                        description 'The MPLS EXP value of the TDM parameter.' ;
                        type enumeration {
                          enum be {
                            value 0 ;
                            description 'The MPLS EXP value is be.' ;
                          }

                          enum af1 {
                            value 1 ;
                            description 'The MPLS EXP value is af1.' ;
                          }

                          enum af2 {
                            value 2 ;
                            description 'The MPLS EXP value is af2.' ;
                          }

                          enum af3 {
                            value 3 ;
                            description 'The MPLS EXP value is af3.' ;
                          }

                          enum af4 {
                            value 4 ;
                            description 'The MPLS EXP value is af4.' ;
                          }

                          enum ef {
                            value 5 ;
                            description 'The MPLS EXP value is ef.' ;
                          }

                          enum cs6 {
                            value 6 ;
                            description 'The MPLS EXP value is cs6.' ;
                          }

                          enum cs7 {
                            value 7 ;
                            description 'The MPLS EXP value is cs7.' ;
                          }

                        }

                        default ef ;
                      }

                      leaf timeslot-compatible {
                        description 'The time slot compatible mode of the TDM parameter.' ;
                        type enumeration {
                          enum disable {
                            value 0 ;
                            description 'The timeslot compatible mode is disable.' ;
                          }

                          enum enable {
                            value 1 ;
                            description 'The timeslot compatible mode is enable.' ;
                          }

                        }

                        default disable ;
                      }

                      container traffic-statistics-params {
                        if-feature ac-traffic-statistics ;

                        if-feature tdm ;

                        description 'The traffic statistics parameters of TDM access.' ;
                        leaf unicast-inrate-bps {
                          description 'The unicast input bytes rate.' ;
                          type uint64 {
                            range 1..18446744073709551615 {
                              description 'The range of unicast input bytes.' ;
                            }

                          }

                          units bps ;
                        }

                        leaf unicast-inrate-pps {
                          description 'The unicast input packets rate.' ;
                          type uint32 {
                            range 1..4294967295 {
                              description 'The range of unicast input packets rate.' ;
                            }

                          }

                          units pps ;
                        }

                        leaf broadcast-inrate-bps {
                          description 'The broadcast input bytes rate.' ;
                          type uint64 {
                            range 1..18446744073709551615 {
                              description 'The range of broadcast input bytes.' ;
                            }

                          }

                          units bps ;
                        }

                        leaf broadcast-inrate-pps {
                          description 'The broadcast input packets rate.' ;
                          type uint32 {
                            range 1..4294967295 {
                              description 'The range of broadcast input packets rate.' ;
                            }

                          }

                          units pps ;
                        }

                        leaf drop-inrate-bps {
                          description 'The drop input bytes rate.' ;
                          type uint64 {
                            range 1..18446744073709551615 {
                              description 'The range of drop input bytes.' ;
                            }

                          }

                          units bps ;
                        }

                        leaf drop-inrate-pps {
                          description 'The drop input packets rate.' ;
                          type uint32 {
                            range 1..4294967295 {
                              description 'The range of drop input packets rate.' ;
                            }

                          }

                          units pps ;
                        }

                      }

                      container hard-pipe {
                        description 'Configure hard pipe info.' ;
                        leaf hard-pipe-flag {
                          description 'The hard pipe enable flag of the AC.' ;
                          type enumeration {
                            enum disable {
                              value 0 ;
                              description 'The hard pipe of the AC is disable.' ;
                            }

                            enum enable {
                              value 1 ;
                              description 'The hard pipe of the AC is enable.' ;
                            }

                          }

                          default disable ;
                        }

                        ncd:revise-date 2016-12-15 ;
                      }

                    }

                  }

                  case atm {
                    if-feature atm ;

                    description 'The ATM access type.' ;
                    container atm-params {
                      description 'ATM access type parameters.' ;
                      presence atm-params ;
                      leaf atm {
                        description 'ATM access type.' ;
                        type empty ;

                        mandatory true ;
                      }

                      leaf fault-spread {
                        description 'Fault transfer switch between the AC and the PW (disable: AC is associated with PW status, enable: AC and PW status are not affected by each other).' ;
                        type enumeration {
                          enum disable {
                            value 0 ;
                            description 'The fault is spread.' ;
                          }

                          enum enable {
                            value 1 ;
                            description 'The fault is not spread.' ;
                          }

                        }

                        default disable ;
                      }

                      leaf traffic-enable {
                        description 'The traffic statistics enable flag of the ATM parameter.' ;
                        type enumeration {
                          enum disable {
                            value 0 ;
                            description 'The traffic statistics flag is disable.' ;
                          }

                          enum enable {
                            value 1 ;
                            description 'The traffic statistics flag is enable.' ;
                          }

                        }

                        default disable ;
                      }

                      leaf max-cells {
                        description 'Configure the maximum ATM cells to concatenate.' ;
                        type uint32 {
                          range 1..28 {
                            description 'Max cells number range.' ;
                          }

                        }

                      }

                      container traffic-statistics-params {
                        if-feature ac-traffic-statistics ;

                        if-feature atm ;

                        description 'The traffic statistics parameters of ATM access.' ;
                        leaf unicast-inrate-bps {
                          description 'The unicast input bytes rate.' ;
                          type uint64 {
                            range 1..18446744073709551615 {
                              description 'The range of unicast input bytes.' ;
                            }

                          }

                          units bps ;
                        }

                        leaf unicast-inrate-pps {
                          description 'The unicast input packets rate.' ;
                          type uint32 {
                            range 1..4294967295 {
                              description 'The range of unicast input packets rate.' ;
                            }

                          }

                          units pps ;
                        }

                        leaf broadcast-inrate-bps {
                          description 'The broadcast input bytes rate.' ;
                          type uint64 {
                            range 1..18446744073709551615 {
                              description 'The range of broadcast input bytes.' ;
                            }

                          }

                          units bps ;
                        }

                        leaf broadcast-inrate-pps {
                          description 'The broadcast input packets rate.' ;
                          type uint32 {
                            range 1..4294967295 {
                              description 'The range of broadcast input packets rate.' ;
                            }

                          }

                          units pps ;
                        }

                        leaf drop-inrate-bps {
                          description 'The drop input bytes rate.' ;
                          type uint64 {
                            range 1..18446744073709551615 {
                              description 'The range of drop input bytes.' ;
                            }

                          }

                          units bps ;
                        }

                        leaf drop-inrate-pps {
                          description 'The drop input packets rate.' ;
                          type uint32 {
                            range 1..4294967295 {
                              description 'The range of drop input packets rate.' ;
                            }

                          }

                          units pps ;
                        }

                      }

                      container hard-pipe {
                        description 'Configure hard pipe info.' ;
                        leaf hard-pipe-flag {
                          description 'The hard pipe enable flag of the AC.' ;
                          type enumeration {
                            enum disable {
                              value 0 ;
                              description 'The hard pipe of the AC is disable.' ;
                            }

                            enum enable {
                              value 1 ;
                              description 'The hard pipe of the AC is enable.' ;
                            }

                          }

                          default disable ;
                        }

                        ncd:revise-date 2016-12-15 ;
                      }

                    }

                  }

                  case ppp {
                    if-feature ppp ;

                    description 'The PPP access type.' ;
                    container ppp-params {
                      description 'PPP access type parameters.' ;
                      presence ppp-params ;
                      leaf ppp {
                        description 'PPP access type.' ;
                        type empty ;

                        mandatory true ;
                      }

                      leaf fault-spread {
                        description 'Fault transfer switch between the AC and the PW (disable: AC is associated with PW status, enable: AC and PW status are not affected by each other).' ;
                        type enumeration {
                          enum disable {
                            value 0 ;
                            description 'The fault is spread.' ;
                          }

                          enum enable {
                            value 1 ;
                            description 'The fault is not spread.' ;
                          }

                        }

                        default disable ;
                      }

                      leaf traffic-enable {
                        description 'The traffic statistics enable flag of the PPP parameter.' ;
                        type enumeration {
                          enum disable {
                            value 0 ;
                            description 'The traffic statistics flag is disable.' ;
                          }

                          enum enable {
                            value 1 ;
                            description 'The traffic statistics flag is enable.' ;
                          }

                        }

                        default disable ;
                      }

                      container traffic-statistics-params {
                        if-feature ac-traffic-statistics ;

                        if-feature ppp ;

                        description 'The traffic statistics parameters of PPP access.' ;
                        leaf unicast-inrate-bps {
                          description 'The unicast input bytes rate.' ;
                          type uint64 {
                            range 1..18446744073709551615 {
                              description 'The range of unicast input bytes.' ;
                            }

                          }

                          units bps ;
                        }

                        leaf unicast-inrate-pps {
                          description 'The unicast input packets rate.' ;
                          type uint32 {
                            range 1..4294967295 {
                              description 'The range of unicast input packets rate.' ;
                            }

                          }

                          units pps ;
                        }

                        leaf broadcast-inrate-bps {
                          description 'The broadcast input bytes rate.' ;
                          type uint64 {
                            range 1..18446744073709551615 {
                              description 'The range of broadcast input bytes.' ;
                            }

                          }

                          units bps ;
                        }

                        leaf broadcast-inrate-pps {
                          description 'The broadcast input packets rate.' ;
                          type uint32 {
                            range 1..4294967295 {
                              description 'The range of broadcast input packets rate.' ;
                            }

                          }

                          units pps ;
                        }

                        leaf drop-inrate-bps {
                          description 'The drop input bytes rate.' ;
                          type uint64 {
                            range 1..18446744073709551615 {
                              description 'The range of drop input bytes.' ;
                            }

                          }

                          units bps ;
                        }

                        leaf drop-inrate-pps {
                          description 'The drop input packets rate.' ;
                          type uint32 {
                            range 1..4294967295 {
                              description 'The range of drop input packets rate.' ;
                            }

                          }

                          units pps ;
                        }

                      }

                      container hard-pipe {
                        description 'Configure hard pipe info.' ;
                        leaf hard-pipe-flag {
                          description 'The hard pipe enable flag of the AC.' ;
                          type enumeration {
                            enum disable {
                              value 0 ;
                              description 'The hard pipe of the AC is disable.' ;
                            }

                            enum enable {
                              value 1 ;
                            }

                          }

                          default disable ;
                        }

                        ncd:revise-date 2016-12-15 ;
                      }

                    }

                  }

                  case hdlc {
                    if-feature hdlc ;

                    description 'The HDLC access type.' ;
                    container hdlc-params {
                      description 'HDLC access type parameters.' ;
                      presence hdlc-params ;
                      leaf hdlc {
                        description 'HDLC access type.' ;
                        type empty ;

                        mandatory true ;
                      }

                      leaf fault-spread {
                        description 'Fault transfer switch between the AC and the PW (disable: AC is associated with PW status, enable: AC and PW status are not affected by each other).' ;
                        type enumeration {
                          enum disable {
                            value 0 ;
                            description 'The fault is spread.' ;
                          }

                          enum enable {
                            value 1 ;
                            description 'The fault is not spread.' ;
                          }

                        }

                        default disable ;
                      }

                      leaf traffic-enable {
                        description 'The traffic statistics enable flag of the HDLC parameter.' ;
                        type enumeration {
                          enum disable {
                            value 0 ;
                            description 'The traffic statistics flag is disable.' ;
                          }

                          enum enable {
                            value 1 ;
                            description 'The traffic statistics flag is enable.' ;
                          }

                        }

                        default disable ;
                      }

                      container traffic-statistics-params {
                        if-feature ac-traffic-statistics ;

                        if-feature hdlc ;

                        description 'The traffic statistics parameters of HDLC access.' ;
                        leaf unicast-inrate-bps {
                          description 'The unicast input bytes rate.' ;
                          type uint64 {
                            range 1..18446744073709551615 {
                              description 'The range of unicast input bytes.' ;
                            }

                          }

                          units bps ;
                        }

                        leaf unicast-inrate-pps {
                          description 'The unicast input packets rate.' ;
                          type uint32 {
                            range 1..4294967295 {
                              description 'The range of unicast input packets rate.' ;
                            }

                          }

                          units pps ;
                        }

                        leaf broadcast-inrate-bps {
                          description 'The broadcast input bytes rate.' ;
                          type uint64 {
                            range 1..18446744073709551615 {
                              description 'The range of broadcast input bytes.' ;
                            }

                          }

                          units bps ;
                        }

                        leaf broadcast-inrate-pps {
                          description 'The broadcast input packets rate.' ;
                          type uint32 {
                            range 1..4294967295 {
                              description 'The range of broadcast input packets rate.' ;
                            }

                          }

                          units pps ;
                        }

                        leaf drop-inrate-bps {
                          description 'The drop input bytes rate.' ;
                          type uint64 {
                            range 1..18446744073709551615 {
                              description 'The range of drop input bytes.' ;
                            }

                          }

                          units bps ;
                        }

                        leaf drop-inrate-pps {
                          description 'The drop input packets rate.' ;
                          type uint32 {
                            range 1..4294967295 {
                              description 'The range of drop input packets rate.' ;
                            }

                          }

                          units pps ;
                        }

                      }

                      container hard-pipe {
                        description 'Configure hard pipe info.' ;
                        leaf hard-pipe-flag {
                          description 'The hard pipe enable flag of the AC.' ;
                          type enumeration {
                            enum disable {
                              value 0 ;
                              description 'The hard pipe of the AC is disable.' ;
                            }

                            enum enable {
                              value 1 ;
                              description 'The hard pipe of the AC is enable.' ;
                            }

                          }

                          default disable ;
                        }

                        ncd:revise-date 2016-12-15 ;
                      }

                    }

                  }

                  case fr {
                    if-feature fr ;

                    description 'The FR access type.' ;
                    container fr-params {
                      description 'FR access type parameters.' ;
                      presence fr-params ;
                      leaf fr {
                        description 'FR access type.' ;
                        type empty ;

                        mandatory true ;
                      }

                      leaf fault-spread {
                        description 'Fault transfer switch between the AC and the PW (disable: AC is associated with PW status, enable: AC and PW status are not affected by each other).' ;
                        type enumeration {
                          enum disable {
                            value 0 ;
                            description 'The fault is spread.' ;
                          }

                          enum enable {
                            value 1 ;
                            description 'The fault is not spread.' ;
                          }

                        }

                        default disable ;
                      }

                      leaf traffic-enable {
                        description 'The traffic statistics enable flag of the FR parameter.' ;
                        type enumeration {
                          enum disable {
                            value 0 ;
                            description 'The traffic statistics flag is disable.' ;
                          }

                          enum enable {
                            value 1 ;
                            description 'The traffic statistics flag is enable.' ;
                          }

                        }

                        default disable ;
                      }

                      container traffic-statistics-params {
                        if-feature ac-traffic-statistics ;

                        if-feature fr ;

                        description 'The traffic statistics parameters of FR access.' ;
                        leaf unicast-inrate-bps {
                          description 'The unicast input bytes rate.' ;
                          type uint64 {
                            range 1..18446744073709551615 {
                              description 'The range of unicast input bytes.' ;
                            }

                          }

                          units bps ;
                        }

                        leaf unicast-inrate-pps {
                          description 'The unicast input packets rate.' ;
                          type uint32 {
                            range 1..4294967295 {
                              description 'The range of unicast input packets rate.' ;
                            }

                          }

                          units pps ;
                        }

                        leaf broadcast-inrate-bps {
                          description 'The broadcast input bytes rate.' ;
                          type uint64 {
                            range 1..18446744073709551615 {
                              description 'The range of broadcast input bytes.' ;
                            }

                          }

                          units bps ;
                        }

                        leaf broadcast-inrate-pps {
                          description 'The broadcast input packets rate.' ;
                          type uint32 {
                            range 1..4294967295 {
                              description 'The range of broadcast input packets rate.' ;
                            }

                          }

                          units pps ;
                        }

                        leaf drop-inrate-bps {
                          description 'The drop input bytes rate.' ;
                          type uint64 {
                            range 1..18446744073709551615 {
                              description 'The range of broadcast input bytes.' ;
                            }

                          }

                          units bps ;
                        }

                        leaf drop-inrate-pps {
                          description 'The drop input packets rate.' ;
                          type uint32 {
                            range 1..4294967295 {
                              description 'The range of drop input packets rate.' ;
                            }

                          }

                          units pps ;
                        }

                      }

                      container hard-pipe {
                        description 'Configure hard pipe info.' ;
                        leaf hard-pipe-flag {
                          description 'The hard pipe enable flag of the AC.' ;
                          type enumeration {
                            enum disable {
                              value 0 ;
                              description 'The hard pipe of the AC is disable.' ;
                            }

                            enum enable {
                              value 1 ;
                              description 'The hard pipe of the AC is enable.' ;
                            }

                          }

                          default disable ;
                        }

                        ncd:revise-date 2016-12-15 ;
                      }

                    }

                  }

                  case iwf-ip {
                    if-feature inter-working-ip ;

                    description 'The IP inter-working access type.' ;
                    container iwf-ip-params {
                      description 'IP inter-working access type parameters.' ;
                      presence iwf-ip-params ;
                      leaf iwf-ip {
                        description 'IP inter-working access type.' ;
                        type empty ;

                        mandatory true ;
                      }

                      leaf track-name {
                        description 'The name of the track object which bind to the AC.' ;
                        type string {
                          length 1..31 {
                            description 'The length of track name.' ;
                          }

                        }

                      }

                      leaf oam-mapping {
                        description 'The oam-mapping flag of the IP inter-working parameter.' ;
                        type enumeration {
                          enum disable {
                            value 0 ;
                            description 'The oam-mapping flag of the IP inter-working parameter is disable.' ;
                          }

                          enum enable {
                            value 1 ;
                            description 'The oam-mapping flag of the IP inter-working parameter is enable.' ;
                          }

                        }

                        default disable ;
                      }

                      leaf fault-spread {
                        description 'Fault transfer switch between the AC and the PW (disable: AC is associated with PW status, enable: AC and PW status are not affected by each other).' ;
                        type enumeration {
                          enum disable {
                            value 0 ;
                            description 'The fault is spread.' ;
                          }

                          enum enable {
                            value 1 ;
                            description 'The fault is not spread.' ;
                          }

                        }

                        default disable ;
                      }

                      leaf traffic-enable {
                        description 'The traffic statistics enable flag of the IP inter-working parameter.' ;
                        type enumeration {
                          enum disable {
                            value 0 ;
                            description 'The traffic statistics flag is disable.' ;
                          }

                          enum enable {
                            value 1 ;
                            description 'The traffic statistics flag is enable.' ;
                          }

                        }

                        default disable ;
                      }

                      leaf local-ce-mac {
                        description 'The local CE MAC address of the IP inter-working parameter.' ;
                        type ncd:mac-address-none-zero ;

                      }

                      leaf remote-ip {
                        description 'The remote CE IP address of the IP inter-working parameter.' ;
                        type ncd:ipv4-address-none-zero ;

                      }

                      container traffic-statistics-params {
                        if-feature ac-traffic-statistics ;

                        if-feature inter-working-ip ;

                        description 'The traffic statistics parameters of IP inter-working access.' ;
                        leaf unicast-inrate-bps {
                          description 'The unicast input bytes rate.' ;
                          type uint64 {
                            range 1..18446744073709551615 {
                              description 'The range of unicast input bytes.' ;
                            }

                          }

                          units bps ;
                        }

                        leaf unicast-inrate-pps {
                          description 'The unicast input packets rate.' ;
                          type uint32 {
                            range 1..4294967295 {
                              description 'The range of unicast input packets rate.' ;
                            }

                          }

                          units pps ;
                        }

                        leaf broadcast-inrate-bps {
                          description 'The broadcast input bytes rate.' ;
                          type uint64 {
                            range 1..18446744073709551615 {
                              description 'The range of broadcast input bytes.' ;
                            }

                          }

                          units bps ;
                        }

                        leaf broadcast-inrate-pps {
                          description 'The broadcast input packets rate.' ;
                          type uint32 {
                            range 1..4294967295 {
                              description 'The range of broadcast input packets rate.' ;
                            }

                          }

                          units pps ;
                        }

                        leaf drop-inrate-bps {
                          description 'The drop input bytes rate.' ;
                          type uint64 {
                            range 1..18446744073709551615 {
                              description 'The range of drop input bytes.' ;
                            }

                          }

                          units bps ;
                        }

                        leaf drop-inrate-pps {
                          description 'The drop input packets rate.' ;
                          type uint32 {
                            range 1..4294967295 {
                              description 'The range of drop input packets rate.' ;
                            }

                          }

                          units pps ;
                        }

                      }

                    }

                  }

                  case iwf-eth {
                    if-feature inter-working-ethernet ;

                    description 'The ethernet inter-working access type.' ;
                    container iwf-eth-params {
                      description 'The ethernet inter-working access type parameters.' ;
                      presence iwf-eth-params ;
                      leaf iwf-eth {
                        description 'The ethernet inter-working access type.' ;
                        type empty ;

                        mandatory true ;
                      }

                      leaf fault-spread {
                        description 'Fault transfer switch between the AC and the PW (disable: AC is associated with PW status, enable: AC and PW status are not affected by each other).' ;
                        type enumeration {
                          enum disable {
                            value 0 ;
                            description 'The fault is spread.' ;
                          }

                          enum enable {
                            value 1 ;
                            description 'The fault is not spread.' ;
                          }

                        }

                        default disable ;
                      }

                      leaf traffic-enable {
                        description 'The traffic statistics enable flag of the inter-working parameter.' ;
                        type enumeration {
                          enum disable {
                            value 0 ;
                            description 'The traffic statistics flag is disable.' ;
                          }

                          enum enable {
                            value 1 ;
                            description 'The traffic statistics flag is enable.' ;
                          }

                        }

                        default disable ;
                      }

                      leaf proxy-mac {
                        description 'The proxy MAC address of the ethernet inter-working parameter.' ;
                        type ncd:mac-address-none-zero ;

                      }

                      leaf local-ip {
                        description 'The local CE IP address of the ethernet inter-working parameter.' ;
                        type ncd:ipv4-address-none-zero ;

                      }

                      leaf remote-ip {
                        description 'The remote CE IP address of the ethernet inter-working parameter.' ;
                        type ncd:ipv4-address-none-zero ;

                      }

                      leaf remote-mac {
                        description 'The proxy MAC address of the ethernet inter-working parameter.' ;
                        type ncd:mac-address-none-zero ;

                      }

                      leaf service-vlan {
                        description 'The service VLAN ID of the ethernet inter-working parameter.Invalid value is 65534.' ;
                        type uint32 {
                          range 0..4094 {
                            description 'The service VLAN value.' ;
                          }

                        }

                      }

                      container traffic-statistics-params {
                        if-feature ac-traffic-statistics ;

                        if-feature inter-working-ethernet ;

                        description 'The traffic statistics parameters of ethernet inter-working access.' ;
                        leaf unicast-inrate-bps {
                          description 'The unicast input bytes rate.' ;
                          type uint64 {
                            range 1..18446744073709551615 {
                              description 'The range of unicast input bytes.' ;
                            }

                          }

                          units bps ;
                        }

                        leaf unicast-inrate-pps {
                          description 'The unicast input packets rate.' ;
                          type uint32 {
                            range 1..4294967295 {
                              description 'The range of unicast input packets rate.' ;
                            }

                          }

                          units pps ;
                        }

                        leaf broadcast-inrate-bps {
                          description 'The broadcast input bytes rate.' ;
                          type uint64 {
                            range 1..18446744073709551615 {
                              description 'The range of broadcast input bytes.' ;
                            }

                          }

                          units bps ;
                        }

                        leaf broadcast-inrate-pps {
                          description 'The broadcast input packets rate.' ;
                          type uint32 {
                            range 1..4294967295 {
                              description 'The range of broadcast input packets rate.' ;
                            }

                          }

                          units pps ;
                        }

                        leaf drop-inrate-bps {
                          description 'The drop input bytes rate.' ;
                          type uint64 {
                            range 1..18446744073709551615 {
                              description 'The range of drop input bytes.' ;
                            }

                          }

                          units bps ;
                        }

                        leaf drop-inrate-pps {
                          description 'The drop input packets rate.' ;
                          type uint32 {
                            range 1..4294967295 {
                              description 'The range of drop input packets rate.' ;
                            }

                          }

                          units pps ;
                        }

                      }

                    }

                  }

                  case sonet-sdh {
                    if-feature sonet-sdh ;

                    description 'The SONET/SDH access type.' ;
                    container sonet-sdh-params {
                      description 'SONET/SDH access type parameters.' ;
                      presence sonet-sdh-params ;
                      leaf sonet-sdh {
                        description 'SONET/SDH access type.' ;
                        type empty ;

                        mandatory true ;
                      }

                      leaf traffic-enable {
                        description 'The traffic statistics enable flag of the SONET/SDH parameter.' ;
                        type enumeration {
                          enum disable {
                            value 0 ;
                            description 'The traffic statistics flag is disable.' ;
                          }

                          enum enable {
                            value 1 ;
                            description 'The traffic statistics flag is enable.' ;
                          }

                        }

                        default disable ;
                      }

                      leaf jitter-buffer {
                        description 'The jitter buffer value of the SONET/SDH parameter.' ;
                        type uint16 {
                          range 1..400 {
                            description 'The jitter buffer value.' ;
                          }

                        }

                        units 125us ;
                        default 20 ;
                      }

                      leaf rtp-header {
                        description 'Configure the RTP header or not.' ;
                        type enumeration {
                          enum disable {
                            value 0 ;
                            description 'The RTP header is disable.' ;
                          }

                          enum enable {
                            value 1 ;
                            description 'The RTP header is enable.' ;
                          }

                        }

                        default disable ;
                      }

                      leaf rtp-timestamp {
                        description 'The RTP timestamp mode of the SONET/SDH parameter.' ;
                        type enumeration {
                          enum absolute {
                            value 1 ;
                            description 'RTP timestamp is absolute.' ;
                          }

                          enum differ {
                            value 2 ;
                            description 'RTP timestamp is differ.' ;
                          }

                        }

                      }

                      leaf sdh-payload-compression {
                        description 'The SDH payload compression  mode of the SONET/SDH parameter.' ;
                        type enumeration {
                          enum basic {
                            value 0 ;
                            description 'The SONET/SDH mode is basic.' ;
                          }

                          enum fractional {
                            value 1 ;
                            description 'The SONET/SDH mode is fractional.' ;
                          }

                        }

                        default basic ;
                      }

                      leaf payload-bytes {
                        description 'The basic mode of SONET/SDH payload-size.' ;
                        type uint16 {
                          range 783..9170 {
                            description 'The basic mode of SONET/SDH payload-size value.' ;
                          }

                        }

                        units bytes ;
                      }

                      leaf payload-units {
                        description 'The fractional mode of SONET/SDH payload-size.' ;
                        type uint16 {
                          range 3..9 {
                            description 'The fractional mode of SONET/SDH payload-size value.' ;
                          }

                        }

                        units 783bytes ;
                      }

                      leaf fault-spread {
                        description 'Fault transfer switch between the AC and the PW (disable: AC is associated with PW status, enable: AC and PW status are not affected by each other).' ;
                        type enumeration {
                          enum disable {
                            value 0 ;
                            description 'The fault is spread.' ;
                          }

                          enum enable {
                            value 1 ;
                            description 'The fault is not spread.' ;
                          }

                        }

                        default disable ;
                        ncd:revise-date 2018-01-19 ;
                      }

                      leaf oam-mapping {
                        description 'The oam-mapping flag of the SONET/SDH parameter.' ;
                        type enumeration {
                          enum disable {
                            value 0 ;
                            description 'The oam-mapping flag of the IP inter-working parameter is disable.' ;
                          }

                          enum enable {
                            value 1 ;
                            description 'The oam-mapping flag of the IP inter-working parameter is enable.' ;
                          }

                        }

                        default disable ;
                        ncd:revise-date 2018-01-19 ;
                      }

                      leaf track-name {
                        description 'The name of the track object which bind to the AC.' ;
                        type string {
                          length 1..31 {
                            description 'The length of the track name.' ;
                          }

                        }

                        ncd:revise-date 2018-01-19 ;
                      }

                      leaf mpls-exp-value {
                        description 'The MPLS EXP value of the SONET/SDH parameter.' ;
                        type enumeration {
                          enum be {
                            value 0 ;
                            description 'The MPLS EXP value is be.' ;
                          }

                          enum af1 {
                            value 1 ;
                            description 'The MPLS EXP value is af1.' ;
                          }

                          enum af2 {
                            value 2 ;
                            description 'The MPLS EXP value is af2.' ;
                          }

                          enum af3 {
                            value 3 ;
                            description 'The MPLS EXP value is af3.' ;
                          }

                          enum af4 {
                            value 4 ;
                            description 'The MPLS EXP value is af4.' ;
                          }

                          enum ef {
                            value 5 ;
                            description 'The MPLS EXP value is ef.' ;
                          }

                          enum cs6 {
                            value 6 ;
                            description 'The MPLS EXP value is cs6.' ;
                          }

                          enum cs7 {
                            value 7 ;
                            description 'The MPLS EXP value is cs7.' ;
                          }

                        }

                        default ef ;
                        ncd:revise-date 2018-01-19 ;
                      }

                      container hard-pipe {
                        description 'Configure hard pipe info.' ;
                        leaf hard-pipe-flag {
                          description 'The hard pipe enable flag of the AC.' ;
                          type enumeration {
                            enum disable {
                              value 0 ;
                              description 'The hard pipe of the AC is disable.' ;
                            }

                            enum enable {
                              value 1 ;
                              description 'The hard pipe of the AC is enable.' ;
                            }

                          }

                          default disable ;
                        }

                        ncd:revise-date 2016-12-15 ;
                      }

                    }

                  }

                  case ethernet-cip {
                    if-feature ethernet-cip ;

                    description 'The ethernet-cip access type.' ;
                    container ethernet-cip-params {
                      description 'Ethernet-cip access type parameters.' ;
                      presence ethernet-cip-params ;
                      leaf ethernet-cip {
                        description 'Ethernet-cip access type.' ;
                        type empty ;

                        mandatory true ;
                      }

                      container access-source {
                        description 'Configure ethernet-cip access type.' ;
                        choice access-source-type {
                          description 'The ethernet-cip access type.' ;
                          case port {
                            description 'The ethernet-cip access type is port.' ;
                            container port-params {
                              description 'The ethernet-cip port parameters.' ;
                              presence port-params ;
                              leaf interface-name {
                                description 'The interface name of port access.' ;
                                type ncd:ifname {
                                  length 1..31 {
                                    description 'The length of interface name.' ;
                                  }

                                }

                                mandatory true ;
                              }

                              leaf port-vlan-id {
                                description 'The VLAN ID of port access.' ;
                                type uint16 {
                                  range 1..4094 {
                                    description 'The range of VLAN ID is 1-4094.' ;
                                  }

                                }

                              }

                            }

                          }

                          case slot {
                            description 'The ethernet-cip access type is slot.' ;
                            container slot-params {
                              description 'The ethernet-cip slot parameters.' ;
                              presence slot-params ;
                              leaf slot-number {
                                description 'The slot number,the invalid value is 0,the minimum and maximal value is controlled by the performance parameters.' ;
                                type uint32 {
                                  range 1..64 {
                                    description 'The slot number value.' ;
                                  }

                                }

                                mandatory true ;
                              }

                              leaf vlan-id {
                                description 'The VLAN ID of slot access.' ;
                                type uint16 {
                                  range 1..4094 {
                                    description 'The range of VLAN ID is 1-4094.' ;
                                  }

                                }

                                mandatory true ;
                              }

                            }

                          }

                        }

                      }

                    }

                  }

                  case tdm-relay {
                    if-feature tdm-relay ;

                    description 'The TDM relay access type.' ;
                    container tdm-relay-params {
                      description 'TDM relay access type parameters.' ;
                      presence tdm-relay-params ;
                      leaf tdm-relay {
                        description 'TDM relay access type.' ;
                        type empty ;

                        mandatory true ;
                      }

                      container access-source {
                        description 'Configure TDM relay access type.' ;
                        presence access-source ;
                        leaf dmac {
                          description 'The destination MAC address.' ;
                          type ncd:mac-address-none-zero ;

                          mandatory true ;
                        }

                        leaf slot-number {
                          description 'The slot number,the invalid value is 0,the minimum and maximal value is controlled by the performance parameters.' ;
                          type uint32 {
                            range 1..64 {
                              description 'The slot number value.' ;
                            }

                          }

                          mandatory true ;
                        }

                        leaf vlan-id {
                          description 'The VLAN ID of TDM relay.' ;
                          type uint16 {
                            range 1..4094 {
                              description 'The range of VLAN ID is 1-4094.' ;
                            }

                          }

                          mandatory true ;
                        }

                        container static-label {
                          description 'The static label of TDM relay.' ;
                          presence static-label ;
                          leaf pw-in-label {
                            description 'The PW in label value.' ;
                            type uint32 {
                              range 16..1048575 {
                                description 'The range of PW local label.' ;
                              }

                            }

                            mandatory true ;
                          }

                          leaf pw-out-label {
                            description 'The PW out label value.' ;
                            type uint32 {
                              range 16..1048575 {
                                description 'The range of PW remote label.' ;
                              }

                            }

                            mandatory true ;
                          }

                          leaf psn-in-label {
                            description 'The PSN in label value.' ;
                            type uint32 {
                              range 16..1048575 {
                                description 'The range of PSN local label.' ;
                              }

                            }

                            mandatory true ;
                          }

                          leaf psn-out-label {
                            description 'The PSN out label value.' ;
                            type uint32 {
                              range 16..1048575 {
                                description 'The range of PSN remote label.' ;
                              }

                            }

                            mandatory true ;
                          }

                        }

                      }

                    }

                  }

                }

              }

            }

            container vpws-receiving-pw-bind {
              if-feature vpws-receiving-pw-bind ;

              description 'VPWS receiving PW binding configuration info.' ;
              list receiving-pw-instance-bind {
                description 'Receiving PW binding instance configuration info.' ;
                key pw-name ;
                leaf pw-name {
                  description 'The name of the receiving PW in the bind.' ;
                  type ncd:ifname ;

                }

                leaf pw-role {
                  description 'Receiving PW role.' ;
                  type enumeration {
                    enum backup-mc-pw {
                      value 1 ;
                      description 'The receiving PW role is backup MC-PW.' ;
                    }

                  }

                  mandatory true ;
                }

              }

              ncd:revise-date 2016-03-30 ;
            }

            container vpws-bridge-if-bind {
              description 'VPWS bridge interface binding configuration info.' ;
              list bridge-if-instance-bind {
                description 'Bridge if binding instance configuration info.' ;
                key ac-name ;
                leaf ac-name {
                  description 'The name of the bridge AC in the bind.' ;
                  type ncd:ifname {
                    length 1..31 {
                      description 'The length of AC name.' ;
                    }

                  }

                }

                choice ac-type {
                  description 'The access type of VPWS instance.' ;
                  case ethernet {
                    description 'The ethernet access type.' ;
                    container ethernet-params {
                      description 'Ethernet access type parameters.' ;
                      presence ethernet-params ;
                      leaf ethernet {
                        description 'Create ethernet object.' ;
                        type empty ;

                        mandatory true ;
                      }

                    }

                  }

                }

              }

              ncd:revise-date 2019-11-19 ;
            }

          }

        }

        container vpls-instances {
          description 'The VPLS instances configuration info.' ;
          list vpls-instance {
            description 'The VPLS instance configuration info.' ;
            key instance-name ;
            leaf instance-name {
              description 'The name of the VPLS instance.' ;
              type string {
                length 1..32 {
                  description 'The length of instance name.' ;
                }

              }

            }

            leaf qualified {
              description 'The qualified flag of the VPLS instance.' ;
              type enumeration {
                enum unqualified {
                  value 0 ;
                  description 'The VPLS instance is unqualified.' ;
                }

                enum qualified {
                  value 1 ;
                  description 'The VPLS instance is qualified.' ;
                }

              }

              mandatory true ;
            }

            leaf description {
              description 'The description of the VPLS instance.' ;
              type ncd:string-with-blank {
                length 1..104 {
                  description 'The description range of instance.' ;
                }

              }

            }

            leaf default-vcid {
              description 'The default VCID of the VPLS instance.' ;
              type uint32 {
                range 1..4294967295 {
                  description 'The instance default VCID value.' ;
                }

              }

            }

            leaf mac-withdraw {
              description 'The MAC-withdraw capability of the VPLS instance.' ;
              type enumeration {
                enum disable {
                  value 0 ;
                  description 'The MAC-withdraw is disable.' ;
                }

                enum enable {
                  value 1 ;
                  description 'The MAC-withdraw is enable.' ;
                }

              }

              default disable ;
            }

            leaf unknown-mac-withdraw-mode {
              description 'Config MAC-withdraw unknown message dispose mode.' ;
              type enumeration {
                enum disable {
                  value 0 ;
                  description 'The unknown-mac-withdraw-mode is disable.' ;
                }

                enum flush-all-but-mine {
                  value 1 ;
                  description 'The unknown-mac-withdraw-mode is flush-all-but-mine.' ;
                }

                enum flush-all-from-me {
                  value 2 ;
                  description 'The unknown-mac-withdraw-mode is flush-all-but-me.' ;
                }

              }

              default disable ;
              ncd:revise-date 2018-01-24 ;
            }

            leaf mac-withdraw-optimized-options {
              description 'MAC-withdraw optimized-options in RFC 7361.' ;
              type enumeration {
                enum disable {
                  value 0 ;
                  description 'MAC-withdraw optimized-options disable.' ;
                }

                enum enable {
                  value 1 ;
                  description 'MAC-withdraw optimized-options enable.' ;
                }

              }

              default disable ;
              ncd:revise-date 2020-07-13 ;
            }

            leaf mtu {
              description 'The MTU value of the VPLS instance.' ;
              type uint16 {
                range 60..65535 {
                  description 'The range of MTU.' ;
                }

              }

              default 1500 ;
            }

            leaf shutdown {
              description 'The enable status of the VPLS instance.' ;
              type enumeration {
                enum disable {
                  value 0 ;
                  description 'The status of the VPLS instance is disable.' ;
                }

                enum enable {
                  value 1 ;
                  description 'The status of the VPLS instance is enable.' ;
                }

              }

              default enable ;
            }

            leaf default-cword {
              description 'The default control-word capability of the VPLS instance.' ;
              type enumeration {
                enum not-preferred {
                  value 0 ;
                  description 'Default cword is not preferred.' ;
                }

                enum preferred {
                  value 1 ;
                  description 'Default cword is preferred.' ;
                }

              }

              default not-preferred ;
            }

            leaf qos-mode {
              description 'The QoS service mode of the VPWS instance.' ;
              type enumeration {
                enum uniform {
                  value 1 ;
                  description 'QoS mode is uniform.' ;
                }

                enum pipe {
                  value 2 ;
                  description 'QoS mode is pipe.' ;
                }

                enum shortPipe {
                  value 3 ;
                  description 'QoS mode is short pipe.' ;
                }

              }

            }

            leaf service-class {
              description 'The QoS service class of the VPLS instance.' ;
              type enumeration {
                enum be {
                  value 1 ;
                  description 'The QoS service class is be.' ;
                }

                enum af1 {
                  value 2 ;
                  description 'The QoS service class is af1.' ;
                }

                enum af2 {
                  value 3 ;
                  description 'The QoS service class is af2.' ;
                }

                enum af3 {
                  value 4 ;
                  description 'The QoS service class is af3.' ;
                }

                enum af4 {
                  value 5 ;
                  description 'The QoS service class is af4.' ;
                }

                enum ef {
                  value 6 ;
                  description 'The QoS service class is ef.' ;
                }

                enum cs6 {
                  value 7 ;
                  description 'The QoS service class is cs6.' ;
                }

                enum cs7 {
                  value 8 ;
                  description 'The QoS service class is cs7.' ;
                }

              }

            }

            leaf colour {
              description 'The QoS packet colour of the VPLS instance.' ;
              type enumeration {
                enum green {
                  value 1 ;
                  description 'The QoS packet colour is green.' ;
                }

                enum yellow {
                  value 2 ;
                  description 'The QoS packet colour is yellow.' ;
                }

                enum red {
                  value 3 ;
                  description 'The QoS packet colour is red.' ;
                }

              }

            }

            leaf default-encapsulation {
              description 'The default encapsulation of the VPLS instance.' ;
              type enumeration {
                enum tagged {
                  value 4 ;
                  description 'The default encapsulation is tagged.' ;
                }

                enum raw {
                  value 5 ;
                  description 'The default encapsulation is raw.' ;
                }

              }

              ncd:revise-date 2015-07-15 ;
            }

            leaf equivalent-vxlan-id {
              description 'The equivalent VXLAN ID,the equivalent VXLAN attribute cannot be modified or removed after its owner instance created.' ;
              type uint32 {
                range 1..16777215 {
                  description 'The equivalent VXLAN ID range.' ;
                }

              }

              ncd:revise-date 2017-06-08 ;
            }

            leaf service-id {
              description 'The service ID of VPLS instance,the service ID attribute cannot be modified or removed after its owner instance created.' ;
              type uint32 {
                range 1..65535 {
                  description 'The range of service ID.' ;
                }

              }

              ncd:revise-date 2017-11-15 ;
            }

            leaf uni-egress-adjust-keep-nni-inner-vlan {
              status obsolete {
                ncd:revise-date 2019-09-29 ;
              }

              description 'Config UNI egress-adjust.' ;
              type enumeration {
                enum disable {
                  value 0 ;
                  description 'The egress adjust keep-nni-inner-vlan is disable.' ;
                }

                enum enable {
                  value 1 ;
                  description 'The egress adjust keep-nni-inner-vlan is enable.' ;
                }

              }

              default disable ;
              ncd:revise-date 2019-06-13 ;
            }

            leaf uni-egress-adjust-nni-inner-vlan {
              description 'Config UNI egress-adjust.' ;
              type enumeration {
                enum changable {
                  value 0 ;
                  description 'The egress adjust nni-inner-vlan is changeable.' ;
                }

                enum unchangable {
                  value 1 ;
                  description 'The egress adjust nni-inner-vlan is unchangeable.' ;
                }

              }

              ncd:revise-date 2019-09-29 ;
            }

            leaf unknown-unicast {
              description 'Config unknown-unicast suppress.' ;
              type enumeration {
                enum suppress {
                  value 1 ;
                  description 'The unknown-unicast is suppressed.' ;
                }

                enum unsuppress {
                  value 0 ;
                  description 'The unknown-unicast is unsuppressed.' ;
                }

              }

              default unsuppress ;
              ncd:revise-date 2020-03-25 ;
            }

            leaf link-acl-name {
              description 'The template of link ACL name.' ;
              type string {
                length 1..31 {
                  description 'The length of link ACL name.' ;
                }

              }

              ncd:revise-date 2021-05-27 ;
            }

            leaf mtu-mismatch-ignore {
              description 'Ignore the MTU mismatch in the PW negotiation.' ;
              type empty ;

              ncd:revise-date 2022-09-13 ;
            }

            container ac-fault-associate {
              description 'AC fault associate PW status or not.' ;
              leaf associate-pw {
                description 'AC fault associate PW status or not.' ;
                type enumeration {
                  enum not-associate-pw {
                    value 0 ;
                    description 'AC fault not associate PW status or signal.' ;
                  }

                  enum associate-pw-status {
                    value 1 ;
                    description 'AC fault associate PW status notify to PWE3.' ;
                  }

                  enum associate-pw-signal {
                    value 2 ;
                    description 'AC fault associate PW signal release notify to PWE3.' ;
                  }

                }

                default not-associate-pw ;
              }

              leaf spoke-pw-as-ac {
                description 'Spoke PW as AC or not.' ;
                type enumeration {
                  enum not-as-ac {
                    value 0 ;
                    description 'Spoke PW not as AC to calculate status.' ;
                  }

                  enum as-ac {
                    value 1 ;
                    description 'Spoke PW as AC to calculate status.' ;
                  }

                }

                default not-as-ac ;
              }

              leaf multi-homed-ce-pool {
                description 'Treat ACs as being attached to the same CE-pool.' ;
                type empty ;

                ncd:revise-date 2022-02-15 ;
              }

              ncd:revise-date 2017-07-05 ;
            }

            container ce-pool {
              description 'A set of CEs which are substitutes of one another.' ;
              leaf active-threshold {
                description 'The threshold for a CE-pool to be treated as up.' ;
                type uint8 {
                  range 1..100 {
                    description "The percent of a CE-pool's active ACs." ;
                  }

                }

              }

              ncd:revise-date 2022-02-15 ;
            }

            container traffic-statistics-params {
              if-feature instances-traffic-statistics ;

              description 'The traffic statistics parameters of VPLS instance.' ;
              leaf traffic-enable {
                description 'The traffic statistics status of VPLS service.' ;
                type enumeration {
                  enum disable {
                    value 0 ;
                    description 'The traffic statistics status of VPLS service is disable.' ;
                  }

                  enum enable {
                    value 1 ;
                    description 'The traffic statistics status of VPLS service is enable.' ;
                  }

                }

                default disable ;
              }

              leaf unicast-inrate-bps {
                description 'The unicast input bytes rate.' ;
                type uint64 {
                  range 1..18446744073709551615 {
                    description 'The range of unicast input bytes.' ;
                  }

                }

                units bps ;
              }

              leaf unicast-inrate-pps {
                description 'The unicast input packets rate.' ;
                type uint32 {
                  range 1..4294967295 {
                    description 'The range of unicast input packets rate.' ;
                  }

                }

                units pps ;
              }

              leaf broadcast-inrate-bps {
                description 'The broadcast input bytes rate.' ;
                type uint64 {
                  range 1..18446744073709551615 {
                    description 'The range of broadcast input bytes.' ;
                  }

                }

                units bps ;
              }

              leaf broadcast-inrate-pps {
                description 'The broadcast input packets rate.' ;
                type uint32 {
                  range 1..4294967295 {
                    description 'The range of broadcast input packets rate.' ;
                  }

                }

                units pps ;
              }

              leaf drop-inrate-bps {
                description 'The drop input bytes rate.' ;
                type uint64 {
                  range 1..18446744073709551615 {
                    description 'The range of drop input bytes.' ;
                  }

                }

                units bps ;
              }

              leaf drop-inrate-pps {
                description 'The drop input packets rate.' ;
                type uint32 {
                  range 1..4294967295 {
                    description 'The range of drop input packets rate.' ;
                  }

                }

                units pps ;
              }

            }

            container vpls-pw-bind {
              description 'VPLS PW binding instance info.' ;
              list pw-instance-bind {
                description 'PW binding instance configuration info.' ;
                key pw-name ;
                leaf pw-name {
                  description 'The name of the PW in the bind.' ;
                  type ncd:ifname ;

                }

                leaf split-horizon {
                  description 'The split-horizon flag of the PW bind.' ;
                  type enumeration {
                    enum spoke {
                      value 0 ;
                      description 'The split-horizon flag is spoke.' ;
                    }

                    enum hub {
                      value 1 ;
                      description 'The split-horizon flag is hub.' ;
                    }

                  }

                  mandatory true ;
                }

                leaf split-horizon-scopes {
                  description 'The split-horizon scope of PW bind.' ;
                  type string {
                    length 1..51 {
                      description 'The length of split-horizon-scopes.' ;
                    }

                  }

                }

              }

            }

            container vpls-ac-bind {
              description 'VPLS AC binding instance info.' ;
              list ac-instance-bind {
                description 'AC binding instance configuration info.' ;
                key ac-name ;
                leaf ac-name {
                  description 'The name of the AC in the bind.' ;
                  type ncd:ifname ;

                }

                leaf split-horizon {
                  description 'The split-horizon flag of the bind.' ;
                  type enumeration {
                    enum server {
                      value 0 ;
                      description 'The split-horizon flag is server.' ;
                    }

                    enum client {
                      value 1 ;
                      description 'The split-horizon flag is client.' ;
                    }

                  }

                  mandatory true ;
                }

                leaf split-horizon-scopes {
                  description 'The split-horizon scope of AC bind.' ;
                  type string {
                    length 1..51 ;

                  }

                }

                leaf nni {
                  description 'The NNI flag of the bind.' ;
                  type enumeration {
                    enum disable {
                      value 0 ;
                      description 'The NNI flag is disable.' ;
                    }

                    enum enable {
                      value 1 ;
                      description 'The NNI flag is enable.' ;
                    }

                  }

                  default disable ;
                  ncd:revise-date 2018-09-07 ;
                }

                leaf description {
                  description 'The description of the interface.' ;
                  type ncd:string-with-blank {
                    length 1..104 {
                      description 'The description range of interface.' ;
                    }

                  }

                  ncd:revise-date 2017-08-25 ;
                }

                choice ac-type {
                  description 'The access type of VPLS instance and  the VPLS only supports Ethernet access.' ;
                  case ethernet {
                    description 'The ethernet access type.' ;
                    container ethernet-params {
                      description 'Ethernet access type parameters.' ;
                      presence ethernet-params ;
                      leaf ethernet {
                        description 'Ethernet access type.' ;
                        type empty ;

                        mandatory true ;
                      }

                      leaf track-name {
                        description 'The name of the track object which bind to the AC.' ;
                        type string {
                          length 1..31 {
                            description 'The length of track name.' ;
                          }

                        }

                      }

                      leaf oam-mapping {
                        description 'The oam-mapping flag of the ethernet parameter.' ;
                        type enumeration {
                          enum disable {
                            value 0 ;
                            description 'The oam-mapping flag of the ethernet parameter is disable.' ;
                          }

                          enum enable {
                            value 1 ;
                            description 'The oam-mapping flag of the ethernet parameter is enable.' ;
                          }

                        }

                        default disable ;
                      }

                      leaf traffic-enable {
                        description 'The traffic statistics enable flag of the ethernet parameter.' ;
                        type enumeration {
                          enum disable {
                            value 0 ;
                            description 'The traffic statistics flag is disable.' ;
                          }

                          enum enable {
                            value 1 ;
                            description 'The traffic statistics flag is enable.' ;
                          }

                        }

                        default disable ;
                      }

                      leaf root-leaf {
                        description 'Configure root or leaf attribution for the ethernet.' ;
                        type enumeration {
                          enum root {
                            value 0 ;
                            description 'Configure root attribution for the ethernet.' ;
                          }

                          enum leaf {
                            value 1 ;
                            description 'Configure leaf attribution for the ethernet.' ;
                          }

                        }

                        default root ;
                      }

                      leaf ingress-adjust-push {
                        description 'The ingress adjust push flag of the ethernet parameter.' ;
                        type enumeration {
                          enum disable {
                            value 0 ;
                            description 'The ingress adjust push flag of the ethernet parameter is disable.' ;
                          }

                          enum enable {
                            value 1 ;
                            description 'The ingress adjust push flag of the ethernet parameter is enable.' ;
                          }

                        }

                        default disable ;
                      }

                      leaf push-vlan-id {
                        description 'The ingress adjust push VLAN ID of the ethernet parameter.' ;
                        type uint16 {
                          range 1..4094 {
                            description 'The range of push VLAN ID is 1-4094.' ;
                          }

                        }

                      }

                      leaf push-tpid {
                        description 'The ingress adjust push TPID of the ethernet parameter.' ;
                        type enumeration {
                          enum 8100 {
                            value 0 ;
                            description 'The ingress adjust push TPID value is 0x8100.' ;
                          }

                          enum 9100 {
                            value 1 ;
                            description 'The ingress adjust push TPID value is 0x9100.' ;
                          }

                          enum 9200 {
                            value 2 ;
                            description 'The ingress adjust push TPID value is 0x9200.' ;
                          }

                          enum 88a8 {
                            value 3 ;
                            description 'The ingress adjust push TPID value is 0x88a8.' ;
                          }

                        }

                        ncd:revise-date 2019-08-06 ;
                      }

                      leaf ingress-adjust-rewrite {
                        description 'The ingress adjust rewrite flag of the ethernet parameter.' ;
                        type enumeration {
                          enum disable {
                            value 0 ;
                            description 'The ingress adjust rewrite flag of the ethernet parameter is disable.' ;
                          }

                          enum enable {
                            value 1 ;
                            description 'The ingress adjust rewrite flag of the ethernet parameter is enable.' ;
                          }

                        }

                        default disable ;
                      }

                      leaf rewrite-vlan-id {
                        description 'The ingress adjust rewrite VLAN ID of the ethernet parameter.' ;
                        type uint16 {
                          range 1..4094 {
                            description 'The range of rewrite VLAN ID is 1-4094.' ;
                          }

                        }

                      }

                      leaf rewrite-outer-vlanid-flag {
                        description 'Rewrite outer VLAN ID flag.' ;
                        type enumeration {
                          enum disable {
                            value 0 ;
                            description 'Rewrite outer VLAN ID flag is disable.' ;
                          }

                          enum enable {
                            value 1 ;
                            description 'Rewrite outer VLAN ID flag is enable.' ;
                          }

                        }

                        default disable ;
                        ncd:revise-date 2021-01-05 ;
                      }

                      leaf rewrite-tpid {
                        description 'The ingress adjust rewrite TPID of the ethernet parameter.' ;
                        type enumeration {
                          enum 8100 {
                            value 0 ;
                            description 'The ingress adjust rewrite TPID value is 0x8100.' ;
                          }

                          enum 9100 {
                            value 1 ;
                            description 'The ingress adjust rewrite TPID value is 0x9100.' ;
                          }

                          enum 9200 {
                            value 2 ;
                            description 'The ingress adjust rewrite TPID value is 0x9200.' ;
                          }

                          enum 88a8 {
                            value 3 ;
                            description 'The ingress adjust rewrite TPID value is 0x88a8.' ;
                          }

                        }

                        ncd:revise-date 2019-08-06 ;
                      }

                      leaf ingress-adjust-tag-as-payload {
                        description 'The ingress tag as payload flag of the ethernet parameter.' ;
                        type enumeration {
                          enum disable {
                            value 0 ;
                            description 'The ingress tag as payload flag is disable.' ;
                          }

                          enum all {
                            value 1 ;
                            description 'The ingress tag as payload flag is from outer most.' ;
                          }

                          enum from-sub-layer {
                            value 2 ;
                            description 'The ingress tag as payload flag is from sub layer.' ;
                          }

                        }

                        default disable ;
                      }

                      leaf ingress-adjust-drop-tagged-frames {
                        description 'The ingress adjust drop tagged frames flag of the ethernet.' ;
                        type enumeration {
                          enum disable {
                            value 0 ;
                            description 'The ingress adjust drop tagged frames flag is disable.' ;
                          }

                          enum enable {
                            value 1 ;
                            description 'The ingress adjust drop tagged frames flag is enable.' ;
                          }

                        }

                      }

                      leaf ingress-adjust-uni-proxy {
                        description 'The ingress UNI proxy flag of the ethernet parameter.' ;
                        type enumeration {
                          enum disable {
                            value 0 ;
                            description 'The ingress UNI proxy flag is disable.' ;
                          }

                          enum pop-all {
                            value 1 ;
                            description 'The ingress UNI proxy flag is pop-all.' ;
                          }

                          enum pop-outer {
                            value 2 ;
                            description 'The ingress UNI proxy flag is pop-outer.' ;
                          }

                        }

                        default disable ;
                        ncd:revise-date 2018-09-07 ;
                      }

                      leaf ingress-adjust-pop-uni-tag {
                        description "The ingress adjust of pop UNI's tag." ;
                        type enumeration {
                          enum disable {
                            value 0 ;
                            description "The ingress adjust of pop UNI's tag is disable." ;
                          }

                          enum all {
                            value 1 ;
                            description "The ingress adjust of pop UNI's tag is all." ;
                          }

                          enum outer {
                            value 2 ;
                            description "The ingress adjust of pop UNI's tag is outer." ;
                          }

                        }

                        ncd:revise-date 2019-09-29 ;
                      }

                      leaf ingress-adjust-serve-as-pvid {
                        description 'The ingress UNI serve-as-pvid flag of the ethernet parameter.' ;
                        type enumeration {
                          enum disable {
                            value 0 ;
                            description 'The ingress UNI serve-as-pvid flag is disable.' ;
                          }

                          enum enable {
                            value 1 ;
                            description 'The ingress UNI serve-as-pvid flag is enable.' ;
                          }

                        }

                        default disable ;
                        ncd:revise-date 2019-06-13 ;
                      }

                      leaf egress-keep-normalized-tag {
                        description 'To keep the normalized tag unchanged onto the egress AC.' ;
                        type enumeration {
                          enum disable {
                            value 0 ;
                            description 'To keep the normalized tag unchanged onto the egress AC is disable.' ;
                          }

                          enum enable {
                            value 1 ;
                            description 'To keep the normalized tag unchanged onto the egress AC is enable.' ;
                          }

                        }

                        default disable ;
                        ncd:revise-date 2021-01-05 ;
                      }

                      leaf lst-for-etree {
                        description 'The lst-for-etree of the ethernet parameter.' ;
                        type enumeration {
                          enum disable {
                            value 0 ;
                            description 'The lst-for-etree is disable.' ;
                          }

                          enum enable {
                            value 1 ;
                            description 'The lst-for-etree is enable.' ;
                          }

                        }

                        default disable ;
                        ncd:revise-date 2021-04-02 ;
                      }

                      container traffic-statistics-params {
                        if-feature ac-traffic-statistics ;

                        description 'The traffic statistics parameters of ethernet access.' ;
                        leaf unicast-inrate-bps {
                          description 'The unicast input bytes rate.' ;
                          type uint64 {
                            range 1..18446744073709551615 {
                              description 'The range of unicast input bytes.' ;
                            }

                          }

                          units bps ;
                        }

                        leaf unicast-inrate-pps {
                          description 'The unicast input packets rate.' ;
                          type uint32 {
                            range 1..4294967295 {
                              description 'The range of unicast input packets rate.' ;
                            }

                          }

                          units pps ;
                        }

                        leaf broadcast-inrate-bps {
                          description 'The broadcast input bytes rate.' ;
                          type uint64 {
                            range 1..18446744073709551615 {
                              description 'The range of broadcast input bytes.' ;
                            }

                          }

                          units bps ;
                        }

                        leaf broadcast-inrate-pps {
                          description 'The broadcast input packets rate.' ;
                          type uint32 {
                            range 1..4294967295 {
                              description 'The range of broadcast input packets rate.' ;
                            }

                          }

                          units pps ;
                        }

                        leaf drop-inrate-bps {
                          description 'The drop input bytes rate.' ;
                          type uint64 {
                            range 1..18446744073709551615 {
                              description 'The range of drop input bytes.' ;
                            }

                          }

                          units bps ;
                        }

                        leaf drop-inrate-pps {
                          description 'The drop input packets rate.' ;
                          type uint32 {
                            range 1..4294967295 {
                              description 'The range of drop input packets rate.' ;
                            }

                          }

                          units pps ;
                        }

                      }

                      container ingress-adjust-params {
                        description 'The ingress adjust tag as endpoint parameters.' ;
                        leaf tag-as-endpoint {
                          description 'The BUM packets broadcast to each VLAN of the sub port VLAN range or not.' ;
                          type enumeration {
                            enum disable {
                              value 0 ;
                              description 'The ingress adjust tag as endpoint flag is disable.' ;
                            }

                            enum enable {
                              value 1 ;
                              description 'The ingress adjust tag as endpoint flag is enable.' ;
                            }

                          }

                          default disable ;
                        }

                        ncd:revise-date 2018-12-07 ;
                      }

                      container nni-egress-adjust-uni-rewrite {
                        description 'The egress adjust rewrite flag of the ethernet parameter.' ;
                        presence nni-egress-adjust-uni-rewrite ;
                        leaf outer-vlan-id {
                          description 'The egress adjust rewrite VLAN ID of the ethernet parameter.' ;
                          type uint16 {
                            range 1..4094 {
                              description 'The range of outer VLAN ID is 1-4094.' ;
                            }

                          }

                          mandatory true ;
                        }

                        leaf inner-vlan-id {
                          description 'The egress adjust rewrite inner VLAN ID of the ethernet parameter.' ;
                          type uint16 {
                            range 1..4094 {
                              description 'The range of inner VLAN ID is 1-4094.' ;
                            }

                          }

                        }

                        ncd:revise-date 2019-06-13 ;
                      }

                      container nni-egress-adjust-uni-tpid {
                        description 'Outer ether-type of remote required.' ;
                        presence nni-egress-adjust-uni-tpid ;
                        leaf outer-tpid {
                          description 'The egress adjust outer TPID value of the ethernet parameter.' ;
                          type enumeration {
                            enum 8100 {
                              value 0 ;
                              description 'The egress adjust outer TPID value is 8100.' ;
                            }

                            enum 9100 {
                              value 1 ;
                              description 'The egress adjust outer TPID value is 9100.' ;
                            }

                            enum 9200 {
                              value 2 ;
                              description 'The egress adjust outer TPID value is 9100.' ;
                            }

                            enum 88a8 {
                              value 3 ;
                              description 'The egress adjust outer TPID value is 88a8.' ;
                            }

                          }

                          mandatory true ;
                        }

                        leaf inner-tpid {
                          description 'The egress adjust inner TPID value of the ethernet parameter.' ;
                          type enumeration {
                            enum 8100 {
                              value 0 ;
                              description 'The egress adjust outer TPID value is 8100.' ;
                            }

                            enum 9100 {
                              value 1 ;
                              description 'The egress adjust outer TPID value is 9100.' ;
                            }

                            enum 9200 {
                              value 2 ;
                              description 'The egress adjust outer TPID value is 9200.' ;
                            }

                            enum 88a8 {
                              value 3 ;
                              description 'The egress adjust outer TPID value is 88a8.' ;
                            }

                          }

                        }

                        ncd:revise-date 2019-06-13 ;
                      }

                      container bgp-multi-homing {
                        description 'The BGP multi-homing parameters of ethernet access.' ;
                        leaf ce-id {
                          description 'The CE ID.' ;
                          type uint16 {
                            range 1..65534 {
                              description 'The range of CE ID is 1-65534.' ;
                            }

                          }

                        }

                        ncd:revise-date 2020-07-29 ;
                      }

                    }

                  }

                  case ethernet-cip {
                    if-feature ethernet-cip ;

                    description 'The ethernet-cip access type.' ;
                    container ethernet-cip-params {
                      description 'Ethernet-cip access type parameters.' ;
                      presence ethernet-cip-params ;
                      leaf ethernet-cip {
                        description 'Ethernet-cip access type.' ;
                        type empty ;

                        mandatory true ;
                      }

                      container access-source {
                        description 'Configure ethernet-cip access type.' ;
                        choice access-source-type {
                          description 'The ethernet-cip access type.' ;
                          case port {
                            description 'The ethernet-cip access type is port.' ;
                            container port-params {
                              description 'The ethernet-cip port parameters.' ;
                              presence port-params ;
                              leaf interface-name {
                                description 'The interface name of port access.' ;
                                type ncd:ifname {
                                  length 1..31 {
                                    description 'The length of interface name.' ;
                                  }

                                }

                                mandatory true ;
                              }

                              leaf port-vlan-id {
                                description 'The VLAN ID of port access.' ;
                                type uint16 {
                                  range 1..4094 {
                                    description 'The range of VLAN ID is 1-4094.' ;
                                  }

                                }

                              }

                            }

                          }

                          case slot {
                            description 'The ethernet-cip access type is slot.' ;
                            container slot-params {
                              description 'The ethernet-cip slot parameters.' ;
                              presence slot-params ;
                              leaf slot-number {
                                description 'The slot number,the invalid value is 0,the minimum and maximal value is controlled by the performance parameters.' ;
                                type uint32 {
                                  range 1..64 {
                                    description 'The slot number value.' ;
                                  }

                                }

                                mandatory true ;
                              }

                              leaf vlan-id {
                                description 'The VLAN ID of slot access.' ;
                                type uint16 {
                                  range 1..4094 {
                                    description 'The range of VLAN ID is 1-4094.' ;
                                  }

                                }

                                mandatory true ;
                              }

                            }

                          }

                        }

                      }

                    }

                  }

                }

              }

            }

            container martini-discovery {
              if-feature martini-discovery ;

              description 'Martini auto discovery configuration info.' ;
              presence "Martini discovery type" ;
              container martini-params {
                description 'Martini auto discovery configuration parameter.' ;
                list martini-vpls-params {
                  description 'Martini auto discovery configuration parameter of VPLS.' ;
                  key vpls-id ;
                  leaf vpls-id {
                    description 'VPLS instance auto-discovery identifier.' ;
                    type union {
                      type ncd:asn-nn ;

                      type ncd:ipadd-nn ;

                    }

                  }

                  leaf sspw-target-differ-from-ldp {
                    description 'The target PE address is different from the target LDP identifier.' ;
                    type empty ;

                    ncd:revise-date 2022-12-05 ;
                  }

                }

              }

              container route-target-params {
                description 'The route target params.' ;
                list route-target {
                  description 'The route target.' ;
                  key 'rt-value effect-type' ;
                  leaf rt-value {
                    description 'The route target parameter.' ;
                    type union {
                      type ncd:asn-nn ;

                      type ncd:ipadd-nn ;

                    }

                  }

                  leaf effect-type {
                    description 'The route target effect type.' ;
                    type enumeration {
                      enum export {
                        value 2 ;
                        description 'The route target effect type is export.' ;
                      }

                      enum import {
                        value 3 ;
                        description 'The route target effect type is import.' ;
                      }

                    }

                  }

                }

              }

              container pw-details-params {
                description 'The PW details params.' ;
                list pw-details {
                  description 'The PW details info.' ;
                  key peer-address ;
                  leaf peer-address {
                    description 'The IP address of remote endpoint.' ;
                    type ncd:ipv4-address-none-zero ;

                  }

                  leaf encap-type {
                    description 'The encapsulation type of the auto PW.' ;
                    type enumeration {
                      enum ethernet-tagged {
                        value 4 ;
                        description 'The encapsulation type of the auto PW is ethernet tagged.' ;
                      }

                      enum ethernet {
                        value 5 ;
                        description 'The encapsulation type of the auto PW is ethernet.' ;
                      }

                    }

                    default ethernet ;
                  }

                  leaf tunnel-policy-name {
                    description 'The tunnel policy name of the auto PW.' ;
                    type string {
                      length 1..63 {
                        description 'The length of tunnel policy name.' ;
                      }

                    }

                  }

                  leaf control-word {
                    description 'The control-word capability of the auto PW.' ;
                    type enumeration {
                      enum not-preferred {
                        value 0 ;
                        description 'The control-word capability of the auto PW is not preferred.' ;
                      }

                      enum preferred {
                        value 1 ;
                        description 'The control-word capability of the auto PW is preferred.' ;
                      }

                    }

                    default not-preferred ;
                  }

                  leaf traffic-enable {
                    description 'The traffic statistics status of Martini PW.' ;
                    type enumeration {
                      enum disable {
                        value 0 ;
                        description 'The traffic statistics status of Martini PW is disable.' ;
                      }

                      enum enable {
                        value 1 ;
                        description 'The traffic statistics status of Martini PW is enable.' ;
                      }

                    }

                    default disable ;
                    ncd:revise-date 2015-04-28 ;
                  }

                  leaf vccv-flow-label {
                    description 'The flow-label for VCCV packets without standard flow-labels.' ;
                    type empty ;

                    ncd:revise-date 2022-03-15 ;
                  }

                  container vccv-bfd-params {
                    description 'The VCCV BFD parameters info of Martini PW.' ;
                    leaf vccv-bfd {
                      description 'The BFD capability of the Martini PW.' ;
                      type enumeration {
                        enum disable {
                          value 0 ;
                          description 'The BFD capability is disable.' ;
                        }

                        enum enable {
                          value 1 ;
                          description 'The BFD capability is enable.' ;
                        }

                      }

                      default disable ;
                    }

                    leaf vccv-bfd-encapsulation {
                      description 'The BFD raw encapsulation capability of the Martini PW.' ;
                      type enumeration {
                        enum ip {
                          value 0 ;
                          description 'The BFD raw encapsulation capability is IP.' ;
                        }

                        enum raw {
                          value 1 ;
                          description 'The BFD raw encapsulation capability is raw.' ;
                        }

                      }

                      default ip ;
                    }

                    leaf vccv-bfd-capability {
                      description 'The BFD signal status capability of the Martini PW.' ;
                      type enumeration {
                        enum basic {
                          value 0 ;
                          description 'The BFD signal status capability is basic.' ;
                        }

                        enum status {
                          value 1 ;
                          description 'The BFD signal status capability is status.' ;
                        }

                      }

                      default basic ;
                    }

                    leaf vccv-bfd-template-name {
                      description 'BFD template name.' ;
                      type string {
                        length 1..31 {
                          description 'The length of BFD template name.' ;
                        }

                      }

                      ncd:revise-date 2021-03-04 ;
                    }

                  }

                  leaf split-horizon-scope {
                    description 'The split-horizon-scope of Martini PW.' ;
                    type enumeration {
                      enum none {
                        value 1 ;
                        description 'No split-horizon scope joined.' ;
                      }

                      enum any {
                        value 2 ;
                        description 'All split-horizon scope joined.' ;
                      }

                    }

                    ncd:revise-date 2017-06-28 ;
                  }

                  container max-traffic-rate-params {
                    description 'The maximum of traffic rate parameters.' ;
                    leaf max-traffic-rate {
                      description 'The maximum of traffic rate.' ;
                      type uint32 {
                        range 64..10000000 {
                          description 'The maximum of traffic rate.' ;
                        }

                      }

                      units kbps ;
                    }

                    leaf max-multicast-rate-percent {
                      description 'The max percent of multicast traffic rate.' ;
                      type uint32 {
                        range 1..100 {
                          description 'The max percent of multicast traffic rate.' ;
                        }

                      }

                      default 100 ;
                    }

                    leaf max-unicast-rate-percent {
                      description 'The max percent of unicast traffic rate.' ;
                      type uint32 {
                        range 1..100 {
                          description 'The max percent of unicast traffic rate.' ;
                        }

                      }

                      default 100 ;
                    }

                    leaf max-unknown-multicast-rate-percent {
                      description 'The max percent of unknown-multicast traffic rate.' ;
                      type uint32 {
                        range 1..100 {
                          description 'The max percent of unknown-multicast traffic rate.' ;
                        }

                      }

                      default 100 ;
                    }

                    leaf max-unknown-unicast-rate-percent {
                      description 'The max percent of unknown-unicast traffic rate.' ;
                      type uint32 {
                        range 1..100 {
                          description 'The max percent of unknown-unicast traffic rate.' ;
                        }

                      }

                      default 100 ;
                    }

                    leaf max-broadcast-rate-percent {
                      description 'The max percent of broadcast traffic rate.' ;
                      type uint32 {
                        range 1..100 {
                          description 'The max percent of broadcast traffic rate.' ;
                        }

                      }

                      default 100 ;
                    }

                    ncd:revise-date 2018-07-08 ;
                  }

                  container mac-limit-params {
                    description 'Maximum MAC entries and action when MAC entries is exceeding the maximum.' ;
                    presence mac-entries ;
                    leaf maximum {
                      description 'Maximum MAC entries.' ;
                      type uint32 {
                        range 1..4294967295 {
                          description 'Minimum is 1. Maximum and default is defined by performance parameter.' ;
                        }

                      }

                      mandatory true ;
                    }

                    leaf action {
                      description 'The action when MAC entries is exceeding the maximum.' ;
                      type enumeration {
                        enum broadcast {
                          value 0 ;
                          description 'The action when MAC entries is exceeding the maximum is broadcast.' ;
                        }

                        enum drop {
                          value 1 ;
                          description 'The action when MAC entries is exceeding the maximum is drop.' ;
                        }

                      }

                      mandatory true ;
                    }

                    ncd:revise-date 2021-01-05 ;
                  }

                  container flow-label {
                    description 'Martini PW support flow label function.' ;
                    leaf push {
                      description 'Flow label transmit capability.' ;
                      type enumeration {
                        enum disable {
                          value 0 ;
                          description 'Flow label transmit capability is disable.' ;
                        }

                        enum enable {
                          value 1 ;
                          description 'Flow label transmit capability is enable.' ;
                        }

                      }

                      default disable ;
                    }

                    leaf pop {
                      description 'Flow label receive capability.' ;
                      type enumeration {
                        enum disable {
                          value 0 ;
                          description 'Flow label receive capability is disable.' ;
                        }

                        enum enable {
                          value 1 ;
                          description 'Flow label receive capability is enable.' ;
                        }

                      }

                      default disable ;
                    }

                    ncd:revise-date 2022-03-15 ;
                  }

                  container split-horizon-scope-params {
                    description 'The split-horizon-scope of Martini PW.' ;
                    choice split-horizon-params-type {
                      description 'The split-horizon-scope of Martini PW type.' ;
                      case split-horizon-scope-enum {
                        leaf split-horizon-scope-enum {
                          type enumeration {
                            enum none {
                              value 1 ;
                              description 'No split-horizon scope joined.' ;
                            }

                            enum any {
                              value 2 ;
                              description 'All split-horizon scope joined.' ;
                            }

                          }

                          description 'The split-horizon-scope of Martini PW.' ;
                        }

                      }

                      case split-horizon-scope-group {
                        leaf split-horizon-scope-group {
                          type string {
                            length 1..51 {
                              description 'The length of split-horizon-scopes.' ;
                            }

                          }

                          description 'The name list of split-horizon group.' ;
                        }

                      }

                    }

                    ncd:revise-date 2023-06-05 ;
                  }

                }

              }

            }

            container kompella-discovery {
              if-feature kompella-discovery ;

              description 'Kompella discovery configuration info.' ;
              presence "Kompella discovery type" ;
              container kompella-params {
                description 'Kompella auto discovery configuration parameter.' ;
                list kompella-vpls-params {
                  description 'VPLS Kompella params.' ;
                  key rd ;
                  leaf rd {
                    description 'The route distinguisher parameter.' ;
                    type union {
                      type ncd:asn-nn ;

                      type ncd:ipadd-nn ;

                    }

                  }

                  leaf ve-id {
                    description 'The VE identification for the VPLS instance.' ;
                    type uint16 {
                      range 0..65534 {
                        description 'VE-ID value.' ;
                      }

                    }

                  }

                  leaf ve-set-style {
                    description 'The style of VE set parameter.' ;
                    type enumeration {
                      enum continuous {
                        value 1 ;
                        description 'The style of VE set parameter is continuous.' ;
                      }

                      enum discrete {
                        value 2 ;
                        description 'The style of VE set parameter is discrete.' ;
                      }

                    }

                  }

                  leaf max-ve-id {
                    description 'The maximum identification for the VPLS instance.' ;
                    type uint32 {
                      range 1..79 {
                        description 'The maximum identification value.' ;
                      }

                    }

                  }

                  leaf tunnel-policy-name {
                    description 'The name of tunnel policy parameter.' ;
                    type string {
                      length 1..63 {
                        description 'The length of tunnel policy name.' ;
                      }

                    }

                  }

                  leaf traffic-enable {
                    description 'The traffic statistics status of Kompella PW.' ;
                    type enumeration {
                      enum disable {
                        value 0 ;
                        description 'The traffic statistics status of Kompella PW is disable.' ;
                      }

                      enum enable {
                        value 1 ;
                        description 'The traffic statistics status of Kompella PW is enable.' ;
                      }

                    }

                    default disable ;
                    ncd:revise-date 2015-04-28 ;
                  }

                  leaf control-word {
                    description 'The control-word capability of the Kompella PW.' ;
                    type enumeration {
                      enum not-preferred {
                        value 0 ;
                        description 'The control-word capability is not preferred.' ;
                      }

                      enum preferred {
                        value 1 ;
                        description 'The control-word capability is preferred.' ;
                      }

                    }

                    default not-preferred ;
                    ncd:revise-date 2016-09-27 ;
                  }

                  container encapulation {
                    description 'The encapsulation params of the Kompella PW.' ;
                    presence encapulation ;
                    leaf encapulation-type {
                      description 'Specify encapsulation mode for Kompella PW.' ;
                      type enumeration {
                        enum vlan {
                          value 4 ;
                          description 'The PW type is VLAN.' ;
                        }

                        enum ethernet {
                          value 5 ;
                          description 'The PW type is ethernet.' ;
                        }

                      }

                      mandatory true ;
                    }

                    leaf separate-in-signal {
                      description 'Encapsulation use separate PW type in signal or not.' ;
                      type enumeration {
                        enum not-separate-encap {
                          value 0 ;
                          description 'Encapsulation not use separate PW type in signal.' ;
                        }

                        enum separate-encap {
                          value 1 ;
                          description 'Encapsulation use separate PW type in signal.' ;
                        }

                      }

                      default not-separate-encap ;
                    }

                    ncd:revise-date 2016-09-27 ;
                  }

                  leaf split-horizon-scope {
                    status obsolete {
                      ncd:revise-date 2022-02-15 ;
                    }

                    description 'The split-horizon-scope of Kompella PW.' ;
                    type enumeration {
                      enum none {
                        value 1 ;
                        description 'No split-horizon scope joined.' ;
                      }

                      enum any {
                        value 2 ;
                        description 'All split-horizon scopes joined.' ;
                      }

                    }

                    ncd:revise-date 2016-09-27 ;
                  }

                  container multi-chassis-pw-params {
                    description 'Multiple chassis PW redundancy parameters.' ;
                    presence multi-chassis-pw-params ;
                    leaf multi-chassis-pw {
                      description 'Multiple chassis PW redundancy grouped by site ID.' ;
                      type empty ;

                      mandatory true ;
                    }

                    container temporary-standby-params {
                      description 'Multiple chassis PW redundancy temporary standby parameters.' ;
                      presence temporary-standby-params ;
                      leaf temporary-standby-time {
                        description 'Wait for other PEs to receive preference update.' ;
                        type uint32 {
                          range 1..5000 {
                            description 'The range of temporary standby time.' ;
                          }

                        }

                        units ms ;
                        mandatory true ;
                      }

                      leaf smoothly {
                        description 'Temporary standby drops packets smoothly or not.' ;
                        type empty ;

                      }

                    }

                    ncd:revise-date 2021-12-13 ;
                  }

                  container site-preference-params {
                    description 'Site preference parameters.' ;
                    presence site-preference-params ;
                    leaf site-preference {
                      description 'Configure site preference.' ;
                      type uint32 {
                        range 1..65535 {
                          description 'Set site preference' ;
                        }

                      }

                      mandatory true ;
                    }

                    leaf backup-preference {
                      description 'Site Preference Value of the other multihomed PE.' ;
                      type uint32 {
                        range 1..65535 {
                          description 'Set site preference.' ;
                        }

                      }

                    }

                    ncd:revise-date 2021-12-22 ;
                  }

                  container flow-label {
                    description 'Configure flow-label capability.' ;
                    leaf push {
                      description 'Set flow-label transmit capability.' ;
                      type enumeration {
                        enum static {
                          value 1 ;
                          description 'Push a flow-label even if R flag is not received.' ;
                        }

                        enum dynamic {
                          value 2 ;
                          description 'Push a flow-label only if R flag is received.' ;
                        }

                      }

                    }

                    leaf pop {
                      description 'Set flow-label receive capability.' ;
                      type enumeration {
                        enum static {
                          value 1 ;
                          description 'Pop a flow-label even if T flag is not received.' ;
                        }

                        enum dynamic {
                          value 2 ;
                          description 'Pop a flow-label only if T flag is received.' ;
                        }

                      }

                    }

                    ncd:revise-date 2021-12-22 ;
                  }

                  container split-horizon-scope-params {
                    description 'The split-horizon-scope of Kompella PW.' ;
                    choice split-horizon-params-type {
                      description 'The split-horizon-scope of Kompella PW type.' ;
                      case split-horizon-scope-enum {
                        description 'The split-horizon-scope of Kompella PW.' ;
                        leaf split-horizon-scope-enum {
                          description 'The split-horizon-scope of Kompella PW.' ;
                          type enumeration {
                            enum none {
                              value 1 ;
                              description 'No split-horizon scope joined.' ;
                            }

                            enum any {
                              value 2 ;
                              description 'All split-horizon scope joined.' ;
                            }

                          }

                        }

                      }

                      case split-horizon-scope-group {
                        description 'The split-horizon-scope-group of Kompella PW.' ;
                        leaf split-horizon-scope-group {
                          description 'The name list of split-horizon group.' ;
                          type string {
                            length 1..51 {
                              description 'The length of split-horizon-scopes.' ;
                            }

                          }

                        }

                      }

                    }

                    ncd:revise-date 2022-02-15 ;
                  }

                }

              }

              container route-target-params {
                description 'The route target params.' ;
                list route-target {
                  description 'The route target.' ;
                  key 'rt-value effect-type' ;
                  leaf rt-value {
                    description 'RT attribute value.' ;
                    type union {
                      type ncd:asn-nn ;

                      type ncd:ipadd-nn ;

                    }

                  }

                  leaf effect-type {
                    description 'The route target effect type.' ;
                    type enumeration {
                      enum export {
                        value 2 ;
                        description 'The route target effect type is export.' ;
                      }

                      enum import {
                        value 3 ;
                        description 'The route target effect type is import.' ;
                      }

                    }

                  }

                }

              }

              container ve-block-params {
                description 'Kompella auto discovery configuration parameter.' ;
                list ve-block {
                  description 'The VE block of VPLS.' ;
                  key begin-ve-id ;
                  leaf begin-ve-id {
                    description 'The begin value of the VE identification block.' ;
                    type uint32 {
                      range 0..65535 {
                        description 'The minimum identification value.' ;
                      }

                    }

                  }

                  leaf end-ve-id {
                    description 'The end value of the VE identification block.' ;
                    type uint32 {
                      range 0..65535 {
                        description 'The maximum identification value.' ;
                      }

                    }

                    mandatory true ;
                  }

                }

              }

            }

            container bridge-interface {
              description 'VPLS bridge interface parameters.' ;
              presence bridge-interface ;
              leaf interface-name {
                description 'The name of the bridge interface.' ;
                type ncd:ifname ;

                mandatory true ;
              }

              ncd:revise-date 2017-12-13 ;
            }

            container broadcast-traffic-rate-params {
              description 'The traffic rate parameters of broadcast.' ;
              presence broadcast-traffic-rate-params ;
              leaf cir {
                description 'Committed information rate.' ;
                type uint32 {
                  range "0 | 1..4294967295" {
                    description 'CIR' ;
                  }

                }

                units kbps ;
                mandatory true ;
              }

              leaf cbs {
                description 'Committed burst size.' ;
                type uint32 {
                  range 1..4294967295 {
                    description 'CBS' ;
                  }

                }

                units KB ;
                mandatory true ;
              }

              leaf pir {
                description 'Peak information rate.' ;
                type uint32 {
                  range "0 | 1..4294967295" {
                    description 'PIR' ;
                  }

                }

                units kbps ;
                mandatory true ;
              }

              leaf pbs {
                description 'Peak burst size.' ;
                type uint32 {
                  range 1..4294967295 {
                    description 'PBS' ;
                  }

                }

                units KB ;
                mandatory true ;
              }

              ncd:revise-date 2020-12-25 ;
            }

            container unknown-multicast-traffic-rate-params {
              description 'The traffic rate parameters of multicast.' ;
              presence unknown-multicast-traffic-rate-params ;
              leaf cir {
                description 'Committed information rate.' ;
                type uint32 {
                  range "0 | 1..4294967295" {
                    description 'CIR' ;
                  }

                }

                units kbps ;
                mandatory true ;
              }

              leaf cbs {
                description 'Committed burst size.' ;
                type uint32 {
                  range 1..4294967295 {
                    description 'CBS' ;
                  }

                }

                units KB ;
                mandatory true ;
              }

              leaf pir {
                description 'Peak information rate.' ;
                type uint32 {
                  range "0 | 1..4294967295" {
                    description 'PIR' ;
                  }

                }

                units kbps ;
                mandatory true ;
              }

              leaf pbs {
                description 'Peak burst size.' ;
                type uint32 {
                  range 1..4294967295 {
                    description 'CBS' ;
                  }

                }

                units KB ;
                mandatory true ;
              }

              ncd:revise-date 2020-12-25 ;
            }

            container unknown-unicast-traffic-rate-params {
              description 'The traffic rate parameters of unknown-unicast.' ;
              presence unknown-unicast-traffic-rate-params ;
              leaf cir {
                description 'Committed information rate.' ;
                type uint32 {
                  range "0 | 1..4294967295" {
                    description 'CIR' ;
                  }

                }

                units kbps ;
                mandatory true ;
              }

              leaf cbs {
                description 'Committed burst size.' ;
                type uint32 {
                  range 1..4294967295 {
                    description 'CBS' ;
                  }

                }

                units KB ;
                mandatory true ;
              }

              leaf pir {
                description 'Peak information rate.' ;
                type uint32 {
                  range "0 | 1..4294967295" {
                    description 'PIR' ;
                  }

                }

                units kbps ;
                mandatory true ;
              }

              leaf pbs {
                description 'Peak burst size.' ;
                type uint32 {
                  range 1..4294967295 {
                    description 'CBS' ;
                  }

                }

                units KB ;
                mandatory true ;
              }

              ncd:revise-date 2020-12-25 ;
            }

          }

        }

        container mspw-instances {
          description 'The MSPW instances configuration info.' ;
          list mspw-instance {
            description 'The MSPW instance configuration info.' ;
            key instance-name ;
            leaf instance-name {
              description 'The name of the MSPW instance.' ;
              type string {
                length 1..32 {
                  description 'The length of instance name.' ;
                }

              }

            }

            leaf encapsulation-pw-type {
              description 'The PW type of the MSPW instance.' ;
              type enumeration {
                enum dlciOld {
                  value 1 ;
                  description 'The PW type of the MSPW is FR-DLCI old.' ;
                }

                enum atmSdu {
                  value 2 ;
                  description 'The PW type of the MSPW is ATM-AAL5-SDU.' ;
                }

                enum atmCell {
                  value 3 ;
                  description 'The PW type of the MSPW is ATM-CELL.' ;
                }

                enum vlan {
                  value 4 ;
                  description 'The PW type of the MSPW is VLAN.' ;
                }

                enum ethernet {
                  value 5 ;
                  description 'The PW type of the MSPW is ethernet.' ;
                }

                enum hdlc {
                  value 6 ;
                  description 'The PW type of the MSPW is HDLC.' ;
                }

                enum ppp {
                  value 7 ;
                  description 'The PW type of the MSPW is PPP.' ;
                }

                enum sdhCESoM {
                  value 8 ;
                  description 'The PW type of the MSPW is SONET/SDH Circuit Emulation Service over MPLS.' ;
                }

                enum atmVCCn {
                  value 9 ;
                  description 'The PW type of the MSPW is ATM n-to-one VCC.' ;
                }

                enum atmVPCn {
                  value 10 ;
                  description 'The PW type of the MSPW is ATM n-to-one VPC.' ;
                }

                enum ipL2 {
                  value 11 ;
                  description 'The PW type of the MSPW is IP-L2.' ;
                }

                enum atmVCC1 {
                  value 12 ;
                  description 'The PW type of the MSPW is ATM one-to-one VCC.' ;
                }

                enum atmVPC1 {
                  value 13 ;
                  description 'The PW type of the MSPW is ATM one-to-one VPC.' ;
                }

                enum atmPDU {
                  value 14 ;
                  description 'The PW type of the MSPW is ATM AAL5 PDU VCC.' ;
                }

                enum frPort {
                  value 15 ;
                  description 'The PW type of the MSPW is FR port.' ;
                }

                enum sdhCEoP {
                  value 16 ;
                  description 'The PW type of the MSPW is SONET/SDH Circuit Emulation over Packet.' ;
                }

                enum saTopE1 {
                  value 17 ;
                  description 'The PW type of the MSPW is Structure-agnostic E1 over Packet.' ;
                }

                enum saTopT1 {
                  value 18 ;
                  description 'The PW type of the MSPW is Structure-agnostic T1 (DS1) over Packet.' ;
                }

                enum saTopE3 {
                  value 19 ;
                  description 'The PW type of the MSPW is Structure-agnostic E3 over Packet.' ;
                }

                enum saTopT3 {
                  value 20 ;
                  description 'The PW type of the MSPW is Structure-agnostic T3 (DS3) over Packet.' ;
                }

                enum ceSoPSNB {
                  value 21 ;
                  description 'The PW type of the MSPW is CESoPSN basic.' ;
                }

                enum tdmAAL1 {
                  value 22 ;
                  description 'The PW type of the MSPW is TDMoIP AAL1.' ;
                }

                enum ceSoPSNC {
                  value 23 ;
                  description 'The PW type of the MSPW is CESoPSN TDM with CAS.' ;
                }

                enum tdmAAL2 {
                  value 24 ;
                  description 'The PW type of the MSPW is TDMoIP AAL2.' ;
                }

                enum dlciNew {
                  value 25 ;
                  description 'The PW type of the MSPW is FR-DLCI.' ;
                }

              }

              mandatory true ;
            }

            leaf description {
              description 'The description of the MSPW instance.' ;
              type ncd:string-with-blank {
                length 1..104 {
                  description 'The description range of instance.' ;
                }

              }

            }

            leaf shutdown {
              description 'The enable status of the MSPW instance.' ;
              type enumeration {
                enum disable {
                  value 0 ;
                  description 'The status of the MSPW instance is disable.' ;
                }

                enum enable {
                  value 1 ;
                  description 'The status of the MSPW instance is enable.' ;
                }

              }

              default enable ;
            }

            leaf cbit-conflict {
              description 'The control-word conflict function of the MSPW instance.' ;
              type enumeration {
                enum disable {
                  value 1 ;
                  description 'Cbit conflict is disable.' ;
                }

                enum enable {
                  value 2 ;
                  description 'Cbit conflict is enable.' ;
                }

              }

              default disable ;
            }

            leaf status-terminal {
              description 'Terminal or not the status notification.' ;
              type enumeration {
                enum disable {
                  value 0 ;
                  description 'Not terminal the status notification.' ;
                }

                enum enable {
                  value 1 ;
                  description 'Terminal the status notification.' ;
                }

              }

              default disable ;
            }

            leaf oam-mapping {
              description 'The oam-mapping flag of the MSPW.' ;
              type enumeration {
                enum disable {
                  value 0 ;
                  description 'The oam-mapping flag is disable.' ;
                }

                enum enable {
                  value 1 ;
                  description 'The oam-mapping flag is enable.' ;
                }

              }

              default disable ;
              ncd:revise-date 2015-04-20 ;
            }

            container traffic-statistics-params {
              if-feature instances-traffic-statistics ;

              description 'The traffic statistics parameters of MSPW instance.' ;
              leaf traffic-enable {
                description 'The traffic statistics status of MSPW service.' ;
                type enumeration {
                  enum disable {
                    value 0 ;
                    description 'The traffic statistics status of MSPW service is disable.' ;
                  }

                  enum enable {
                    value 1 ;
                    description 'The traffic statistics status of MSPW service is enable.' ;
                  }

                }

                default disable ;
              }

              leaf unicast-inrate-bps {
                description 'The unicast input bytes rate.' ;
                type uint64 {
                  range 1..18446744073709551615 {
                    description 'The range of unicast input bytes.' ;
                  }

                }

                units bps ;
              }

              leaf unicast-inrate-pps {
                description 'The unicast input packets rate.' ;
                type uint32 {
                  range 1..4294967295 {
                    description 'The range of unicast input packets rate.' ;
                  }

                }

                units pps ;
              }

              leaf broadcast-inrate-bps {
                description 'The broadcast input bytes rate.' ;
                type uint64 {
                  range 1..18446744073709551615 {
                    description 'The range of broadcast input bytes.' ;
                  }

                }

                units bps ;
              }

              leaf broadcast-inrate-pps {
                description 'The broadcast input packets rate.' ;
                type uint32 {
                  range 1..4294967295 {
                    description 'The range of broadcast input packets rate.' ;
                  }

                }

                units pps ;
              }

              leaf drop-inrate-bps {
                description 'The drop input bytes rate.' ;
                type uint64 {
                  range 1..18446744073709551615 {
                    description 'The range of drop input bytes.' ;
                  }

                }

                units bps ;
              }

              leaf drop-inrate-pps {
                description 'The drop input packets rate.' ;
                type uint32 {
                  range 1..4294967295 {
                    description 'The range of drop input packets rate.' ;
                  }

                }

                units pps ;
              }

            }

            container remote-parameters {
              if-feature mspw-remote-parameters ;

              description 'Remote parameters of MSPW instance.' ;
              leaf mtu {
                description 'The MTU value of the remote interface parameter.' ;
                type uint16 {
                  range 60..65535 {
                    description 'The value of MTU.' ;
                  }

                }

                default 1500 ;
              }

              leaf intf-description {
                description 'Interface description of the remote interface parameter.' ;
                type ncd:string-with-blank {
                  length 1..80 {
                    description 'The length of remote access interface description.' ;
                  }

                }

              }

              leaf fragment {
                description 'Fragmentation flag of the remote interface parameter.' ;
                type enumeration {
                  enum disable {
                    value 0 ;
                    description 'Fragmentation flag is disable.' ;
                  }

                  enum enable {
                    value 1 ;
                    description 'Fragmentation flag is enable.' ;
                  }

                }

                default disable ;
              }

              leaf fcs-retention-headlength-flag {
                description 'Frame check sequence retention head length flag of the remote interface parameter.' ;
                type enumeration {
                  enum fcsHeadLensTwo {
                    value 1 ;
                    description 'Frame check sequence retention head length is two.' ;
                  }

                  enum fcsHeadLensFour {
                    value 2 ;
                    description 'Frame check sequence retention head length is four.' ;
                  }

                }

              }

              leaf atm-cell-connetion {
                description 'The maximum of ATM cell concatenate of the remote interface parameter.' ;
                type uint16 {
                  range 1..64 {
                    description 'The maximum of ATM cell concatenate value.' ;
                  }

                }

              }

              leaf requested-vlan-id {
                description 'Ethernet request VLAN ID of the remote interface parameter.' ;
                type uint16 {
                  range 1..4094 {
                    description 'The range of requested VLAN ID is 1-4094.' ;
                  }

                }

              }

              leaf fr-dlci-header-length {
                description 'FR DLCI header length of the remote interface parameter.' ;
                type enumeration {
                  enum dlciHeadlengthTwo {
                    value 2 ;
                    description 'FR DLCI head length is two.' ;
                  }

                  enum dlciHeadlengthThree {
                    value 3 ;
                    description 'FR DLCI head length is three.' ;
                  }

                  enum dlciHeadlengthFour {
                    value 4 ;
                    description 'FR DLCI head length is four.' ;
                  }

                }

              }

              leaf mtu-mismatch-ignore {
                description 'Ignore the MTU mismatch in the PW negotiation.' ;
                type empty ;

                ncd:revise-date 2022-09-13 ;
              }

              container tdm-parameters {
                description 'The TDM parameters of remote parameters.' ;
                leaf tdm-time-slots {
                  description 'TDM time slots count of the remote interface parameter.' ;
                  type uint16 {
                    range 1..400 {
                      description 'TDM time slots value.' ;
                    }

                  }

                }

                leaf tdm-distribute-period {
                  description 'TDM distribute period of the remote interface parameter.' ;
                  type uint8 {
                    range 2..64 {
                      description 'TDM distribute period value.' ;
                    }

                  }

                  units 125us ;
                }

                leaf tdm-rtp-header {
                  description 'The RTP header used flag of the remote interface parameter.' ;
                  type enumeration {
                    enum disable {
                      value 0 ;
                      description 'The RTP header is unused.' ;
                    }

                    enum enable {
                      value 1 ;
                      description 'The RTP header is used' ;
                    }

                  }

                  default disable ;
                }

                leaf rtp-differential-timestamp-mode {
                  description 'The RTP differential timestamp mode flag of the remote interface parameter.' ;
                  type enumeration {
                    enum disable {
                      value 0 ;
                      description 'The RTP differential timestamp mode is disable.' ;
                    }

                    enum enable {
                      value 1 ;
                      description 'The RTP differential timestamp mode is enable.' ;
                    }

                  }

                  default disable ;
                }

                leaf rtp-sync-source-id {
                  description 'The RTP synchronization source ID of the remote interface parameter.' ;
                  type uint32 {
                    range 1..4294967295 {
                      description 'The RTP synchronization source ID.' ;
                    }

                  }

                }

                leaf rtp-frequency {
                  description 'The RTP frequency of the remote interface parameter.' ;
                  type uint16 {
                    range 1..65535 {
                      description 'The RTP frequency value.' ;
                    }

                  }

                  units 8kHz ;
                }

                leaf payload-type {
                  description 'TDM payload type of the remote interface parameter.' ;
                  type uint8 {
                    range 1..127 {
                      description 'TDM payload type value.' ;
                    }

                  }

                }

                leaf cas-trunk-type {
                  description 'TDM CAS trunk type of the remote interface parameter.' ;
                  type enumeration {
                    enum E1 {
                      value 1 ;
                      description 'TDM CAS trunk type is E1.' ;
                    }

                    enum "T1/ESF" {
                      value 2 ;
                      description 'TDM CAS trunk type is T1/ESF.' ;
                    }

                    enum T1Sf {
                      value 3 ;
                      description 'TDM CAS trunk type is T1SF.' ;
                    }

                  }

                }

                leaf signal-packets-mode {
                  description 'TDM signalling packets type of the remote interface parameter.' ;
                  type enumeration {
                    enum non-transmitted {
                      value 0 ;
                      description 'TDM signalling packets type is not transmitted.' ;
                    }

                    enum together-with-data {
                      value 1 ;
                      description 'TDM signalling packets type is together with data.' ;
                    }

                    enum apart-from-data-just-here {
                      value 2 ;
                      description 'TDM signalling packets type is apart from data and transmitted with current PW.' ;
                    }

                    enum apartFromDataOverThere {
                      value 3 ;
                      description 'TDM signalling packets type is apart from data and transmitted with another PW.' ;
                    }

                  }

                  default non-transmitted ;
                }

                leaf dba-trigger-event-ais {
                  description 'TDM CEP DBA trigger event of AIS flag of the remote interface parameter.' ;
                  type enumeration {
                    enum disable {
                      value 0 ;
                      description 'TDM CEP DBA trigger event of AIS flag is disable.' ;
                    }

                    enum enable {
                      value 1 ;
                      description 'TDM CEP DBA trigger event of AIS flag is enable.' ;
                    }

                  }

                  default disable ;
                }

                leaf dba-trigger-event-une {
                  description 'TDM CEP DBA trigger event of UNE flag of the remote interface parameter.' ;
                  type enumeration {
                    enum disable {
                      value 0 ;
                      description 'TDM CEP DBA trigger event of UNE flag is disable.' ;
                    }

                    enum enable {
                      value 1 ;
                      description 'TDM CEP DBA trigger event of UNE flag is enable.' ;
                    }

                  }

                  default disable ;
                }

                leaf emb-extent-head-used {
                  description 'TDM CEP EMB flag of the remote interface parameter.' ;
                  type enumeration {
                    enum disable {
                      value 0 ;
                      description 'TDM CEP EMB flag is disable.' ;
                    }

                    enum enable {
                      value 1 ;
                      description 'TDM CEP EMB flag is enable.' ;
                    }

                  }

                  default disable ;
                }

                leaf async-type {
                  description 'TDM CEP Async E3/T3 bandwidth reduction type of the remote interface parameter.' ;
                  type enumeration {
                    enum t3 {
                      value 1 ;
                      description 'TDM CEP Async E3/T3 bandwidth reduction type is t3.' ;
                    }

                    enum e3 {
                      value 2 ;
                      description 'TDM CEP Async E3/T3 bandwidth reduction type is e3.' ;
                    }

                  }

                }

                leaf cep-type {
                  description 'TDM CEP type of the remote interface parameter.' ;
                  type enumeration {
                    enum SPE {
                      value 0 ;
                      description 'TDM CEP connection type is SPE.' ;
                    }

                    enum VT {
                      value 1 ;
                      description 'TDM CEP connection type is VT.' ;
                    }

                    enum FractionalSPE {
                      value 2 ;
                      description 'TDM CEP connection type is fractional SPE.' ;
                    }

                  }

                  default SPE ;
                }

                leaf aal1-cells-per-packet {
                  description 'TDM AAL1 cell per packet of the remote interface parameter.' ;
                  type uint16 {
                    range 1..100 {
                      description 'TDM AAL1 cell per packet value.' ;
                    }

                  }

                }

                leaf aal1-mode {
                  description 'TDM AAL1 mode of the remote interface parameter.' ;
                  type enumeration {
                    enum unstructured {
                      value 0 ;
                      description 'TDM AAL1 mode is unstructured.' ;
                    }

                    enum structured {
                      value 1 ;
                      description 'TDM AAL1 mode is structured.' ;
                    }

                    enum structuredWithCas {
                      value 2 ;
                      description 'TDM AAL1 mode is structured with CAS.' ;
                    }

                  }

                  default structured ;
                }

                leaf aal2-max-duration {
                  description 'TDM AAL2 max duration of the remote interface parameter.' ;
                  type uint32 {
                    range 1..64 {
                      description 'TDM AAL2 max duration value.' ;
                    }

                  }

                  units 125us ;
                }

                leaf aal2-vad-mode {
                  description 'TDM AAL2 VAD mode of the remote interface parameter.' ;
                  type enumeration {
                    enum by-signal {
                      value 0 ;
                      description 'TDM AAL2 VAD mode is by signal.' ;
                    }

                    enum by-dectection {
                      value 1 ;
                      description 'TDM AAL2 VAD mode is by detection.' ;
                    }

                    enum always-active {
                      value 2 ;
                      description 'TDM AAL2 VAD mode is always active.' ;
                    }

                  }

                  default by-signal ;
                }

              }

            }

            container mspw-pw-bind {
              description 'MSPW PW binding instance info.' ;
              list pw-instance-bind {
                description 'PW binding instance configuration info.' ;
                key pw-name ;
                leaf pw-name {
                  description 'The name of the PW in the bind.' ;
                  type ncd:ifname ;

                }

              }

            }

          }

        }

        container vlss-instances {
          if-feature vlss-instances ;

          description 'The VLSS instances configuration info.' ;
          list vlss-instance {
            description 'The VLSS instance configuration info.' ;
            key instance-name ;
            leaf instance-name {
              description 'The name of the VLSS instance.' ;
              type string {
                length 1..32 {
                  description 'The length of instance name.' ;
                }

              }

            }

            leaf description {
              description 'The description of the VLSS instance.' ;
              type ncd:string-with-blank {
                length 1..104 {
                  description 'The description range of instance.' ;
                }

              }

            }

            leaf shutdown {
              description 'The enable status of the VLSS instance.' ;
              type enumeration {
                enum disable {
                  value 0 ;
                  description 'The status of the VLSS instance is disable.' ;
                }

                enum enable {
                  value 1 ;
                  description 'The status of the VLSS instance is enable.' ;
                }

              }

              default enable ;
            }

            leaf mtu {
              type uint16 {
                range 60..65535 {
                  description 'The range of MTU.' ;
                }

              }

              description 'The MTU value of the VLSS instance.' ;
              ncd:revise-date 2024-01-02 ;
            }

            leaf mtu-mismatch-ignore {
              type empty ;

              description 'Ignore the MTU mismatch in the PW negotiation.' ;
              ncd:revise-date 2025-06-03 ;
            }

            leaf uni-egress-adjust-keep-nni-inner-vlan {
              status obsolete {
                ncd:revise-date 2019-09-29 ;
              }

              description 'Config UNI egress-adjust.' ;
              type enumeration {
                enum disable {
                  value 0 ;
                  description 'The egress adjust keep-nni-inner-vlan is disable.' ;
                }

                enum enable {
                  value 1 ;
                  description 'The egress adjust keep-nni-inner-vlan is enable.' ;
                }

              }

              default disable ;
              ncd:revise-date 2019-06-13 ;
            }

            leaf uni-egress-adjust-nni-inner-vlan {
              description 'Config UNI egress-adjust.' ;
              type enumeration {
                enum changable {
                  value 0 ;
                  description 'The egress adjust nni-inner-vlan is changeable.' ;
                }

                enum unchangable {
                  value 1 ;
                  description 'The egress adjust keep-nni-inner-vlan is unchangeable.' ;
                }

              }

              ncd:revise-date 2019-09-29 ;
            }

            container l2protocol-control-policy {
              description 'L2protocol packet filtering function.' ;
              leaf abm {
                description 'All bridge multicast frame protocol packet filtering.' ;
                type enumeration {
                  enum tunnelled {
                    value 0 ;
                    description 'All bridge multicast frame protocol packet filtering is tunnelled.' ;
                  }

                  enum dropped {
                    value 1 ;
                    description 'All bridge multicast frame protocol packet filtering is dropped.' ;
                  }

                  enum terminated {
                    value 2 ;
                    description 'All bridge multicast frame protocol packet filtering is terminated.' ;
                  }

                }

              }

              leaf dot1x {
                description '802.1x protocol frame packet filtering.' ;
                type enumeration {
                  enum tunnelled {
                    value 0 ;
                    description '802.1x protocol frame packet filtering is tunnelled.' ;
                  }

                  enum dropped {
                    value 1 ;
                    description '802.1x protocol frame packet filtering is dropped.' ;
                  }

                  enum terminated {
                    value 2 ;
                    description '802.1x protocol frame packet filtering is terminated.' ;
                  }

                }

              }

              leaf dot3x {
                description '802.3x protocol frame packet filtering.' ;
                type enumeration {
                  enum tunnelled {
                    value 0 ;
                    description '802.3x protocol frame packet filtering is tunnelled.' ;
                  }

                  enum dropped {
                    value 1 ;
                    description '802.3x protocol frame packet filtering is dropped.' ;
                  }

                  enum terminated {
                    value 2 ;
                    description '802.3x protocol frame packet filtering is terminated.' ;
                  }

                }

              }

              leaf garp {
                description 'GARP protocol packet filtering.' ;
                type enumeration {
                  enum tunnelled {
                    value 0 ;
                    description 'GARP protocol packet filtering is tunnelled.' ;
                  }

                  enum dropped {
                    value 1 ;
                    description 'GARP protocol packet filtering is dropped.' ;
                  }

                  enum terminated {
                    value 2 ;
                    description 'GARP protocol packet filtering is terminated.' ;
                  }

                }

              }

              leaf gmrp {
                description 'GMRP protocol packet filtering.' ;
                type enumeration {
                  enum tunnelled {
                    value 0 ;
                    description 'GMRP protocol packet filtering is tunnelled.' ;
                  }

                  enum dropped {
                    value 1 ;
                    description 'GMRP protocol packet filtering is dropped.' ;
                  }

                  enum terminated {
                    value 2 ;
                    description 'GMRP protocol packet filtering is terminated.' ;
                  }

                }

              }

              leaf gvrp {
                description 'GVRP protocol packet filtering.' ;
                type enumeration {
                  enum tunnelled {
                    value 0 ;
                    description 'GVRP protocol packet filtering is tunnelled.' ;
                  }

                  enum dropped {
                    value 1 ;
                    description 'GVRP protocol packet filtering is dropped.' ;
                  }

                  enum terminated {
                    value 2 ;
                    description 'GVRP protocol packet filtering is terminated.' ;
                  }

                }

              }

              leaf cisco {
                description 'CISCO protocol packet filtering.' ;
                type enumeration {
                  enum tunnelled {
                    value 0 ;
                    description 'CISCO protocol packet filtering is tunnelled.' ;
                  }

                  enum dropped {
                    value 1 ;
                    description 'CISCO protocol packet filtering is dropped.' ;
                  }

                  enum terminated {
                    value 2 ;
                    description 'CISCO protocol packet filtering is terminated.' ;
                  }

                }

              }

              leaf dldp {
                description 'DLDP protocol packet filtering.' ;
                type enumeration {
                  enum tunnelled {
                    value 0 ;
                    description 'DLDP protocol packet filtering is tunnelled.' ;
                  }

                  enum dropped {
                    value 1 ;
                    description 'DLDP protocol packet filtering is dropped.' ;
                  }

                  enum terminated {
                    value 2 ;
                    description 'DLDP protocol packet filtering is terminated.' ;
                  }

                }

              }

              leaf efm {
                description 'EFM protocol packet filtering.' ;
                type enumeration {
                  enum tunnelled {
                    value 0 ;
                    description 'EFM protocol packet filtering is tunnelled.' ;
                  }

                  enum dropped {
                    value 1 ;
                    description 'EFM protocol packet filtering is dropped.' ;
                  }

                  enum terminated {
                    value 2 ;
                    description 'EFM protocol packet filtering is terminated.' ;
                  }

                }

              }

              leaf cfm {
                description 'CFM protocol packet filtering.' ;
                type enumeration {
                  enum tunnelled {
                    value 0 ;
                    description 'EFM protocol packet filtering is tunnelled.' ;
                  }

                  enum dropped {
                    value 1 ;
                    description 'EFM protocol packet filtering is dropped.' ;
                  }

                  enum terminated {
                    value 2 ;
                    description 'EFM protocol packet filtering is terminated.' ;
                  }

                }

              }

              leaf pvst {
                description 'PVST protocol packet filtering.' ;
                type enumeration {
                  enum tunnelled {
                    value 0 ;
                    description 'PVST protocol packet filtering is tunnelled.' ;
                  }

                  enum dropped {
                    value 1 ;
                    description 'PVST protocol packet filtering is dropped.' ;
                  }

                  enum terminated {
                    value 2 ;
                    description 'PVST protocol packet filtering is terminated.' ;
                  }

                }

              }

              leaf zdp {
                description 'ZDP protocol packet filtering.' ;
                type enumeration {
                  enum tunnelled {
                    value 0 ;
                    description 'ZDP protocol packet filtering is tunnelled.' ;
                  }

                  enum dropped {
                    value 1 ;
                    description 'ZDP protocol packet filtering is dropped.' ;
                  }

                  enum terminated {
                    value 2 ;
                    description 'ZDP protocol packet filtering is terminated.' ;
                  }

                }

              }

              leaf lacp {
                description 'LACP protocol packet filtering.' ;
                type enumeration {
                  enum tunnelled {
                    value 0 ;
                    description 'LACP protocol packet filtering is tunnelled.' ;
                  }

                  enum dropped {
                    value 1 ;
                    description 'LACP protocol packet filtering is dropped.' ;
                  }

                  enum terminated {
                    value 2 ;
                    description 'LACP protocol packet filtering is terminated.' ;
                  }

                }

              }

              leaf lldp {
                description 'LLDP protocol packet filtering.' ;
                type enumeration {
                  enum tunnelled {
                    value 0 ;
                    description 'LLDP protocol packet filtering is tunnelled.' ;
                  }

                  enum dropped {
                    value 1 ;
                    description 'LLDP protocol packet filtering is dropped.' ;
                  }

                  enum terminated {
                    value 2 ;
                    description 'LLDP protocol packet filtering is terminated.' ;
                  }

                }

              }

              leaf stp {
                description 'STP protocol packet filtering.' ;
                type enumeration {
                  enum tunnelled {
                    value 0 ;
                    description 'STP protocol packet filtering is tunnelled.' ;
                  }

                  enum dropped {
                    value 1 ;
                    description 'STP protocol packet filtering is dropped.' ;
                  }

                  enum terminated {
                    value 2 ;
                    description 'STP protocol packet filtering is terminated.' ;
                  }

                  enum tunnelled-monitored {
                    value 3 ;
                    description 'STP protocol packet filtering is tunnelled-monitored.' ;
                  }

                }

              }

              leaf erps {
                description 'ERPS protocol packet filtering.' ;
                type enumeration {
                  enum tunnelled {
                    value 0 ;
                    description 'ERPS protocol packet filtering is tunnelled.' ;
                  }

                  enum dropped {
                    value 1 ;
                    description 'ERPS protocol packet filtering is dropped.' ;
                  }

                  enum terminated {
                    value 2 ;
                    description 'ERPS protocol packet filtering is terminated.' ;
                  }

                }

              }

              leaf udld {
                description 'UDLD protocol packet filtering.' ;
                type enumeration {
                  enum tunnelled {
                    value 0 ;
                    description 'UDLD protocol packet filtering is tunnelled.' ;
                  }

                  enum dropped {
                    value 1 ;
                    description 'UDLD protocol packet filtering is dropped.' ;
                  }

                  enum terminated {
                    value 2 ;
                    description 'UDLD protocol packet filtering is terminated.' ;
                  }

                }

              }

              leaf vtp {
                description 'VTP protocol packet filtering.' ;
                type enumeration {
                  enum tunnelled {
                    value 0 ;
                    description 'VTP protocol packet filtering is tunnelled.' ;
                  }

                  enum dropped {
                    value 1 ;
                    description 'VTP protocol packet filtering is dropped.' ;
                  }

                  enum terminated {
                    value 2 ;
                    description 'VTP protocol packet filtering is terminated.' ;
                  }

                }

              }

              leaf zesr {
                description 'ZESR protocol packet filtering.' ;
                type enumeration {
                  enum tunnelled {
                    value 0 ;
                    description 'ZESR protocol packet filtering is tunnelled.' ;
                  }

                  enum dropped {
                    value 1 ;
                    description 'ZESR protocol packet filtering is dropped.' ;
                  }

                  enum terminated {
                    value 2 ;
                    description 'ZESR protocol packet filtering is terminated.' ;
                  }

                }

              }

              leaf l2bfd {
                description 'L2BFD protocol packet filtering.' ;
                type enumeration {
                  enum tunnelled {
                    value 0 ;
                    description 'L2BFD protocol packet filtering is tunnelled.' ;
                  }

                  enum terminated {
                    value 2 ;
                    description 'L2BFD protocol packet filtering is terminated.' ;
                  }

                }

              }

              leaf mac-control {
                description 'MAC-control protocol packet filtering.' ;
                type enumeration {
                  enum tunnelled {
                    value 0 ;
                    description 'MAC-control protocol packet filtering is tunnelled.' ;
                  }

                  enum dropped {
                    value 1 ;
                    description 'MAC-control protocol packet filtering is dropped.' ;
                  }

                  enum terminated {
                    value 2 ;
                    description 'MAC-control protocol packet filtering is terminated.' ;
                  }

                }

                ncd:revise-date 2023-03-25 ;
              }

              container user-protocol-template {
                description 'The template of user protocol.' ;
                presence user-protocol-template ;
                leaf user-protocol-name {
                  description 'The class name of user protocol.' ;
                  type string {
                    length 1..31 {
                      description 'The length of user protocol class name.' ;
                    }

                  }

                  mandatory true ;
                }

                leaf user-protocol-action {
                  description 'User protocol template action.' ;
                  type enumeration {
                    enum tunnelled {
                      value 0 ;
                      description 'User protocol template action is tunnelled.' ;
                    }

                    enum dropped {
                      value 1 ;
                      description 'User protocol template action is dropped.' ;
                    }

                    enum terminated {
                      value 2 ;
                      description 'User protocol template action is terminated.' ;
                    }

                  }

                  mandatory true ;
                }

              }

              ncd:revise-date 2021-06-07 ;
            }

            container traffic-statistics-params {
              if-feature instances-traffic-statistics ;

              if-feature vlss-instances ;

              description 'The traffic statistics of VLSS service.' ;
              leaf traffic-enable {
                description 'The traffic statistics status of VLSS service.' ;
                type enumeration {
                  enum disable {
                    value 0 ;
                    description 'The traffic statistics status of VLSS service is disable.' ;
                  }

                  enum enable {
                    value 1 ;
                    description 'The traffic statistics status of VLSS service is enable.' ;
                  }

                }

                default disable ;
              }

              leaf unicast-inrate-bps {
                description 'The unicast input bytes rate.' ;
                type uint64 {
                  range 1..18446744073709551615 {
                    description 'The range of unicast input bytes.' ;
                  }

                }

                units bps ;
              }

              leaf unicast-inrate-pps {
                description 'The unicast input packets rate.' ;
                type uint32 {
                  range 1..4294967295 {
                    description 'The range of unicast input packets rate.' ;
                  }

                }

                units pps ;
              }

              leaf broadcast-inrate-bps {
                description 'The broadcast input bytes rate.' ;
                type uint64 {
                  range 1..18446744073709551615 {
                    description 'The range of broadcast input bytes.' ;
                  }

                }

                units bps ;
              }

              leaf broadcast-inrate-pps {
                description 'The broadcast input packets rate.' ;
                type uint32 {
                  range 1..4294967295 {
                    description 'The range of broadcast input packets rate.' ;
                  }

                }

                units pps ;
              }

              leaf drop-inrate-bps {
                description 'The drop input bytes rate.' ;
                type uint64 {
                  range 1..18446744073709551615 {
                    description 'The range of drop input bytes.' ;
                  }

                }

                units bps ;
              }

              leaf drop-inrate-pps {
                description 'The drop input packets rate.' ;
                type uint32 {
                  range 1..4294967295 {
                    description 'The range of drop input packets rate.' ;
                  }

                }

                units pps ;
              }

            }

            container vlss-ac-bind {
              description 'VLSS AC binding instance info.' ;
              list ac-instance-bind {
                description 'AC binding instance configuration info.' ;
                key ac-name ;
                leaf ac-name {
                  description 'The name of the AC in the bind.' ;
                  type ncd:ifname ;

                }

                leaf nni {
                  description 'The NNI flag of the bind.' ;
                  type enumeration {
                    enum disable {
                      value 0 ;
                      description 'The NNI flag is disable.' ;
                    }

                    enum enable {
                      value 1 ;
                      description 'The NNI flag is enable.' ;
                    }

                  }

                  default disable ;
                  ncd:revise-date 2018-09-07 ;
                }

                leaf description {
                  description 'The description of the interface.' ;
                  type ncd:string-with-blank {
                    length 1..104 {
                      description 'The description range of interface.' ;
                    }

                  }

                  ncd:revise-date 2017-08-25 ;
                }

                leaf vpws-id {
                  description 'VPWS ID.' ;
                  type uint32 {
                    range 1..4294967294 {
                      description 'The range of VPWS ID.' ;
                    }

                  }

                  ncd:revise-date 2023-02-14 ;
                }

                choice ac-type {
                  description 'The access type of VLSS instance,All the access type is mutual exclusion.' ;
                  case ethernet {
                    description 'The ethernet access type.' ;
                    container ethernet-params {
                      description 'Ethernet access type parameters.' ;
                      presence ethernet-params ;
                      leaf ethernet {
                        description 'Ethernet access type.' ;
                        type empty ;

                        mandatory true ;
                      }

                      leaf traffic-enable {
                        description 'The traffic statistics enable flag of the ethernet parameter.' ;
                        type enumeration {
                          enum disable {
                            value 0 ;
                            description 'The traffic statistics flag is disable.' ;
                          }

                          enum enable {
                            value 1 ;
                            description 'The traffic statistics flag is enable.' ;
                          }

                        }

                        default disable ;
                      }

                      leaf ingress-adjust-push {
                        description 'The ingress adjust push flag of the ethernet parameter.' ;
                        type enumeration {
                          enum disable {
                            value 0 ;
                            description 'The ingress adjust push flag of the ethernet parameter is disable.' ;
                          }

                          enum enable {
                            value 1 ;
                            description 'The ingress adjust push flag of the ethernet parameter is enable.' ;
                          }

                        }

                        default disable ;
                      }

                      leaf push-vlan-id {
                        description 'The ingress adjust push VLAN ID of the ethernet parameter.' ;
                        type uint16 {
                          range 1..4094 {
                            description 'The range of push VLAN ID is 1-4094.' ;
                          }

                        }

                      }

                      leaf push-tpid {
                        description 'The ingress adjust push TPID of the ethernet parameter.' ;
                        type enumeration {
                          enum 8100 {
                            value 0 ;
                            description 'The ingress adjust push TPID value is 0x8100.' ;
                          }

                          enum 9100 {
                            value 1 ;
                            description 'The ingress adjust push TPID value is 0x9100.' ;
                          }

                          enum 9200 {
                            value 2 ;
                            description 'The ingress adjust push TPID value is 0x9200.' ;
                          }

                          enum 88a8 {
                            value 3 ;
                            description 'The ingress adjust push TPID value is 0x88a8.' ;
                          }

                        }

                        ncd:revise-date 2019-08-06 ;
                      }

                      leaf ingress-adjust-rewrite {
                        description 'The ingress adjust rewrite flag of the ethernet parameter.' ;
                        type enumeration {
                          enum disable {
                            value 0 ;
                            description 'The ingress adjust rewrite flag of the ethernet parameter is disable.' ;
                          }

                          enum enable {
                            value 1 ;
                            description 'The ingress adjust rewrite flag of the ethernet parameter is enable.' ;
                          }

                        }

                        default disable ;
                      }

                      leaf rewrite-vlan-id {
                        description 'The ingress adjust rewrite VLAN ID of the ethernet parameter.' ;
                        type uint16 {
                          range 1..4094 {
                            description 'The range of rewrite VLAN ID is 1-4094.' ;
                          }

                        }

                      }

                      leaf rewrite-tpid {
                        description 'The ingress adjust rewrite TPID of the ethernet parameter.' ;
                        type enumeration {
                          enum 8100 {
                            value 0 ;
                            description 'The ingress adjust rewrite TPID value is 0x8100.' ;
                          }

                          enum 9100 {
                            value 1 ;
                            description 'The ingress adjust rewrite TPID value is 0x9100.' ;
                          }

                          enum 9200 {
                            value 2 ;
                            description 'The ingress adjust rewrite TPID value is 0x9200.' ;
                          }

                          enum 88a8 {
                            value 3 ;
                            description 'The ingress adjust rewrite TPID value is 0x88a8.' ;
                          }

                        }

                        ncd:revise-date 2019-08-06 ;
                      }

                      leaf ingress-adjust-tag-as-payload {
                        description 'The ingress tag as payload flag of the ethernet parameter.' ;
                        type enumeration {
                          enum disable {
                            value 0 ;
                            description 'The ingress tag as payload flag is disable.' ;
                          }

                          enum all {
                            value 1 ;
                            description 'The ingress tag as payload flag is from outer most.' ;
                          }

                          enum from-sub-layer {
                            value 2 ;
                            description 'The ingress tag as payload flag is from sub layer.' ;
                          }

                        }

                        default disable ;
                      }

                      leaf ingress-adjust-drop-tagged-frames {
                        description 'The ingress adjust drop tagged frames flag of the ethernet.' ;
                        type enumeration {
                          enum disable {
                            value 0 ;
                            description 'The ingress adjust drop tagged frames flag is disable.' ;
                          }

                          enum enable {
                            value 1 ;
                            description 'The ingress adjust drop tagged frames flag is enable.' ;
                          }

                        }

                      }

                      leaf ingress-adjust-uni-proxy {
                        description 'The ingress UNI proxy flag of the ethernet parameter.' ;
                        type enumeration {
                          enum disable {
                            value 0 ;
                            description 'The ingress UNI proxy flag is disable.' ;
                          }

                          enum pop-all {
                            value 1 ;
                            description 'The ingress UNI proxy flag is pop-all.' ;
                          }

                          enum pop-outer {
                            value 2 ;
                            description 'The ingress UNI proxy flag is pop-outer.' ;
                          }

                        }

                        default disable ;
                        ncd:revise-date 2018-09-07 ;
                      }

                      leaf ingress-adjust-pop-uni-tag {
                        description "The ingress adjust of pop UNI's tag." ;
                        type enumeration {
                          enum disable {
                            value 0 ;
                            description "The ingress adjust of pop UNI's tag is disable." ;
                          }

                          enum all {
                            value 1 ;
                            description "The ingress adjust of pop UNI's tag is all." ;
                          }

                          enum outer {
                            value 2 ;
                            description "The ingress adjust of pop UNI's tag is outer." ;
                          }

                        }

                        ncd:revise-date 2019-09-29 ;
                      }

                      leaf ingress-adjust-serve-as-pvid {
                        description 'The ingress UNI serve-as-pvid flag of the ethernet parameter.' ;
                        type enumeration {
                          enum disable {
                            value 0 ;
                            description 'The ingress UNI serve-as-pvid flag is disable.' ;
                          }

                          enum enable {
                            value 1 ;
                            description 'The ingress UNI serve-as-pvid flag is enable.' ;
                          }

                        }

                        default disable ;
                        ncd:revise-date 2019-06-13 ;
                      }

                      leaf monitor-ip {
                        description 'The NNI ping monitor IP address.' ;
                        type ncd:ipv4-address-none-zero ;

                      }

                      leaf monitor-mac {
                        description 'The NNI ping monitor MAC address.' ;
                        type ncd:mac-address-none-zero ;

                      }

                      leaf monitor-mode {
                        description 'The NNI ping monitor mode.' ;
                        type enumeration {
                          enum master-slave {
                            value 0 ;
                            description 'The monitor mode is master-slave.' ;
                          }

                          enum load-balance {
                            value 1 ;
                            description 'The monitor mode is load-balance.' ;
                          }

                        }

                        default master-slave ;
                      }

                      leaf lst-flag {
                        description 'The lst flag of the ethernet parameter.' ;
                        type enumeration {
                          enum disable {
                            value 0 ;
                            description 'Lst flag of the ethernet parameter is disable.' ;
                          }

                          enum enable {
                            value 1 ;
                            description 'Lst flag of the ethernet parameter is enable.' ;
                          }

                        }

                        default disable ;
                        ncd:revise-date 2019-08-06 ;
                      }

                      leaf lst-holdoff {
                        description 'Lst holdoff time.' ;
                        type uint16 {
                          range 1..1000 {
                            description 'The range of lst holdoff time.' ;
                          }

                        }

                        units 10ms ;
                        ncd:revise-date 2019-08-06 ;
                      }

                      container traffic-statistics-params {
                        if-feature ac-traffic-statistics ;

                        if-feature vlss-instances ;

                        description 'The traffic statistics parameters of ethernet access.' ;
                        leaf unicast-inrate-bps {
                          description 'The unicast input bytes rate.' ;
                          type uint64 {
                            range 1..18446744073709551615 {
                              description 'The range of unicast input bytes.' ;
                            }

                          }

                          units bps ;
                        }

                        leaf unicast-inrate-pps {
                          description 'The unicast input packets rate.' ;
                          type uint32 {
                            range 1..4294967295 {
                              description 'The range of unicast input packets rate.' ;
                            }

                          }

                          units pps ;
                        }

                        leaf broadcast-inrate-bps {
                          description 'The broadcast input bytes rate.' ;
                          type uint64 {
                            range 1..18446744073709551615 {
                              description 'The range of broadcast input bytes.' ;
                            }

                          }

                          units bps ;
                        }

                        leaf broadcast-inrate-pps {
                          description 'The broadcast input packets rate.' ;
                          type uint32 {
                            range 1..4294967295 {
                              description 'The range of broadcast input packets rate.' ;
                            }

                          }

                          units pps ;
                        }

                        leaf drop-inrate-bps {
                          description 'The drop input bytes rate.' ;
                          type uint64 {
                            range 1..18446744073709551615 {
                              description 'The range of drop input bytes.' ;
                            }

                          }

                          units bps ;
                        }

                        leaf drop-inrate-pps {
                          description 'The drop input packets rate.' ;
                          type uint32 {
                            range 1..4294967295 {
                              description 'The range of drop input packets rate.' ;
                            }

                          }

                          units pps ;
                        }

                      }

                      container udp-echo {
                        description 'Configure UDP echo function.' ;
                        leaf echo-ip {
                          description 'UDP echo IP address.' ;
                          type ncd:ipv4-address-none-zero ;

                        }

                        leaf echo-mac {
                          description 'UDP echo MAC address.' ;
                          type ncd:mac-address-none-zero ;

                        }

                        leaf echo-port-number {
                          description 'UDP echo port number.' ;
                          type uint16 {
                            range 1..65535 {
                              description 'UDP echo port number range.' ;
                            }

                          }

                        }

                      }

                      container hard-pipe {
                        description 'Configure hard pipe info.' ;
                        presence hard-pipe ;
                        leaf bandwidth {
                          description 'The bandwidth of hard pipe.' ;
                          type uint32 {
                            range 1..4294967295 {
                              description 'The range of bandwidth.' ;
                            }

                          }

                          mandatory true ;
                        }

                        leaf expand-ratio {
                          description 'The expand-ratio of hard pipe.' ;
                          type uint8 {
                            range 1..100 {
                              description 'The range of expand ratio.' ;
                            }

                          }

                          mandatory true ;
                        }

                        ncd:revise-date 2016-12-15 ;
                      }

                      container nni-egress-adjust-uni-rewrite {
                        description 'The egress adjust rewrite flag of the ethernet parameter.' ;
                        presence nni-egress-adjust-uni-rewrite ;
                        leaf outer-vlan-id {
                          description 'The egress adjust rewrite VLAN ID of the ethernet parameter.' ;
                          type uint16 {
                            range 1..4094 {
                              description 'The range of outer VLAN ID is 1-4094.' ;
                            }

                          }

                          mandatory true ;
                        }

                        leaf inner-vlan-id {
                          description 'The egress adjust rewrite inner VLAN ID of the ethernet parameter.' ;
                          type uint16 {
                            range 1..4094 {
                              description 'The range of inner VLAN ID is 1-4094.' ;
                            }

                          }

                        }

                        ncd:revise-date 2019-06-13 ;
                      }

                      container nni-egress-adjust-uni-tpid {
                        description 'Outer ether-type of remote required.' ;
                        presence nni-egress-adjust-uni-tpid ;
                        leaf outer-tpid {
                          description 'The egress adjust outer TPID value of the ethernet parameter.' ;
                          type enumeration {
                            enum 8100 {
                              value 0 ;
                              description 'The egress adjust outer TPID value is 8100.' ;
                            }

                            enum 9100 {
                              value 1 ;
                              description 'The egress adjust outer TPID value is 9100.' ;
                            }

                            enum 9200 {
                              value 2 ;
                              description 'The egress adjust outer TPID value is 9100.' ;
                            }

                            enum 88a8 {
                              value 3 ;
                              description 'The egress adjust outer TPID value is 88a8.' ;
                            }

                          }

                          mandatory true ;
                        }

                        leaf inner-tpid {
                          description 'The egress adjust inner TPID value of the ethernet parameter.' ;
                          type enumeration {
                            enum 8100 {
                              value 0 ;
                              description 'The egress adjust outer TPID value is 8100.' ;
                            }

                            enum 9100 {
                              value 1 ;
                              description 'The egress adjust outer TPID value is 9100.' ;
                            }

                            enum 9200 {
                              value 2 ;
                              description 'The egress adjust outer TPID value is 9200.' ;
                            }

                            enum 88a8 {
                              value 3 ;
                              description 'The egress adjust outer TPID value is 88a8.' ;
                            }

                          }

                        }

                        ncd:revise-date 2019-06-13 ;
                      }

                    }

                  }

                  case tdm {
                    if-feature tdm ;

                    if-feature vlss-instances ;

                    description 'The TDM access type.' ;
                    container tdm-params {
                      description 'TDM access type parameters.' ;
                      presence tdm-params ;
                      leaf tdm {
                        description 'TDM access type.' ;
                        type empty ;

                        mandatory true ;
                      }

                      leaf traffic-enable {
                        description 'The traffic statistics enable flag of the TDM parameter.' ;
                        type enumeration {
                          enum disable {
                            value 0 ;
                            description 'The traffic statistics flag is disable.' ;
                          }

                          enum enable {
                            value 1 ;
                            description 'The traffic statistics flag is enable.' ;
                          }

                        }

                        default disable ;
                      }

                      leaf distribute-period {
                        description 'The distribute period value of the TDM parameter.' ;
                        type uint8 {
                          range 2..64 {
                            description 'The distribute period value.' ;
                          }

                        }

                        units 125us ;
                      }

                      leaf jitter-buffer {
                        description 'The jitter buffer value of the TDM parameter.' ;
                        type uint16 {
                          range 1..400 {
                            description 'The jitter buffer value.' ;
                          }

                        }

                        units 125us ;
                        default 20 ;
                      }

                      leaf rtp-header {
                        description 'Configure the RTP header or not.' ;
                        type enumeration {
                          enum disable {
                            value 0 ;
                            description 'The RTP header is disable.' ;
                          }

                          enum enable {
                            value 1 ;
                            description 'The RTP header is enable.' ;
                          }

                        }

                        default disable ;
                      }

                      leaf rtp-timestamp {
                        description 'The RTP timestamp mode of the TDM parameter.' ;
                        type enumeration {
                          enum absolute {
                            value 1 ;
                            description 'RTP timestamp is absolute.' ;
                          }

                          enum differ {
                            value 2 ;
                            description 'RTP timestamp is differ.' ;
                          }

                        }

                      }

                      leaf idle-code {
                        if-feature idle-code-enum ;

                        description 'The idle code value of the TDM parameter.' ;
                        type enumeration {
                          enum 0xff {
                            value 0 ;
                            description 'The idle code is 0xff.' ;
                          }

                          enum 0x7e {
                            value 1 ;
                            description 'The idle code is 0x7e.' ;
                          }

                        }

                        default 0xff ;
                      }

                      leaf idle-code-new {
                        if-feature idle-code-range ;

                        description 'The idle code value of the TDM parameter.' ;
                        type uint8 {
                          range 0..255 {
                            description 'The value of idle code.' ;
                          }

                        }

                        default 255 ;
                        ncd:revise-date 2019-04-09 ;
                      }

                      leaf mpls-exp-value {
                        description 'The MPLS EXP value of the TDM parameter.' ;
                        type enumeration {
                          enum be {
                            value 0 ;
                            description 'The MPLS EXP value is be.' ;
                          }

                          enum af1 {
                            value 1 ;
                            description 'The MPLS EXP value is af1.' ;
                          }

                          enum af2 {
                            value 2 ;
                            description 'The MPLS EXP value is af2.' ;
                          }

                          enum af3 {
                            value 3 ;
                            description 'The MPLS EXP value is af3.' ;
                          }

                          enum af4 {
                            value 4 ;
                            description 'The MPLS EXP value is af4.' ;
                          }

                          enum ef {
                            value 5 ;
                            description 'The MPLS EXP value is ef.' ;
                          }

                          enum cs6 {
                            value 6 ;
                            description 'The MPLS EXP value is cs6.' ;
                          }

                          enum cs7 {
                            value 7 ;
                            description 'The MPLS EXP value is cs7.' ;
                          }

                        }

                        default ef ;
                      }

                      leaf structure {
                        description 'Configure TDM structure.' ;
                        type enumeration {
                          enum aware {
                            value 1 ;
                            description 'CESoPSN basic mode.' ;
                          }

                          enum aware-with-cas {
                            value 2 ;
                            description 'CESoPSN TDM with CAS.' ;
                          }

                          enum agnostic {
                            value 3 ;
                            description 'Structure-agnostic TDM over Packet.' ;
                          }

                        }

                        default agnostic ;
                      }

                      container traffic-statistics-params {
                        if-feature ac-traffic-statistics ;

                        if-feature tdm ;

                        if-feature vlss-instances ;

                        description 'The traffic statistics parameters of TDM access.' ;
                        leaf unicast-inrate-bps {
                          description 'The unicast input bytes rate.' ;
                          type uint64 {
                            range 1..18446744073709551615 {
                              description 'The range of unicast input bytes.' ;
                            }

                          }

                          units bps ;
                        }

                        leaf unicast-inrate-pps {
                          description 'The unicast input packets rate.' ;
                          type uint32 {
                            range 1..4294967295 {
                              description 'The range of unicast input packets rate.' ;
                            }

                          }

                          units pps ;
                        }

                        leaf broadcast-inrate-bps {
                          description 'The broadcast input bytes rate.' ;
                          type uint64 {
                            range 1..18446744073709551615 {
                              description 'The range of broadcast input bytes.' ;
                            }

                          }

                          units bps ;
                        }

                        leaf broadcast-inrate-pps {
                          description 'The broadcast input packets rate.' ;
                          type uint32 {
                            range 1..4294967295 {
                              description 'The range of broadcast input packets rate.' ;
                            }

                          }

                          units pps ;
                        }

                        leaf drop-inrate-bps {
                          description 'The drop input bytes rate.' ;
                          type uint64 {
                            range 1..18446744073709551615 {
                              description 'The range of drop input bytes.' ;
                            }

                          }

                          units bps ;
                        }

                        leaf drop-inrate-pps {
                          description 'The drop input packets rate.' ;
                          type uint32 {
                            range 1..4294967295 {
                              description 'The range of drop input packets rate.' ;
                            }

                          }

                          units pps ;
                        }

                      }

                      container hard-pipe {
                        description 'Configure hard pipe info.' ;
                        leaf hard-pipe-flag {
                          description 'The hard pipe enable flag of the AC.' ;
                          type enumeration {
                            enum disable {
                              value 0 ;
                              description 'The hard pipe of the AC is disable.' ;
                            }

                            enum enable {
                              value 1 ;
                              description 'The hard pipe of the AC is enable.' ;
                            }

                          }

                          default disable ;
                        }

                        ncd:revise-date 2016-12-15 ;
                      }

                    }

                  }

                  case atm {
                    if-feature atm ;

                    if-feature vlss-instances ;

                    description 'The ATM access type.' ;
                    container atm-params {
                      description 'ATM access type parameters.' ;
                      presence atm-params ;
                      leaf atm {
                        description 'ATM access type.' ;
                        type empty ;

                        mandatory true ;
                      }

                      leaf max-cells {
                        description 'Configure the maximum ATM cells to concatenate.' ;
                        type uint32 {
                          range 1..28 {
                            description 'Max cells number range.' ;
                          }

                        }

                      }

                      leaf traffic-enable {
                        description 'The traffic statistics enable flag of the ATM parameter.' ;
                        type enumeration {
                          enum disable {
                            value 0 ;
                            description 'The traffic statistics flag is disable.' ;
                          }

                          enum enable {
                            value 1 ;
                            description 'The traffic statistics flag is enable.' ;
                          }

                        }

                        default disable ;
                      }

                      container traffic-statistics-params {
                        if-feature ac-traffic-statistics ;

                        if-feature atm ;

                        if-feature vlss-instances ;

                        description 'The traffic statistics parameters of ATM access.' ;
                        leaf unicast-inrate-bps {
                          description 'The unicast input bytes rate.' ;
                          type uint64 {
                            range 1..18446744073709551615 {
                              description 'The range of unicast input bytes.' ;
                            }

                          }

                          units bps ;
                        }

                        leaf unicast-inrate-pps {
                          description 'The unicast input packets rate.' ;
                          type uint32 {
                            range 1..4294967295 {
                              description 'The range of unicast input packets rate.' ;
                            }

                          }

                          units pps ;
                        }

                        leaf broadcast-inrate-bps {
                          description 'The broadcast input bytes rate.' ;
                          type uint64 {
                            range 1..18446744073709551615 {
                              description 'The range of broadcast input bytes.' ;
                            }

                          }

                          units bps ;
                        }

                        leaf broadcast-inrate-pps {
                          description 'The broadcast input packets rate.' ;
                          type uint32 {
                            range 1..4294967295 {
                              description 'The range of broadcast input packets rate.' ;
                            }

                          }

                          units pps ;
                        }

                        leaf drop-inrate-bps {
                          description 'The drop input bytes rate.' ;
                          type uint64 {
                            range 1..18446744073709551615 {
                              description 'The range of drop input bytes.' ;
                            }

                          }

                          units bps ;
                        }

                        leaf drop-inrate-pps {
                          description 'The drop input packets rate.' ;
                          type uint32 {
                            range 1..4294967295 {
                              description 'The range of drop input packets rate.' ;
                            }

                          }

                          units pps ;
                        }

                      }

                      container hard-pipe {
                        description 'Configure hard pipe info.' ;
                        leaf hard-pipe-flag {
                          description 'The hard pipe enable flag of the AC.' ;
                          type enumeration {
                            enum disable {
                              value 0 ;
                              description 'The hard pipe of the AC is disable.' ;
                            }

                            enum enable {
                              value 1 ;
                              description 'The hard pipe of the AC is enable.' ;
                            }

                          }

                          default disable ;
                        }

                        ncd:revise-date 2016-12-15 ;
                      }

                    }

                  }

                  case ppp {
                    if-feature ppp ;

                    if-feature vlss-instances ;

                    description 'The PPP access type.' ;
                    container ppp-params {
                      description 'PPP access type parameters.' ;
                      presence ppp-params ;
                      leaf ppp {
                        description 'PPP access type.' ;
                        type empty ;

                        mandatory true ;
                      }

                      leaf traffic-enable {
                        description 'The traffic statistics enable flag of the PPP parameter.' ;
                        type enumeration {
                          enum disable {
                            value 0 ;
                            description 'The traffic statistics flag is disable.' ;
                          }

                          enum enable {
                            value 1 ;
                            description 'The traffic statistics flag is enable.' ;
                          }

                        }

                        default disable ;
                      }

                      container traffic-statistics-params {
                        if-feature ac-traffic-statistics ;

                        if-feature ppp ;

                        if-feature vlss-instances ;

                        description 'The traffic statistics parameters of PPP access.' ;
                        leaf unicast-inrate-bps {
                          description 'The unicast input bytes rate.' ;
                          type uint64 {
                            range 1..18446744073709551615 {
                              description 'The range of unicast input bytes.' ;
                            }

                          }

                          units bps ;
                        }

                        leaf unicast-inrate-pps {
                          description 'The unicast input packets rate.' ;
                          type uint32 {
                            range 1..4294967295 {
                              description 'The range of unicast input packets rate.' ;
                            }

                          }

                          units pps ;
                        }

                        leaf broadcast-inrate-bps {
                          description 'The broadcast input bytes rate.' ;
                          type uint64 {
                            range 1..18446744073709551615 {
                              description 'The range of broadcast input bytes.' ;
                            }

                          }

                          units bps ;
                        }

                        leaf broadcast-inrate-pps {
                          description 'The broadcast input packets rate.' ;
                          type uint32 {
                            range 1..4294967295 {
                              description 'The range of broadcast input packets rate.' ;
                            }

                          }

                          units pps ;
                        }

                        leaf drop-inrate-bps {
                          description 'The drop input bytes rate.' ;
                          type uint64 {
                            range 1..18446744073709551615 {
                              description 'The range of drop input bytes.' ;
                            }

                          }

                          units bps ;
                        }

                        leaf drop-inrate-pps {
                          description 'The drop input packets rate.' ;
                          type uint32 {
                            range 1..4294967295 {
                              description 'The range of drop input packets rate.' ;
                            }

                          }

                          units pps ;
                        }

                      }

                      container hard-pipe {
                        description 'Configure hard pipe info.' ;
                        leaf hard-pipe-flag {
                          description 'The hard pipe enable flag of the AC.' ;
                          type enumeration {
                            enum disable {
                              value 0 ;
                              description 'The hard pipe of the AC is disable.' ;
                            }

                            enum enable {
                              value 1 ;
                              description 'The hard pipe of the AC is enable.' ;
                            }

                          }

                          default disable ;
                        }

                        ncd:revise-date 2016-12-15 ;
                      }

                    }

                  }

                  case hdlc {
                    if-feature hdlc ;

                    if-feature vlss-instances ;

                    description 'The HDLC access type.' ;
                    container hdlc-params {
                      description 'HDLC access type parameters.' ;
                      presence hdlc-params ;
                      leaf hdlc {
                        description 'HDLC access type.' ;
                        type empty ;

                        mandatory true ;
                      }

                      leaf traffic-enable {
                        description 'The traffic statistics enable flag of the HDLC parameter.' ;
                        type enumeration {
                          enum disable {
                            value 0 ;
                            description 'The traffic statistics flag is disable.' ;
                          }

                          enum enable {
                            value 1 ;
                            description 'The traffic statistics flag is enable.' ;
                          }

                        }

                        default disable ;
                      }

                      container traffic-statistics-params {
                        if-feature ac-traffic-statistics ;

                        if-feature hdlc ;

                        if-feature vlss-instances ;

                        description 'The traffic statistics parameters of HDLC access.' ;
                        leaf unicast-inrate-bps {
                          description 'The unicast input bytes rate.' ;
                          type uint64 {
                            range 1..18446744073709551615 {
                              description 'The range of unicast input bytes.' ;
                            }

                          }

                          units bps ;
                        }

                        leaf unicast-inrate-pps {
                          description 'The unicast input packets rate.' ;
                          type uint32 {
                            range 1..4294967295 {
                              description 'The range of unicast input packets rate.' ;
                            }

                          }

                          units pps ;
                        }

                        leaf broadcast-inrate-bps {
                          description 'The broadcast input bytes rate.' ;
                          type uint64 {
                            range 1..18446744073709551615 {
                              description 'The range of broadcast input bytes.' ;
                            }

                          }

                          units bps ;
                        }

                        leaf broadcast-inrate-pps {
                          description 'The broadcast input packets rate.' ;
                          type uint32 {
                            range 1..4294967295 {
                              description 'The range of broadcast input packets rate.' ;
                            }

                          }

                          units pps ;
                        }

                        leaf drop-inrate-bps {
                          description 'The drop input bytes rate.' ;
                          type uint64 {
                            range 1..18446744073709551615 {
                              description 'The range of drop input bytes.' ;
                            }

                          }

                          units bps ;
                        }

                        leaf drop-inrate-pps {
                          description 'The drop input packets rate.' ;
                          type uint32 {
                            range 1..4294967295 {
                              description 'The range of drop input packets rate.' ;
                            }

                          }

                          units pps ;
                        }

                      }

                      container hard-pipe {
                        description 'Configure hard pipe info.' ;
                        leaf hard-pipe-flag {
                          description 'The hard pipe enable flag of the AC.' ;
                          type enumeration {
                            enum disable {
                              value 0 ;
                              description 'The hard pipe of the AC is disable.' ;
                            }

                            enum enable {
                              value 1 ;
                              description 'The hard pipe of the AC is enable.' ;
                            }

                          }

                          default disable ;
                        }

                        ncd:revise-date 2016-12-15 ;
                      }

                    }

                  }

                  case fr {
                    if-feature fr ;

                    if-feature vlss-instances ;

                    description 'The FR access type.' ;
                    container fr-params {
                      description 'FR access type parameters.' ;
                      presence fr-params ;
                      leaf fr {
                        description 'FR access type.' ;
                        type empty ;

                        mandatory true ;
                      }

                      leaf traffic-enable {
                        description 'The traffic statistics enable flag of the FR parameter.' ;
                        type enumeration {
                          enum disable {
                            value 0 ;
                            description 'The traffic statistics flag is disable.' ;
                          }

                          enum enable {
                            value 1 ;
                            description 'The traffic statistics flag is enable.' ;
                          }

                        }

                        default disable ;
                      }

                      container traffic-statistics-params {
                        if-feature ac-traffic-statistics ;

                        if-feature fr ;

                        if-feature vlss-instances ;

                        description 'The traffic statistics parameters of FR access.' ;
                        leaf unicast-inrate-bps {
                          description 'The unicast input bytes rate.' ;
                          type uint64 {
                            range 1..18446744073709551615 {
                              description 'The range of unicast input bytes.' ;
                            }

                          }

                          units bps ;
                        }

                        leaf unicast-inrate-pps {
                          description 'The unicast input packets rate.' ;
                          type uint32 {
                            range 1..4294967295 {
                              description 'The range of unicast input packets rate.' ;
                            }

                          }

                          units pps ;
                        }

                        leaf broadcast-inrate-bps {
                          description 'The broadcast input bytes rate.' ;
                          type uint64 {
                            range 1..18446744073709551615 {
                              description 'The range of broadcast input bytes.' ;
                            }

                          }

                          units bps ;
                        }

                        leaf broadcast-inrate-pps {
                          description 'The broadcast input packets rate.' ;
                          type uint32 {
                            range 1..4294967295 {
                              description 'The range of broadcast input packets rate.' ;
                            }

                          }

                          units pps ;
                        }

                        leaf drop-inrate-bps {
                          description 'The drop input bytes rate.' ;
                          type uint64 {
                            range 1..18446744073709551615 {
                              description 'The range of drop input bytes.' ;
                            }

                          }

                          units bps ;
                        }

                        leaf drop-inrate-pps {
                          description 'The drop input packets rate.' ;
                          type uint32 {
                            range 1..4294967295 {
                              description 'The range of drop input packets rate.' ;
                            }

                          }

                          units pps ;
                        }

                      }

                      container hard-pipe {
                        description 'Configure hard pipe info.' ;
                        leaf hard-pipe-flag {
                          description 'The hard pipe enable flag of the AC.' ;
                          type enumeration {
                            enum disable {
                              value 0 ;
                              description 'The hard pipe of the AC is disable.' ;
                            }

                            enum enable {
                              value 1 ;
                              description 'The hard pipe of the AC is enable.' ;
                            }

                          }

                          default disable ;
                        }

                        ncd:revise-date 2016-12-15 ;
                      }

                    }

                  }

                  case iwf-ip {
                    if-feature inter-working-ip ;

                    if-feature vlss-instances ;

                    description 'The IP inter-working access type.' ;
                    container iwf-ip-params {
                      description 'IP inter-working access type parameters.' ;
                      presence iwf-ip-params ;
                      leaf iwf-ip {
                        description 'IP inter-working access type.' ;
                        type empty ;

                        mandatory true ;
                      }

                      leaf local-ce-mac {
                        description 'The local CE MAC address of the IP inter-working parameter.' ;
                        type ncd:mac-address-none-zero ;

                      }

                      leaf remote-ip {
                        description 'The remote CE IP address of the IP inter-working parameter.' ;
                        type ncd:ipv4-address-none-zero ;

                      }

                      leaf traffic-enable {
                        description 'The traffic statistics enable flag of the IP inter-working parameter.' ;
                        type enumeration {
                          enum disable {
                            value 0 ;
                            description 'The traffic statistics flag is disable.' ;
                          }

                          enum enable {
                            value 1 ;
                            description 'The traffic statistics flag is enable.' ;
                          }

                        }

                        default disable ;
                      }

                      container traffic-statistics-params {
                        if-feature ac-traffic-statistics ;

                        if-feature inter-working-ip ;

                        if-feature vlss-instances ;

                        description 'The traffic statistics parameters of IP inter-working access.' ;
                        leaf unicast-inrate-bps {
                          description 'The unicast input bytes rate.' ;
                          type uint64 {
                            range 1..18446744073709551615 {
                              description 'The range of unicast input bytes.' ;
                            }

                          }

                          units bps ;
                        }

                        leaf unicast-inrate-pps {
                          description 'The unicast input packets rate.' ;
                          type uint32 {
                            range 1..4294967295 {
                              description 'The range of unicast input packets rate.' ;
                            }

                          }

                          units pps ;
                        }

                        leaf broadcast-inrate-bps {
                          description 'The broadcast input bytes rate.' ;
                          type uint64 {
                            range 1..18446744073709551615 {
                              description 'The range of broadcast input bytes.' ;
                            }

                          }

                          units bps ;
                        }

                        leaf broadcast-inrate-pps {
                          description 'The broadcast input packets rate.' ;
                          type uint32 {
                            range 1..4294967295 {
                              description 'The range of broadcast input packets rate.' ;
                            }

                          }

                          units pps ;
                        }

                        leaf drop-inrate-bps {
                          description 'The drop input bytes rate.' ;
                          type uint64 {
                            range 1..18446744073709551615 {
                              description 'The range of drop input bytes.' ;
                            }

                          }

                          units bps ;
                        }

                        leaf drop-inrate-pps {
                          description 'The drop input packets rate.' ;
                          type uint32 {
                            range 1..4294967295 {
                              description 'The range of drop input packets rate.' ;
                            }

                          }

                          units pps ;
                        }

                      }

                    }

                  }

                  case iwf-eth {
                    if-feature inter-working-ethernet ;

                    if-feature vlss-instances ;

                    description 'The ethernet inter-working access type.' ;
                    container iwf-eth-params {
                      description 'The ethernet inter-working access type parameters.' ;
                      presence iwf-eth-params ;
                      leaf iwf-eth {
                        description 'The ethernet inter-working access type.' ;
                        type empty ;

                        mandatory true ;
                      }

                      leaf proxy-mac {
                        description 'The proxy MAC address of the ethernet inter-working parameter' ;
                        type ncd:mac-address-none-zero ;

                      }

                      leaf local-ip {
                        description 'The local CE IP address of the ethernet inter-working parameter.' ;
                        type ncd:ipv4-address-none-zero ;

                      }

                      leaf remote-ip {
                        description 'The remote CE IP address of the ethernet inter-working parameter.' ;
                        type ncd:ipv4-address-none-zero ;

                      }

                      leaf remote-mac {
                        description 'The proxy MAC address of the ethernet inter-working parameter.' ;
                        type ncd:mac-address-none-zero ;

                      }

                      leaf service-vlan {
                        description 'The service VLAN ID of the ethernet inter-working parameter.Invalid value is 65534' ;
                        type uint32 {
                          range 0..4094 {
                            description 'The service VLAN value.' ;
                          }

                        }

                        ncd:revise-date 2015-08-21 ;
                      }

                      leaf traffic-enable {
                        description 'The traffic statistics enable flag of the ethernet inter-working parameter.' ;
                        type enumeration {
                          enum disable {
                            value 0 ;
                            description 'The traffic statistics flag is disable.' ;
                          }

                          enum enable {
                            value 1 ;
                            description 'The traffic statistics flag is enable.' ;
                          }

                        }

                        default disable ;
                      }

                      container traffic-statistics-params {
                        if-feature ac-traffic-statistics ;

                        if-feature inter-working-ethernet ;

                        if-feature vlss-instances ;

                        description 'The traffic statistics parameters of ethernet inter-working access.' ;
                        leaf unicast-inrate-bps {
                          description 'The unicast input bytes rate.' ;
                          type uint64 {
                            range 1..18446744073709551615 {
                              description 'The range of unicast input bytes.' ;
                            }

                          }

                          units bps ;
                        }

                        leaf unicast-inrate-pps {
                          description 'The unicast input packets rate.' ;
                          type uint32 {
                            range 1..4294967295 {
                              description 'The range of unicast input packets rate.' ;
                            }

                          }

                          units pps ;
                        }

                        leaf broadcast-inrate-bps {
                          description 'The broadcast input packets rate.' ;
                          type uint64 {
                            range 1..18446744073709551615 {
                              description 'The range of broadcast input bytes.' ;
                            }

                          }

                          units bps ;
                        }

                        leaf broadcast-inrate-pps {
                          description 'The broadcast input packets rate.' ;
                          type uint32 {
                            range 1..4294967295 {
                              description 'The range of broadcast input packets rate.' ;
                            }

                          }

                          units pps ;
                        }

                        leaf drop-inrate-bps {
                          description 'The drop input bytes rate.' ;
                          type uint64 {
                            range 1..18446744073709551615 {
                              description 'The range of drop input bytes.' ;
                            }

                          }

                          units bps ;
                        }

                        leaf drop-inrate-pps {
                          description 'The drop input packets rate.' ;
                          type uint32 {
                            range 1..4294967295 {
                              description 'The range of drop input packets rate.' ;
                            }

                          }

                          units pps ;
                        }

                      }

                    }

                  }

                  case sonet-sdh {
                    if-feature sonet-sdh ;

                    description 'The SONET/SDH access type.' ;
                    container sonet-sdh-params {
                      description 'SONET/SDH access type parameters.' ;
                      presence sonet-sdh-params ;
                      leaf sonet-sdh {
                        description 'SONET/SDH access type.' ;
                        type empty ;

                        mandatory true ;
                      }

                      leaf traffic-enable {
                        description 'The traffic statistics enable flag of the SONET/SDH parameter.' ;
                        type enumeration {
                          enum disable {
                            value 0 ;
                            description 'The traffic statistics flag is disable.' ;
                          }

                          enum enable {
                            value 1 ;
                            description 'The traffic statistics flag is enable.' ;
                          }

                        }

                        default disable ;
                      }

                      leaf jitter-buffer {
                        description 'The jitter buffer value of the SONET/SDH parameter.' ;
                        type uint16 {
                          range 1..400 {
                            description 'The jitter buffer value.' ;
                          }

                        }

                        units 125us ;
                        default 20 ;
                      }

                      leaf rtp-header {
                        description 'Configure the RTP header or not.' ;
                        type enumeration {
                          enum disable {
                            value 0 ;
                            description 'The RTP header is disable.' ;
                          }

                          enum enable {
                            value 1 ;
                            description 'The RTP header is enable.' ;
                          }

                        }

                        default disable ;
                      }

                      leaf rtp-timestamp {
                        description 'The RTP timestamp mode of the SONET/SDH parameter.' ;
                        type enumeration {
                          enum absolute {
                            value 1 ;
                            description 'RTP timestamp is absolute.' ;
                          }

                          enum differ {
                            value 2 ;
                            description 'RTP timestamp is differ.' ;
                          }

                        }

                      }

                      leaf sdh-payload-compression {
                        description 'The SDH payload compression mode of the SONET/SDH parameter.' ;
                        type enumeration {
                          enum basic {
                            value 0 ;
                            description 'The SONET/SDH mode is basic.' ;
                          }

                          enum fractional {
                            value 1 ;
                            description 'The SONET/SDH mode is fractional.' ;
                          }

                        }

                        default basic ;
                      }

                      leaf payload-bytes {
                        description 'The basic mode of SONET/SDH payload-size.' ;
                        type uint16 {
                          range 783..9170 {
                            description 'The basic mode of SONET/SDH payload-size value.' ;
                          }

                        }

                        units bytes ;
                      }

                      leaf payload-units {
                        description 'The fractional mode of SONET/SDH payload-size.' ;
                        type uint16 {
                          range 3..9 {
                            description 'The fractional mode of SONET/SDH payload-size value.' ;
                          }

                        }

                        units 783bytes ;
                      }

                      leaf mpls-exp-value {
                        description 'The MPLS EXP value of the SONET/SDH parameter.' ;
                        type enumeration {
                          enum be {
                            value 0 ;
                            description 'The MPLS EXP value is be' ;
                          }

                          enum af1 {
                            value 1 ;
                            description 'The MPLS EXP value is af1' ;
                          }

                          enum af2 {
                            value 2 ;
                            description 'The MPLS EXP value is af2' ;
                          }

                          enum af3 {
                            value 3 ;
                            description 'The MPLS EXP value is af3' ;
                          }

                          enum af4 {
                            value 4 ;
                            description 'The MPLS EXP value is af4' ;
                          }

                          enum ef {
                            value 5 ;
                            description 'The MPLS EXP value is ef' ;
                          }

                          enum cs6 {
                            value 6 ;
                            description 'The MPLS EXP value is cs6' ;
                          }

                          enum cs7 {
                            value 7 ;
                            description 'The MPLS EXP value is cs7' ;
                          }

                        }

                        default ef ;
                        ncd:revise-date 2018-01-19 ;
                      }

                      container hard-pipe {
                        description 'Configure hard pipe info.' ;
                        leaf hard-pipe-flag {
                          description 'The hard pipe enable flag of the AC.' ;
                          type enumeration {
                            enum disable {
                              value 0 ;
                              description 'The hard pipe of the AC is disable.' ;
                            }

                            enum enable {
                              value 1 ;
                              description 'The hard pipe of the AC is enable.' ;
                            }

                          }

                          default disable ;
                        }

                        ncd:revise-date 2016-12-15 ;
                      }

                    }

                  }

                }

                container vlss-protect-rules {
                  leaf pw-role {
                    type enumeration {
                      enum common {
                        value 0 ;
                        description 'The PW role is common.' ;
                      }

                    }

                    description 'The PW role which is configured with the PW protectable.' ;
                    mandatory true ;
                  }

                  description 'The VLSS protect rules configuration info.' ;
                  presence vlss-protect-rules ;
                  if-feature vlss-access-pw-group ;

                  container access-pw-params {
                    list access-protect-pw {
                      leaf access-protect-pw-name {
                        type ncd:ifname ;

                        description 'Access protect PW name.' ;
                      }

                      container protect-strategy {
                        leaf protect-type {
                          type enumeration {
                            enum one-by-one {
                              value 2 ;
                              description 'The protect type of the PW protect strategy is one by one.' ;
                            }

                          }

                          description 'The protect type of the PW protect strategy.' ;
                          mandatory true ;
                        }

                        leaf direction {
                          type enumeration {
                            enum unidirectional {
                              value 1 ;
                              description 'The protected direction of the PW protect strategy is unidirectional.' ;
                            }

                          }

                          description 'The protected direction of the PW protect strategy.' ;
                          default unidirectional ;
                        }

                        leaf receiver-parameters {
                          type enumeration {
                            enum selective {
                              value 1 ;
                              description 'The protected receiver of the PW protect strategy is selective.' ;
                            }

                            enum both {
                              value 2 ;
                              description 'The protected receiver of the PW protect strategy is both.' ;
                            }

                          }

                          description 'The protected receiver of the PW protect strategy.' ;
                          default selective ;
                        }

                        leaf aps-mode {
                          type enumeration {
                            enum aps {
                              value 1 ;
                              description 'The APS mode of the PW protect strategy is APS.' ;
                            }

                          }

                          description 'The APS mode of the PW protect strategy.' ;
                          mandatory true ;
                        }

                        description 'The protect strategy parameters.' ;
                        presence common-group-params ;
                      }

                      key access-protect-pw-name ;
                      description 'Access protect PW configure info.' ;
                    }

                    description 'The access protect PW parameters of VLSS.' ;
                  }

                  ncd:revise-date 2024-01-02 ;
                }

              }

            }

          }

        }

        container remote-monitor-instances {
          if-feature remote-monitor-instances ;

          description 'The remote-monitor instances configuration info.' ;
          list remote-monitor-instance {
            description 'The remote-monitor instance configuration info.' ;
            key instance-name ;
            leaf instance-name {
              description 'The name of the remote monitor instance.' ;
              type string {
                length 1..32 {
                  description 'The length of instance name.' ;
                }

              }

            }

            leaf description {
              description 'The description of the remote monitor instance.' ;
              type ncd:string-with-blank {
                length 1..104 {
                  description 'The description range of instance.' ;
                }

              }

            }

            leaf mtu {
              type uint16 {
                range 60..65535 {
                  description 'The range of MTU.' ;
                }

              }

              description 'The MTU value of the remote monitor instance.' ;
              default 1500 ;
              ncd:revise-date 2025-08-14 ;
            }

            leaf mtu-mismatch-ignore {
              type empty ;

              description 'Ignore the MTU mismatch in the PW negotiation.' ;
              ncd:revise-date 2025-08-14 ;
            }

            container monitor-pw-bind {
              description 'Remote monitor PW binding instance info.' ;
              list pw-instance-bind {
                description 'PW binding instance configuration info.' ;
                key pw-name ;
                leaf pw-name {
                  description 'The name of the PW in the bind.' ;
                  type ncd:ifname ;

                }

              }

            }

          }

        }

        container admin-vpls-instances {
          if-feature admin-vpls-instances ;

          description 'The administrator VPLS instances configuration info.' ;
          list admin-vpls-instance {
            description 'The admin VPLS instance.' ;
            key instance-name ;
            leaf instance-name {
              description 'The name of the administrator VPLS instance.' ;
              type string {
                length 1..32 {
                  description 'The length of instance name.' ;
                }

              }

            }

            leaf description {
              description 'The description of the administrator VPLS instance.' ;
              type ncd:string-with-blank {
                length 1..104 {
                  description 'The description range of instance.' ;
                }

              }

            }

            leaf mtu {
              type uint16 {
                range 60..65535 {
                  description 'The range of MTU.' ;
                }

              }

              description 'The MTU value of the administrator VPLS instance.' ;
              default 1500 ;
              ncd:revise-date 2025-08-14 ;
            }

            leaf mtu-mismatch-ignore {
              type empty ;

              description 'Ignore the MTU mismatch in the PW negotiation.' ;
              ncd:revise-date 2025-08-14 ;
            }

            container admin-vpls-pw-bind {
              description 'Administrator VPLS PW binding instance info.' ;
              list pw-instance-bind {
                description 'PW binding instance configuration info.' ;
                key pw-name ;
                leaf pw-name {
                  description 'The name of the PW in the bind.' ;
                  type ncd:ifname ;

                }

              }

            }

          }

        }

        container evpn-vpls-instances {
          description 'The EVPN VPLS instances configuration info.' ;
          list evpn-vpls-instance {
            description 'The EVPN VPLS instance configuration info.' ;
            key instance-name ;
            leaf instance-name {
              description 'The name of the EVPN VPLS instance.' ;
              type string {
                length 1..32 {
                  description 'The length of instance name.' ;
                }

              }

            }

            leaf service-id {
              description 'The service ID of EVPN VPLS instance,the service ID attribute cannot be modified or removed after its owner instance created.' ;
              type uint32 {
                range 1..65535 {
                  description 'The range of service ID.' ;
                }

              }

              ncd:revise-date 2017-11-15 ;
            }

            leaf equivalent-vxlan-id {
              description 'The equivalent VXLAN ID,the equivalent VXLAN attribute cannot be modified or removed after its owner instance created.' ;
              type uint32 {
                range 1..16777215 {
                  description 'The equivalent VXLAN ID range.' ;
                }

              }

              ncd:revise-date 2018-01-26 ;
            }

            leaf qualified {
              description 'The qualified flag of the EVPN VPLS instance.' ;
              type enumeration {
                enum unqualified {
                  value 0 ;
                  description 'The EVPN VPLS instance is unqualified.' ;
                }

                enum qualified {
                  value 1 ;
                  description 'The EVPN VPLS instance is qualified.' ;
                }

              }

              default unqualified ;
              ncd:revise-date 2019-04-30 ;
            }

            leaf shared-flood-list {
              description 'A common flood-list shared by these MAC spaces.' ;
              type enumeration {
                enum disable {
                  value 0 ;
                  description 'The EVPN VPLS instance shared-flood-list is disabled.' ;
                }

                enum enable {
                  value 1 ;
                  description 'The EVPN VPLS instance shared-flood-list is enabled.' ;
                }

              }

              default disable ;
              ncd:revise-date 2023-01-31 ;
            }

            leaf wtr-time {
              type uint8 {
                range 0..12 {
                  description 'The length of WTR time in minute.' ;
                }

              }

              description 'Set minutes in WTR. Requires setting wtr-second-with-minute simultaneously. The range is 0-12(minutes).' ;
              default 3 ;
              units min ;
              ncd:revise-date 2019-02-15 ;
            }

            leaf wtr-second-with-minute {
              type uint8 {
                range 0..59 {
                  description 'The length of WTR second time in minute.' ;
                }

              }

              description 'Set seconds in WTR. Requires setting wtr-time node simultaneously. The range is 0-59(seconds).' ;
              units second ;
              ncd:revise-date 2024-08-13 ;
            }

            leaf second {
              type uint32 {
                range 0..720 {
                  description 'The length of WTR time in second.' ;
                }

              }

              description 'Set seconds in WTR. Cannot be configured simultaneously with wtr-time node or wtr-second-with-minute node. The range is 0-720(seconds). ' ;
              units second ;
              ncd:revise-date 2023-12-12 ;
            }

            leaf encapsulation {
              description 'The encapsulation type of the EVPN.' ;
              type enumeration {
                enum tagged {
                  value 4 ;
                  description 'The encapsulation type is tagged.' ;
                }

                enum raw {
                  value 5 ;
                  description 'The encapsulation type is raw.' ;
                }

              }

              ncd:revise-date 2019-09-17 ;
            }

            leaf originator-ip {
              description 'Configure originator IP interface.' ;
              type ncd:ifname ;

              ncd:revise-date 2019-06-29 ;
            }

            leaf df-election {
              description 'choose mode of DF.' ;
              type enumeration {
                enum lowest-preference {
                  value 1 ;
                  description 'The adjacent-node with lowest-preference is DF' ;
                }

                enum highest-preference {
                  value 2 ;
                  description 'The adjacent-node with highest-preference is DF' ;
                }

              }

              ncd:revise-date 2018-07-08 ;
            }

            leaf entropy-label {
              description 'Enable or disable entropy label.' ;
              type enumeration {
                enum disable {
                  value 0 ;
                  description 'The entropy label is disable.' ;
                }

                enum enable {
                  value 1 ;
                  description 'The entropy label is enable.' ;
                }

              }

              default disable ;
              ncd:revise-date 2019-08-10 ;
            }

            leaf instance-description {
              description 'The description of the instance.' ;
              type ncd:string-with-blank {
                length 1..104 {
                  description 'The description range of instance.' ;
                }

              }

              ncd:revise-date 2019-09-29 ;
            }

            leaf unknown-unicast {
              description 'Configure unknown unicast suppression.' ;
              type enumeration {
                enum suppress {
                  value 1 ;
                  description 'The unknown-unicast is suppressed.' ;
                }

                enum unsuppress {
                  value 0 ;
                  description 'The unknown-unicast is unsuppressed.' ;
                }

              }

              default unsuppress ;
              ncd:revise-date 2020-03-25 ;
            }

            leaf umr {
              description 'Configure the VPLS EVPN UMR role.' ;
              type enumeration {
                enum distributor {
                  value 1 ;
                  description 'Config UMR as distributor.' ;
                }

                enum receiver {
                  value 2 ;
                  description 'Config UMR as receiver.' ;
                }

                enum native {
                  value 3 ;
                  description 'Config UMR as native.' ;
                }

              }

              ncd:revise-date 2020-12-14 ;
            }

            leaf best-path {
              description 'Select the best path nexthop-priority.' ;
              type enumeration {
                enum ipv4 {
                  value 1 ;
                  description 'Select IPv4 nexthop.' ;
                }

                enum ipv6 {
                  value 2 ;
                  description 'Select IPv6 nexthop.' ;
                }

              }

              ncd:revise-date 2021-04-27 ;
            }

            leaf best-path-sr {
              description 'Configure the best route selection rule in the SR domain.' ;
              type enumeration {
                enum te-tunnel {
                  value 1 ;
                  description 'Route recursived to TE tunnel preferred.' ;
                }

                enum end-point {
                  value 2 ;
                  description 'Route with smaller end-point address preferred.' ;
                }

              }

              ncd:revise-date 2022-03-24 ;
            }

            leaf link-acl-name {
              description 'The template of link ACL name.' ;
              type string {
                length 1..31 {
                  description 'The length of link ACL name.' ;
                }

              }

              ncd:revise-date 2021-05-27 ;
            }

            leaf mtu {
              description 'The MTU value of the VPLS EVPN instance.' ;
              type uint16 {
                range 60..65535 {
                  description 'The range of MTU.' ;
                }

              }

              default 1500 ;
              ncd:revise-date 2021-11-01 ;
            }

            leaf default-color {
              description 'Configure default color.' ;
              type uint32 {
                range 1..4294967295 ;

              }

              ncd:revise-date 2021-11-25 ;
            }

            leaf mtu-mismatch-ignore {
              description 'Ignore the MTU mismatch in the PW negotiation.' ;
              type empty ;

              ncd:revise-date 2022-09-13 ;
            }

            leaf esi-proxy {
              description "Null-ESI-ACs should be a normal ESI from an external PE's viewpoint." ;
              type enumeration {
                enum single-homed-as-single-active {
                  value 1 ;
                  description 'Viewed as a single-active ESI by external PEs.' ;
                }

                enum single-homed-as-all-active {
                  value 2 ;
                  description 'Viewed as an all-active ESI by external PEs.' ;
                }

              }

              ncd:revise-date 2022-10-10 ;
            }

            container evpn-redundancy-adjust {
              description 'Redundancy-mode adjustment for remote EVPN routes.' ;
              leaf frr {
                description 'Fast-Reroute (FRR) protection mode.' ;
                type empty ;

              }

              leaf load-balance {
                description 'Load-Balance (LB) protection mode.' ;
                type empty ;

              }

              ncd:revise-date 2022-09-19 ;
            }

            container evpn-multicast {
              description 'Enter EVPN VPLS multicast configuration mode.' ;
              leaf signal-smet {
                description 'Selective multicast flag.' ;
                type enumeration {
                  enum smet {
                    value 1 ;
                    description 'The signal selective multicast value.' ;
                  }

                }

              }

              leaf signal-sync {
                description 'Selective multicast synchronization.' ;
                type enumeration {
                  enum synchronization {
                    value 1 ;
                    description 'The signal synchronization value.' ;
                  }

                }

              }

              leaf signal-igmp-proxy {
                description 'Selective multicast IGMP proxy.' ;
                type enumeration {
                  enum igmp-proxy {
                    value 1 ;
                    description 'Selective multicast IGMP proxy value.' ;
                  }

                }

              }

              leaf signal-mld-proxy {
                type enumeration {
                  enum mld-proxy {
                    description 'Selective multicast MLD proxy value.' ;
                    value 1 ;
                  }

                }

                description 'Selective multicast MLD proxy.' ;
                ncd:revise-date 2023-05-09 ;
              }

              ncd:revise-date 2021-06-16 ;
            }

            container split-horizon-params {
              description 'Configure split-horizon parameters.' ;
              leaf scenario {
                description 'Scenario of dividing split-horizon scopes.' ;
                type enumeration {
                  enum ac-isolate {
                    value 1 ;
                    description 'Different ACs are isolated from each other.' ;
                  }

                  enum multi-chassis-ac-isolate {
                    value 2 ;
                    description 'AC-isolation between different chassis' ;
                  }

                }

              }

              ncd:revise-date 2022-02-15 ;
            }

            container neighbour-ipv4 {
              description 'The neighbour address type is IPv4.' ;
              list neighbor-ipv4-params {
                description 'IPv4 address parameters.' ;
                key ipv4-address ;
                leaf ipv4-address {
                  description 'IPv4 address.' ;
                  type ncd:ipv4-address-none-zero ;

                }

                leaf domain-border {
                  description 'Domain boundary.' ;
                  type enumeration {
                    enum split-horizon-scope {
                      value 1 ;
                      description 'Configure splitHorizonBypass flag' ;
                    }

                  }

                }

              }

              ncd:revise-date 2022-02-15 ;
            }

            container neighbour-ipv6 {
              description 'The neighbour address type is IPv6.' ;
              list neighbor-ipv6-params {
                description 'IPv6 address parameters.' ;
                key ipv6-address ;
                leaf ipv6-address {
                  description 'IPv6 address.' ;
                  type ncd:ipv6-address ;

                }

                leaf domain-border {
                  description 'Domain boundary.' ;
                  type enumeration {
                    enum split-horizon-scope {
                      value 1 ;
                      description 'Configure splitHorizonBypass flag' ;
                    }

                  }

                }

              }

              ncd:revise-date 2022-02-15 ;
            }

            container traffic-statistics-params {
              description 'The traffic statistics of L2VPN service.' ;
              leaf traffic-enable {
                description 'The traffic statistics status of VPLS EVPN service.' ;
                type enumeration {
                  enum disable {
                    value 0 ;
                    description 'The traffic statistics status of VPLS EVPN service is disable.' ;
                  }

                  enum enable {
                    value 1 ;
                    description 'The traffic statistics status of VPLS EVPN service is enable.' ;
                  }

                }

                default disable ;
              }

              ncd:revise-date 2021-06-07 ;
            }

            container ip-move-dampening {
              description 'Dampening for the IP mobility among certain MACs.' ;
              leaf move-dampening-flag {
                description 'Disable or enable IP move-dampening.' ;
                type enumeration {
                  enum disable {
                    value 0 ;
                    description 'Disable IP move-dampening.' ;
                  }

                  enum enable {
                    value 1 ;
                    description 'Enable IP move-dampening.' ;
                  }

                }

                default disable ;
              }

              leaf move-dampening-count {
                description 'Set IP move-dampening count attribute.' ;
                type uint32 {
                  range 1..4294967295 {
                    description 'The range of IP move dampening count.Its maximum value depends on product,between 1-30 and to be 30 ingenerally;Its minmum value depends on product,between 1-30 and to be 1 ingenerally.' ;
                  }

                }

              }

              leaf move-dampening-interval {
                description 'Set IP move-dampening time interval attribute.' ;
                type uint32 {
                  range 1..4294967295 {
                    description 'The range of IP move dampening interval.Its maximum value depends on product,between 1-900 and to be 900 ingenerally;Its minmum value depends on product,between 1-900 and to be 1 ingenerally.' ;
                  }

                }

                units seconds ;
              }

              leaf move-dampening-timeout {
                description 'Set IP move-dampening retry timeout attribute.' ;
                type uint32 {
                  range 0..4294967295 {
                    description 'The range of IP move dampening timeout.Its maximum value depends on product,between 0-1200 and to be 1200 ingenerally;Its minmum value depends on product,between 0-1200 and to be 0 ingenerally.' ;
                  }

                }

                units seconds ;
              }

              ncd:revise-date 2019-12-18 ;
            }

            container evpn-vpls-ds-mode {
              description 'The DS mode of the EVPN VPLS instance.' ;
              leaf ds-mode {
                description 'The DS service mode of the EVPN VPLS instance.' ;
                type enumeration {
                  enum uniform {
                    value 1 ;
                    description 'DS mode is uniform.' ;
                  }

                  enum pipe {
                    value 2 ;
                    description 'DS mode is pipe.' ;
                  }

                  enum shortPipe {
                    value 3 ;
                    description 'DS mode is shortPipe.' ;
                  }

                }

              }

              leaf service-class {
                description 'The DS service class and local scheduling priority of the EVPN VPLS instance.' ;
                type enumeration {
                  enum be {
                    value 1 ;
                    description 'The DS service class is be.' ;
                  }

                  enum af1 {
                    value 2 ;
                    description 'The DS service class is af1.' ;
                  }

                  enum af2 {
                    value 3 ;
                    description 'The DS service class is af2.' ;
                  }

                  enum af3 {
                    value 4 ;
                    description 'The DS service class is af3.' ;
                  }

                  enum af4 {
                    value 5 ;
                    description 'The DS service class is af4.' ;
                  }

                  enum ef {
                    value 6 ;
                    description 'The DS service class is ef.' ;
                  }

                  enum cs6 {
                    value 7 ;
                    description 'The DS service class is cs6.' ;
                  }

                  enum cs7 {
                    value 8 ;
                    description 'The DS service class is cs7.' ;
                  }

                }

              }

              leaf colour {
                description 'The DS packet colour of the EVPN VPLS instance.' ;
                type enumeration {
                  enum green {
                    value 1 ;
                    description 'The DS packet colour is green.' ;
                  }

                  enum yellow {
                    value 2 ;
                    description 'The DS packet colour is yellow.' ;
                  }

                  enum red {
                    value 3 ;
                    description 'The DS packet colour is red.' ;
                  }

                }

              }

              ncd:revise-date 2019-06-10 ;
            }

            container route-map-params {
              description 'Route map parameters.' ;
              leaf export-map-name {
                description 'Export route map name.' ;
                type string {
                  length 1..200 {
                    description 'The length of export route map name.' ;
                  }

                }

              }

              leaf import-map-name {
                description 'Import route map name.' ;
                type string {
                  length 1..200 {
                    description 'The length of import route map name.' ;
                  }

                }

              }

              ncd:revise-date 2018-12-17 ;
            }

            container ac-fault-associate {
              description 'AC fault associate PW status or not.' ;
              leaf associate-pw {
                description 'AC fault associate PW status or not.' ;
                type enumeration {
                  enum not-associate-pw {
                    value 0 ;
                    description 'AC fault not associate PW status or signal.' ;
                  }

                  enum associate-pw-status {
                    value 1 ;
                    description 'AC fault associate PW status notify to PWE3.' ;
                  }

                  enum associate-pw-signal {
                    value 2 ;
                    description 'AC fault associate PW signal release notify to PWE3.' ;
                  }

                }

                default not-associate-pw ;
              }

              leaf spoke-pw-as-ac {
                description 'Spoke PW as AC or not.' ;
                type enumeration {
                  enum not-as-ac {
                    value 0 ;
                    description 'Spoke PW not as AC to calculate status.' ;
                  }

                  enum as-ac {
                    value 1 ;
                    description 'Spoke PW as AC to calculate status.' ;
                  }

                }

                default not-as-ac ;
              }

              leaf multi-homed-ce-pool {
                description 'Treat ACs as being attached to the same CE-pool.' ;
                type empty ;

              }

              ncd:revise-date 2022-02-15 ;
            }

            container ce-pool {
              description 'A set of CEs which are substitutes of one another.' ;
              leaf active-threshold {
                description 'The threshold for a CE-pool to be treated as up.' ;
                type uint8 {
                  range 1..100 {
                    description "The percent of a CE-pool's active ACs." ;
                  }

                }

              }

              ncd:revise-date 2022-02-15 ;
            }

            container rt-2 {
              description 'EVPN route-type 2 (MAC/IP Advertisement Route).' ;
              leaf single-active-esi-not-preferred {
                description "Type 2 route's single active ESI is not preferred." ;
                type empty ;

              }

              leaf originate {
                description 'Whether to generate EVPN MAC/IP Routes per EVPN VPLS basis.' ;
                type enumeration {
                  enum enable {
                    value 1 ;
                    description 'Local EVPN MAC/IP routes are generated.' ;
                  }

                  enum disable {
                    value 0 ;
                    description 'No local EVPN MAC/IP routes are generated.' ;
                  }

                }

                default enable ;
                ncd:revise-date 2023-01-10 ;
              }

              ncd:revise-date 2022-05-12 ;
            }

            container evpn-vpls-rd {
              description 'EVPN VPLS route distinguisher params.' ;
              presence evpn-vpls-rd ;
              choice rd-type {
                description 'RD generation type.' ;
                case rd-manual {
                  description 'RD configured manually.' ;
                  leaf rd {
                    description 'The route distinguisher parameter.' ;
                    type union {
                      type ncd:asn-nn ;

                      type ncd:ipadd-nn ;

                      type ncd:asnd-nn ;

                    }

                    mandatory true ;
                  }

                }

                case rd-auto {
                  description 'RD generated automatically.' ;
                  leaf template-based {
                    description 'Automatically generated RD based on RD template.' ;
                    type empty ;

                    mandatory true ;
                  }

                  ncd:revise-date 2022-04-20 ;
                }

              }

            }

            container bridge-interface {
              if-feature bridge-interface ;

              description 'EVPN VPLS bridge interface.' ;
              presence bridge-interface ;
              leaf interface-name {
                description 'The name of the bridge interface.' ;
                type ncd:ifname ;

                mandatory true ;
              }

            }

            container bridge-mapping {
              if-feature bridge-mapping ;

              description 'EVPN VPLS bridge mapping params.' ;
              list mapping-interface {
                description 'EVPN VPLS bridge mapping interface params.' ;
                key interface-name ;
                leaf interface-name {
                  description 'The name of the bridge interface.' ;
                  type ncd:ifname ;

                }

              }

              ncd:revise-date 2017-11-17 ;
            }

            container evpn-vpls-dynamic-vxlan {
              description 'EVPN VPLS VXLAN params.' ;
              presence evpn-vpls-dynamic-vxlan ;
              leaf dynamic-vxlan {
                description 'EVPN VPLS VXLAN auto-discovery mode.' ;
                type enumeration {
                  enum auto-discovery-vxlan {
                    value 1 ;
                    description 'VXLAN EVPN auto-discovery mode.' ;
                  }

                }

                mandatory true ;
              }

              container route-target-params {
                description 'The route target params.' ;
                list route-target {
                  description 'The route target.' ;
                  key 'rt-value effect-type' ;
                  leaf rt-value {
                    description 'RT attribute value.' ;
                    type union {
                      type ncd:asn-nn ;

                      type ncd:ipadd-nn ;

                      type ncd:asnd-nn ;

                    }

                  }

                  leaf effect-type {
                    description 'The route target effect type.' ;
                    type enumeration {
                      enum export {
                        value 2 ;
                        description 'The route target effect type is export.' ;
                      }

                      enum import {
                        value 3 ;
                        description 'The route target effect type is import.' ;
                      }

                    }

                  }

                  leaf split-horizon {
                    description 'Split-horizon group,the range is A-Z.' ;
                    type string {
                      length 1..51 ;

                    }

                    ncd:revise-date 2016-12-26 ;
                  }

                  leaf evi-rt-flag {
                    type enumeration {
                      enum evi-rt {
                        value 1 ;
                        description 'The EVI-RT flag is enable.' ;
                      }

                    }

                    description 'The EVI-RT flag.' ;
                    ncd:revise-date 2023-05-09 ;
                  }

                }

              }

              container evpn-vpls-vni-labels {
                description 'VXLAN dynamic VNI labels.' ;
                list evpn-vpls-vni-label {
                  description 'VXLAN dynamic VNI label.' ;
                  key vni-label ;
                  leaf vni-label {
                    description 'VNI label.' ;
                    type uint32 {
                      range 1..16777215 {
                        description 'The VNI label range.' ;
                      }

                    }

                  }

                  leaf split-horizon {
                    description 'Split-horizon group,the range is A-Z.' ;
                    type string {
                      length 1..51 ;

                    }

                    ncd:revise-date 2016-12-26 ;
                  }

                }

                list evpn-vpls-equivalent-vni-label {
                  description 'VXLAN equivalent VNI label.' ;
                  key vni-label ;
                  leaf vni-label {
                    description 'The equivalent VNI label.' ;
                    type uint32 {
                      range 1..16777215 {
                        description 'The equivalent VNI label range.' ;
                      }

                    }

                  }

                  leaf split-horizon {
                    description 'Split-horizon group,the range is A-Z.' ;
                    type string {
                      length 1..51 ;

                    }

                    mandatory true ;
                  }

                  ncd:revise-date 2016-12-26 ;
                }

              }

              container vtep-interface {
                status obsolete {
                  ncd:revise-date 2019-10-29 ;
                }

                description 'VTEP interface for broadcast tunnel.' ;
                presence vtep-interface ;
                leaf interface-name {
                  description 'The name of the VTEP interface.' ;
                  type ncd:ifname {
                    length 1..31 {
                      description 'The length of VTEP interface.' ;
                    }

                  }

                  mandatory true ;
                }

                ncd:revise-date 2017-09-07 ;
              }

              container vni-symmetric-params {
                description 'VNI label symmetric check parameters.' ;
                leaf symmetric-flag {
                  description 'The VNI label symmetric check flag.' ;
                  type enumeration {
                    enum unforced {
                      value 0 ;
                      description 'Not forced check VNI label symmetric.' ;
                    }

                    enum forced {
                      value 1 ;
                      description 'Forced check VNI label symmetric.' ;
                    }

                  }

                  default unforced ;
                }

                ncd:revise-date 2018-12-17 ;
              }

              container rt-2-params {
                description 'RT2 parameters.' ;
                choice rt-2-params-type {
                  description 'RT2 parameters type.' ;
                  case rt-2-label {
                    description 'RT2 label parameters.' ;
                    container single-label {
                      description 'RT2 single-label.' ;
                      presence single-label ;
                      leaf single-label-enable {
                        description 'Single label enable flag.' ;
                        type empty ;

                        mandatory true ;
                      }

                      leaf enhanced {
                        description 'Single label enhanced flag.' ;
                        type empty ;

                      }

                    }

                  }

                  case rt-2-gateway {
                    description 'RT2 gateway parameters.' ;
                    container self-as-gateway {
                      description 'RT2 self as gateway.' ;
                      leaf self-as-gateway-enable {
                        description 'Self as gateway enable flag.' ;
                        type empty ;

                      }

                    }

                  }

                }

                leaf rt-2-router-mac {
                  description 'RT2 router-MAC.' ;
                  type enumeration {
                    enum mc {
                      value 0 ;
                      description 'RT2 router-MAC type is MC.' ;
                    }

                    enum host {
                      value 1 ;
                      description 'RT2 router-MAC type is host.' ;
                    }

                  }

                  default mc ;
                  ncd:revise-date 2019-03-25 ;
                }

                ncd:revise-date 2018-12-17 ;
              }

            }

            container evpn-vpls-mpls-evpn {
              description 'EVPN VPLS MPLS EVPN params.' ;
              presence evpn-vpls-mpls-evpn ;
              leaf mpls-evpn {
                description 'MPLS EVPN auto-discovery mode.' ;
                type enumeration {
                  enum auto-discovery-mpls-vxlan {
                    value 1 ;
                    description 'MPLS EVPN auto-discovery mode.' ;
                  }

                }

                mandatory true ;
              }

              leaf etree-advertise-leaf {
                description 'Advertise leaf attribute for etree.' ;
                type enumeration {
                  enum disable {
                    value 0 ;
                    description 'The advertise leaf function is disable.' ;
                  }

                  enum enable {
                    value 1 ;
                    description 'The advertise leaf function is enable.' ;
                  }

                }

                default disable ;
                ncd:revise-date 2019-01-16 ;
              }

              leaf seperated-bum-label {
                description 'Separated BUM label.' ;
                type enumeration {
                  enum none {
                    value 0 ;
                    description 'No separated BUM label.' ;
                  }

                  enum dynamic {
                    value 1 ;
                    description 'Separate BUM label in dynamic.' ;
                  }

                }

                default none ;
                if-feature separated-bum-label {
                  ncd:revise-date 2023-08-24 ;
                }

                ncd:revise-date 2019-04-30 ;
              }

              leaf seamless-integrated {
                description 'EVPN is seamless integrated.' ;
                type enumeration {
                  enum seamless-integrated {
                    value 1 ;
                    description 'EVPN is seamless integrated.' ;
                  }

                }

                ncd:revise-date 2021-03-23 ;
              }

              leaf traffic-enable {
                type enumeration {
                  enum disable {
                    value 0 ;
                    description 'The traffic statistics status of VPLS MPLS EVPN is disable.' ;
                  }

                  enum enable {
                    value 1 ;
                    description 'The traffic statistics status of VPLS MPLS EVPN is enable.' ;
                  }

                }

                description 'The traffic statistics status of VPLS MPLS EVPN.' ;
                default disable ;
                ncd:revise-date 2023-12-11 ;
              }

              container broadcast-tunnel {
                description 'Tunnel for overlay broadcast and inclusive-multicast.' ;
                choice tunnel-type {
                  description 'The broadcast-tunnel type.' ;
                  case mldp-type {
                    description 'The broadcast-tunnel type is mLDP.' ;
                    leaf mldp {
                      description 'The broadcast-tunnel type is mLDP.' ;
                      type enumeration {
                        enum mldp {
                          value 1 ;
                          description 'The broadcast-tunnel type is MLDP.' ;
                        }

                      }

                    }

                  }

                }

                ncd:revise-date 2019-10-29 ;
              }

              container dcb {
                description 'Domain-wide common block.' ;
                leaf label {
                  description 'Domain-wide common block label.' ;
                  type uint32 {
                    range 16..1048575 {
                      description 'The range of domain-wide common block label.' ;
                    }

                  }

                }

                ncd:revise-date 2021-06-24 ;
              }

              container route-target-params {
                description 'The route target params.' ;
                list route-target {
                  description 'The route target.' ;
                  key 'rt-value effect-type' ;
                  leaf rt-value {
                    description 'RT attribute value.' ;
                    type union {
                      type ncd:asn-nn ;

                      type ncd:ipadd-nn ;

                      type ncd:asnd-nn ;

                    }

                  }

                  leaf effect-type {
                    description 'The route target effect type.' ;
                    type enumeration {
                      enum export {
                        value 2 ;
                        description 'The route target effect type is export.' ;
                      }

                      enum import {
                        value 3 ;
                        description 'The route target effect type is import.' ;
                      }

                    }

                  }

                  leaf split-horizon {
                    description 'Split-horizon group,the range is A-Z.' ;
                    type string {
                      length 1..51 ;

                    }

                    ncd:revise-date 2019-09-02 ;
                  }

                  leaf evi-rt-flag {
                    description 'The EVI-RT flag.' ;
                    type enumeration {
                      enum evi-rt {
                        value 1 ;
                        description 'The EVI-RT flag is enable.' ;
                      }

                    }

                    ncd:revise-date 2021-06-16 ;
                  }

                }

              }

              container evpn-vpls-evi-labels {
                description 'MPLS EVI labels.' ;
                list evpn-vpls-evi-label {
                  description 'MPLS EVI label.' ;
                  key evi-label ;
                  leaf evi-label {
                    description 'EVI label.' ;
                    type uint32 {
                      range 16..1048575 {
                        description 'The EVI label range.' ;
                      }

                    }

                  }

                  leaf split-horizon {
                    description 'Split-horizon group,the range is A-Z.' ;
                    type string {
                      length 1..51 ;

                    }

                  }

                }

                ncd:revise-date 2019-09-02 ;
              }

              container evpn-vpls-equivalent-evi-labels {
                description 'MPLS equivalent EVI labels.' ;
                list evpn-vpls-equivalent-evi-label {
                  description 'MPLS equivalent EVI label.' ;
                  key equivalent-evi-label ;
                  leaf equivalent-evi-label {
                    description 'The equivalent EVI label.' ;
                    type uint32 {
                      range 16..1048575 {
                        description 'The equivalent EVI label range.' ;
                      }

                    }

                  }

                  leaf split-horizon {
                    description 'Split-horizon group,the range is A-Z.' ;
                    type string {
                      length 1..51 ;

                    }

                    mandatory true ;
                  }

                }

                ncd:revise-date 2019-09-02 ;
              }

              container rt-2-params {
                description 'EVPN route-type 2 (MAC/IP Advertisement Route) parameters.' ;
                choice rt-2-params-type {
                  description 'EVPN route-type 2 (MAC/IP Advertisement Route) parameters type.' ;
                  case label-assign-proxy {
                    description 'Initiate the Label2 field of a repropagated RT-2.' ;
                    container evpn-irb-params {
                      description 'Label parameter that identifies the IP-VRF of the IRB.' ;
                      leaf evpn-irb {
                        description 'Label that identifies the IP-VRF of the IRB.' ;
                        type empty ;

                      }

                    }

                  }

                }

                ncd:revise-date 2021-09-04 ;
              }

              container rt-2-single-label {
                description 'RT2 single label.' ;
                presence rt-2-single-label ;
                leaf single-label-enable {
                  description 'Single label enable flag.' ;
                  type empty ;

                  mandatory true ;
                }

                ncd:revise-date 2022-06-30 ;
              }

              container flow-label {
                description 'Configure flow-label capability.' ;
                leaf push {
                  description 'Set flow-label send capability.' ;
                  type enumeration {
                    enum static {
                      value 1 ;
                      description 'Push a flow-label even if R flag is not received.' ;
                    }

                  }

                }

                leaf pop {
                  description 'Set flow-label receive capability.' ;
                  type enumeration {
                    enum static {
                      value 1 ;
                      description 'Pop a flow-label even if T flag is not received.' ;
                    }

                  }

                }

                ncd:revise-date 2022-02-15 ;
              }

              container split-horizon-params {
                description 'Configure split-horizon parameters.' ;
                leaf inbound {
                  description 'The inbound split-horizon scope for MPLS, the range is A-Z.' ;
                  type string {
                    length 1..51 {
                      description 'The length of split-horizon-scopes.' ;
                    }

                  }

                }

                ncd:revise-date 2022-02-15 ;
              }

              leaf cword-usage-forced {
                type enumeration {
                  enum force-unused {
                    value 1 ;
                    description 'Control-word usage forced flag is force unused.' ;
                  }

                  enum force-used {
                    description 'Control-word usage forced flag is force used.' ;
                    value 2 ;
                  }

                }

                description 'To statically decide if a control-word is used.' ;
                ncd:revise-date 2023-09-02 ;
              }

              ncd:revise-date 2017-06-20 ;
            }

            container evpn-vpls-srv6-evpn {
              description 'EVPN VPLS SRv6 EVPN params.' ;
              presence evpn-vpls-srv6-evpn ;
              leaf srv6-evpn {
                description 'SRv6 EVPN auto-discovery mode.' ;
                type enumeration {
                  enum auto-discovery-srv6-evpn {
                    value 1 ;
                    description 'SRv6 EVPN auto-discovery mode.' ;
                  }

                }

                mandatory true ;
              }

              leaf etree-advertise-leaf {
                description 'Advertise leaf attribute for etree.' ;
                type enumeration {
                  enum disable {
                    value 0 ;
                    description 'The advertise leaf function is disable.' ;
                  }

                  enum enable {
                    value 1 ;
                    description 'The advertise leaf function is enable.' ;
                  }

                }

                default disable ;
                ncd:revise-date 2021-01-30 ;
              }

              leaf seamless-integrated {
                description 'EVPN is seamless integrated.' ;
                type enumeration {
                  enum seamless-integrated {
                    value 1 ;
                    description 'EVPN is seamless integrated.' ;
                  }

                }

                ncd:revise-date 2021-05-27 ;
              }

              leaf traffic-enable {
                type enumeration {
                  enum disable {
                    value 0 ;
                    description 'The traffic statistics status of VPLS SRv6 EVPN is disable.' ;
                  }

                  enum enable {
                    value 1 ;
                    description 'The traffic statistics status of VPLS SRv6 EVPN is enable.' ;
                  }

                }

                description 'The traffic statistics status of VPLS SRv6 EVPN.' ;
                default disable ;
                ncd:revise-date 2023-12-11 ;
              }

              container split-horizon-params {
                description 'Configure split-horizon parameters.' ;
                leaf inbound {
                  description 'The inbound split-horizon scope for SRv6, the range is A-Z.' ;
                  type string {
                    length 1..51 {
                      description 'The length of split-horizon-scopes.' ;
                    }

                  }

                }

                ncd:revise-date 2022-03-15 ;
              }

              container srv6-tunnel-params {
                description 'Configure SRv6 tunnel params.' ;
                leaf srv6-best-effort {
                  description 'Select SRv6 BE.' ;
                  type empty ;

                }

                leaf srv6-traffic-engineer {
                  description 'Select SRv6 TE.' ;
                  type empty ;

                }

                ncd:revise-date 2022-03-15 ;
              }

              container route-target-params {
                description 'The route target params.' ;
                list route-target {
                  description 'The route target.' ;
                  key 'rt-value effect-type' ;
                  leaf rt-value {
                    description 'RT attribute value.' ;
                    type union {
                      type ncd:asn-nn ;

                      type ncd:ipadd-nn ;

                      type ncd:asnd-nn ;

                    }

                  }

                  leaf effect-type {
                    description 'The route target effect type.' ;
                    type enumeration {
                      enum export {
                        value 2 ;
                        description 'The route target effect type is export.' ;
                      }

                      enum import {
                        value 3 ;
                        description 'The route target effect type is import.' ;
                      }

                    }

                  }

                  leaf split-horizon {
                    description 'Split-horizon group,the range is A-Z.' ;
                    type string {
                      length 1..51 ;

                    }

                    ncd:revise-date 2020-12-08 ;
                  }

                  leaf evi-rt-flag {
                    type enumeration {
                      enum evi-rt {
                        value 1 ;
                        description 'The EVI-RT flag is enable.' ;
                      }

                    }

                    description 'The EVI-RT flag.' ;
                    ncd:revise-date 2023-04-26 ;
                  }

                }

              }

              container srv6-sid-params {
                status obsolete {
                  ncd:revise-date 2020-07-18 ;
                }

                description 'The SRv6 SID params of VPLS EVPN instance.' ;
                choice srv6-sid-type {
                  description 'The SRv6 SID type of VPLS EVPN instance.' ;
                  case sid-label {
                    description 'The SRv6 SID type is label.' ;
                    leaf sid-label {
                      description 'The SRv6 SID type is label.' ;
                      type uint32 {
                        range 1..16777215 {
                          description 'The range of SID label.' ;
                        }

                      }

                    }

                  }

                }

              }

              container srv6-locator-params {
                description 'SRv6 locator parameters.' ;
                leaf srv6-locator-name {
                  description 'The SRv6 locator name.' ;
                  type string {
                    length 1..31 {
                      description 'The length of SRv6 locator name.' ;
                    }

                  }

                }

                ncd:revise-date 2020-06-08 ;
              }

              container srv6-local-sid-params {
                description 'SRv6 local sid parameters.' ;
                presence srv6-local-sid-params ;
                leaf dt2m {
                  description 'The SRv6 DT2M.' ;
                  type ncd:ipv6-address-none-zero ;

                  mandatory true ;
                }

                leaf dt2u {
                  description 'The SRv6 DT2U.' ;
                  type ncd:ipv6-address-none-zero ;

                  mandatory true ;
                }

                leaf split-horizon {
                  description 'Split-horizon group,the range is A-Z.' ;
                  type string {
                    length 1..51 ;

                  }

                }

                ncd:revise-date 2020-12-08 ;
              }

              container srv6-equivalent-sid-params {
                description 'SRv6 equivalent SID parameters.' ;
                list srv6-equivalent-sid {
                  description 'SRv6 equivalent SID.' ;
                  key 'dt2u dt2m' ;
                  leaf dt2m {
                    description 'The SRv6 DT2M.' ;
                    type ncd:ipv6-address-none-zero ;

                  }

                  leaf dt2u {
                    description 'The SRv6 DT2U.' ;
                    type ncd:ipv6-address-none-zero ;

                  }

                  leaf split-horizon {
                    description 'Split-horizon group,the range is A-Z.' ;
                    type string {
                      length 1..51 ;

                    }

                    mandatory true ;
                  }

                }

                ncd:revise-date 2020-12-08 ;
              }

              container rt-2-params {
                description 'EVPN route-type 2 (MAC/IP Advertisement Route) parameters.' ;
                choice rt-2-params-type {
                  description 'EVPN route-type 2 (MAC/IP Advertisement Route) parameters type.' ;
                  case label-assign-proxy {
                    description 'Initiate the Label2 field of a repropagated RT-2.' ;
                    container evpn-irb-params {
                      description 'Label parameter that identifies the IP-VRF of the IRB.' ;
                      leaf evpn-irb {
                        description 'Label parameter that identifies the IP-VRF of the IRB.' ;
                        type empty ;

                      }

                    }

                  }

                }

                ncd:revise-date 2021-09-04 ;
              }

              container rt-2-single-label {
                description 'RT2 single-label.' ;
                presence rt-2-single-label ;
                leaf single-label-enable {
                  description 'Single label enable flag.' ;
                  type empty ;

                  mandatory true ;
                }

                ncd:revise-date 2022-06-30 ;
              }

              ncd:revise-date 2020-03-02 ;
            }

            container evpn-vpls-ac-bind {
              description 'EVPN VPLS AC binding instance info.' ;
              list ac-instance-bind {
                description 'AC binding instance configuration info.' ;
                key ac-name ;
                leaf ac-name {
                  description 'The name of the AC in the bind.' ;
                  type ncd:ifname ;

                }

                leaf split-horizon {
                  description 'The split-horizon flag of the bind.' ;
                  type enumeration {
                    enum server {
                      value 0 ;
                      description 'The split-horizon flag is server.' ;
                    }

                    enum client {
                      value 1 ;
                      description 'The split-horizon flag is client.' ;
                    }

                  }

                  default server ;
                  ncd:revise-date 2017-03-31 ;
                }

                leaf split-horizon-scopes {
                  description 'The split-horizon scope of AC bind.' ;
                  type string {
                    length 1..51 ;

                  }

                  ncd:revise-date 2017-03-31 ;
                }

                leaf description {
                  description 'The description of the interface.' ;
                  type ncd:string-with-blank {
                    length 1..104 {
                      description 'The description range of interface.' ;
                    }

                  }

                  ncd:revise-date 2017-08-25 ;
                }

                choice ac-type {
                  description 'The access type of EVPN VPLS instance.' ;
                  case ethernet {
                    description 'The ethernet access type.' ;
                    container ethernet-params {
                      description 'Ethernet access type parameters.' ;
                      presence ethernet-params ;
                      leaf ethernet {
                        description 'Ethernet access type.' ;
                        type empty ;

                        mandatory true ;
                      }

                      leaf ingress-adjust-tag-as-payload {
                        description 'The ingress tag as payload flag of the ethernet parameter.' ;
                        type enumeration {
                          enum disable {
                            value 0 ;
                            description 'The ingress tag as payload flag is disable.' ;
                          }

                          enum all {
                            value 1 ;
                            description 'The ingress tag as payload flag is from outer most.' ;
                          }

                          enum from-sub-layer {
                            value 2 ;
                            description 'The ingress tag as payload flag is from sub layer.' ;
                          }

                        }

                        default disable ;
                      }

                      leaf ingress-adjust-drop-tagged-frames {
                        description 'The ingress adjust drop tagged frames flag of the ethernet.' ;
                        type enumeration {
                          enum disable {
                            value 0 ;
                            description 'The ingress adjust drop tagged frames flag is disable.' ;
                          }

                          enum enable {
                            value 1 ;
                            description 'The ingress adjust drop tagged frames flag is enable.' ;
                          }

                        }

                        ncd:revise-date 2023-03-10 ;
                      }

                      container ingress-adjust-push-params {
                        description 'The ingress adjust push parameters of the ethernet parameter.' ;
                        leaf ingress-adjust-push {
                          description 'The ingress adjust push flag of the ethernet parameter.' ;
                          type enumeration {
                            enum disable {
                              value 0 ;
                              description 'The ingress adjust push flag of the ethernet parameter is disable.' ;
                            }

                            enum enable {
                              value 1 ;
                              description 'The ingress adjust push flag of the ethernet parameter is enable.' ;
                            }

                          }

                          default disable ;
                        }

                        leaf push-vlan-id {
                          description 'The ingress adjust push VLAN ID of the ethernet parameter.' ;
                          type uint16 {
                            range 1..4094 {
                              description 'The range of push VLAN ID is 1-4094.' ;
                            }

                          }

                        }

                        ncd:revise-date 2018-10-31 ;
                      }

                      container ingress-adjust-rewrite-params {
                        description 'The ingress adjust rewrite parameters of the ethernet parameter.' ;
                        leaf ingress-adjust-rewrite {
                          description 'The ingress adjust rewrite flag of the ethernet parameter.' ;
                          type enumeration {
                            enum disable {
                              value 0 ;
                              description 'The ingress adjust rewrite flag of the ethernet parameter is disable.' ;
                            }

                            enum enable {
                              value 1 ;
                              description 'The ingress adjust rewrite flag of the ethernet parameter is enable.' ;
                            }

                          }

                          default disable ;
                        }

                        leaf rewrite-vlan-id {
                          description 'The ingress adjust rewrite VLAN ID of the ethernet parameter.' ;
                          type uint16 {
                            range 1..4094 {
                              description 'The range of rewrite VLAN ID is 1-4094.' ;
                            }

                          }

                        }

                        leaf rewrite-outer-vlanid-flag {
                          description 'Rewrite outer VLAN ID flag.' ;
                          type enumeration {
                            enum disable {
                              value 0 ;
                              description 'Rewrite outer VLAN ID flag is disable.' ;
                            }

                            enum enable {
                              value 1 ;
                              description 'Rewrite outer VLAN ID flag is enable.' ;
                            }

                          }

                          default disable ;
                          ncd:revise-date 2021-01-05 ;
                        }

                        ncd:revise-date 2018-10-31 ;
                      }

                      leaf ingress-adjust-tag-as-endpoint {
                        description 'The BUM packets broadcast to each VLAN of the sub port VLAN range or not.' ;
                        type enumeration {
                          enum disable {
                            value 0 ;
                            description 'The ingress adjust tag-as-endpoint flag is disable.' ;
                          }

                          enum enable {
                            value 1 ;
                            description 'The ingress adjust tag-as-endpoint flag is enable.' ;
                          }

                        }

                        default disable ;
                        ncd:revise-date 2021-04-22 ;
                      }

                      leaf leaf-role {
                        description 'Leaf attribute.' ;
                        type enumeration {
                          enum no {
                            value 0 ;
                            description 'The AC is not leaf.' ;
                          }

                          enum yes {
                            value 1 ;
                            description 'The AC is leaf.' ;
                          }

                        }

                        default no ;
                        ncd:revise-date 2019-01-16 ;
                      }

                      leaf traffic-enable {
                        description 'The traffic statistics enable flag of the ethernet parameter.' ;
                        type enumeration {
                          enum disable {
                            value 0 ;
                            description 'The traffic statistics flag is disable.' ;
                          }

                          enum enable {
                            value 1 ;
                            description 'The traffic statistics flag is enable.' ;
                          }

                        }

                        default disable ;
                      }

                      leaf egress-keep-normalized-tag {
                        description 'To keep the normalized tag unchanged onto the egress AC.' ;
                        type enumeration {
                          enum disable {
                            value 0 ;
                            description 'To keep the normalized tag unchanged onto the egress AC is disable.' ;
                          }

                          enum enable {
                            value 1 ;
                            description 'To keep the normalized tag unchanged onto the egress AC is enable.' ;
                          }

                        }

                        default disable ;
                        ncd:revise-date 2021-01-05 ;
                      }

                      container traffic-statistics-params {
                        if-feature ac-traffic-statistics ;

                        description 'The traffic statistics parameters of ethernet access.' ;
                        leaf unicast-inrate-bps {
                          description 'The unicast input bytes rate.' ;
                          type uint64 {
                            range 1..18446744073709551615 {
                              description 'The range of unicast input bytes.' ;
                            }

                          }

                          units bps ;
                        }

                        leaf unicast-inrate-pps {
                          description 'The unicast input packets rate.' ;
                          type uint32 {
                            range 1..4294967295 {
                              description 'The range of unicast input packets rate.' ;
                            }

                          }

                          units pps ;
                        }

                        leaf broadcast-inrate-bps {
                          description 'The broadcast input bytes rate.' ;
                          type uint64 {
                            range 1..18446744073709551615 {
                              description 'The range of broadcast input bytes.' ;
                            }

                          }

                          units bps ;
                        }

                        leaf broadcast-inrate-pps {
                          description 'The broadcast input packets rate.' ;
                          type uint32 {
                            range 1..4294967295 {
                              description 'The range of broadcast input packets rate.' ;
                            }

                          }

                          units pps ;
                        }

                        leaf drop-inrate-bps {
                          description 'The drop input bytes rate.' ;
                          type uint64 {
                            range 1..18446744073709551615 {
                              description 'The range of drop input bytes.' ;
                            }

                          }

                          units bps ;
                        }

                        leaf drop-inrate-pps {
                          description 'The drop input packets rate.' ;
                          type uint32 {
                            range 1..4294967295 {
                              description 'The range of drop input packets rate.' ;
                            }

                          }

                          units pps ;
                        }

                      }

                    }

                  }

                }

              }

            }

            container evpn-vpls-static-vxlans {
              description 'EVPN VPLS static VXLAN configuration info.' ;
              list evpn-vpls-static-vxlan {
                description 'EVPN VPLS static VXLAN configuration info.' ;
                key static-vni ;
                leaf static-vni {
                  description 'Static VNI value.' ;
                  type uint32 {
                    range 1..16777215 ;

                  }

                }

                leaf split-horizon {
                  description 'Split-horizon group,the range is A-Z.' ;
                  type string {
                    length 1..51 ;

                  }

                  ncd:revise-date 2017-03-07 ;
                }

                container static-tunnel-binds {
                  description 'Static tunnel bind table.' ;
                  list static-tunnel-bind {
                    description 'Static tunnel bind table.' ;
                    key static-tunnel-name ;
                    leaf static-tunnel-name {
                      description 'Static tunnel interface name.' ;
                      type ncd:ifname {
                        length 1..31 ;

                      }

                    }

                  }

                }

              }

            }

            container peer-ipv4 {
              description 'The peer address type is IPv4.' ;
              list peer-ipv4-params {
                description 'IPv4 address parameters.' ;
                key ipv4-address ;
                leaf ipv4-address {
                  description 'IPv4 address.' ;
                  type ncd:ipv4-address-none-zero ;

                }

                leaf tunnel-policy-name {
                  description 'The name of the tunnel policy.' ;
                  type string {
                    length 1..63 {
                      description 'The length of tunnel policy name.' ;
                    }

                  }

                  mandatory true ;
                }

              }

              ncd:revise-date 2018-07-08 ;
            }

            container peer-ipv6 {
              description 'The peer address type is IPv6.' ;
              list peer-ipv6-params {
                description 'IPv6 address parameters.' ;
                key ipv6-address ;
                leaf ipv6-address {
                  description 'IPv6 address.' ;
                  type ncd:ipv6-address {
                    pattern "([0-9a-fA-F]{1,4}:){7}([0-9a-fA-F]{0,4})$|^([0-9a-fA-F]{1,4}:){1,6}(:[0-9a-fA-F]{0,4}){1,6}$|^([:]{2})(([0-9a-fA-F]{1,4}:){0,6})([0-9a-fA-F]{1,4})$|^([0-9a-fA-F]{1,4}:){6}([0-9]{1,3}.){3}([0-9]{1,3})$|^([0-9a-fA-F]{1,4}:){1,5}(:[0-9a-fA-F]{0,4}){1,5}([0-9]{1,3}.){3}([0-9]{1,3})$|^([:]{2})(([0-9a-fA-F]{1,4}:){0,5})([0-9]{1,3}.){3}([0-9]{1,3})" ;

                  }

                }

                leaf tunnel-policy-name {
                  description 'The name of the tunnel policy.' ;
                  type string {
                    length 1..63 {
                      description 'The length of tunnel policy name.' ;
                    }

                  }

                  mandatory true ;
                }

              }

              ncd:revise-date 2018-07-08 ;
            }

            container df-shortcut-params {
              description 'DF shortcut parameters of EVPN VPLS.' ;
              presence df-shortcut-params ;
              leaf df-shortcut-flag {
                description 'DF shortcut flag of EVPN VPLS.' ;
                type enumeration {
                  enum disable {
                    value 0 ;
                    description 'The DF shortcut flag is disable.' ;
                  }

                  enum enable {
                    value 1 ;
                    description 'The DF shortcut flag is enable.' ;
                  }

                }

                default disable ;
              }

              ncd:revise-date 2019-02-15 ;
            }

            container evpn-vpls-pw-bind {
              description 'EVPN VPLS PW binding instance info.' ;
              list pw-instance-bind {
                description 'PW binding instance configuration info.' ;
                key pw-name ;
                leaf pw-name {
                  description 'The name of the PW in the bind.' ;
                  type ncd:ifname ;

                }

                leaf split-horizon {
                  description 'The split-horizon flag of the PW bind.' ;
                  type enumeration {
                    enum spoke {
                      value 0 ;
                      description 'The split-horizon flag is spoke.' ;
                    }

                    enum hub {
                      value 1 ;
                      description 'The split-horizon flag is hub.' ;
                    }

                  }

                  mandatory true ;
                }

                leaf split-horizon-scopes {
                  description 'Split-horizon group,the range is A-Z.' ;
                  type string {
                    length 1..51 {
                      description 'The length of split-horizon-scopes.' ;
                    }

                  }

                }

              }

              ncd:revise-date 2019-04-09 ;
            }

            container evpn-vpls-evpn-pw-bind {
              description 'EVPN VPLS EVPN-PW binding instance info.' ;
              list evpn-pw-instance-bind {
                description 'EVPN-PW binding instance configuration info.' ;
                key pw-name ;
                leaf pw-name {
                  description 'The name of the EVPN-PW in the bind.' ;
                  type ncd:ifname ;

                }

                leaf split-horizon {
                  description 'The split-horizon flag of the EVPN-PW bind.' ;
                  type enumeration {
                    enum spoke {
                      value 0 ;
                      description 'The split-horizon flag is spoke.' ;
                    }

                    enum hub {
                      value 1 ;
                      description 'The split-horizon flag is hub.' ;
                    }

                  }

                  default spoke ;
                }

                leaf split-horizon-scopes {
                  description 'Split-horizon group,the range is A-Z.' ;
                  type string {
                    length 1..51 {
                      description 'The length of split-horizon-scopes.' ;
                    }

                  }

                }

                container peer-evpn-vpws {
                  description 'Specify peer type of the remote PE is EVPN-VPWS.' ;
                  choice type {
                    description 'The local encapsulation type.' ;
                    case mpls {
                      description 'The local encapsulation is MPLS.' ;
                      container evpn-vpws-mpls {
                        description 'MPLS encapsulation of EVPN VPWS.' ;
                        presence evpn-vpws-mpls ;
                        leaf local-vpws-id {
                          description 'Config local VPWS ID.' ;
                          type uint32 {
                            range 4096..4294967294 {
                              description 'The range of local VPWS ID.' ;
                            }

                          }

                          mandatory true ;
                        }

                        leaf remote-vpws-id {
                          description 'Config remote VPWS ID.' ;
                          type uint32 {
                            range 4096..4294967294 {
                              description 'The range of remote VPWS ID.' ;
                            }

                          }

                          mandatory true ;
                        }

                        leaf encapsulation {
                          description 'The encapsulation of the EVPN-PW.' ;
                          type enumeration {
                            enum tagged {
                              value 4 ;
                              description 'The default encapsulation is tagged.' ;
                            }

                            enum raw {
                              value 5 ;
                              description 'The default encapsulation is raw.' ;
                            }

                          }

                        }

                        leaf control-word {
                          description 'The control-word capability.' ;
                          type enumeration {
                            enum not-preferred {
                              value 0 ;
                              description 'The control-word capability is not preferred.' ;
                            }

                            enum preferred {
                              value 1 ;
                              description 'The control-word capability is preferred.' ;
                            }

                          }

                          default not-preferred ;
                        }

                        leaf tunnel-policy-name {
                          description 'The tunnel policy name.' ;
                          type string {
                            length 1..63 {
                              description 'The length of tunnel policy name.' ;
                            }

                          }

                        }

                        leaf track-name {
                          description 'The name of the track object.' ;
                          type string {
                            length 1..31 {
                              description 'The length of track name.' ;
                            }

                          }

                        }

                        container tunnel-destination {
                          description 'The address as tunnel destination.' ;
                          choice destination-type {
                            description 'The tunnel destination type.' ;
                            case ipv6 {
                              description 'The tunnel destination type is ipv6.' ;
                              leaf tunnel-destination-ipv6 {
                                description 'IPv6 address as tunnel destination.' ;
                                type ncd:ipv6-address {
                                  pattern "([0-9a-fA-F]{1,4}:){7}([0-9a-fA-F]{0,4})$|^([0-9a-fA-F]{1,4}:){1,6}(:[0-9a-fA-F]{0,4}){1,6}$|^([:]{2})(([0-9a-fA-F]{1,4}:){0,6})([0-9a-fA-F]{1,4})$|^([0-9a-fA-F]{1,4}:){6}([0-9]{1,3}.){3}([0-9]{1,3})$|^([0-9a-fA-F]{1,4}:){1,5}(:[0-9a-fA-F]{0,4}){1,5}([0-9]{1,3}.){3}([0-9]{1,3})$|^([:]{2})(([0-9a-fA-F]{1,4}:){0,5})([0-9]{1,3}.){3}([0-9]{1,3})" ;

                                }

                              }

                            }

                            case ipv4 {
                              description 'The tunnel destination type is ipv4.' ;
                              leaf tunnel-destination-ipv4 {
                                description 'IPv4 address as tunnel destination.' ;
                                type ncd:ipv4-address-none-zero ;

                              }

                            }

                          }

                        }

                      }

                    }

                    case srv6 {
                      description 'The local encapsulation is SRv6.' ;
                      container evpn-vpws-srv6 {
                        description 'SRv6 encapsulation of EVPN VPWS.' ;
                        presence evpn-vpws-srv6 ;
                        leaf local-vpws-id {
                          description 'Config local VPWS ID.' ;
                          type uint32 {
                            range 4096..4294967294 {
                              description 'The range of local VPWS ID.' ;
                            }

                          }

                          mandatory true ;
                        }

                        leaf remote-vpws-id {
                          description 'Config remote VPWS ID.' ;
                          type uint32 {
                            range 4096..4294967294 {
                              description 'The range of remote VPWS ID.' ;
                            }

                          }

                          mandatory true ;
                        }

                        leaf encapsulation {
                          description 'The encapsulation of the EVPN-PW.' ;
                          type enumeration {
                            enum tagged {
                              value 4 ;
                              description 'The default encapsulation is tagged.' ;
                            }

                            enum raw {
                              value 5 ;
                              description 'The default encapsulation is raw.' ;
                            }

                          }

                        }

                        leaf tunnel-policy-name {
                          description 'The tunnel policy name.' ;
                          type string {
                            length 1..63 {
                              description 'The length of tunnel policy name.' ;
                            }

                          }

                        }

                        leaf track-name {
                          description 'The name of the track object.' ;
                          type string {
                            length 1..31 {
                              description 'The length of track name.' ;
                            }

                          }

                        }

                        leaf srv6-locator-name {
                          description 'The SRv6 locator name.' ;
                          type string {
                            length 1..31 {
                              description 'The length of SRv6 locator name.' ;
                            }

                          }

                        }

                        container tunnel-destination {
                          description 'The address as tunnel destination.' ;
                          choice destination-type {
                            description 'The tunnel destination type.' ;
                            case ipv6 {
                              description 'The tunnel destination type is ipv6.' ;
                              leaf tunnel-destination-ipv6 {
                                description 'IPv6 address as tunnel destination.' ;
                                type ncd:ipv6-address {
                                  pattern "([0-9a-fA-F]{1,4}:){7}([0-9a-fA-F]{0,4})$|^([0-9a-fA-F]{1,4}:){1,6}(:[0-9a-fA-F]{0,4}){1,6}$|^([:]{2})(([0-9a-fA-F]{1,4}:){0,6})([0-9a-fA-F]{1,4})$|^([0-9a-fA-F]{1,4}:){6}([0-9]{1,3}.){3}([0-9]{1,3})$|^([0-9a-fA-F]{1,4}:){1,5}(:[0-9a-fA-F]{0,4}){1,5}([0-9]{1,3}.){3}([0-9]{1,3})$|^([:]{2})(([0-9a-fA-F]{1,4}:){0,5})([0-9]{1,3}.){3}([0-9]{1,3})" ;

                                }

                              }

                            }

                            case ipv4 {
                              description 'The tunnel destination type is ipv4.' ;
                              leaf tunnel-destination-ipv4 {
                                description 'IPv4 address as tunnel destination.' ;
                                type ncd:ipv4-address-none-zero ;

                              }

                            }

                          }

                        }

                      }

                    }

                  }

                }

              }

              ncd:revise-date 2022-12-20 ;
            }

            container martini-discovery {
              if-feature martini-discovery ;

              description 'Martini auto discovery configuration info.' ;
              presence "Martini discovery type" ;
              container martini-params {
                description 'Martini auto discovery configuration parameter.' ;
                list martini-vpls-params {
                  description 'Martini auto discovery configuration parameter of VPLS.' ;
                  key vpls-id ;
                  leaf vpls-id {
                    description 'VPLS instance auto-discovery identifier.' ;
                    type union {
                      type ncd:asn-nn ;

                      type ncd:ipadd-nn ;

                    }

                  }

                  leaf sspw-target-differ-from-ldp {
                    description 'The target PE address is different from the target LDP identifier.' ;
                    type empty ;

                    ncd:revise-date 2022-12-05 ;
                  }

                }

              }

              container route-target-params {
                description 'The route target params.' ;
                list route-target {
                  description 'The route target.' ;
                  key 'rt-value effect-type' ;
                  leaf rt-value {
                    description 'The route target parameter.' ;
                    type union {
                      type ncd:asn-nn ;

                      type ncd:ipadd-nn ;

                    }

                  }

                  leaf effect-type {
                    description 'The route target effect type.' ;
                    type enumeration {
                      enum export {
                        value 2 ;
                        description 'The route target effect type is export.' ;
                      }

                      enum import {
                        value 3 ;
                        description 'The route target effect type is import.' ;
                      }

                    }

                  }

                }

              }

              container pw-details-params {
                description 'The PW details params.' ;
                list pw-details {
                  description 'The PW details info.' ;
                  key peer-address ;
                  leaf peer-address {
                    description 'The IP address of remote endpoint.' ;
                    type ncd:ipv4-address-none-zero ;

                  }

                  leaf encap-type {
                    description 'The encapsulation type of the auto PW.' ;
                    type enumeration {
                      enum ethernet-tagged {
                        value 4 ;
                        description 'The encapsulation type of the auto PW is ethernet tagged.' ;
                      }

                      enum ethernet {
                        value 5 ;
                        description 'The encapsulation type of the auto PW is ethernet.' ;
                      }

                    }

                    default ethernet ;
                  }

                  leaf tunnel-policy-name {
                    description 'The tunnel policy name of the auto PW.' ;
                    type string {
                      length 1..63 {
                        description 'The length of tunnel policy name.' ;
                      }

                    }

                  }

                  leaf control-word {
                    description 'The control-word capability of the auto PW.' ;
                    type enumeration {
                      enum not-preferred {
                        value 0 ;
                        description 'The control-word capability of the auto PW is not preferred.' ;
                      }

                      enum preferred {
                        value 1 ;
                        description 'The control-word capability of the auto PW is preferred.' ;
                      }

                    }

                    default not-preferred ;
                  }

                  leaf traffic-enable {
                    description 'The traffic statistics status of Martini PW.' ;
                    type enumeration {
                      enum disable {
                        value 0 ;
                        description 'The traffic statistics status of Martini PW is disable.' ;
                      }

                      enum enable {
                        value 1 ;
                        description 'The traffic statistics status of Martini PW is enable.' ;
                      }

                    }

                    default disable ;
                  }

                  leaf vccv-flow-label {
                    description 'The flow-label for VCCV packets without standard flow-labels.' ;
                    type empty ;

                    ncd:revise-date 2022-03-15 ;
                  }

                  container vccv-bfd-params {
                    description 'The VCCV BFD parameters info of Martini PW.' ;
                    leaf vccv-bfd {
                      description 'The BFD capability of the Martini PW.' ;
                      type enumeration {
                        enum disable {
                          value 0 ;
                          description 'The BFD capability is disable.' ;
                        }

                        enum enable {
                          value 1 ;
                          description 'The BFD capability is enable.' ;
                        }

                      }

                      default disable ;
                    }

                    leaf vccv-bfd-encapsulation {
                      description 'The BFD raw encapsulation capability of the Martini PW.' ;
                      type enumeration {
                        enum ip {
                          value 0 ;
                          description 'The BFD raw encapsulation capability is IP.' ;
                        }

                        enum raw {
                          value 1 ;
                          description 'The BFD raw encapsulation capability is raw.' ;
                        }

                      }

                      default ip ;
                    }

                    leaf vccv-bfd-capability {
                      description 'The BFD signal status capability of the Martini PW.' ;
                      type enumeration {
                        enum basic {
                          value 0 ;
                          description 'The BFD signal status capability is basic.' ;
                        }

                        enum status {
                          value 1 ;
                          description 'The BFD signal status capability is status.' ;
                        }

                      }

                      default basic ;
                    }

                    leaf vccv-bfd-template-name {
                      description 'BFD template name.' ;
                      type string {
                        length 1..31 {
                          description 'The length of BFD template name.' ;
                        }

                      }

                      ncd:revise-date 2021-03-04 ;
                    }

                  }

                  leaf split-horizon-scope {
                    description 'The split-horizon-scope of Martini PW.' ;
                    type enumeration {
                      enum none {
                        value 1 ;
                        description 'No split-horizon scope joined.' ;
                      }

                      enum any {
                        value 2 ;
                        description 'All split-horizon scope joined.' ;
                      }

                    }

                  }

                  container max-traffic-rate-params {
                    description 'The maximum of traffic rate parameters.' ;
                    leaf max-traffic-rate {
                      description 'The maximum of traffic rate.' ;
                      type uint32 {
                        range 64..10000000 {
                          description 'The maximum of traffic rate.' ;
                        }

                      }

                      units kbps ;
                    }

                    leaf max-multicast-rate-percent {
                      description 'The max percent of multicast traffic rate.' ;
                      type uint32 {
                        range 1..100 {
                          description 'The max percent of multicast traffic rate.' ;
                        }

                      }

                      default 100 ;
                    }

                    leaf max-unicast-rate-percent {
                      description 'The max percent of unicast traffic rate.' ;
                      type uint32 {
                        range 1..100 {
                          description 'The max percent of unicast traffic rate.' ;
                        }

                      }

                      default 100 ;
                    }

                    leaf max-unknown-multicast-rate-percent {
                      description 'The max percent of unknown-multicast traffic rate.' ;
                      type uint32 {
                        range 1..100 {
                          description 'The max percent of unknown-multicast traffic rate.' ;
                        }

                      }

                      default 100 ;
                    }

                    leaf max-unknown-unicast-rate-percent {
                      description 'The max percent of unknown-unicast traffic rate.' ;
                      type uint32 {
                        range 1..100 {
                          description 'The max percent of unknown-unicast traffic rate.' ;
                        }

                      }

                      default 100 ;
                    }

                    leaf max-broadcast-rate-percent {
                      description 'The max percent of broadcast traffic rate.' ;
                      type uint32 {
                        range 1..100 {
                          description 'The max percent of broadcast traffic rate.' ;
                        }

                      }

                      default 100 ;
                    }

                  }

                  container mac-limit-params {
                    description 'Maximum MAC entries and action when MAC entries is exceeding the maximum.' ;
                    presence mac-entries ;
                    leaf maximum {
                      description 'Maximum MAC entries.' ;
                      type uint32 {
                        range 1..4294967295 {
                          description 'Minimum is 1. Maximum and default is defined by performance parameter.' ;
                        }

                      }

                      mandatory true ;
                    }

                    leaf action {
                      description 'The action when MAC entries is exceeding the maximum.' ;
                      type enumeration {
                        enum broadcast {
                          value 0 ;
                          description 'The action when MAC entries is exceeding the maximum is broadcast.' ;
                        }

                        enum drop {
                          value 1 ;
                          description 'The action when MAC entries is exceeding the maximum is drop.' ;
                        }

                      }

                      mandatory true ;
                    }

                    ncd:revise-date 2021-01-05 ;
                  }

                  container flow-label {
                    description 'Martini PW support flow label function.' ;
                    leaf push {
                      description 'Flow label transmit capability.' ;
                      type enumeration {
                        enum disable {
                          value 0 ;
                          description 'Flow label transmit capability is disable.' ;
                        }

                        enum enable {
                          value 1 ;
                          description 'Flow label transmit capability is enable.' ;
                        }

                      }

                      default disable ;
                    }

                    leaf pop {
                      description 'Flow label receive capability.' ;
                      type enumeration {
                        enum disable {
                          value 0 ;
                          description 'Flow label receive capability is disable.' ;
                        }

                        enum enable {
                          value 1 ;
                          description 'Flow label receive capability is enable.' ;
                        }

                      }

                      default disable ;
                    }

                    ncd:revise-date 2022-03-15 ;
                  }

                  container split-horizon-scope-params {
                    choice split-horizon-params-type {
                      case split-horizon-scope-enum {
                        leaf split-horizon-scope-enum {
                          type enumeration {
                            enum none {
                              value 1 ;
                              description 'No split-horizon scope joined.' ;
                            }

                            enum any {
                              description 'All split-horizon scope joined.' ;
                              value 2 ;
                            }

                          }

                          description 'The split-horizon-scope of Martini PW.' ;
                        }

                      }

                      case split-horizon-scope-group {
                        leaf split-horizon-scope-group {
                          type string {
                            length 1..51 {
                              description 'The length of split-horizon-scopes.' ;
                            }

                          }

                          description 'The name list of split-horizon group.' ;
                        }

                      }

                      description 'The split-horizon-scope of Martini PW type.' ;
                    }

                    description 'The split-horizon-scope of Martini PW.' ;
                    ncd:revise-date 2023-06-05 ;
                  }

                }

              }

              ncd:revise-date 2019-04-09 ;
            }

            container kompella-discovery {
              if-feature kompella-discovery ;

              description 'Kompella discovery configuration info.' ;
              presence "Kompella discovery type" ;
              container kompella-params {
                description 'Kompella auto discovery configuration parameter.' ;
                list kompella-vpls-params {
                  description 'VPLS Kompella params.' ;
                  key rd ;
                  leaf rd {
                    description 'The route distinguisher parameter.' ;
                    type union {
                      type ncd:asn-nn ;

                      type ncd:ipadd-nn ;

                    }

                  }

                  leaf ve-id {
                    description 'The VE identification for the VPLS instance.' ;
                    type uint16 {
                      range 0..65534 {
                        description 'VE-ID value.' ;
                      }

                    }

                  }

                  leaf ve-set-style {
                    description 'The style of VE set parameter.' ;
                    type enumeration {
                      enum continuous {
                        value 1 ;
                        description 'The style of VE set parameter is continuous.' ;
                      }

                      enum discrete {
                        value 2 ;
                        description 'The style of VE set parameter is discrete.' ;
                      }

                    }

                  }

                  leaf max-ve-id {
                    description 'The maximum identification for the VPLS instance.' ;
                    type uint32 {
                      range 1..79 {
                        description 'The maximum identification value.' ;
                      }

                    }

                  }

                  leaf tunnel-policy-name {
                    description 'The name of tunnel policy parameter.' ;
                    type string {
                      length 1..63 {
                        description 'The length of tunnel policy name.' ;
                      }

                    }

                  }

                  leaf traffic-enable {
                    description 'The traffic statistics status of Kompella PW.' ;
                    type enumeration {
                      enum disable {
                        value 0 ;
                        description 'The traffic statistics status of Kompella PW is disable.' ;
                      }

                      enum enable {
                        value 1 ;
                        description 'The traffic statistics status of Kompella PW is enable.' ;
                      }

                    }

                    default disable ;
                  }

                  leaf control-word {
                    description 'The control-word capability of the Kompella PW.' ;
                    type enumeration {
                      enum not-preferred {
                        value 0 ;
                        description 'The control-word capability is not preferred.' ;
                      }

                      enum preferred {
                        value 1 ;
                        description 'The control-word capability is preferred.' ;
                      }

                    }

                    default not-preferred ;
                  }

                  container encapulation {
                    description 'The encapsulation params of the Kompella PW.' ;
                    presence encapulation ;
                    leaf encapulation-type {
                      description 'Specify encapsulation mode for Kompella PW.' ;
                      type enumeration {
                        enum vlan {
                          value 4 ;
                          description 'The PW type is VLAN.' ;
                        }

                        enum ethernet {
                          value 5 ;
                          description 'The PW type is ethernet.' ;
                        }

                      }

                      mandatory true ;
                    }

                    leaf separate-in-signal {
                      description 'Encapsulation use separate PW type in signal or not.' ;
                      type enumeration {
                        enum not-separate-encap {
                          value 0 ;
                          description 'Encapsulation not use separate PW type in signal.' ;
                        }

                        enum separate-encap {
                          value 1 ;
                          description 'Encapsulation use separate PW type in signal.' ;
                        }

                      }

                      default not-separate-encap ;
                    }

                  }

                  leaf split-horizon-scope {
                    status obsolete {
                      ncd:revise-date 2022-02-15 ;
                    }

                    description 'The split-horizon-scope of Kompella PW.' ;
                    type enumeration {
                      enum none {
                        value 1 ;
                        description 'No split-horizon scope joined.' ;
                      }

                      enum any {
                        value 2 ;
                        description 'All split-horizon scopes joined.' ;
                      }

                    }

                  }

                  container multi-chassis-pw-params {
                    description 'Multiple chassis PW redundancy parameters.' ;
                    presence multi-chassis-pw-params ;
                    leaf multi-chassis-pw {
                      description 'Multiple chassis PW redundancy grouped by site ID.' ;
                      type empty ;

                      mandatory true ;
                    }

                    container temporary-standby-params {
                      description 'Multiple chassis PW redundancy temporary standby parameters.' ;
                      presence temporary-standby-params ;
                      leaf temporary-standby-time {
                        description 'Wait for other PEs to receive preference update.' ;
                        type uint32 {
                          range 1..5000 {
                            description 'The range of temporary standby time.' ;
                          }

                        }

                        units ms ;
                        mandatory true ;
                      }

                      leaf smoothly {
                        description 'Temporary standby drops packets smoothly or not.' ;
                        type empty ;

                      }

                    }

                    ncd:revise-date 2021-12-13 ;
                  }

                  container site-preference-params {
                    description 'Site preference parameters.' ;
                    presence site-preference-params ;
                    leaf site-preference {
                      description 'Configure site preference.' ;
                      type uint32 {
                        range 1..65535 {
                          description 'Set site preference' ;
                        }

                      }

                      mandatory true ;
                    }

                    leaf backup-preference {
                      description 'Site Preference Value of the other multihomed PE.' ;
                      type uint32 {
                        range 1..65535 {
                          description 'Set site preference.' ;
                        }

                      }

                    }

                    ncd:revise-date 2021-12-22 ;
                  }

                  container flow-label {
                    description 'Configure flow-label capability.' ;
                    leaf push {
                      description 'Set flow-label transmit capability.' ;
                      type enumeration {
                        enum static {
                          value 1 ;
                          description 'Push a flow-label even if R flag is not received.' ;
                        }

                        enum dynamic {
                          value 2 ;
                          description 'Push a flow-label only if R flag is received.' ;
                        }

                      }

                    }

                    leaf pop {
                      description 'Set flow-label receive capability.' ;
                      type enumeration {
                        enum static {
                          value 1 ;
                          description 'Pop a flow-label even if T flag is not received.' ;
                        }

                        enum dynamic {
                          value 2 ;
                          description 'Pop a flow-label only if T flag is received.' ;
                        }

                      }

                    }

                    ncd:revise-date 2021-12-22 ;
                  }

                  container split-horizon-scope-params {
                    description 'The split-horizon-scope of Kompella PW.' ;
                    choice split-horizon-params-type {
                      description 'The split-horizon-scope of Kompella PW type.' ;
                      case split-horizon-scope-enum {
                        description 'The split-horizon-scope of Kompella PW.' ;
                        leaf split-horizon-scope-enum {
                          description 'The split-horizon-scope of Kompella PW.' ;
                          type enumeration {
                            enum none {
                              value 1 ;
                              description 'No split-horizon scope joined.' ;
                            }

                            enum any {
                              value 2 ;
                              description 'All split-horizon scope joined.' ;
                            }

                          }

                        }

                      }

                      case split-horizon-scope-group {
                        description 'The split-horizon-scope-group of Kompella PW.' ;
                        leaf split-horizon-scope-group {
                          description 'The name list of split-horizon group.' ;
                          type string {
                            length 1..51 {
                              description 'The length of split-horizon-scopes.' ;
                            }

                          }

                        }

                      }

                    }

                    ncd:revise-date 2022-02-15 ;
                  }

                }

              }

              container route-target-params {
                description 'The route target params.' ;
                list route-target {
                  description 'The route target.' ;
                  key 'rt-value effect-type' ;
                  leaf rt-value {
                    description 'RT attribute value.' ;
                    type union {
                      type ncd:asn-nn ;

                      type ncd:ipadd-nn ;

                    }

                  }

                  leaf effect-type {
                    description 'The route target effect type.' ;
                    type enumeration {
                      enum export {
                        value 2 ;
                        description 'The route target effect type is export.' ;
                      }

                      enum import {
                        value 3 ;
                        description 'The route target effect type is import.' ;
                      }

                    }

                  }

                }

              }

              container ve-block-params {
                description 'Kompella auto discovery configuration parameter.' ;
                list ve-block {
                  description 'The VE block of VPLS.' ;
                  key begin-ve-id ;
                  leaf begin-ve-id {
                    description 'The begin value of the VE identification block.' ;
                    type uint32 {
                      range 0..65535 {
                        description 'The minimum identification value.' ;
                      }

                    }

                  }

                  leaf end-ve-id {
                    description 'The end value of the VE identification block.' ;
                    type uint32 {
                      range 0..65535 {
                        description 'The maximum identification value.' ;
                      }

                    }

                    mandatory true ;
                  }

                }

              }

              ncd:revise-date 2019-04-09 ;
            }

            container max-traffic-rate-params {
              status obsolete {
                ncd:revise-date 2021-01-07 ;
              }

              description 'The maximum of traffic rate parameters.' ;
              leaf max-traffic-rate {
                description 'The maximum of traffic rate.' ;
                type uint32 {
                  range 64..10000000 {
                    description 'The maximum of traffic rate.' ;
                  }

                }

                units kbps ;
              }

              leaf max-unknown-unicast-rate-percent {
                description 'The max percent of unknown-unicast traffic rate percent.' ;
                type uint8 {
                  range 1..100 {
                    description 'The range of rate percent.' ;
                  }

                }

                default 100 ;
              }

              leaf max-multicast-rate-percent {
                description 'The max percent of multicast traffic rate percent.' ;
                type uint8 {
                  range 1..100 {
                    description 'The range of rate percent.' ;
                  }

                }

                default 100 ;
              }

              leaf max-broadcast-rate-percent {
                description 'The max percent of broadcast traffic rate percent.' ;
                type uint8 {
                  range 1..100 {
                    description 'The range of rate percent.' ;
                  }

                }

                default 100 ;
              }

              ncd:revise-date 2019-07-11 ;
            }

            container broadcast-traffic-rate-params {
              description 'The traffic rate parameters of broadcast.' ;
              presence broadcast-traffic-rate-params ;
              leaf cir {
                description 'Committed information rate.' ;
                type uint32 {
                  range "0 | 1..4294967295" {
                    description 'CIR' ;
                  }

                }

                units kbps ;
                mandatory true ;
              }

              leaf cbs {
                description 'Committed burst size.' ;
                type uint32 {
                  range 1..4294967295 {
                    description 'CBS' ;
                  }

                }

                units KB ;
                mandatory true ;
              }

              leaf pir {
                description 'Peak information rate.' ;
                type uint32 {
                  range "0 | 1..4294967295" {
                    description 'PIR' ;
                  }

                }

                units kbps ;
                mandatory true ;
              }

              leaf pbs {
                description 'Peak burst size.' ;
                type uint32 {
                  range 1..4294967295 {
                    description 'CBS' ;
                  }

                }

                units KB ;
                mandatory true ;
              }

              ncd:revise-date 2020-12-25 ;
            }

            container unknown-multicast-traffic-rate-params {
              description 'The traffic rate parameters of multicast.' ;
              presence unknown-multicast-traffic-rate-params ;
              leaf cir {
                description 'Committed information rate.' ;
                type uint32 {
                  range "0 | 1..4294967295" {
                    description 'CIR' ;
                  }

                }

                units kbps ;
                mandatory true ;
              }

              leaf cbs {
                description 'Committed burst size.' ;
                type uint32 {
                  range 1..4294967295 {
                    description 'CBS' ;
                  }

                }

                units KB ;
                mandatory true ;
              }

              leaf pir {
                description 'Peak information rate.' ;
                type uint32 {
                  range "0 | 1..4294967295" {
                    description 'PIR' ;
                  }

                }

                units kbps ;
                mandatory true ;
              }

              leaf pbs {
                description 'Peak burst size.' ;
                type uint32 {
                  range 1..4294967295 {
                    description 'CBS' ;
                  }

                }

                units KB ;
                mandatory true ;
              }

              ncd:revise-date 2020-12-25 ;
            }

            container unknown-unicast-traffic-rate-params {
              description 'The traffic rate parameters of unknown-unicast.' ;
              presence unknown-unicast-traffic-rate-params ;
              leaf cir {
                description 'Committed information rate.' ;
                type uint32 {
                  range "0 | 1..4294967295" {
                    description 'CIR' ;
                  }

                }

                units kbps ;
                mandatory true ;
              }

              leaf cbs {
                description 'Committed burst size.' ;
                type uint32 {
                  range 1..4294967295 {
                    description 'CBS' ;
                  }

                }

                units KB ;
                mandatory true ;
              }

              leaf pir {
                description 'Peak information rate.' ;
                type uint32 {
                  range "0 | 1..4294967295" {
                    description 'PIR' ;
                  }

                }

                units kbps ;
                mandatory true ;
              }

              leaf pbs {
                description 'Peak burst size.' ;
                type uint32 {
                  range 1..4294967295 {
                    description 'CBS' ;
                  }

                }

                units KB ;
                mandatory true ;
              }

              ncd:revise-date 2020-12-25 ;
            }

          }

          ncd:revise-date 2016-07-22 ;
        }

        container vpws-community-instances {
          description 'The VPWS community instances configuration info.' ;
          list vpws-community-instance {
            description 'The VPWS community instance configuration info.' ;
            key instance-name ;
            leaf instance-name {
              description 'The name of the VPWS community instance.' ;
              type string {
                length 1..32 {
                  description 'The length of instance name.' ;
                }

              }

            }

            leaf instance-description {
              description 'The description of the instance.' ;
              type ncd:string-with-blank {
                length 1..104 {
                  description 'The description range of instance.' ;
                }

              }

              ncd:revise-date 2019-09-29 ;
            }

            leaf best-path {
              description 'Select the best path nexthop priority.' ;
              type enumeration {
                enum ipv4 {
                  value 1 ;
                  description 'Select IPv4 nexthop.' ;
                }

                enum ipv6 {
                  value 2 ;
                  description 'Select IPv6 nexthop.' ;
                }

              }

              ncd:revise-date 2021-04-27 ;
            }

            leaf best-path-sr {
              description 'Configure the best route selection rule in the SR domain.' ;
              type enumeration {
                enum te-tunnel {
                  value 1 ;
                  description 'Route recursived to TE tunnel preferred.' ;
                }

                enum end-point {
                  value 2 ;
                  description 'Route with smaller end-point address preferred.' ;
                }

              }

              ncd:revise-date 2022-03-24 ;
            }

            leaf eti-redundancy {
              description 'Redundancy for Ethernet Tag ID (ETI) of null-ESI.' ;
              type enumeration {
                enum frr {
                  value 1 ;
                  description 'FRR protection for remote ETIs.' ;
                }

                enum load-balance {
                  value 2 ;
                  description 'Load-Balance (LB) protection for remote ETIs.' ;
                }

              }

              ncd:revise-date 2021-09-08 ;
            }

            leaf traffic-enable {
              description 'The traffic statistics status of VPWS EVPN service.' ;
              type enumeration {
                enum disable {
                  value 0 ;
                  description 'The traffic statistics status of VPWS EVPN service is disable.' ;
                }

                enum enable {
                  value 1 ;
                  description 'The traffic statistics status of VPWS EVPN service is enable.' ;
                }

              }

              default disable ;
              ncd:revise-date 2021-06-07 ;
            }

            leaf mtu-mismatch-ignore {
              description 'Ignore the MTU mismatch in the PW negotiation.' ;
              type empty ;

              ncd:revise-date 2022-09-13 ;
            }

            container evpn-redundancy-adjust {
              description 'Redundancy-mode adjustment for remote EVPN routes.' ;
              leaf frr {
                description 'Fast-Reroute (FRR) protection mode.' ;
                type empty ;

              }

              leaf load-balance {
                description 'Load-Balance (LB) protection mode.' ;
                type empty ;

              }

              ncd:revise-date 2022-09-19 ;
            }

            container route-map-params {
              description 'Route map parameters.' ;
              leaf export-map-name {
                description 'Export route map name.' ;
                type string {
                  length 1..200 {
                    description 'The length of export route map name.' ;
                  }

                }

              }

              leaf import-map-name {
                description 'Import route map name.' ;
                type string {
                  length 1..200 {
                    description 'The length of import route map name.' ;
                  }

                }

              }

              ncd:revise-date 2020-03-27 ;
            }

            container vpws-community-rd {
              description 'VPWS community route distinguisher parameters.' ;
              presence vpws-community-rd ;
              choice rd-type {
                description 'RD generation type.' ;
                case rd-manual {
                  description 'RD configured manually.' ;
                  leaf rd {
                    description 'The route distinguisher parameter.' ;
                    type union {
                      type ncd:asn-nn ;

                      type ncd:ipadd-nn ;

                      type ncd:asnd-nn ;

                    }

                    mandatory true ;
                  }

                }

                case rd-auto {
                  description 'RD generated automatically.' ;
                  leaf template-based {
                    description 'Automatically generated RD based on RD template.' ;
                    type empty ;

                    mandatory true ;
                  }

                  ncd:revise-date 2022-04-20 ;
                }

              }

            }

            container auto-discovery-type {
              description 'The auto-discovery type of VPWS community instance.' ;
              choice type {
                description 'The auto-discovery type of VPWS community instance.' ;
                case kompella {
                  description 'The Kompella auto-discovery type.' ;
                  container kompella-params {
                    description 'The parameters of Kompella type.' ;
                    presence kompella-params ;
                    leaf mode {
                      description 'The Kompella mode of vpws-community-instance.' ;
                      type enumeration {
                        enum kompella {
                          value 1 ;
                          description 'The mode is Kompella.' ;
                        }

                      }

                      mandatory true ;
                    }

                    leaf control-word {
                      description 'The control-word capability.' ;
                      type enumeration {
                        enum not-preferred {
                          value 0 ;
                          description 'The control-word capability is not preferred.' ;
                        }

                        enum preferred {
                          value 1 ;
                          description 'The control-word capability is preferred.' ;
                        }

                      }

                      default not-preferred ;
                    }

                    leaf circuit-status-vector {
                      description 'Signal and receive circuit status vector(CSV).' ;
                      type enumeration {
                        enum enable {
                          value 1 ;
                          description 'Enable circuit status vector capability.' ;
                        }

                        enum disable {
                          value 0 ;
                          description 'Disable circuit status vector capability.' ;
                        }

                      }

                      default disable ;
                      ncd:revise-date 2022-06-09 ;
                    }

                    container encapulation {
                      description 'The encapsulation parameter of the Kompella.' ;
                      leaf encapulation-type {
                        description 'Specify encapsulation mode for Kompella PW.' ;
                        type enumeration {
                          enum raw {
                            value 5 ;
                            description 'The PW type is raw.' ;
                          }

                          enum tagged {
                            value 4 ;
                            description 'The PW type is tagged.' ;
                          }

                        }

                        default tagged ;
                      }

                      leaf vpls-access {
                        description 'VPWS as a remote access of VPLS instance or not.' ;
                        type enumeration {
                          enum disable {
                            value 0 ;
                            description 'VPWS not as a remote access of VPLS instance.' ;
                          }

                          enum enable {
                            value 1 ;
                            description 'VPWS as a remote access of VPLS instance.' ;
                          }

                        }

                        default disable ;
                      }

                    }

                    container flow-label {
                      description 'Configure flow-label capability.' ;
                      leaf push {
                        description 'Set flow-label send capability.' ;
                        type enumeration {
                          enum static {
                            value 1 ;
                            description 'Push a flow-label even if R flag is not received' ;
                          }

                          enum dynamic {
                            value 2 ;
                            description 'Push a flow-label only if R flag is received' ;
                          }

                        }

                      }

                      leaf pop {
                        description 'Set flow-label receive capability.' ;
                        type enumeration {
                          enum static {
                            value 1 ;
                            description 'Pop a flow-label even if T flag is not received.' ;
                          }

                          enum dynamic {
                            value 2 ;
                            description 'Pop a flow-label only if T flag is received.' ;
                          }

                        }

                      }

                      ncd:revise-date 2021-12-22 ;
                    }

                    container route-target-params {
                      description 'The route target parameters.' ;
                      list route-target {
                        description 'The route target.' ;
                        key 'rt-value effect-type' ;
                        leaf rt-value {
                          description 'RT attribute value.' ;
                          type union {
                            type ncd:asn-nn ;

                            type ncd:ipadd-nn ;

                          }

                        }

                        leaf effect-type {
                          description 'The route target effect type.' ;
                          type enumeration {
                            enum export {
                              value 2 ;
                              description 'The route target effect type is export.' ;
                            }

                            enum import {
                              value 3 ;
                              description 'The route target effect type is import.' ;
                            }

                          }

                        }

                      }

                    }

                    container site-params {
                      description 'The site parameters of VPWS community instance.' ;
                      list site {
                        description 'The site information of VPWS community instance.' ;
                        key site-id ;
                        leaf site-id {
                          description 'The site value of VPWS community instance.' ;
                          type uint16 {
                            range 0..65534 {
                              description 'The range of site value.' ;
                            }

                          }

                        }

                        container multi-chassis-pw-params {
                          description 'Multiple chassis PW redundancy parameters.' ;
                          presence multi-chassis-pw-params ;
                          leaf multi-chassis-pw {
                            description 'Multiple chassis PW redundancy grouped by site ID.' ;
                            type empty ;

                            mandatory true ;
                          }

                          container temporary-standby-params {
                            description 'Multiple chassis PW redundancy temporary standby parameters.' ;
                            presence temporary-standby-params ;
                            leaf temporary-standby-time {
                              description 'Wait for other PEs to receive preference update.' ;
                              type uint32 {
                                range 1..5000 {
                                  description 'The range of temporary standby time.' ;
                                }

                              }

                              units ms ;
                              mandatory true ;
                            }

                            leaf smoothly {
                              description 'Temporary standby drops packets smoothly or not.' ;
                              type empty ;

                            }

                          }

                          ncd:revise-date 2021-12-13 ;
                        }

                        container remote-ce-ranges {
                          description 'The remote CE ranges of VPWS community instance.' ;
                          list remote-ce-range {
                            description 'The remote CE ranges of VPWS community instance.' ;
                            key begin-ce-id ;
                            leaf begin-ce-id {
                              description 'The begin CE value of remote CE range.' ;
                              type uint16 {
                                range 0..65535 {
                                  description 'The range of begin CE.' ;
                                }

                              }

                            }

                            leaf end-ce-id {
                              description 'The end CE value of remote CE range.' ;
                              type uint16 {
                                range 0..65535 {
                                  description 'The range of end CE.' ;
                                }

                              }

                              mandatory true ;
                            }

                            container ac-instance-bind {
                              description 'AC bind instance info.' ;
                              list ac-bind {
                                description 'AC bind info.' ;
                                key ac-name ;
                                leaf ac-name {
                                  description 'The name of the AC in the bind.' ;
                                  type ncd:ifname {
                                    length 1..31 {
                                      description 'The length of AC name.' ;
                                    }

                                  }

                                }

                                leaf ce-id {
                                  description 'The CE ID of AC bind.' ;
                                  type uint16 {
                                    range 0..65535 {
                                      description 'The range of CE ID.' ;
                                    }

                                  }

                                }

                                choice ac-type {
                                  description 'The access type of VPWS community instance.' ;
                                  case ethernet {
                                    description 'The ethernet access type.' ;
                                    container ethernet-params {
                                      description 'Ethernet access type parameters.' ;
                                      presence ethernet-params ;
                                      leaf ethernet {
                                        description 'Ethernet access type.' ;
                                        type empty ;

                                        mandatory true ;
                                      }

                                      leaf ingress-adjust-tag-as-payload {
                                        description 'The ingress tag as payload flag of the ethernet parameter.' ;
                                        type enumeration {
                                          enum disable {
                                            value 0 ;
                                            description 'The ingress tag as payload flag is disable.' ;
                                          }

                                          enum all {
                                            value 1 ;
                                            description 'The ingress tag as payload flag is from outer most.' ;
                                          }

                                          enum from-sub-layer {
                                            value 2 ;
                                            description 'Payload from sub-layer tag.' ;
                                          }

                                        }

                                        default disable ;
                                      }

                                      leaf ingress-adjust-drop-tagged-frames {
                                        description 'The ingress adjust drop tagged frames flag of the ethernet.' ;
                                        type enumeration {
                                          enum disable {
                                            value 0 ;
                                            description 'The ingress adjust drop tagged frames flag is disable.' ;
                                          }

                                          enum enable {
                                            value 1 ;
                                            description 'The ingress adjust drop tagged frames flag is enable.' ;
                                          }

                                        }

                                        ncd:revise-date 2023-03-10 ;
                                      }

                                      container ingress-adjust-rewrite-params {
                                        description 'The ingress adjust rewrite parameters of the ethernet parameter.' ;
                                        leaf ingress-adjust-rewrite {
                                          description 'The ingress adjust rewrite flag of the ethernet parameter.' ;
                                          type enumeration {
                                            enum disable {
                                              value 0 ;
                                              description 'The ingress adjust rewrite flag of the ethernet parameter is disable.' ;
                                            }

                                            enum enable {
                                              value 1 ;
                                              description 'The ingress adjust rewrite flag of the ethernet parameter is enable.' ;
                                            }

                                          }

                                          default disable ;
                                        }

                                        leaf rewrite-vlan-id {
                                          description 'The ingress adjust rewrite VLAN ID of the ethernet parameter.' ;
                                          type uint16 {
                                            range 1..4094 {
                                              description 'The range of rewrite VLAN ID is 1-4094.' ;
                                            }

                                          }

                                        }

                                        ncd:revise-date 2021-10-12 ;
                                      }

                                    }

                                  }

                                }

                              }

                            }

                          }

                        }

                        container site-preference-params {
                          description 'Site preference parameters.' ;
                          presence site-preference-params ;
                          leaf site-preference {
                            description 'Configure site preference.' ;
                            type uint32 {
                              range 1..65535 {
                                description 'Set site preference' ;
                              }

                            }

                            mandatory true ;
                          }

                          leaf backup-preference {
                            description 'Configure backup site preference.' ;
                            type uint32 {
                              range 1..65535 {
                                description 'Set backup site preference' ;
                              }

                            }

                          }

                          ncd:revise-date 2021-12-22 ;
                        }

                      }

                    }

                  }

                }

                case vxlan-evpn {
                  description 'The VXLAN EVPN auto-discovery type.' ;
                  container vxlan-evpn-params {
                    description 'The parameters of VXLAN EVPN type.' ;
                    presence vxlan-evpn-params ;
                    leaf mode {
                      description 'The VXLAN EVPN mode of vpws-community-instance.' ;
                      type enumeration {
                        enum vxlan-evpn {
                          value 2 ;
                          description 'The mode is VXLAN EVPN.' ;
                        }

                      }

                      mandatory true ;
                    }

                    leaf control-word {
                      status obsolete {
                        ncd:revise-date 2019-10-23 ;
                      }

                      description 'The control-word capability.' ;
                      type enumeration {
                        enum not-preferred {
                          value 0 ;
                          description 'The control-word capability is not preferred.' ;
                        }

                        enum preferred {
                          value 1 ;
                          description 'The control-word capability is preferred.' ;
                        }

                      }

                      default not-preferred ;
                    }

                    leaf df-election {
                      description 'DF(Designated Forwarder) election mode.' ;
                      type enumeration {
                        enum lowest-preference {
                          value 1 ;
                          description 'The adjacent-node with lowest-preference is DF.' ;
                        }

                        enum highest-preference {
                          value 2 ;
                          description 'The adjacent-node with highest-preference is DF.' ;
                        }

                      }

                    }

                    leaf wtr-time {
                      type uint8 {
                        range 0..12 {
                          description 'The length of WTR time in minute.' ;
                        }

                      }

                      description 'Set minutes in WTR. Requires setting wtr-second-with-minute node simultaneously. The range is 0-12(minutes).' ;
                      default 3 ;
                      units min ;
                      ncd:revise-date 2022-09-19 ;
                    }

                    leaf wtr-second-with-minute {
                      type uint8 {
                        range 0..59 {
                          description 'The length of WTR second time in minute.' ;
                        }

                      }

                      description 'Set seconds in WTR. Requires setting wtr-time node simultaneously. The range is 0-59(seconds).' ;
                      units second ;
                      ncd:revise-date 2024-08-13 ;
                    }

                    leaf second {
                      type uint32 {
                        range 0..720 {
                          description 'The length of WTR time in second.' ;
                        }

                      }

                      description 'Set seconds in WTR. Cannot be configured simultaneously with wtr-time node or wtr-second-with-minute node. The range is 0-720(seconds). ' ;
                      units second ;
                      ncd:revise-date 2023-12-12 ;
                    }

                    container encapulation {
                      description 'The encapsulation parameter of the VXLAN EVPN.' ;
                      leaf encapulation-type {
                        description 'Specify encapsulation mode for VXLAN EVPN.' ;
                        type enumeration {
                          enum raw {
                            value 5 ;
                            description 'The encapsulation mode is raw.' ;
                          }

                          enum tagged {
                            value 4 ;
                            description 'The encapsulation mode is tagged.' ;
                          }

                        }

                        default raw ;
                      }

                    }

                    container route-target-params {
                      description 'The route target parameters.' ;
                      list route-target {
                        description 'The route target.' ;
                        key 'rt-value effect-type' ;
                        leaf rt-value {
                          description 'RT attribute value.' ;
                          type union {
                            type ncd:asn-nn ;

                            type ncd:ipadd-nn ;

                            type ncd:asnd-nn ;

                          }

                        }

                        leaf effect-type {
                          description 'The route target effect type.' ;
                          type enumeration {
                            enum export {
                              value 2 ;
                              description 'The route target effect type is export.' ;
                            }

                            enum import {
                              value 3 ;
                              description 'The route target effect type is import.' ;
                            }

                          }

                        }

                      }

                    }

                    container vxlan-evpn-ac-bind {
                      description "VXLAN EVPN's AC binding configuration info." ;
                      list ac-instance-bind {
                        description 'AC binding instance configuration info.' ;
                        key ac-name ;
                        leaf ac-name {
                          description 'The name of the AC in the bind.' ;
                          type ncd:ifname {
                            length 1..31 {
                              description 'The length of AC name.' ;
                            }

                          }

                        }

                        leaf local-vpws-id {
                          description 'Config local VPWS ID.' ;
                          type uint32 {
                            range 1..4294967294 {
                              description 'The range of local VPWS ID.' ;
                            }

                          }

                        }

                        leaf remote-vpws-id {
                          description 'Config remote VPWS ID.' ;
                          type uint32 {
                            range 1..4294967294 {
                              description 'The range of remote VPWS ID.' ;
                            }

                          }

                        }

                        leaf if-description {
                          description 'The description of the interface.' ;
                          type ncd:string-with-blank {
                            length 1..104 {
                              description 'The description range of interface.' ;
                            }

                          }

                          ncd:revise-date 2019-09-29 ;
                        }

                        container encapsulation {
                          leaf encapsulation-type {
                            type enumeration {
                              enum raw {
                                value 5 ;
                                description 'The encapsulation mode is raw.' ;
                              }

                              enum tagged {
                                value 4 ;
                                description 'The encapsulation mode is tagged.' ;
                              }

                            }

                            description 'Specify encapsulation mode for VXLAN EVPN AC.' ;
                            ncd:revise-date 2024-06-01 ;
                          }

                          description 'The encapsulation parameter of the VXLAN EVPN AC.' ;
                        }

                        choice ac-type {
                          description 'The access type of VPWS community instance.' ;
                          case ethernet {
                            description 'The ethernet access type.' ;
                            container ethernet-params {
                              description 'Ethernet access type parameters.' ;
                              presence ethernet-params ;
                              leaf ethernet {
                                description 'Ethernet access type.' ;
                                type empty ;

                                mandatory true ;
                              }

                              leaf ingress-adjust-tag-as-payload {
                                description 'The ingress tag as payload flag of the ethernet parameter.' ;
                                type enumeration {
                                  enum disable {
                                    value 0 ;
                                    description 'The ingress tag as payload flag is disable.' ;
                                  }

                                  enum all {
                                    value 1 ;
                                    description 'All of tags are payload.' ;
                                  }

                                  enum from-sub-layer {
                                    value 2 ;
                                    description 'Payload from sub-layer tag.' ;
                                  }

                                }

                                default disable ;
                              }

                              leaf ingress-adjust-drop-tagged-frames {
                                description 'The ingress adjust drop tagged frames flag of the ethernet.' ;
                                type enumeration {
                                  enum disable {
                                    value 0 ;
                                    description 'The ingress adjust drop tagged frames flag is disable.' ;
                                  }

                                  enum enable {
                                    value 1 ;
                                    description 'The ingress adjust drop tagged frames flag is enable.' ;
                                  }

                                }

                                ncd:revise-date 2023-03-10 ;
                              }

                              leaf traffic-enable {
                                description 'The traffic statistics enable flag of the ethernet parameter.' ;
                                type enumeration {
                                  enum disable {
                                    value 0 ;
                                    description 'The traffic statistics flag is disable.' ;
                                  }

                                  enum enable {
                                    value 1 ;
                                    description 'The traffic statistics flag is enable.' ;
                                  }

                                }

                                default disable ;
                                ncd:revise-date 2019-06-10 ;
                              }

                              container l2protocol-control-policy {
                                description 'L2protocol packet filtering function.' ;
                                leaf abm {
                                  description 'All bridge multicast frame protocol packet filtering.' ;
                                  type enumeration {
                                    enum tunnelled {
                                      value 0 ;
                                      description 'All bridge multicast frame protocol packet filtering is tunnelled.' ;
                                    }

                                    enum dropped {
                                      value 1 ;
                                      description 'All bridge multicast frame protocol packet filtering is dropped.' ;
                                    }

                                    enum terminated {
                                      value 2 ;
                                      description 'All bridge multicast frame protocol packet filtering is terminated.' ;
                                    }

                                  }

                                }

                                leaf dot1x {
                                  description '802.1x protocol frame packet filtering.' ;
                                  type enumeration {
                                    enum tunnelled {
                                      value 0 ;
                                      description '802.1x protocol frame packet filtering is tunnelled.' ;
                                    }

                                    enum dropped {
                                      value 1 ;
                                      description '802.1x protocol frame packet filtering is dropped.' ;
                                    }

                                    enum terminated {
                                      value 2 ;
                                      description '802.1x protocol frame packet filtering is terminated.' ;
                                    }

                                  }

                                }

                                leaf dot3x {
                                  description '802.3x protocol frame packet filtering.' ;
                                  type enumeration {
                                    enum tunnelled {
                                      value 0 ;
                                      description '802.3x protocol frame packet filtering is tunnelled.' ;
                                    }

                                    enum dropped {
                                      value 1 ;
                                      description '802.3x protocol frame packet filtering is dropped.' ;
                                    }

                                    enum terminated {
                                      value 2 ;
                                      description '802.3x protocol frame packet filtering is terminated.' ;
                                    }

                                  }

                                }

                                leaf garp {
                                  description 'GARP protocol packet filtering.' ;
                                  type enumeration {
                                    enum tunnelled {
                                      value 0 ;
                                      description 'GARP protocol packet filtering is tunnelled.' ;
                                    }

                                    enum dropped {
                                      value 1 ;
                                      description 'GARP protocol packet filtering is dropped.' ;
                                    }

                                    enum terminated {
                                      value 2 ;
                                      description 'GARP protocol packet filtering is terminated.' ;
                                    }

                                  }

                                }

                                leaf gmrp {
                                  description 'GMRP protocol packet filtering.' ;
                                  type enumeration {
                                    enum tunnelled {
                                      value 0 ;
                                      description 'GMRP protocol packet filtering is tunnelled.' ;
                                    }

                                    enum dropped {
                                      value 1 ;
                                      description 'GMRP protocol packet filtering is dropped.' ;
                                    }

                                    enum terminated {
                                      value 2 ;
                                      description 'GMRP protocol packet filtering is terminated.' ;
                                    }

                                  }

                                }

                                leaf gvrp {
                                  description 'GVRP protocol packet filtering.' ;
                                  type enumeration {
                                    enum tunnelled {
                                      value 0 ;
                                      description 'GVRP protocol packet filtering is tunnelled.' ;
                                    }

                                    enum dropped {
                                      value 1 ;
                                      description 'GVRP protocol packet filtering is dropped.' ;
                                    }

                                    enum terminated {
                                      value 2 ;
                                      description 'GVRP protocol packet filtering is terminated.' ;
                                    }

                                  }

                                }

                                leaf cisco {
                                  description 'CISCO protocol packet filtering.' ;
                                  type enumeration {
                                    enum tunnelled {
                                      value 0 ;
                                      description 'CISCO protocol packet filtering is tunnelled.' ;
                                    }

                                    enum dropped {
                                      value 1 ;
                                      description 'CISCO protocol packet filtering is dropped.' ;
                                    }

                                    enum terminated {
                                      value 2 ;
                                      description 'CISCO protocol packet filtering is terminated.' ;
                                    }

                                  }

                                }

                                leaf dldp {
                                  description 'DLDP protocol packet filtering.' ;
                                  type enumeration {
                                    enum tunnelled {
                                      value 0 ;
                                      description 'DLDP protocol packet filtering is tunnelled.' ;
                                    }

                                    enum dropped {
                                      value 1 ;
                                      description 'DLDP protocol packet filtering is dropped.' ;
                                    }

                                    enum terminated {
                                      value 2 ;
                                      description 'DLDP protocol packet filtering is terminated.' ;
                                    }

                                  }

                                }

                                leaf efm {
                                  description 'EFM protocol packet filtering.' ;
                                  type enumeration {
                                    enum tunnelled {
                                      value 0 ;
                                      description 'EFM protocol packet filtering is tunnelled.' ;
                                    }

                                    enum dropped {
                                      value 1 ;
                                      description 'EFM protocol packet filtering is dropped.' ;
                                    }

                                    enum terminated {
                                      value 2 ;
                                      description 'EFM protocol packet filtering is terminated.' ;
                                    }

                                  }

                                }

                                leaf cfm {
                                  description 'CFM protocol packet filtering.' ;
                                  type enumeration {
                                    enum tunnelled {
                                      value 0 ;
                                      description 'EFM protocol packet filtering is tunnelled.' ;
                                    }

                                    enum dropped {
                                      value 1 ;
                                      description 'EFM protocol packet filtering is dropped.' ;
                                    }

                                    enum terminated {
                                      value 2 ;
                                      description 'EFM protocol packet filtering is terminated.' ;
                                    }

                                  }

                                }

                                leaf pvst {
                                  description 'PVST protocol packet filtering.' ;
                                  type enumeration {
                                    enum tunnelled {
                                      value 0 ;
                                      description 'PVST protocol packet filtering is tunnelled.' ;
                                    }

                                    enum dropped {
                                      value 1 ;
                                      description 'PVST protocol packet filtering is dropped.' ;
                                    }

                                    enum terminated {
                                      value 2 ;
                                      description 'PVST protocol packet filtering is terminated.' ;
                                    }

                                  }

                                }

                                leaf zdp {
                                  description 'ZDP protocol packet filtering.' ;
                                  type enumeration {
                                    enum tunnelled {
                                      value 0 ;
                                      description 'ZDP protocol packet filtering is tunnelled.' ;
                                    }

                                    enum dropped {
                                      value 1 ;
                                      description 'ZDP protocol packet filtering is dropped.' ;
                                    }

                                    enum terminated {
                                      value 2 ;
                                      description 'ZDP protocol packet filtering is terminated.' ;
                                    }

                                  }

                                }

                                leaf lacp {
                                  description 'LACP protocol packet filtering.' ;
                                  type enumeration {
                                    enum tunnelled {
                                      value 0 ;
                                      description 'LACP protocol packet filtering is tunnelled.' ;
                                    }

                                    enum dropped {
                                      value 1 ;
                                      description 'LACP protocol packet filtering is dropped.' ;
                                    }

                                    enum terminated {
                                      value 2 ;
                                      description 'LACP protocol packet filtering is terminated.' ;
                                    }

                                  }

                                }

                                leaf lldp {
                                  description 'LLDP protocol packet filtering.' ;
                                  type enumeration {
                                    enum tunnelled {
                                      value 0 ;
                                      description 'LLDP protocol packet filtering is tunnelled.' ;
                                    }

                                    enum dropped {
                                      value 1 ;
                                      description 'LLDP protocol packet filtering is dropped.' ;
                                    }

                                    enum terminated {
                                      value 2 ;
                                      description 'LLDP protocol packet filtering is terminated.' ;
                                    }

                                  }

                                }

                                leaf stp {
                                  description 'STP protocol packet filtering.' ;
                                  type enumeration {
                                    enum tunnelled {
                                      value 0 ;
                                      description 'STP protocol packet filtering is tunnelled.' ;
                                    }

                                    enum dropped {
                                      value 1 ;
                                      description 'STP protocol packet filtering is dropped.' ;
                                    }

                                    enum terminated {
                                      value 2 ;
                                      description 'STP protocol packet filtering is terminated.' ;
                                    }

                                    enum tunnelled-monitored {
                                      value 3 ;
                                      description 'STP protocol packet filtering is tunnelled-monitored.' ;
                                    }

                                  }

                                }

                                leaf erps {
                                  description 'ERPS protocol packet filtering.' ;
                                  type enumeration {
                                    enum tunnelled {
                                      value 0 ;
                                      description 'ERPS protocol packet filtering is tunnelled.' ;
                                    }

                                    enum dropped {
                                      value 1 ;
                                      description 'ERPS protocol packet filtering is dropped.' ;
                                    }

                                    enum terminated {
                                      value 2 ;
                                      description 'ERPS protocol packet filtering is terminated.' ;
                                    }

                                  }

                                }

                                leaf udld {
                                  description 'UDLD protocol packet filtering.' ;
                                  type enumeration {
                                    enum tunnelled {
                                      value 0 ;
                                      description 'UDLD protocol packet filtering is tunnelled.' ;
                                    }

                                    enum dropped {
                                      value 1 ;
                                      description 'UDLD protocol packet filtering is dropped.' ;
                                    }

                                    enum terminated {
                                      value 2 ;
                                      description 'UDLD protocol packet filtering is terminated.' ;
                                    }

                                  }

                                }

                                leaf vtp {
                                  description 'VTP protocol packet filtering.' ;
                                  type enumeration {
                                    enum tunnelled {
                                      value 0 ;
                                      description 'VTP protocol packet filtering is tunnelled.' ;
                                    }

                                    enum dropped {
                                      value 1 ;
                                      description 'VTP protocol packet filtering is dropped.' ;
                                    }

                                    enum terminated {
                                      value 2 ;
                                      description 'VTP protocol packet filtering is terminated.' ;
                                    }

                                  }

                                }

                                leaf zesr {
                                  description 'ZESR protocol packet filtering.' ;
                                  type enumeration {
                                    enum tunnelled {
                                      value 0 ;
                                      description 'ZESR protocol packet filtering is tunnelled.' ;
                                    }

                                    enum dropped {
                                      value 1 ;
                                      description 'ZESR protocol packet filtering is dropped.' ;
                                    }

                                    enum terminated {
                                      value 2 ;
                                      description 'ZESR protocol packet filtering is terminated.' ;
                                    }

                                  }

                                }

                                leaf l2bfd {
                                  description 'L2BFD protocol packet filtering.' ;
                                  type enumeration {
                                    enum tunnelled {
                                      value 0 ;
                                      description 'L2BFD protocol packet filtering is tunnelled.' ;
                                    }

                                    enum terminated {
                                      value 2 ;
                                      description 'L2BFD protocol packet filtering is terminated.' ;
                                    }

                                  }

                                }

                                leaf mac-control {
                                  description 'MAC-control protocol packet filtering.' ;
                                  type enumeration {
                                    enum tunnelled {
                                      value 0 ;
                                      description 'MAC-control protocol packet filtering is tunnelled.' ;
                                    }

                                    enum dropped {
                                      value 1 ;
                                      description 'MAC-control protocol packet filtering is dropped.' ;
                                    }

                                    enum terminated {
                                      value 2 ;
                                      description 'MAC-control protocol packet filtering is terminated.' ;
                                    }

                                  }

                                  ncd:revise-date 2023-03-25 ;
                                }

                                container user-protocol-template {
                                  description 'The template of user protocol.' ;
                                  presence user-protocol-template ;
                                  leaf user-protocol-name {
                                    description 'The class name of user protocol.' ;
                                    type string {
                                      length 1..31 {
                                        description 'The length of user protocol class name.' ;
                                      }

                                    }

                                    mandatory true ;
                                  }

                                  leaf user-protocol-action {
                                    description 'User protocol template action.' ;
                                    type enumeration {
                                      enum tunnelled {
                                        value 0 ;
                                        description 'User protocol template action is tunnelled.' ;
                                      }

                                      enum dropped {
                                        value 1 ;
                                        description 'User protocol template action is dropped.' ;
                                      }

                                      enum terminated {
                                        value 2 ;
                                        description 'User protocol template action is terminated.' ;
                                      }

                                    }

                                    mandatory true ;
                                  }

                                }

                                leaf lamp {
                                  description 'LAMP protocol packet filtering.' ;
                                  type enumeration {
                                    enum tunnelled {
                                      value 0 ;
                                      description 'LAMP protocol packet filtering is tunnelled.' ;
                                    }

                                    enum dropped {
                                      description 'LAMP protocol packet filtering is dropped.' ;
                                      value 1 ;
                                    }

                                    enum terminated {
                                      value 2 ;
                                      description 'LAMP protocol packet filtering is terminated.' ;
                                    }

                                  }

                                  ncd:revise-date 2023-11-09 ;
                                }

                                leaf lacp-tagged {
                                  description 'LACP with VLAN tag protocol packet filtering.' ;
                                  type enumeration {
                                    enum tunnelled {
                                      value 0 ;
                                      description 'LACP with VLAN tag protocol packet filtering is tunnelled.' ;
                                    }

                                    enum dropped {
                                      description 'LACP with VLAN tag protocol packet filtering is dropped.' ;
                                      value 1 ;
                                    }

                                    enum terminated {
                                      description 'LACP with VLAN tag protocol packet filtering is terminated.' ;
                                      value 2 ;
                                    }

                                  }

                                  ncd:revise-date 2023-11-09 ;
                                }

                                ncd:revise-date 2021-06-07 ;
                              }

                              container vni-label-params {
                                description 'The VNI label parameters.' ;
                                presence vni-label-params ;
                                leaf vni-label {
                                  description 'VNI label.' ;
                                  type uint32 {
                                    range 1..16777215 {
                                      description 'The VNI label range.' ;
                                    }

                                  }

                                  mandatory true ;
                                }

                              }

                            }

                          }

                        }

                      }

                    }

                  }

                  ncd:revise-date 2018-07-08 ;
                }

                case srv6-evpn {
                  description 'The SRv6 EVPN auto-discovery type.' ;
                  container srv6-evpn-params {
                    description 'The parameters of SRv6 EVPN type.' ;
                    presence srv6-evpn-params ;
                    leaf mode {
                      description 'The SRv6 EVPN mode of vpws-community-instance.' ;
                      type enumeration {
                        enum srv6-evpn {
                          value 4 ;
                          description 'The mode is SRv6 EVPN.' ;
                        }

                      }

                      mandatory true ;
                    }

                    leaf control-word {
                      status obsolete {
                        ncd:revise-date 2019-10-23 ;
                      }

                      description 'The control-word capability.' ;
                      type enumeration {
                        enum not-preferred {
                          value 0 ;
                          description 'The control-word capability is not preferred.' ;
                        }

                        enum preferred {
                          value 1 ;
                          description 'The control-word capability is preferred.' ;
                        }

                      }

                      default not-preferred ;
                    }

                    leaf df-election {
                      description 'the choice mode of DF.' ;
                      type enumeration {
                        enum lowest-preference {
                          value 1 ;
                          description 'The adjacent-node with lowest-preference is DF' ;
                        }

                        enum highest-preference {
                          value 2 ;
                          description 'The adjacent-node with highest-preference is DF' ;
                        }

                      }

                      ncd:revise-date 2020-03-27 ;
                    }

                    leaf wtr-time {
                      type uint8 {
                        range 0..12 {
                          description 'The length of WTR time in minute.' ;
                        }

                      }

                      description 'Set minutes in WTR. Requires setting wtr-second-with-minute node simultaneously. The range is 0-12(minutes).' ;
                      units min ;
                      default 3 ;
                      ncd:revise-date 2020-06-08 ;
                    }

                    leaf wtr-second-with-minute {
                      type uint8 {
                        range 0..59 {
                          description 'The length of WTR second time in minute.' ;
                        }

                      }

                      description 'Set seconds in WTR. Requires setting wtr-time node simultaneously. The range is 0-59(seconds).' ;
                      units second ;
                      ncd:revise-date 2024-08-13 ;
                    }

                    leaf second {
                      type uint32 {
                        range 0..720 {
                          description 'The length of WTR time in second.' ;
                        }

                      }

                      description 'Set seconds in WTR. Cannot be configured simultaneously with wtr-time node or wtr-second-with-minute node. The range is 0-720(seconds). ' ;
                      units second ;
                      ncd:revise-date 2023-12-12 ;
                    }

                    leaf traffic-enable {
                      type enumeration {
                        enum disable {
                          value 0 ;
                          description 'The traffic statistics status of VPWS SRv6 EVPN is disable.' ;
                        }

                        enum enable {
                          value 1 ;
                          description 'The traffic statistics status of VPWS SRv6 EVPN is enable.' ;
                        }

                      }

                      description 'The traffic statistics status of VPWS SRv6 EVPN.' ;
                      default disable ;
                      ncd:revise-date 2023-12-11 ;
                    }

                    container srv6-tunnel-params {
                      description 'Configure SRv6 tunnel params.' ;
                      leaf srv6-best-effort {
                        description 'Select SRv6 BE.' ;
                        type empty ;

                      }

                      leaf srv6-traffic-engineer {
                        description 'Select SRv6 TE.' ;
                        type empty ;

                      }

                      ncd:revise-date 2022-03-15 ;
                    }

                    container encapulation {
                      description 'The encapsulation parameter of the SRv6 EVPN.' ;
                      leaf encapulation-type {
                        description 'Specify encapsulation mode for SRv6 EVPN.' ;
                        type enumeration {
                          enum raw {
                            value 5 ;
                            description 'The encapsulation mode is raw.' ;
                          }

                          enum tagged {
                            value 4 ;
                            description 'The encapsulation mode is tagged.' ;
                          }

                        }

                        default raw ;
                      }

                    }

                    container srv6-evpn-ds-mode {
                      description 'The DS mode of the SRV6 EVPN.' ;
                      leaf ds-mode {
                        description 'The DS service mode.' ;
                        type enumeration {
                          enum uniform {
                            value 1 ;
                            description 'DS mode is uniform.' ;
                          }

                          enum pipe {
                            value 2 ;
                            description 'DS mode is pipe.' ;
                          }

                          enum shortPipe {
                            value 3 ;
                            description 'DS mode is shortPipe.' ;
                          }

                        }

                      }

                      leaf service-class {
                        description 'The DS service class.' ;
                        type enumeration {
                          enum be {
                            value 1 ;
                            description 'The DS service class is be.' ;
                          }

                          enum af1 {
                            value 2 ;
                            description 'The DS service class is af1.' ;
                          }

                          enum af2 {
                            value 3 ;
                            description 'The DS service class is af2.' ;
                          }

                          enum af3 {
                            value 4 ;
                            description 'The DS service class is af3.' ;
                          }

                          enum af4 {
                            value 5 ;
                            description 'The DS service class is af4.' ;
                          }

                          enum ef {
                            value 6 ;
                            description 'The DS service class is ef.' ;
                          }

                          enum cs6 {
                            value 7 ;
                            description 'The DS service class is cs6.' ;
                          }

                          enum cs7 {
                            value 8 ;
                            description 'The DS service class is cs7.' ;
                          }

                        }

                      }

                      leaf colour {
                        description 'The DS packet colour.' ;
                        type enumeration {
                          enum green {
                            value 1 ;
                            description 'The DS packet colour is green.' ;
                          }

                          enum yellow {
                            value 2 ;
                            description 'The DS packet colour is yellow.' ;
                          }

                          enum red {
                            value 3 ;
                            description 'The DS packet colour is red.' ;
                          }

                        }

                      }

                      ncd:revise-date 2020-08-11 ;
                    }

                    container route-target-params {
                      description 'The route target parameters.' ;
                      list route-target {
                        description 'The route target.' ;
                        key 'rt-value effect-type' ;
                        leaf rt-value {
                          description 'RT attribute value.' ;
                          type union {
                            type ncd:asn-nn ;

                            type ncd:ipadd-nn ;

                            type ncd:asnd-nn ;

                          }

                        }

                        leaf effect-type {
                          description 'The route target effect type.' ;
                          type enumeration {
                            enum export {
                              value 2 ;
                              description 'The route target effect type is export.' ;
                            }

                            enum import {
                              value 3 ;
                              description 'The route target effect type is import.' ;
                            }

                          }

                        }

                      }

                    }

                    container srv6-evpn-ac-bind {
                      description "SRv6 EVPN's AC binding configuration info." ;
                      list ac-instance-bind {
                        description 'AC binding instance configuration info.' ;
                        key ac-name ;
                        leaf ac-name {
                          description 'The name of the AC in the bind.' ;
                          type ncd:ifname {
                            length 1..31 {
                              description 'The length of AC name.' ;
                            }

                          }

                        }

                        leaf local-vpws-id {
                          description 'Config local VPWS ID.' ;
                          type uint32 {
                            range 1..4294967294 {
                              description 'The range of local VPWS ID.' ;
                            }

                          }

                        }

                        leaf remote-vpws-id {
                          description 'Config remote VPWS ID.' ;
                          type uint32 {
                            range 1..4294967294 {
                              description 'The range of remote VPWS ID.' ;
                            }

                          }

                        }

                        leaf if-description {
                          description 'The description of the interface.' ;
                          type ncd:string-with-blank {
                            length 1..104 {
                              description 'The description range of interface.' ;
                            }

                          }

                          ncd:revise-date 2019-09-29 ;
                        }

                        container encapsulation {
                          leaf encapsulation-type {
                            type enumeration {
                              enum raw {
                                value 5 ;
                                description 'The encapsulation mode is raw.' ;
                              }

                              enum tagged {
                                value 4 ;
                                description 'The encapsulation mode is tagged.' ;
                              }

                            }

                            description 'Specify encapsulation mode for SRv6 EVPN AC.' ;
                            ncd:revise-date 2024-06-01 ;
                          }

                          description 'The encapsulation parameter of the SRv6 EVPN AC.' ;
                        }

                        choice ac-type {
                          description 'The access type of VPWS community instance.' ;
                          case ethernet {
                            description 'The ethernet access type.' ;
                            container ethernet-params {
                              description 'Ethernet access type parameters.' ;
                              presence ethernet-params ;
                              leaf ethernet {
                                description 'Ethernet access type.' ;
                                type empty ;

                                mandatory true ;
                              }

                              leaf ingress-adjust-tag-as-payload {
                                description 'The ingress tag as payload flag of the ethernet parameter.' ;
                                type enumeration {
                                  enum disable {
                                    value 0 ;
                                    description 'The ingress tag as payload flag is disable.' ;
                                  }

                                  enum all {
                                    value 1 ;
                                    description 'All of tags are payload.' ;
                                  }

                                  enum from-sub-layer {
                                    value 2 ;
                                    description 'Payload from sub-layer tag.' ;
                                  }

                                }

                                default disable ;
                              }

                              leaf ingress-adjust-drop-tagged-frames {
                                description 'The ingress adjust drop tagged frames flag of the ethernet.' ;
                                type enumeration {
                                  enum disable {
                                    value 0 ;
                                    description 'The ingress adjust drop tagged frames flag is disable.' ;
                                  }

                                  enum enable {
                                    value 1 ;
                                    description 'The ingress adjust drop tagged frames flag is enable.' ;
                                  }

                                }

                                ncd:revise-date 2023-03-10 ;
                              }

                              leaf traffic-enable {
                                description 'The traffic statistics enable flag of the ethernet parameter.' ;
                                type enumeration {
                                  enum disable {
                                    value 0 ;
                                    description 'The traffic statistics flag is disable.' ;
                                  }

                                  enum enable {
                                    value 1 ;
                                    description 'The traffic statistics flag is enable.' ;
                                  }

                                }

                                default disable ;
                                ncd:revise-date 2019-06-10 ;
                              }

                              leaf egress-keep-normalized-tag {
                                description 'To keep the normalized tag unchanged onto the egress AC.' ;
                                type enumeration {
                                  enum disable {
                                    value 0 ;
                                    description 'To keep the normalized tag unchanged onto the egress AC is disable.' ;
                                  }

                                  enum enable {
                                    value 1 ;
                                    description 'To keep the normalized tag unchanged onto the egress AC is enable.' ;
                                  }

                                }

                                default disable ;
                                ncd:revise-date 2021-01-05 ;
                              }

                              container l2protocol-control-policy {
                                description 'L2protocol packet filtering function.' ;
                                leaf abm {
                                  description 'All bridge multicast frame protocol packet filtering.' ;
                                  type enumeration {
                                    enum tunnelled {
                                      value 0 ;
                                      description 'All bridge multicast frame protocol packet filtering is tunnelled.' ;
                                    }

                                    enum dropped {
                                      value 1 ;
                                      description 'All bridge multicast frame protocol packet filtering is dropped.' ;
                                    }

                                    enum terminated {
                                      value 2 ;
                                      description 'All bridge multicast frame protocol packet filtering is terminated.' ;
                                    }

                                  }

                                }

                                leaf dot1x {
                                  description '802.1x protocol frame packet filtering.' ;
                                  type enumeration {
                                    enum tunnelled {
                                      value 0 ;
                                      description '802.1x protocol frame packet filtering is tunnelled.' ;
                                    }

                                    enum dropped {
                                      value 1 ;
                                      description '802.1x protocol frame packet filtering is dropped.' ;
                                    }

                                    enum terminated {
                                      value 2 ;
                                      description '802.1x protocol frame packet filtering is terminated.' ;
                                    }

                                  }

                                }

                                leaf dot3x {
                                  description '802.3x protocol frame packet filtering.' ;
                                  type enumeration {
                                    enum tunnelled {
                                      value 0 ;
                                      description '802.3x protocol frame packet filtering is tunnelled.' ;
                                    }

                                    enum dropped {
                                      value 1 ;
                                      description '802.3x protocol frame packet filtering is dropped.' ;
                                    }

                                    enum terminated {
                                      value 2 ;
                                      description '802.3x protocol frame packet filtering is terminated.' ;
                                    }

                                  }

                                }

                                leaf garp {
                                  description 'GARP protocol packet filtering.' ;
                                  type enumeration {
                                    enum tunnelled {
                                      value 0 ;
                                      description 'GARP protocol packet filtering is tunnelled.' ;
                                    }

                                    enum dropped {
                                      value 1 ;
                                      description 'GARP protocol packet filtering is dropped.' ;
                                    }

                                    enum terminated {
                                      value 2 ;
                                      description 'GARP protocol packet filtering is terminated.' ;
                                    }

                                  }

                                }

                                leaf gmrp {
                                  description 'GMRP protocol packet filtering.' ;
                                  type enumeration {
                                    enum tunnelled {
                                      value 0 ;
                                      description 'GMRP protocol packet filtering is tunnelled.' ;
                                    }

                                    enum dropped {
                                      value 1 ;
                                      description 'GMRP protocol packet filtering is dropped.' ;
                                    }

                                    enum terminated {
                                      value 2 ;
                                      description 'GMRP protocol packet filtering is terminated.' ;
                                    }

                                  }

                                }

                                leaf gvrp {
                                  description 'GVRP protocol packet filtering.' ;
                                  type enumeration {
                                    enum tunnelled {
                                      value 0 ;
                                      description 'GVRP protocol packet filtering is tunnelled.' ;
                                    }

                                    enum dropped {
                                      value 1 ;
                                      description 'GVRP protocol packet filtering is dropped.' ;
                                    }

                                    enum terminated {
                                      value 2 ;
                                      description 'GVRP protocol packet filtering is terminated.' ;
                                    }

                                  }

                                }

                                leaf cisco {
                                  description 'CISCO protocol packet filtering.' ;
                                  type enumeration {
                                    enum tunnelled {
                                      value 0 ;
                                      description 'CISCO protocol packet filtering is tunnelled.' ;
                                    }

                                    enum dropped {
                                      value 1 ;
                                      description 'CISCO protocol packet filtering is dropped.' ;
                                    }

                                    enum terminated {
                                      value 2 ;
                                      description 'CISCO protocol packet filtering is terminated.' ;
                                    }

                                  }

                                }

                                leaf dldp {
                                  description 'DLDP protocol packet filtering.' ;
                                  type enumeration {
                                    enum tunnelled {
                                      value 0 ;
                                      description 'DLDP protocol packet filtering is tunnelled.' ;
                                    }

                                    enum dropped {
                                      value 1 ;
                                      description 'DLDP protocol packet filtering is dropped.' ;
                                    }

                                    enum terminated {
                                      value 2 ;
                                      description 'DLDP protocol packet filtering is terminated.' ;
                                    }

                                  }

                                }

                                leaf efm {
                                  description 'EFM protocol packet filtering.' ;
                                  type enumeration {
                                    enum tunnelled {
                                      value 0 ;
                                      description 'EFM protocol packet filtering is tunnelled.' ;
                                    }

                                    enum dropped {
                                      value 1 ;
                                      description 'EFM protocol packet filtering is dropped.' ;
                                    }

                                    enum terminated {
                                      value 2 ;
                                      description 'EFM protocol packet filtering is terminated.' ;
                                    }

                                  }

                                }

                                leaf cfm {
                                  description 'CFM protocol packet filtering.' ;
                                  type enumeration {
                                    enum tunnelled {
                                      value 0 ;
                                      description 'EFM protocol packet filtering is tunnelled.' ;
                                    }

                                    enum dropped {
                                      value 1 ;
                                      description 'EFM protocol packet filtering is dropped.' ;
                                    }

                                    enum terminated {
                                      value 2 ;
                                      description 'EFM protocol packet filtering is terminated.' ;
                                    }

                                  }

                                }

                                leaf pvst {
                                  description 'PVST protocol packet filtering.' ;
                                  type enumeration {
                                    enum tunnelled {
                                      value 0 ;
                                      description 'PVST protocol packet filtering is tunnelled.' ;
                                    }

                                    enum dropped {
                                      value 1 ;
                                      description 'PVST protocol packet filtering is dropped.' ;
                                    }

                                    enum terminated {
                                      value 2 ;
                                      description 'PVST protocol packet filtering is terminated.' ;
                                    }

                                  }

                                }

                                leaf zdp {
                                  description 'ZDP protocol packet filtering.' ;
                                  type enumeration {
                                    enum tunnelled {
                                      value 0 ;
                                      description 'ZDP protocol packet filtering is tunnelled.' ;
                                    }

                                    enum dropped {
                                      value 1 ;
                                      description 'ZDP protocol packet filtering is dropped.' ;
                                    }

                                    enum terminated {
                                      value 2 ;
                                      description 'ZDP protocol packet filtering is terminated.' ;
                                    }

                                  }

                                }

                                leaf lacp {
                                  description 'LACP protocol packet filtering.' ;
                                  type enumeration {
                                    enum tunnelled {
                                      value 0 ;
                                      description 'LACP protocol packet filtering is tunnelled.' ;
                                    }

                                    enum dropped {
                                      value 1 ;
                                      description 'LACP protocol packet filtering is dropped.' ;
                                    }

                                    enum terminated {
                                      value 2 ;
                                      description 'LACP protocol packet filtering is terminated.' ;
                                    }

                                  }

                                }

                                leaf lldp {
                                  description 'LLDP protocol packet filtering.' ;
                                  type enumeration {
                                    enum tunnelled {
                                      value 0 ;
                                      description 'LLDP protocol packet filtering is tunnelled.' ;
                                    }

                                    enum dropped {
                                      value 1 ;
                                      description 'LLDP protocol packet filtering is dropped.' ;
                                    }

                                    enum terminated {
                                      value 2 ;
                                      description 'LLDP protocol packet filtering is terminated.' ;
                                    }

                                  }

                                }

                                leaf stp {
                                  description 'STP protocol packet filtering.' ;
                                  type enumeration {
                                    enum tunnelled {
                                      value 0 ;
                                      description 'STP protocol packet filtering is tunnelled.' ;
                                    }

                                    enum dropped {
                                      value 1 ;
                                      description 'STP protocol packet filtering is dropped.' ;
                                    }

                                    enum terminated {
                                      value 2 ;
                                      description 'STP protocol packet filtering is terminated.' ;
                                    }

                                    enum tunnelled-monitored {
                                      value 3 ;
                                      description 'STP protocol packet filtering is tunnelled-monitored.' ;
                                    }

                                  }

                                }

                                leaf erps {
                                  description 'ERPS protocol packet filtering.' ;
                                  type enumeration {
                                    enum tunnelled {
                                      value 0 ;
                                      description 'ERPS protocol packet filtering is tunnelled.' ;
                                    }

                                    enum dropped {
                                      value 1 ;
                                      description 'ERPS protocol packet filtering is dropped.' ;
                                    }

                                    enum terminated {
                                      value 2 ;
                                      description 'ERPS protocol packet filtering is terminated.' ;
                                    }

                                  }

                                }

                                leaf udld {
                                  description 'UDLD protocol packet filtering.' ;
                                  type enumeration {
                                    enum tunnelled {
                                      value 0 ;
                                      description 'UDLD protocol packet filtering is tunnelled.' ;
                                    }

                                    enum dropped {
                                      value 1 ;
                                      description 'UDLD protocol packet filtering is dropped.' ;
                                    }

                                    enum terminated {
                                      value 2 ;
                                      description 'UDLD protocol packet filtering is terminated.' ;
                                    }

                                  }

                                }

                                leaf vtp {
                                  description 'VTP protocol packet filtering.' ;
                                  type enumeration {
                                    enum tunnelled {
                                      value 0 ;
                                      description 'VTP protocol packet filtering is tunnelled.' ;
                                    }

                                    enum dropped {
                                      value 1 ;
                                      description 'VTP protocol packet filtering is dropped.' ;
                                    }

                                    enum terminated {
                                      value 2 ;
                                      description 'VTP protocol packet filtering is terminated.' ;
                                    }

                                  }

                                }

                                leaf zesr {
                                  description 'ZESR protocol packet filtering.' ;
                                  type enumeration {
                                    enum tunnelled {
                                      value 0 ;
                                      description 'ZESR protocol packet filtering is tunnelled.' ;
                                    }

                                    enum dropped {
                                      value 1 ;
                                      description 'ZESR protocol packet filtering is dropped.' ;
                                    }

                                    enum terminated {
                                      value 2 ;
                                      description 'ZESR protocol packet filtering is terminated.' ;
                                    }

                                  }

                                }

                                leaf l2bfd {
                                  description 'L2BFD protocol packet filtering.' ;
                                  type enumeration {
                                    enum tunnelled {
                                      value 0 ;
                                      description 'L2BFD protocol packet filtering is tunnelled.' ;
                                    }

                                    enum terminated {
                                      value 2 ;
                                      description 'L2BFD protocol packet filtering is terminated.' ;
                                    }

                                  }

                                }

                                leaf mac-control {
                                  description 'MAC-control protocol packet filtering.' ;
                                  type enumeration {
                                    enum tunnelled {
                                      value 0 ;
                                      description 'MAC-control protocol packet filtering is tunnelled.' ;
                                    }

                                    enum dropped {
                                      value 1 ;
                                      description 'MAC-control protocol packet filtering is dropped.' ;
                                    }

                                    enum terminated {
                                      value 2 ;
                                      description 'MAC-control protocol packet filtering is terminated.' ;
                                    }

                                  }

                                  ncd:revise-date 2023-03-25 ;
                                }

                                container user-protocol-template {
                                  description 'The template of user protocol.' ;
                                  presence user-protocol-template ;
                                  leaf user-protocol-name {
                                    description 'The class name of user protocol.' ;
                                    type string {
                                      length 1..31 {
                                        description 'The length of user protocol class name.' ;
                                      }

                                    }

                                    mandatory true ;
                                  }

                                  leaf user-protocol-action {
                                    description 'User protocol template action.' ;
                                    type enumeration {
                                      enum tunnelled {
                                        value 0 ;
                                        description 'User protocol template action is tunnelled.' ;
                                      }

                                      enum dropped {
                                        value 1 ;
                                        description 'User protocol template action is dropped.' ;
                                      }

                                      enum terminated {
                                        value 2 ;
                                        description 'User protocol template action is terminated.' ;
                                      }

                                    }

                                    mandatory true ;
                                  }

                                }

                                leaf lamp {
                                  type enumeration {
                                    enum tunnelled {
                                      value 0 ;
                                      description 'LAMP protocol packet filtering is tunnelled.' ;
                                    }

                                    enum dropped {
                                      value 1 ;
                                      description 'LAMP protocol packet filtering is dropped.' ;
                                    }

                                    enum terminated {
                                      description 'LAMP protocol packet filtering is terminated.' ;
                                      value 2 ;
                                    }

                                  }

                                  description 'LAMP protocol packet filtering.' ;
                                  ncd:revise-date 2023-11-09 ;
                                }

                                leaf lacp-tagged {
                                  type enumeration {
                                    enum tunnelled {
                                      value 0 ;
                                      description 'LACP with VLAN tag protocol packet filtering is tunnelled.' ;
                                    }

                                    enum dropped {
                                      value 1 ;
                                      description 'LACP with VLAN tag protocol packet filtering is dropped.' ;
                                    }

                                    enum terminated {
                                      value 2 ;
                                      description 'LACP with VLAN tag protocol packet filtering is terminated.' ;
                                    }

                                  }

                                  description 'LACP with VLAN tag protocol packet filtering.' ;
                                  ncd:revise-date 2023-11-09 ;
                                }

                                ncd:revise-date 2021-06-07 ;
                              }

                              container bfd-params {
                                description 'Configure BFD parameter.' ;
                                presence bfd-params ;
                                leaf bfd {
                                  description 'Configure BFD.' ;
                                  type empty ;

                                  mandatory true ;
                                }

                                leaf template {
                                  description 'Configure template name.' ;
                                  type string {
                                    length 1..31 {
                                      description 'The length of BFD template name.' ;
                                    }

                                  }

                                }

                                leaf encap-type {
                                  type enumeration {
                                    enum insert {
                                      description 'Insert encapsulation type.' ;
                                      value 0 ;
                                    }

                                    enum encaps {
                                      value 1 ;
                                      description 'Encaps encapsulation type.' ;
                                    }

                                  }

                                  description 'Encapsulation type of BFD.' ;
                                  default insert ;
                                  ncd:revise-date 2024-01-18 ;
                                }

                                ncd:revise-date 2022-04-27 ;
                              }

                              container ingress-adjust-push-params {
                                description 'The ingress adjust push parameters of the ethernet parameter.' ;
                                leaf ingress-adjust-push {
                                  description 'The ingress adjust push flag of the ethernet parameter.' ;
                                  type enumeration {
                                    enum disable {
                                      value 0 ;
                                      description 'The ingress adjust push flag of the ethernet parameter is disable.' ;
                                    }

                                    enum enable {
                                      value 1 ;
                                      description 'The ingress adjust push flag of the ethernet parameter is enable.' ;
                                    }

                                  }

                                  default disable ;
                                }

                                leaf push-vlan-id {
                                  description 'The ingress adjust push VLAN ID of the ethernet parameter.' ;
                                  type uint16 {
                                    range 1..4094 {
                                      description 'The range of push VLAN ID is 1-4094.' ;
                                    }

                                  }

                                }

                                ncd:revise-date 2020-07-03 ;
                              }

                              container ingress-adjust-rewrite-params {
                                description 'The ingress adjust rewrite parameters of the ethernet parameter.' ;
                                leaf ingress-adjust-rewrite {
                                  description 'The ingress adjust rewrite flag of the ethernet parameter.' ;
                                  type enumeration {
                                    enum disable {
                                      value 0 ;
                                      description 'The ingress adjust rewrite flag of the ethernet parameter is disable.' ;
                                    }

                                    enum enable {
                                      value 1 ;
                                      description 'The ingress adjust rewrite flag of the ethernet parameter is enable.' ;
                                    }

                                  }

                                  default disable ;
                                }

                                leaf rewrite-vlan-id {
                                  description 'The ingress adjust rewrite VLAN ID of the ethernet parameter.' ;
                                  type uint16 {
                                    range 1..4094 {
                                      description 'The range of rewrite VLAN ID is 1-4094.' ;
                                    }

                                  }

                                }

                                leaf rewrite-outer-vlanid-flag {
                                  description 'Rewrite outer VLAN ID flag.' ;
                                  type enumeration {
                                    enum disable {
                                      value 0 ;
                                      description 'Rewrite outer VLAN ID flag is disable.' ;
                                    }

                                    enum enable {
                                      value 1 ;
                                      description 'Rewrite outer VLAN ID flag is enable.' ;
                                    }

                                  }

                                  default disable ;
                                  ncd:revise-date 2021-01-05 ;
                                }

                                ncd:revise-date 2020-07-03 ;
                              }

                              container duplicate {
                                if-feature vpws-community-srv6-duplicate ;

                                description 'Duplicate configuration node.' ;
                                leaf nd-enable {
                                  description 'ND duplicate switch flag,the default is off.' ;
                                  type boolean ;

                                  default false ;
                                }

                                leaf arp-enable {
                                  description 'ARP duplicate switch flag, the default is off.' ;
                                  type boolean ;

                                  default false ;
                                }

                                leaf send-arp-enable {
                                  description 'ARP duplicate free ARP sending switch flag, the default is off.' ;
                                  type boolean ;

                                  default false ;
                                }

                                leaf send-nd-enable {
                                  description 'ND duplicate free ND switch flag, the default is off.' ;
                                  type boolean ;

                                  default false ;
                                }

                                leaf send-periodic-arp {
                                  description 'ARP duplicate free ARP delivery interval in seconds.' ;
                                  type uint32 {
                                    range 1..2147483 ;

                                  }

                                  default 600 ;
                                }

                                leaf send-periodic-nd {
                                  description 'ND duplicate free ND time interval in seconds.' ;
                                  type uint32 {
                                    range 1..2147483 ;

                                  }

                                  default 600 ;
                                }

                                ncd:revise-date 2020-09-21 ;
                              }

                            }

                          }

                        }

                        container srv6-sid-params {
                          status obsolete {
                            ncd:revise-date 2020-07-18 ;
                          }

                          description 'the SID parameter of VPWS community instance.' ;
                          choice srv6-sid-type {
                            description 'the SRv6 SID type of VPWS community instance.' ;
                            case sid-auto {
                              status obsolete {
                                ncd:revise-date 2020-03-09 ;
                              }

                              description 'The auto SID type.' ;
                              leaf sid-auto {
                                status obsolete {
                                  ncd:revise-date 2020-03-09 ;
                                }

                                description 'The auto SID type.' ;
                                type enumeration {
                                  enum not-auto {
                                    value 0 ;
                                    description 'The SID of auto type value is not-auto.' ;
                                  }

                                  enum auto {
                                    value 1 ;
                                    description 'The SID of auto type value is auto.' ;
                                  }

                                }

                                default not-auto ;
                              }

                            }

                            case sid-label {
                              description 'The label SID type.' ;
                              leaf sid-label {
                                description 'The label SID type.' ;
                                type uint32 {
                                  range 1..16777215 {
                                    description 'The range of SID label.' ;
                                  }

                                }

                              }

                            }

                            case sid-ipv6 {
                              description 'The IPv6 SID type.' ;
                              leaf sid-ipv6 {
                                description 'The IPv6 SID type.' ;
                                type ncd:ipv6-address {
                                  pattern "([0-9a-fA-F]{1,4}:){7}([0-9a-fA-F]{0,4})$|^([0-9a-fA-F]{1,4}:){1,6}(:[0-9a-fA-F]{0,4}){1,6}$|^([:]{2})(([0-9a-fA-F]{1,4}:){0,6})([0-9a-fA-F]{1,4})$|^([0-9a-fA-F]{1,4}:){6}([0-9]{1,3}.){3}([0-9]{1,3})$|^([0-9a-fA-F]{1,4}:){1,5}(:[0-9a-fA-F]{0,4}){1,5}([0-9]{1,3}.){3}([0-9]{1,3})$|^([:]{2})(([0-9a-fA-F]{1,4}:){0,5})([0-9]{1,3}.){3}([0-9]{1,3})" ;

                                }

                              }

                            }

                          }

                        }

                        container srv6-locator-params {
                          description 'SRv6 locator parameters.' ;
                          leaf srv6-locator-name {
                            description 'The SRv6 locator name.' ;
                            type string {
                              length 1..31 {
                                description 'The length of SRv6 locator name.' ;
                              }

                            }

                          }

                          ncd:revise-date 2020-06-08 ;
                        }

                      }

                    }

                    container srv6-evpn-access-pw-bind {
                      description "SRv6 EVPN's access PW binding configuration info." ;
                      list pw-instance-bind {
                        description 'PW binding instance configuration info.' ;
                        key pw-name ;
                        leaf pw-name {
                          description 'The name of the PW.' ;
                          type ncd:ifname ;

                        }

                        leaf locat-vpws-id {
                          description 'Config local VPWS ID.' ;
                          type uint32 {
                            range 1..4294967294 {
                              description 'The range of local VPWS ID.' ;
                            }

                          }

                        }

                        leaf remote-vpws-id {
                          description 'Config remote VPWS ID.' ;
                          type uint32 {
                            range 1..4294967294 {
                              description 'The range of remote VPWS ID.' ;
                            }

                          }

                        }

                        container srv6-sid-params {
                          status obsolete {
                            ncd:revise-date 2020-07-18 ;
                          }

                          description 'The SID parameter of VPWS community instance.' ;
                          choice srv6-sid-type {
                            description 'The SRv6 SID type of VPWS community instance.' ;
                            case sid-label {
                              description 'The label type of SID.' ;
                              leaf sid-label {
                                description 'The label value of SID.' ;
                                type uint32 {
                                  range 1..16777215 {
                                    description 'The range of SID label.' ;
                                  }

                                }

                              }

                            }

                            case sid-ipv6 {
                              description 'The IPv6 type of SID.' ;
                              leaf sid-ipv6 {
                                description 'The IPv6 value of SID.' ;
                                type ncd:ipv6-address-none-zero ;

                              }

                            }

                          }

                        }

                        container srv6-locator-params {
                          description 'SRv6 locator parameters.' ;
                          leaf srv6-locator-name {
                            description 'The SRv6 locator name.' ;
                            type string {
                              length 1..31 {
                                description 'The length of SRv6 locator name.' ;
                              }

                            }

                          }

                        }

                      }

                      ncd:revise-date 2020-06-19 ;
                    }

                    container srv6-evpn-bridge-if-bind {
                      description 'The bridge if binding configuration info of SRv6 EVPN.' ;
                      list bridge-if-instance-bind {
                        description 'Bridge if binding instance configuration info.' ;
                        key ac-name ;
                        leaf ac-name {
                          description 'The name of the bridge AC in the bind.' ;
                          type ncd:ifname ;

                        }

                        leaf local-vpws-id {
                          description 'Config local VPWS ID.' ;
                          type uint32 {
                            range 1..4294967295 {
                              description 'The range of local VPWS ID.' ;
                            }

                          }

                        }

                        leaf remote-vpws-id {
                          description 'Config remote VPWS ID.' ;
                          type uint32 {
                            range 1..4294967295 {
                              description 'The range of remote VPWS ID.' ;
                            }

                          }

                        }

                        choice ac-type {
                          description 'The access type of VPWS community instance.' ;
                          case ethernet {
                            description 'The ethernet access type.' ;
                            container ethernet-params {
                              description 'Ethernet access type parameters.' ;
                              presence ethernet-params ;
                              leaf ethernet {
                                description 'Create ethernet object.' ;
                                type empty ;

                                mandatory true ;
                              }

                            }

                          }

                        }

                        container srv6-sid-params {
                          status obsolete {
                            ncd:revise-date 2020-07-18 ;
                          }

                          description 'The SID parameter of VPWS community instance.' ;
                          choice srv6-sid-type {
                            description 'The SRv6 SID type of VPWS community instance.' ;
                            case sid-label {
                              description 'The label type of SID.' ;
                              leaf sid-label {
                                description 'The label value of SID.' ;
                                type uint32 {
                                  range 1..16777215 {
                                    description 'The range of SID label.' ;
                                  }

                                }

                              }

                            }

                            case sid-ipv6 {
                              description 'The IPv6 type of SID.' ;
                              leaf sid-ipv6 {
                                description 'The IPv6 value of SID.' ;
                                type ncd:ipv6-address-none-zero ;

                              }

                            }

                          }

                        }

                        container srv6-locator-params {
                          description 'SRv6 locator parameters.' ;
                          leaf srv6-locator-name {
                            description 'The SRv6 locator name.' ;
                            type string {
                              length 1..31 {
                                description 'The length of SRv6 locator name.' ;
                              }

                            }

                          }

                        }

                      }

                      ncd:revise-date 2020-07-08 ;
                    }

                    container srv6-evpn-evpl-bind {
                      description "SRv6 EVPN's EVPL binding configuration info." ;
                      list evpl-instance-bind {
                        description 'Bind an Ethernet Virtual Private Line (EVPL) which is an E-line service.' ;
                        key eline-service-name ;
                        leaf eline-service-name {
                          description 'L2VPN E-line service name.' ;
                          type string {
                            length 1..32 {
                              description 'The length of E-line service name.' ;
                            }

                          }

                        }

                        leaf srv6-locator-name {
                          description 'The SRv6 locator name.' ;
                          type string {
                            length 1..31 {
                              description 'The length of SRv6 locator name.' ;
                            }

                          }

                        }

                      }

                      ncd:revise-date 2023-02-14 ;
                    }

                  }

                  ncd:revise-date 2018-07-08 ;
                }

                case mpls-evpn {
                  description 'The MPLS EVPN auto-discovery type.' ;
                  container mpls-evpn-params {
                    description 'The parameters of MPLS EVPN type.' ;
                    presence mpls-evpn-params ;
                    leaf mode {
                      description 'The MPLS EVPN mode of VPWS community instance.' ;
                      type enumeration {
                        enum mpls-evpn {
                          value 3 ;
                          description 'The mode is MPLS EVPN.' ;
                        }

                      }

                      mandatory true ;
                    }

                    leaf control-word {
                      description 'The control-word capability.' ;
                      type enumeration {
                        enum not-preferred {
                          value 0 ;
                          description 'The control-word capability is not preferred.' ;
                        }

                        enum preferred {
                          value 1 ;
                          description 'The control-word capability is preferred.' ;
                        }

                      }

                      default not-preferred ;
                    }

                    leaf wtr-time {
                      type uint8 {
                        range 0..12 {
                          description 'The length of WTR time in minute.' ;
                        }

                      }

                      description 'Set minutes in WTR. Requires setting wtr-second-with-minute node simultaneously. The range is 0-12(minutes).' ;
                      default 3 ;
                      units min ;
                      ncd:revise-date 2019-02-15 ;
                    }

                    leaf wtr-second-with-minute {
                      type uint8 {
                        range 0..59 {
                          description 'The length of WTR second time in minute.' ;
                        }

                      }

                      description 'Set seconds in WTR. Requires setting wtr-time node simultaneously. The range is 0-59(seconds).' ;
                      units second ;
                      ncd:revise-date 2024-08-13 ;
                    }

                    leaf second {
                      type uint32 {
                        range 0..720 {
                          description 'The length of WTR time in second.' ;
                        }

                      }

                      description 'Set seconds in WTR. Cannot be configured simultaneously with wtr-time node or wtr-second-with-minute node. The range is 0-720(seconds). ' ;
                      units second ;
                      ncd:revise-date 2023-12-12 ;
                    }

                    leaf df-election {
                      description 'the choice mode of DF.' ;
                      type enumeration {
                        enum lowest-preference {
                          value 1 ;
                          description 'The adjacent-node with lowest-preference is DF' ;
                        }

                        enum highest-preference {
                          value 2 ;
                          description 'The adjacent-node with highest-preference is DF' ;
                        }

                      }

                    }

                    leaf entropy-label {
                      description 'Enable or disable entropy label.' ;
                      type enumeration {
                        enum disable {
                          value 0 ;
                          description 'The entropy label is disable.' ;
                        }

                        enum enable {
                          value 1 ;
                          description 'The entropy label is enable.' ;
                        }

                      }

                      default disable ;
                      ncd:revise-date 2019-08-10 ;
                    }

                    leaf traffic-enable {
                      description 'The traffic statistics status of VPWS MPLS EVPN.' ;
                      default disable ;
                      type enumeration {
                        enum disable {
                          value 0 ;
                          description 'The traffic statistics status of VPWS MPLS EVPN is disable.' ;
                        }

                        enum enable {
                          value 1 ;
                          description 'The traffic statistics status of VPWS MPLS EVPN is enable.' ;
                        }

                      }

                      ncd:revise-date 2023-12-11 ;
                    }

                    container mpls-evpn-ds-mode {
                      description 'The DS mode of the MPLS EVPN.' ;
                      leaf ds-mode {
                        description 'The DS service mode.' ;
                        type enumeration {
                          enum uniform {
                            value 1 ;
                            description 'DS mode is uniform.' ;
                          }

                          enum pipe {
                            value 2 ;
                            description 'DS mode is pipe.' ;
                          }

                          enum shortPipe {
                            value 3 ;
                            description 'DS mode is shortPipe.' ;
                          }

                        }

                      }

                      leaf service-class {
                        description 'The DS service class.' ;
                        type enumeration {
                          enum be {
                            value 1 ;
                            description 'The DS service class is be.' ;
                          }

                          enum af1 {
                            value 2 ;
                            description 'The DS service class is af1.' ;
                          }

                          enum af2 {
                            value 3 ;
                            description 'The DS service class is af2.' ;
                          }

                          enum af3 {
                            value 4 ;
                            description 'The DS service class is af3.' ;
                          }

                          enum af4 {
                            value 5 ;
                            description 'The DS service class is af4.' ;
                          }

                          enum ef {
                            value 6 ;
                            description 'The DS service class is ef.' ;
                          }

                          enum cs6 {
                            value 7 ;
                            description 'The DS service class is cs6.' ;
                          }

                          enum cs7 {
                            value 8 ;
                            description 'The DS service class is cs7.' ;
                          }

                        }

                      }

                      leaf colour {
                        description 'The DS packet colour.' ;
                        type enumeration {
                          enum green {
                            value 1 ;
                            description 'The DS packet colour is green.' ;
                          }

                          enum yellow {
                            value 2 ;
                            description 'The DS packet colour is yellow.' ;
                          }

                          enum red {
                            value 3 ;
                            description 'The DS packet colour is red.' ;
                          }

                        }

                      }

                      ncd:revise-date 2019-06-10 ;
                    }

                    container encapulation {
                      description 'The encapsulation parameter of the MPLS EVPN.' ;
                      leaf encapulation-type {
                        description 'Specify encapsulation mode for MPLS EVPN.' ;
                        type enumeration {
                          enum raw {
                            value 5 ;
                            description 'The encapsulation mode is raw.' ;
                          }

                          enum tagged {
                            value 4 ;
                            description 'The encapsulation mode is tagged.' ;
                          }

                        }

                        default raw ;
                      }

                    }

                    container route-target-params {
                      description 'The route target parameters.' ;
                      list route-target {
                        description 'The route target.' ;
                        key 'rt-value effect-type' ;
                        leaf rt-value {
                          description 'RT attribute value.' ;
                          type union {
                            type ncd:asn-nn ;

                            type ncd:ipadd-nn ;

                            type ncd:asnd-nn ;

                          }

                        }

                        leaf effect-type {
                          description 'The route target effect type.' ;
                          type enumeration {
                            enum export {
                              value 2 ;
                              description 'The route target effect type is export.' ;
                            }

                            enum import {
                              value 3 ;
                              description 'The route target effect type is import.' ;
                            }

                          }

                        }

                      }

                    }

                    container mpls-evpn-ac-bind {
                      description "MPLS EVPN's AC binding configuration info." ;
                      list ac-instance-bind {
                        description 'AC binding instance configuration info.' ;
                        key ac-name ;
                        leaf ac-name {
                          description 'The name of the AC in the bind.' ;
                          type ncd:ifname {
                            length 1..31 {
                              description 'The length of AC name.' ;
                            }

                          }

                        }

                        leaf local-vpws-id {
                          description 'Config local VPWS ID.' ;
                          type uint32 {
                            range 1..4294967294 {
                              description 'The range of local VPWS ID.' ;
                            }

                          }

                        }

                        leaf remote-vpws-id {
                          description 'Config remote VPWS ID.' ;
                          type uint32 {
                            range 1..4294967294 {
                              description 'The range of remote VPWS ID.' ;
                            }

                          }

                        }

                        leaf if-description {
                          description 'The description of the interface.' ;
                          type ncd:string-with-blank {
                            length 1..104 {
                              description 'The description range of interface.' ;
                            }

                          }

                          ncd:revise-date 2019-09-29 ;
                        }

                        container encapsulation {
                          leaf encapsulation-type {
                            description 'Specify encapsulation mode for MPLS EVPN AC.' ;
                            type enumeration {
                              enum raw {
                                value 5 ;
                                description 'The encapsulation mode is raw.' ;
                              }

                              enum tagged {
                                value 4 ;
                                description 'The encapsulation mode is tagged.' ;
                              }

                            }

                            ncd:revise-date 2024-06-01 ;
                          }

                          description 'The encapsulation parameter of the MPLS EVPN AC.' ;
                        }

                        choice ac-type {
                          description 'The access type of VPWS community instance.' ;
                          case ethernet {
                            description 'The ethernet access type.' ;
                            container ethernet-params {
                              description 'Ethernet access type parameters.' ;
                              presence ethernet-params ;
                              leaf ethernet {
                                description 'Ethernet access type.' ;
                                type empty ;

                                mandatory true ;
                              }

                              leaf ingress-adjust-tag-as-payload {
                                description 'The ingress tag as payload flag of the ethernet parameter.' ;
                                type enumeration {
                                  enum disable {
                                    value 0 ;
                                    description 'The ingress tag as payload flag is disable.' ;
                                  }

                                  enum all {
                                    value 1 ;
                                    description 'All of tags are payload.' ;
                                  }

                                  enum from-sub-layer {
                                    value 2 ;
                                    description 'Payload from sub-layer tag.' ;
                                  }

                                }

                                default disable ;
                              }

                              leaf ingress-adjust-drop-tagged-frames {
                                description 'The ingress adjust drop tagged frames flag of the ethernet.' ;
                                type enumeration {
                                  enum disable {
                                    value 0 ;
                                    description 'The ingress adjust drop tagged frames flag is disable.' ;
                                  }

                                  enum enable {
                                    value 1 ;
                                    description 'The ingress adjust drop tagged frames flag is enable.' ;
                                  }

                                }

                                ncd:revise-date 2023-03-10 ;
                              }

                              leaf traffic-enable {
                                description 'The traffic statistics enable flag of the ethernet parameter.' ;
                                type enumeration {
                                  enum disable {
                                    value 0 ;
                                    description 'The traffic statistics flag is disable.' ;
                                  }

                                  enum enable {
                                    value 1 ;
                                    description 'The traffic statistics flag is enable.' ;
                                  }

                                }

                                default disable ;
                                ncd:revise-date 2019-06-10 ;
                              }

                              leaf egress-keep-normalized-tag {
                                description 'To keep the normalized tag unchanged onto the egress AC.' ;
                                type enumeration {
                                  enum disable {
                                    value 0 ;
                                    description 'To keep the normalized tag unchanged onto the egress AC is disable.' ;
                                  }

                                  enum enable {
                                    value 1 ;
                                    description 'To keep the normalized tag unchanged onto the egress AC is enable.' ;
                                  }

                                }

                                default disable ;
                                ncd:revise-date 2021-01-05 ;
                              }

                              container ingress-adjust-push-params {
                                description 'The ingress adjust push parameters of the ethernet parameter.' ;
                                leaf ingress-adjust-push {
                                  description 'The ingress adjust push flag of the ethernet parameter.' ;
                                  type enumeration {
                                    enum disable {
                                      value 0 ;
                                      description 'The ingress adjust push flag of the ethernet parameter is disable.' ;
                                    }

                                    enum enable {
                                      value 1 ;
                                      description 'The ingress adjust push flag of the ethernet parameter is enable.' ;
                                    }

                                  }

                                  default disable ;
                                }

                                leaf push-vlan-id {
                                  description 'The ingress adjust push VLAN ID of the ethernet parameter.' ;
                                  type uint16 {
                                    range 1..4094 {
                                      description 'The range of push VLAN ID is 1-4094.' ;
                                    }

                                  }

                                }

                                ncd:revise-date 2020-07-03 ;
                              }

                              container ingress-adjust-rewrite-params {
                                description 'The ingress adjust rewrite parameters of the ethernet parameter.' ;
                                leaf ingress-adjust-rewrite {
                                  description 'The ingress adjust rewrite flag of the ethernet parameter.' ;
                                  type enumeration {
                                    enum disable {
                                      value 0 ;
                                      description 'The ingress adjust rewrite flag of the ethernet parameter is disable.' ;
                                    }

                                    enum enable {
                                      value 1 ;
                                      description 'The ingress adjust rewrite flag of the ethernet parameter is enable.' ;
                                    }

                                  }

                                  default disable ;
                                }

                                leaf rewrite-vlan-id {
                                  description 'The ingress adjust rewrite VLAN ID of the ethernet parameter.' ;
                                  type uint16 {
                                    range 1..4094 {
                                      description 'The range of rewrite VLAN ID is 1-4094.' ;
                                    }

                                  }

                                }

                                leaf rewrite-outer-vlanid-flag {
                                  description 'Rewrite outer VLAN ID flag.' ;
                                  type enumeration {
                                    enum disable {
                                      value 0 ;
                                      description 'Rewrite outer VLAN ID flag is disable.' ;
                                    }

                                    enum enable {
                                      value 1 ;
                                      description 'Rewrite outer VLAN ID flag is enable.' ;
                                    }

                                  }

                                  default disable ;
                                  ncd:revise-date 2021-01-05 ;
                                }

                                ncd:revise-date 2020-07-03 ;
                              }

                              container l2protocol-control-policy {
                                description 'L2protocol packet filtering function.' ;
                                leaf abm {
                                  description 'All bridge multicast frame protocol packet filtering.' ;
                                  type enumeration {
                                    enum tunnelled {
                                      value 0 ;
                                      description 'All bridge multicast frame protocol packet filtering is tunnelled.' ;
                                    }

                                    enum dropped {
                                      value 1 ;
                                      description 'All bridge multicast frame protocol packet filtering is dropped.' ;
                                    }

                                    enum terminated {
                                      value 2 ;
                                      description 'All bridge multicast frame protocol packet filtering is terminated.' ;
                                    }

                                  }

                                }

                                leaf dot1x {
                                  description '802.1x protocol frame packet filtering.' ;
                                  type enumeration {
                                    enum tunnelled {
                                      value 0 ;
                                      description '802.1x protocol frame packet filtering is tunnelled.' ;
                                    }

                                    enum dropped {
                                      value 1 ;
                                      description '802.1x protocol frame packet filtering is dropped.' ;
                                    }

                                    enum terminated {
                                      value 2 ;
                                      description '802.1x protocol frame packet filtering is terminated.' ;
                                    }

                                  }

                                }

                                leaf dot3x {
                                  description '802.3x protocol frame packet filtering.' ;
                                  type enumeration {
                                    enum tunnelled {
                                      value 0 ;
                                      description '802.3x protocol frame packet filtering is tunnelled.' ;
                                    }

                                    enum dropped {
                                      value 1 ;
                                      description '802.3x protocol frame packet filtering is dropped.' ;
                                    }

                                    enum terminated {
                                      value 2 ;
                                      description '802.3x protocol frame packet filtering is terminated.' ;
                                    }

                                  }

                                }

                                leaf garp {
                                  description 'GARP protocol packet filtering.' ;
                                  type enumeration {
                                    enum tunnelled {
                                      value 0 ;
                                      description 'GARP protocol packet filtering is tunnelled.' ;
                                    }

                                    enum dropped {
                                      value 1 ;
                                      description 'GARP protocol packet filtering is dropped.' ;
                                    }

                                    enum terminated {
                                      value 2 ;
                                      description 'GARP protocol packet filtering is terminated.' ;
                                    }

                                  }

                                }

                                leaf gmrp {
                                  description 'GMRP protocol packet filtering.' ;
                                  type enumeration {
                                    enum tunnelled {
                                      value 0 ;
                                      description 'GMRP protocol packet filtering is tunnelled.' ;
                                    }

                                    enum dropped {
                                      value 1 ;
                                      description 'GMRP protocol packet filtering is dropped.' ;
                                    }

                                    enum terminated {
                                      value 2 ;
                                      description 'GMRP protocol packet filtering is terminated.' ;
                                    }

                                  }

                                }

                                leaf gvrp {
                                  description 'GVRP protocol packet filtering.' ;
                                  type enumeration {
                                    enum tunnelled {
                                      value 0 ;
                                      description 'GVRP protocol packet filtering is tunnelled.' ;
                                    }

                                    enum dropped {
                                      value 1 ;
                                      description 'GVRP protocol packet filtering is dropped.' ;
                                    }

                                    enum terminated {
                                      value 2 ;
                                      description 'GVRP protocol packet filtering is terminated.' ;
                                    }

                                  }

                                }

                                leaf cisco {
                                  description 'CISCO protocol packet filtering.' ;
                                  type enumeration {
                                    enum tunnelled {
                                      value 0 ;
                                      description 'CISCO protocol packet filtering is tunnelled.' ;
                                    }

                                    enum dropped {
                                      value 1 ;
                                      description 'CISCO protocol packet filtering is dropped.' ;
                                    }

                                    enum terminated {
                                      value 2 ;
                                      description 'CISCO protocol packet filtering is terminated.' ;
                                    }

                                  }

                                }

                                leaf dldp {
                                  description 'DLDP protocol packet filtering.' ;
                                  type enumeration {
                                    enum tunnelled {
                                      value 0 ;
                                      description 'DLDP protocol packet filtering is tunnelled.' ;
                                    }

                                    enum dropped {
                                      value 1 ;
                                      description 'DLDP protocol packet filtering is dropped.' ;
                                    }

                                    enum terminated {
                                      value 2 ;
                                      description 'DLDP protocol packet filtering is terminated.' ;
                                    }

                                  }

                                }

                                leaf efm {
                                  description 'EFM protocol packet filtering.' ;
                                  type enumeration {
                                    enum tunnelled {
                                      value 0 ;
                                      description 'EFM protocol packet filtering is tunnelled.' ;
                                    }

                                    enum dropped {
                                      value 1 ;
                                      description 'EFM protocol packet filtering is dropped.' ;
                                    }

                                    enum terminated {
                                      value 2 ;
                                      description 'EFM protocol packet filtering is terminated.' ;
                                    }

                                  }

                                }

                                leaf cfm {
                                  description 'CFM protocol packet filtering.' ;
                                  type enumeration {
                                    enum tunnelled {
                                      value 0 ;
                                      description 'EFM protocol packet filtering is tunnelled.' ;
                                    }

                                    enum dropped {
                                      value 1 ;
                                      description 'EFM protocol packet filtering is dropped.' ;
                                    }

                                    enum terminated {
                                      value 2 ;
                                      description 'EFM protocol packet filtering is terminated.' ;
                                    }

                                  }

                                }

                                leaf pvst {
                                  description 'PVST protocol packet filtering.' ;
                                  type enumeration {
                                    enum tunnelled {
                                      value 0 ;
                                      description 'PVST protocol packet filtering is tunnelled.' ;
                                    }

                                    enum dropped {
                                      value 1 ;
                                      description 'PVST protocol packet filtering is dropped.' ;
                                    }

                                    enum terminated {
                                      value 2 ;
                                      description 'PVST protocol packet filtering is terminated.' ;
                                    }

                                  }

                                }

                                leaf zdp {
                                  description 'ZDP protocol packet filtering.' ;
                                  type enumeration {
                                    enum tunnelled {
                                      value 0 ;
                                      description 'ZDP protocol packet filtering is tunnelled.' ;
                                    }

                                    enum dropped {
                                      value 1 ;
                                      description 'ZDP protocol packet filtering is dropped.' ;
                                    }

                                    enum terminated {
                                      value 2 ;
                                      description 'ZDP protocol packet filtering is terminated.' ;
                                    }

                                  }

                                }

                                leaf lacp {
                                  description 'LACP protocol packet filtering.' ;
                                  type enumeration {
                                    enum tunnelled {
                                      value 0 ;
                                      description 'LACP protocol packet filtering is tunnelled.' ;
                                    }

                                    enum dropped {
                                      value 1 ;
                                      description 'LACP protocol packet filtering is dropped.' ;
                                    }

                                    enum terminated {
                                      value 2 ;
                                      description 'LACP protocol packet filtering is terminated.' ;
                                    }

                                  }

                                }

                                leaf lldp {
                                  description 'LLDP protocol packet filtering.' ;
                                  type enumeration {
                                    enum tunnelled {
                                      value 0 ;
                                      description 'LLDP protocol packet filtering is tunnelled.' ;
                                    }

                                    enum dropped {
                                      value 1 ;
                                      description 'LLDP protocol packet filtering is dropped.' ;
                                    }

                                    enum terminated {
                                      value 2 ;
                                      description 'LLDP protocol packet filtering is terminated.' ;
                                    }

                                  }

                                }

                                leaf stp {
                                  description 'STP protocol packet filtering.' ;
                                  type enumeration {
                                    enum tunnelled {
                                      value 0 ;
                                      description 'STP protocol packet filtering is tunnelled.' ;
                                    }

                                    enum dropped {
                                      value 1 ;
                                      description 'STP protocol packet filtering is dropped.' ;
                                    }

                                    enum terminated {
                                      value 2 ;
                                      description 'STP protocol packet filtering is terminated.' ;
                                    }

                                    enum tunnelled-monitored {
                                      value 3 ;
                                      description 'STP protocol packet filtering is tunnelled-monitored.' ;
                                    }

                                  }

                                }

                                leaf erps {
                                  description 'ERPS protocol packet filtering.' ;
                                  type enumeration {
                                    enum tunnelled {
                                      value 0 ;
                                      description 'ERPS protocol packet filtering is tunnelled.' ;
                                    }

                                    enum dropped {
                                      value 1 ;
                                      description 'ERPS protocol packet filtering is dropped.' ;
                                    }

                                    enum terminated {
                                      value 2 ;
                                      description 'ERPS protocol packet filtering is terminated.' ;
                                    }

                                  }

                                }

                                leaf udld {
                                  description 'UDLD protocol packet filtering.' ;
                                  type enumeration {
                                    enum tunnelled {
                                      value 0 ;
                                      description 'UDLD protocol packet filtering is tunnelled.' ;
                                    }

                                    enum dropped {
                                      value 1 ;
                                      description 'UDLD protocol packet filtering is dropped.' ;
                                    }

                                    enum terminated {
                                      value 2 ;
                                      description 'UDLD protocol packet filtering is terminated.' ;
                                    }

                                  }

                                }

                                leaf vtp {
                                  description 'VTP protocol packet filtering.' ;
                                  type enumeration {
                                    enum tunnelled {
                                      value 0 ;
                                      description 'VTP protocol packet filtering is tunnelled.' ;
                                    }

                                    enum dropped {
                                      value 1 ;
                                      description 'VTP protocol packet filtering is dropped.' ;
                                    }

                                    enum terminated {
                                      value 2 ;
                                      description 'VTP protocol packet filtering is terminated.' ;
                                    }

                                  }

                                }

                                leaf zesr {
                                  description 'ZESR protocol packet filtering.' ;
                                  type enumeration {
                                    enum tunnelled {
                                      value 0 ;
                                      description 'ZESR protocol packet filtering is tunnelled.' ;
                                    }

                                    enum dropped {
                                      value 1 ;
                                      description 'ZESR protocol packet filtering is dropped.' ;
                                    }

                                    enum terminated {
                                      value 2 ;
                                      description 'ZESR protocol packet filtering is terminated.' ;
                                    }

                                  }

                                }

                                leaf l2bfd {
                                  description 'L2BFD protocol packet filtering.' ;
                                  type enumeration {
                                    enum tunnelled {
                                      value 0 ;
                                      description 'L2BFD protocol packet filtering is tunnelled.' ;
                                    }

                                    enum terminated {
                                      value 2 ;
                                      description 'L2BFD protocol packet filtering is terminated.' ;
                                    }

                                  }

                                }

                                leaf mac-control {
                                  description 'MAC-control protocol packet filtering.' ;
                                  type enumeration {
                                    enum tunnelled {
                                      value 0 ;
                                      description 'MAC-control protocol packet filtering is tunnelled.' ;
                                    }

                                    enum dropped {
                                      value 1 ;
                                      description 'MAC-control protocol packet filtering is dropped.' ;
                                    }

                                    enum terminated {
                                      value 2 ;
                                      description 'MAC-control protocol packet filtering is terminated.' ;
                                    }

                                  }

                                  ncd:revise-date 2023-03-25 ;
                                }

                                container user-protocol-template {
                                  description 'The template of user protocol.' ;
                                  presence user-protocol-template ;
                                  leaf user-protocol-name {
                                    description 'The class name of user protocol.' ;
                                    type string {
                                      length 1..31 {
                                        description 'The length of user protocol class name.' ;
                                      }

                                    }

                                    mandatory true ;
                                  }

                                  leaf user-protocol-action {
                                    description 'User protocol template action.' ;
                                    type enumeration {
                                      enum tunnelled {
                                        value 0 ;
                                        description 'User protocol template action is tunnelled.' ;
                                      }

                                      enum dropped {
                                        value 1 ;
                                        description 'User protocol template action is dropped.' ;
                                      }

                                      enum terminated {
                                        value 2 ;
                                        description 'User protocol template action is terminated.' ;
                                      }

                                    }

                                    mandatory true ;
                                  }

                                }

                                leaf lamp {
                                  description 'LAMP protocol packet filtering.' ;
                                  type enumeration {
                                    enum tunnelled {
                                      value 0 ;
                                      description 'LAMP protocol packet filtering is tunnelled.' ;
                                    }

                                    enum dropped {
                                      value 1 ;
                                      description 'LAMP protocol packet filtering is dropped.' ;
                                    }

                                    enum terminated {
                                      value 2 ;
                                      description 'LAMP protocol packet filtering is terminated.' ;
                                    }

                                  }

                                  ncd:revise-date 2023-11-09 ;
                                }

                                leaf lacp-tagged {
                                  description 'LACP with VLAN tag protocol packet filtering.' ;
                                  type enumeration {
                                    enum tunnelled {
                                      value 0 ;
                                      description 'LACP with VLAN tag protocol packet filtering is tunnelled.' ;
                                    }

                                    enum dropped {
                                      description 'LACP with VLAN tag protocol packet filtering is dropped.' ;
                                      value 1 ;
                                    }

                                    enum terminated {
                                      description 'LACP with VLAN tag protocol packet filtering is terminated.' ;
                                      value 2 ;
                                    }

                                  }

                                  ncd:revise-date 2023-11-09 ;
                                }

                                ncd:revise-date 2021-06-07 ;
                              }

                              container duplicate {
                                if-feature vpws-community-mpls-duplicate ;

                                description 'Duplicate configuration node.' ;
                                leaf nd-enable {
                                  description 'ND duplicate switch flag,the default is off.' ;
                                  type boolean ;

                                  default false ;
                                }

                                leaf arp-enable {
                                  description 'ARP duplicate switch flag, the default is off.' ;
                                  type boolean ;

                                  default false ;
                                }

                                leaf send-arp-enable {
                                  description 'ARP duplicate free ARP sending switch flag, the default is off.' ;
                                  type boolean ;

                                  default false ;
                                }

                                leaf send-nd-enable {
                                  description 'ND duplicate free ND switch flag, the default is off.' ;
                                  type boolean ;

                                  default false ;
                                }

                                leaf send-periodic-arp {
                                  description 'ARP duplicate free ARP delivery interval in seconds.' ;
                                  type uint32 {
                                    range 1..2147483 ;

                                  }

                                  default 600 ;
                                }

                                leaf send-periodic-nd {
                                  description 'ND duplicate free ND time interval in seconds.' ;
                                  type uint32 {
                                    range 1..2147483 ;

                                  }

                                  default 600 ;
                                }

                                ncd:revise-date 2019-08-12 ;
                              }

                              container evpn-vpws-evi-labels {
                                description 'MPLS EVI labels.' ;
                                list evpn-vpws-evi-label {
                                  description 'MPLS EVI label.' ;
                                  key evi-label ;
                                  leaf evi-label {
                                    description 'EVI label.' ;
                                    type uint32 {
                                      range 16..1048575 {
                                        description 'The EVI label range.' ;
                                      }

                                    }

                                  }

                                }

                                ncd:revise-date 2019-10-29 ;
                              }

                            }

                          }

                        }

                      }

                    }

                    container mpls-evpn-bridge-if-bind {
                      description "MPLS EVPN's bridge if binding configuration info." ;
                      list bridge-if-instance-bind {
                        description 'Bridge if binding instance configuration info.' ;
                        key ac-name ;
                        leaf ac-name {
                          description 'The name of the bridge AC in the bind.' ;
                          type ncd:ifname {
                            length 1..31 {
                              description 'The length of AC name.' ;
                            }

                          }

                        }

                        leaf local-vpws-id {
                          description 'Config local VPWS ID.' ;
                          type uint32 {
                            range 1..4294967294 {
                              description 'The range of local VPWS ID.' ;
                            }

                          }

                        }

                        leaf remote-vpws-id {
                          description 'Config remote VPWS ID.' ;
                          type uint32 {
                            range 1..4294967294 {
                              description 'The range of remote VPWS ID.' ;
                            }

                          }

                        }

                        choice ac-type {
                          description 'The access type of VPWS community instance.' ;
                          case ethernet {
                            description 'The ethernet access type.' ;
                            container ethernet-params {
                              description 'Ethernet access type parameters.' ;
                              presence ethernet-params ;
                              leaf ethernet {
                                description 'Ethernet access type.' ;
                                type empty ;

                                mandatory true ;
                              }

                            }

                          }

                        }

                      }

                      ncd:revise-date 2019-02-15 ;
                    }

                    container mpls-evpn-access-pw-bind {
                      description "MPLS EVPN's access PW binding configuration info." ;
                      list pw-instance-bind {
                        description 'PW binding instance configuration info.' ;
                        key pw-name ;
                        leaf pw-name {
                          description 'The name of the PW in the bind.' ;
                          type ncd:ifname ;

                        }

                        leaf local-vpws-id {
                          description 'Config local VPWS ID.' ;
                          type uint32 {
                            range 1..4294967294 {
                              description 'The range of local VPWS ID.' ;
                            }

                          }

                        }

                        leaf remote-vpws-id {
                          description 'Config remote VPWS ID.' ;
                          type uint32 {
                            range 1..4294967294 {
                              description 'The range of remote VPWS ID.' ;
                            }

                          }

                        }

                      }

                      ncd:revise-date 2019-04-09 ;
                    }

                    container flow-label {
                      description 'Configure flow-label capability.' ;
                      leaf push {
                        description 'Set flow-label send capability.' ;
                        type enumeration {
                          enum static {
                            value 1 ;
                            description 'Push a flow-label even if R flag is not received.' ;
                          }

                        }

                      }

                      leaf pop {
                        description 'Set flow-label receive capability.' ;
                        type enumeration {
                          enum static {
                            value 1 ;
                            description 'Push a flow-label even if R flag is not received.' ;
                          }

                        }

                      }

                      ncd:revise-date 2022-02-15 ;
                    }

                    container mpls-evpn-evpl-bind {
                      description "MPLS EVPN's EVPL binding configuration info." ;
                      list evpl-instance-bind {
                        description 'Bind an Ethernet Virtual Private Line (EVPL) which is an E-line service.' ;
                        key eline-service-name ;
                        leaf eline-service-name {
                          description 'L2VPN E-line service name.' ;
                          type string {
                            length 1..32 {
                              description 'The length of E-line service name.' ;
                            }

                          }

                        }

                      }

                      ncd:revise-date 2023-02-14 ;
                    }

                  }

                  ncd:revise-date 2018-07-08 ;
                }

              }

            }

            container peer-ipv4 {
              description 'The peer address type is IPv4.' ;
              list peer-ipv4-params {
                description 'IPv4 address parameters.' ;
                key ipv4-address ;
                leaf ipv4-address {
                  description 'IPv4 address.' ;
                  type ncd:ipv4-address-none-zero ;

                }

                leaf tunnel-policy-name {
                  description 'The name of the tunnel policy.' ;
                  type string {
                    length 1..63 {
                      description 'The length of tunnel policy name.' ;
                    }

                  }

                  mandatory true ;
                }

              }

              ncd:revise-date 2018-07-08 ;
            }

            container peer-ipv6 {
              description 'The peer address type is IPv6.' ;
              list peer-ipv6-params {
                description 'IPv6 address parameters.' ;
                key ipv6-address ;
                leaf ipv6-address {
                  description 'IPv6 address.' ;
                  type ncd:ipv6-address {
                    pattern "([0-9a-fA-F]{1,4}:){7}([0-9a-fA-F]{0,4})$|^([0-9a-fA-F]{1,4}:){1,6}(:[0-9a-fA-F]{0,4}){1,6}$|^([:]{2})(([0-9a-fA-F]{1,4}:){0,6})([0-9a-fA-F]{1,4})$|^([0-9a-fA-F]{1,4}:){6}([0-9]{1,3}.){3}([0-9]{1,3})$|^([0-9a-fA-F]{1,4}:){1,5}(:[0-9a-fA-F]{0,4}){1,5}([0-9]{1,3}.){3}([0-9]{1,3})$|^([:]{2})(([0-9a-fA-F]{1,4}:){0,5})([0-9]{1,3}.){3}([0-9]{1,3})" ;

                  }

                }

                leaf tunnel-policy-name {
                  description 'The name of the tunnel policy.' ;
                  type string {
                    length 1..63 {
                      description 'The length of tunnel policy name.' ;
                    }

                  }

                  mandatory true ;
                }

              }

              ncd:revise-date 2018-07-08 ;
            }

            leaf default-color {
              description 'Configure default color.' ;
              type uint32 {
                range 1..4294967295 ;

              }

              ncd:revise-date 2021-11-25 ;
            }

          }

          ncd:revise-date 2017-12-01 ;
        }

        container vpws-vxlan-instances {
          description 'The VPWS VXLAN instances configuration info.' ;
          list vpws-vxlan-instance {
            description 'The VPWS VXLAN instance configuration info.' ;
            key instance-name ;
            leaf instance-name {
              description 'The name of the VPWS VXLAN instance.' ;
              type string {
                length 1..32 {
                  description 'The length of instance name.' ;
                }

              }

            }

            container vpws-vxlan-ac-bind {
              description "VPWS VXLAN's AC binding configuration info." ;
              list ac-instance-bind {
                description 'AC binding instance configuration info.' ;
                key ac-name ;
                leaf ac-name {
                  description 'The name of the AC in the bind.' ;
                  type ncd:ifname ;

                }

                choice ac-type {
                  description 'The access type of VPWS VXLAN instance,All the access type is mutual exclusion.' ;
                  case ethernet {
                    description 'The ethernet access type.' ;
                    container ethernet-params {
                      description 'Ethernet access type parameters.' ;
                      presence ethernet-params ;
                      leaf ethernet {
                        description 'Ethernet access type.' ;
                        type empty ;

                        mandatory true ;
                      }

                      leaf ingress-adjust-push {
                        description 'The ingress adjust push flag of the ethernet parameter.' ;
                        type enumeration {
                          enum disable {
                            value 0 ;
                            description 'The ingress adjust push flag of the ethernet parameter is disable.' ;
                          }

                          enum enable {
                            value 1 ;
                            description 'The ingress adjust push flag of the ethernet parameter is enable.' ;
                          }

                        }

                        default disable ;
                      }

                      leaf push-vlan-id {
                        description 'The ingress adjust push VLAN ID of the ethernet parameter.' ;
                        type uint16 {
                          range 1..4094 {
                            description 'The range of push VLAN ID is 1-4094.' ;
                          }

                        }

                      }

                      leaf ingress-adjust-rewrite {
                        description 'The ingress adjust rewrite flag of the ethernet parameter.' ;
                        type enumeration {
                          enum disable {
                            value 0 ;
                            description 'The ingress adjust rewrite flag of the ethernet parameter is disable.' ;
                          }

                          enum enable {
                            value 1 ;
                            description 'The ingress adjust rewrite flag of the ethernet parameter is enable.' ;
                          }

                        }

                        default disable ;
                      }

                      leaf rewrite-vlan-id {
                        description 'The ingress adjust rewrite VLAN ID of the ethernet parameter.' ;
                        type uint16 {
                          range 1..4094 {
                            description 'The range of rewrite VLAN ID is 1-4094.' ;
                          }

                        }

                      }

                      leaf ingress-adjust-drop-tagged-frames {
                        description 'The ingress adjust drop tagged frames flag of the ethernet.' ;
                        type enumeration {
                          enum disable {
                            value 0 ;
                            description 'The ingress adjust drop tagged frames flag is disable.' ;
                          }

                          enum enable {
                            value 1 ;
                            description 'The ingress adjust drop tagged frames flag is enable.' ;
                          }

                        }

                        ncd:revise-date 2023-03-10 ;
                      }

                      leaf ingress-adjust-tag-as-payload {
                        description 'The ingress tag as payload flag of the ethernet parameter.' ;
                        type enumeration {
                          enum disable {
                            value 0 ;
                            description 'The ingress tag as payload flag is disable.' ;
                          }

                          enum all {
                            value 1 ;
                            description 'The ingress tag as payload flag is from outer most.' ;
                          }

                          enum from-sub-layer {
                            value 2 ;
                            description 'The ingress tag as payload flag is from sub layer.' ;
                          }

                        }

                        default disable ;
                      }

                      container l2protocol-control-policy {
                        description 'L2protocol packet filtering function.' ;
                        leaf abm {
                          description 'All bridge multicast frame protocol packet filtering.' ;
                          type enumeration {
                            enum tunnelled {
                              value 0 ;
                              description 'All bridge multicast frame protocol packet filtering is tunnelled.' ;
                            }

                            enum dropped {
                              value 1 ;
                              description 'All bridge multicast frame protocol packet filtering is dropped.' ;
                            }

                            enum terminated {
                              value 2 ;
                              description 'All bridge multicast frame protocol packet filtering is terminated.' ;
                            }

                          }

                        }

                        leaf dot1x {
                          description '802.1x protocol frame packet filtering.' ;
                          type enumeration {
                            enum tunnelled {
                              value 0 ;
                              description '802.1x protocol frame packet filtering is tunnelled.' ;
                            }

                            enum dropped {
                              value 1 ;
                              description '802.1x protocol frame packet filtering is dropped.' ;
                            }

                            enum terminated {
                              value 2 ;
                              description '802.1x protocol frame packet filtering is terminated.' ;
                            }

                          }

                        }

                        leaf dot3x {
                          description '802.3x protocol frame packet filtering.' ;
                          type enumeration {
                            enum tunnelled {
                              value 0 ;
                              description '802.3x protocol frame packet filtering is tunnelled.' ;
                            }

                            enum dropped {
                              value 1 ;
                              description '802.3x protocol frame packet filtering is dropped.' ;
                            }

                            enum terminated {
                              value 2 ;
                              description '802.3x protocol frame packet filtering is terminated.' ;
                            }

                          }

                        }

                        leaf garp {
                          description 'GARP protocol packet filtering.' ;
                          type enumeration {
                            enum tunnelled {
                              value 0 ;
                              description 'GARP protocol packet filtering is tunnelled.' ;
                            }

                            enum dropped {
                              value 1 ;
                              description 'GARP protocol packet filtering is dropped.' ;
                            }

                            enum terminated {
                              value 2 ;
                              description 'GARP protocol packet filtering is terminated.' ;
                            }

                          }

                        }

                        leaf gmrp {
                          description 'GMRP protocol packet filtering.' ;
                          type enumeration {
                            enum tunnelled {
                              value 0 ;
                              description 'GMRP protocol packet filtering is tunnelled.' ;
                            }

                            enum dropped {
                              value 1 ;
                              description 'GMRP protocol packet filtering is dropped.' ;
                            }

                            enum terminated {
                              value 2 ;
                              description 'GMRP protocol packet filtering is terminated.' ;
                            }

                          }

                        }

                        leaf gvrp {
                          description 'GVRP protocol packet filtering.' ;
                          type enumeration {
                            enum tunnelled {
                              value 0 ;
                              description 'GVRP protocol packet filtering is tunnelled.' ;
                            }

                            enum dropped {
                              value 1 ;
                              description 'GVRP protocol packet filtering is dropped.' ;
                            }

                            enum terminated {
                              value 2 ;
                              description 'GVRP protocol packet filtering is terminated.' ;
                            }

                          }

                        }

                        leaf cisco {
                          description 'CISCO protocol packet filtering.' ;
                          type enumeration {
                            enum tunnelled {
                              value 0 ;
                              description 'CISCO protocol packet filtering is tunnelled.' ;
                            }

                            enum dropped {
                              value 1 ;
                              description 'CISCO protocol packet filtering is dropped.' ;
                            }

                            enum terminated {
                              value 2 ;
                              description 'CISCO protocol packet filtering is terminated.' ;
                            }

                          }

                        }

                        leaf dldp {
                          description 'DLDP protocol packet filtering.' ;
                          type enumeration {
                            enum tunnelled {
                              value 0 ;
                              description 'DLDP protocol packet filtering is tunnelled.' ;
                            }

                            enum dropped {
                              value 1 ;
                              description 'DLDP protocol packet filtering is dropped.' ;
                            }

                            enum terminated {
                              value 2 ;
                              description 'DLDP protocol packet filtering is terminated.' ;
                            }

                          }

                        }

                        leaf efm {
                          description 'EFM protocol packet filtering.' ;
                          type enumeration {
                            enum tunnelled {
                              value 0 ;
                              description 'EFM protocol packet filtering is tunnelled.' ;
                            }

                            enum dropped {
                              value 1 ;
                              description 'EFM protocol packet filtering is dropped.' ;
                            }

                            enum terminated {
                              value 2 ;
                              description 'EFM protocol packet filtering is terminated.' ;
                            }

                          }

                        }

                        leaf cfm {
                          description 'CFM protocol packet filtering.' ;
                          type enumeration {
                            enum tunnelled {
                              value 0 ;
                              description 'EFM protocol packet filtering is tunnelled.' ;
                            }

                            enum dropped {
                              value 1 ;
                              description 'EFM protocol packet filtering is dropped.' ;
                            }

                            enum terminated {
                              value 2 ;
                              description 'EFM protocol packet filtering is terminated.' ;
                            }

                          }

                        }

                        leaf pvst {
                          description 'PVST protocol packet filtering.' ;
                          type enumeration {
                            enum tunnelled {
                              value 0 ;
                              description 'PVST protocol packet filtering is tunnelled.' ;
                            }

                            enum dropped {
                              value 1 ;
                              description 'PVST protocol packet filtering is dropped.' ;
                            }

                            enum terminated {
                              value 2 ;
                              description 'PVST protocol packet filtering is terminated.' ;
                            }

                          }

                        }

                        leaf zdp {
                          description 'ZDP protocol packet filtering.' ;
                          type enumeration {
                            enum tunnelled {
                              value 0 ;
                              description 'ZDP protocol packet filtering is tunnelled.' ;
                            }

                            enum dropped {
                              value 1 ;
                              description 'ZDP protocol packet filtering is dropped.' ;
                            }

                            enum terminated {
                              value 2 ;
                              description 'ZDP protocol packet filtering is terminated.' ;
                            }

                          }

                        }

                        leaf lacp {
                          description 'LACP protocol packet filtering.' ;
                          type enumeration {
                            enum tunnelled {
                              value 0 ;
                              description 'LACP protocol packet filtering is tunnelled.' ;
                            }

                            enum dropped {
                              value 1 ;
                              description 'LACP protocol packet filtering is dropped.' ;
                            }

                            enum terminated {
                              value 2 ;
                              description 'LACP protocol packet filtering is terminated.' ;
                            }

                          }

                        }

                        leaf lldp {
                          description 'LLDP protocol packet filtering.' ;
                          type enumeration {
                            enum tunnelled {
                              value 0 ;
                              description 'LLDP protocol packet filtering is tunnelled.' ;
                            }

                            enum dropped {
                              value 1 ;
                              description 'LLDP protocol packet filtering is dropped.' ;
                            }

                            enum terminated {
                              value 2 ;
                              description 'LLDP protocol packet filtering is terminated.' ;
                            }

                          }

                        }

                        leaf stp {
                          description 'STP protocol packet filtering.' ;
                          type enumeration {
                            enum tunnelled {
                              value 0 ;
                              description 'STP protocol packet filtering is tunnelled.' ;
                            }

                            enum dropped {
                              value 1 ;
                              description 'STP protocol packet filtering is dropped.' ;
                            }

                            enum terminated {
                              value 2 ;
                              description 'STP protocol packet filtering is terminated.' ;
                            }

                            enum tunnelled-monitored {
                              value 3 ;
                              description 'STP protocol packet filtering is tunnelled-monitored.' ;
                            }

                          }

                        }

                        leaf erps {
                          description 'ERPS protocol packet filtering.' ;
                          type enumeration {
                            enum tunnelled {
                              value 0 ;
                              description 'ERPS protocol packet filtering is tunnelled.' ;
                            }

                            enum dropped {
                              value 1 ;
                              description 'ERPS protocol packet filtering is dropped.' ;
                            }

                            enum terminated {
                              value 2 ;
                              description 'ERPS protocol packet filtering is terminated.' ;
                            }

                          }

                        }

                        leaf udld {
                          description 'UDLD protocol packet filtering.' ;
                          type enumeration {
                            enum tunnelled {
                              value 0 ;
                              description 'UDLD protocol packet filtering is tunnelled.' ;
                            }

                            enum dropped {
                              value 1 ;
                              description 'UDLD protocol packet filtering is dropped.' ;
                            }

                            enum terminated {
                              value 2 ;
                              description 'UDLD protocol packet filtering is terminated.' ;
                            }

                          }

                        }

                        leaf vtp {
                          description 'VTP protocol packet filtering.' ;
                          type enumeration {
                            enum tunnelled {
                              value 0 ;
                              description 'VTP protocol packet filtering is tunnelled.' ;
                            }

                            enum dropped {
                              value 1 ;
                              description 'VTP protocol packet filtering is dropped.' ;
                            }

                            enum terminated {
                              value 2 ;
                              description 'VTP protocol packet filtering is terminated.' ;
                            }

                          }

                        }

                        leaf zesr {
                          description 'ZESR protocol packet filtering.' ;
                          type enumeration {
                            enum tunnelled {
                              value 0 ;
                              description 'ZESR protocol packet filtering is tunnelled.' ;
                            }

                            enum dropped {
                              value 1 ;
                              description 'ZESR protocol packet filtering is dropped.' ;
                            }

                            enum terminated {
                              value 2 ;
                              description 'ZESR protocol packet filtering is terminated.' ;
                            }

                          }

                        }

                        leaf l2bfd {
                          description 'L2BFD protocol packet filtering.' ;
                          type enumeration {
                            enum tunnelled {
                              value 0 ;
                              description 'L2BFD protocol packet filtering is tunnelled.' ;
                            }

                            enum terminated {
                              value 2 ;
                              description 'L2BFD protocol packet filtering is terminated.' ;
                            }

                          }

                        }

                        leaf mac-control {
                          description 'MAC-control protocol packet filtering.' ;
                          type enumeration {
                            enum tunnelled {
                              value 0 ;
                              description 'MAC-control protocol packet filtering is tunnelled.' ;
                            }

                            enum dropped {
                              value 1 ;
                              description 'MAC-control protocol packet filtering is dropped.' ;
                            }

                            enum terminated {
                              value 2 ;
                              description 'MAC-control protocol packet filtering is terminated.' ;
                            }

                          }

                          ncd:revise-date 2023-03-25 ;
                        }

                        container user-protocol-template {
                          description 'The template of user protocol.' ;
                          presence user-protocol-template ;
                          leaf user-protocol-name {
                            description 'The class name of user protocol.' ;
                            type string {
                              length 1..31 {
                                description 'The length of user protocol class name.' ;
                              }

                            }

                            mandatory true ;
                          }

                          leaf user-protocol-action {
                            description 'User protocol template action.' ;
                            type enumeration {
                              enum tunnelled {
                                value 0 ;
                                description 'User protocol template action is tunnelled.' ;
                              }

                              enum dropped {
                                value 1 ;
                                description 'User protocol template action is dropped.' ;
                              }

                              enum terminated {
                                value 2 ;
                                description 'User protocol template action is terminated.' ;
                              }

                            }

                            mandatory true ;
                          }

                        }

                        ncd:revise-date 2021-06-07 ;
                      }

                    }

                  }

                }

              }

            }

            container vpws-vxlan-static-vxlans {
              description 'VPWS VXLAN static VXLAN configuration info.' ;
              presence vpws-vxlan-static-vxlan ;
              list static-vxlan {
                description 'The static VXLAN configuration info.' ;
                key static-vni ;
                leaf static-vni {
                  description 'Static VNI value.' ;
                  type uint32 {
                    range 1..16777215 ;

                  }

                }

                leaf remote-vni {
                  description 'Remote VNI value.' ;
                  type uint32 {
                    range 1..16777215 ;

                  }

                }

                container static-tunnel-bind {
                  description 'Static tunnel bind table.' ;
                  presence static-tunnel-bind ;
                  leaf static-tunnel-name {
                    description 'Static tunnel interface name.' ;
                    type ncd:ifname ;

                    mandatory true ;
                  }

                }

              }

              ncd:revise-date 2018-08-27 ;
            }

          }

          ncd:revise-date 2018-07-08 ;
        }

        container b-vpls-instances {
          description 'The B-VPLS instances configuration info.' ;
          list b-vpls-instance {
            description 'The B-VPLS instance configuration info.' ;
            key instance-name ;
            leaf instance-name {
              description 'The name of the B-VPLS instance.' ;
              type string {
                length 1..32 {
                  description 'The length of instance name.' ;
                }

              }

            }

            leaf description {
              description 'The description of the B-VPLS instance.' ;
              type ncd:string-with-blank {
                length 1..104 {
                  description 'The description range of instance.' ;
                }

              }

              ncd:revise-date 2022-07-26 ;
            }

            leaf default-vcid {
              description 'The default VCID of the B-VPLS instance.' ;
              type uint32 {
                range 1..4294967295 {
                  description 'The instance default VCID value.' ;
                }

              }

              ncd:revise-date 2022-12-05 ;
            }

            leaf mtu {
              description 'The MTU value of the B-VPLS instance.' ;
              type uint16 {
                range 60..65535 {
                  description 'The range of MTU.' ;
                }

              }

              default 1500 ;
              ncd:revise-date 2022-12-05 ;
            }

            leaf mac-withdraw {
              description 'The MAC-withdraw capability of the B-VPLS instance.' ;
              type enumeration {
                enum disable {
                  value 0 ;
                  description 'The MAC-withdraw is disable.' ;
                }

                enum enable {
                  value 1 ;
                  description 'The MAC-withdraw is enable.' ;
                }

              }

              default disable ;
              ncd:revise-date 2022-12-05 ;
            }

            leaf default-cword {
              description 'The default control-word capability of the B-VPLS instance.' ;
              type enumeration {
                enum not-preferred {
                  value 0 ;
                  description 'Default cword is not preferred.' ;
                }

                enum preferred {
                  value 1 ;
                  description 'Default cword is preferred.' ;
                }

              }

              default not-preferred ;
              ncd:revise-date 2022-12-05 ;
            }

            leaf mtu-mismatch-ignore {
              description 'Ignore the MTU mismatch in the PW negotiation.' ;
              type empty ;

              ncd:revise-date 2022-12-05 ;
            }

            leaf mac-withdraw-optimized-options {
              type enumeration {
                enum disable {
                  value 0 ;
                  description 'MAC-withdraw optimized-options disable.' ;
                }

                enum enable {
                  value 1 ;
                  description 'MAC-withdraw optimized-options enable.' ;
                }

              }

              description 'MAC-withdraw optimized-options in RFC 7361.' ;
              default disable ;
              ncd:revise-date 2024-07-10 ;
            }

            leaf unknown-mac-withdraw-mode {
              type enumeration {
                enum disable {
                  value 0 ;
                  description 'The unknown-mac-withdraw-mode is disable.' ;
                }

                enum flush-all-but-mine {
                  value 1 ;
                  description 'The unknown-mac-withdraw-mode is flush-all-but-mine.' ;
                }

                enum flush-all-from-me {
                  value 2 ;
                  description 'The unknown-mac-withdraw-mode is flush-all-but-me.' ;
                }

              }

              description 'Config MAC-withdraw unknown message dispose mode.' ;
              default disable ;
              ncd:revise-date 2024-07-10 ;
            }

            container b-vpls-ds-mode {
              description 'The DS mode of the B-VPLS instance.' ;
              leaf ds-mode {
                description 'The DS service mode of the B-VPLS instance.' ;
                type enumeration {
                  enum uniform {
                    value 1 ;
                    description 'DS mode is uniform.' ;
                  }

                  enum pipe {
                    value 2 ;
                    description 'DS mode is pipe.' ;
                  }

                  enum shortPipe {
                    value 3 ;
                    description 'DS mode is shortPipe.' ;
                  }

                }

              }

              leaf service-class {
                description 'The DS service class of the B-VPLS instance.' ;
                type enumeration {
                  enum be {
                    value 1 ;
                    description 'The DS service class is be.' ;
                  }

                  enum af1 {
                    value 2 ;
                    description 'The DS service class is af1.' ;
                  }

                  enum af2 {
                    value 3 ;
                    description 'The DS service class is af2.' ;
                  }

                  enum af3 {
                    value 4 ;
                    description 'The DS service class is af3.' ;
                  }

                  enum af4 {
                    value 5 ;
                    description 'The DS service class is af4.' ;
                  }

                  enum ef {
                    value 6 ;
                    description 'The DS service class is ef.' ;
                  }

                  enum cs6 {
                    value 7 ;
                    description 'The DS service class is cs6.' ;
                  }

                  enum cs7 {
                    value 8 ;
                    description 'The DS service class is cs7.' ;
                  }

                }

              }

              leaf colour {
                description 'The DS packet colour of the B-VPLS instance.' ;
                type enumeration {
                  enum green {
                    value 1 ;
                    description 'The DS packet colour is green.' ;
                  }

                  enum yellow {
                    value 2 ;
                    description 'The DS packet colour is yellow.' ;
                  }

                  enum red {
                    value 3 ;
                    description 'The DS packet colour is red.' ;
                  }

                }

              }

              ncd:revise-date 2022-12-05 ;
            }

            container b-vpls-rd {
              status obsolete {
                ncd:revise-date 2023-08-16 ;
              }

              description 'B-VPLS route distinguisher parameters.' ;
              presence b-vpls-rd ;
              leaf rd {
                description 'The route distinguisher parameter.' ;
                type union {
                  type ncd:asn-nn ;

                  type ncd:ipadd-nn ;

                }

                mandatory true ;
                status obsolete {
                  ncd:revise-date 2023-08-16 ;
                }

              }

            }

            container auto-discovery-type {
              status obsolete {
                ncd:revise-date 2023-08-16 ;
              }

              description 'The auto-discovery type of B-VPLS instance.' ;
              choice type {
                status obsolete {
                  ncd:revise-date 2023-08-16 ;
                }

                description 'The auto-discovery type of B-VPLS instance.' ;
                case pbb-evpn {
                  description 'The PBB EVPN auto-discovery type.' ;
                  container pbb-evpn-params {
                    status obsolete {
                      ncd:revise-date 2023-08-16 ;
                    }

                    description 'The parameters of PBB EVPN type.' ;
                    presence pbb-evpn-params ;
                    leaf mode {
                      description 'The PBB EVPN mode of B-VPLS instance.' ;
                      type enumeration {
                        enum pbb-evpn {
                          value 1 ;
                          description 'The mode is PBB EVPN.' ;
                        }

                      }

                      mandatory true ;
                      status obsolete {
                        ncd:revise-date 2023-08-16 ;
                      }

                    }

                    container route-target-params {
                      description 'The route target parameters.' ;
                      list route-target {
                        description 'The route target.' ;
                        key 'rt-value effect-type' ;
                        leaf rt-value {
                          description 'RT attribute value.' ;
                          type union {
                            type ncd:asn-nn ;

                            type ncd:ipadd-nn ;

                          }

                          status obsolete {
                            ncd:revise-date 2023-08-16 ;
                          }

                        }

                        leaf effect-type {
                          description 'The route target effect type.' ;
                          type enumeration {
                            enum export {
                              value 2 ;
                              description 'The route target effect type is export.' ;
                            }

                            enum import {
                              value 3 ;
                              description 'The route target effect type is import.' ;
                            }

                          }

                          status obsolete {
                            ncd:revise-date 2023-08-16 ;
                          }

                        }

                        status obsolete {
                          ncd:revise-date 2023-08-16 ;
                        }

                      }

                      status obsolete {
                        ncd:revise-date 2023-08-16 ;
                      }

                    }

                  }

                }

              }

            }

            container bum-bmac {
              status obsolete {
                ncd:revise-date 2023-08-16 ;
              }

              description 'BUM-BMAC configuration info.' ;
              presence bum-bmac ;
              leaf bum-bmac {
                description 'The BUM-BMAC address.' ;
                type ncd:mac-address-none-zero ;

                mandatory true ;
                status obsolete {
                  ncd:revise-date 2023-08-16 ;
                }

              }

            }

            container customer-backbone-point {
              description 'Customer Backbone Point (CBP) parameters.' ;
              list backbone-point {
                description 'Bind a CBP to the B-VPLS instance.' ;
                key cbp ;
                leaf cbp {
                  description 'The name of the CBP interface.' ;
                  type ncd:ifname ;

                }

                container pbb-params {
                  description 'PBB access type parameters.' ;
                  presence pbb-params ;
                  leaf pbb {
                    description 'Configure Provider Backbone Bridge (PBB) parameters.' ;
                    type empty ;

                    mandatory true ;
                  }

                }

              }

              ncd:revise-date 2022-07-26 ;
            }

            container b-vpls-pw-bind {
              description 'B-VPLS PW binding instance info.' ;
              list pw-instance-bind {
                description 'PW binding instance configuration info.' ;
                key pw-name ;
                leaf pw-name {
                  description 'The name of the PW.' ;
                  type ncd:ifname ;

                }

                leaf split-horizon {
                  description 'The split-horizon flag of the PW bind.' ;
                  type enumeration {
                    enum spoke {
                      value 0 ;
                      description 'The split-horizon flag is spoke.' ;
                    }

                    enum hub {
                      value 1 ;
                      description 'The split-horizon flag is hub.' ;
                    }

                  }

                  mandatory true ;
                }

                leaf split-horizon-scopes {
                  description 'The split-horizon scope of PW bind.' ;
                  type string {
                    length 1..51 {
                      description 'The length of split-horizon-scopes.' ;
                    }

                  }

                }

              }

              ncd:revise-date 2022-07-26 ;
            }

            container traffic-statistics-params {
              if-feature instances-traffic-statistics ;

              description 'The traffic statistics parameters of B-VPLS instance.' ;
              leaf traffic-enable {
                description 'The traffic statistics status of B-VPLS service.' ;
                type enumeration {
                  enum disable {
                    value 0 ;
                    description 'The traffic statistics status of B-VPLS service is disable.' ;
                  }

                  enum enable {
                    value 1 ;
                    description 'The traffic statistics status of B-VPLS service is enable.' ;
                  }

                }

                default disable ;
              }

              leaf unicast-inrate-bps {
                description 'The unicast input bytes rate.' ;
                type uint64 {
                  range 1..18446744073709551615 {
                    description 'The range of unicast input bytes.' ;
                  }

                }

                units bps ;
              }

              leaf unicast-inrate-pps {
                description 'The unicast input packets rate.' ;
                type uint32 {
                  range 1..4294967295 {
                    description 'The range of unicast input packets rate.' ;
                  }

                }

                units pps ;
              }

              leaf broadcast-inrate-bps {
                description 'The broadcast input bytes rate.' ;
                type uint64 {
                  range 1..18446744073709551615 {
                    description 'The range of broadcast input bytes.' ;
                  }

                }

                units bps ;
              }

              leaf broadcast-inrate-pps {
                description 'The broadcast input packets rate.' ;
                type uint32 {
                  range 1..4294967295 {
                    description 'The range of broadcast input packets rate.' ;
                  }

                }

                units pps ;
              }

              leaf drop-inrate-bps {
                description 'The drop input bytes rate.' ;
                type uint64 {
                  range 1..18446744073709551615 {
                    description 'The range of drop input bytes.' ;
                  }

                }

                units bps ;
              }

              leaf drop-inrate-pps {
                description 'The drop input packets rate.' ;
                type uint32 {
                  range 1..4294967295 {
                    description 'The range of drop input packets rate.' ;
                  }

                }

                units pps ;
              }

              ncd:revise-date 2022-12-05 ;
            }

          }

          ncd:revise-date 2018-07-25 ;
        }

        container i-vpls-instances {
          description 'The I-VPLS instances configuration info.' ;
          list i-vpls-instance {
            description 'The I-VPLS instance configuration info.' ;
            key instance-name ;
            leaf instance-name {
              description 'The name of the I-VPLS instance.' ;
              type string {
                length 1..32 {
                  description 'The length of instance name.' ;
                }

              }

            }

            leaf df-election {
              status obsolete {
                ncd:revise-date 2023-08-16 ;
              }

              description 'DF election rule per EVI (preference-based mode).' ;
              type enumeration {
                enum lowest-preference {
                  value 1 ;
                  description 'The adjacent-node with lowest-preference is DF.' ;
                }

                enum highest-preference {
                  value 2 ;
                  description 'The adjacent-node with highest-preference is DF.' ;
                }

              }

            }

            leaf default-encapsulation {
              description 'The default encapsulation of the I-VPLS instance.' ;
              type enumeration {
                enum tagged {
                  value 4 ;
                  description 'The default encapsulation is tagged.' ;
                }

                enum raw {
                  value 5 ;
                  description 'The default encapsulation is raw.' ;
                }

              }

              ncd:revise-date 2022-07-26 ;
            }

            leaf description {
              description 'The description of the I-VPLS instance.' ;
              type ncd:string-with-blank {
                length 1..104 {
                  description 'The description range of instance.' ;
                }

              }

              ncd:revise-date 2022-07-26 ;
            }

            container i-vpls-ac-bind {
              description 'I-VPLS AC binding instance info.' ;
              list ac-instance-bind {
                description 'AC binding instance configuration info.' ;
                key ac-name ;
                leaf ac-name {
                  description 'The name of the AC in the bind.' ;
                  type ncd:ifname {
                    length 1..31 {
                      description 'The length of AC name.' ;
                    }

                  }

                }

                leaf description {
                  description 'The description of the interface.' ;
                  type ncd:string-with-blank {
                    length 1..104 {
                      description 'The description range of interface.' ;
                    }

                  }

                }

                choice ac-type {
                  description 'The access type of I-VPLS instance.' ;
                  case ethernet {
                    description 'The ethernet access type.' ;
                    container ethernet-params {
                      description 'Ethernet access type parameters.' ;
                      presence ethernet-params ;
                      leaf ethernet {
                        description 'Ethernet access type.' ;
                        type empty ;

                        mandatory true ;
                      }

                      leaf ingress-adjust-tag-as-payload {
                        description 'The ingress tag as payload flag of the ethernet parameter.' ;
                        type enumeration {
                          enum disable {
                            value 0 ;
                            description 'The ingress tag as payload flag is disable.' ;
                          }

                          enum all {
                            value 1 ;
                            description 'The ingress tag as payload flag is from outer most.' ;
                          }

                          enum from-sub-layer {
                            value 2 ;
                            description 'The ingress tag as payload flag is from sub layer.' ;
                          }

                        }

                        default disable ;
                      }

                      leaf ingress-adjust-drop-tagged-frames {
                        description 'The ingress adjust drop tagged frames flag of the ethernet.' ;
                        type enumeration {
                          enum disable {
                            value 0 ;
                            description 'The ingress adjust drop tagged frames flag is disable.' ;
                          }

                          enum enable {
                            value 1 ;
                            description 'The ingress adjust drop tagged frames flag is enable.' ;
                          }

                        }

                        ncd:revise-date 2023-03-10 ;
                      }

                      leaf traffic-enable {
                        type enumeration {
                          enum disable {
                            value 0 ;
                            description 'The traffic statistics flag is disable.' ;
                          }

                          enum enable {
                            value 1 ;
                            description 'The traffic statistics flag is enable.' ;
                          }

                        }

                        description 'The traffic statistics enable flag of the ethernet parameter.' ;
                        default disable ;
                        ncd:revise-date 2024-06-28 ;
                      }

                      container ingress-adjust-push-params {
                        description 'The ingress adjust push parameters of the ethernet parameter.' ;
                        leaf ingress-adjust-push {
                          description 'The ingress adjust push flag of the ethernet parameter.' ;
                          type enumeration {
                            enum disable {
                              value 0 ;
                              description 'The ingress adjust push flag of the ethernet parameter is disable.' ;
                            }

                            enum enable {
                              value 1 ;
                              description 'The ingress adjust push flag of the ethernet parameter is enable.' ;
                            }

                          }

                          default disable ;
                        }

                        leaf push-vlan-id {
                          description 'The ingress adjust push VLAN ID of the ethernet parameter.' ;
                          type uint16 {
                            range 1..4094 {
                              description 'The range of push VLAN ID is 1-4094.' ;
                            }

                          }

                        }

                        ncd:revise-date 2022-07-26 ;
                      }

                      container ingress-adjust-rewrite-params {
                        description 'The ingress adjust rewrite parameters of the ethernet parameter.' ;
                        leaf ingress-adjust-rewrite {
                          description 'The ingress adjust rewrite flag of the ethernet parameter.' ;
                          type enumeration {
                            enum disable {
                              value 0 ;
                              description 'The ingress adjust rewrite flag of the ethernet parameter is disable.' ;
                            }

                            enum enable {
                              value 1 ;
                              description 'The ingress adjust rewrite flag of the ethernet parameter is enable.' ;
                            }

                          }

                          default disable ;
                        }

                        leaf rewrite-vlan-id {
                          description 'The ingress adjust rewrite VLAN ID of the ethernet parameter.' ;
                          type uint16 {
                            range 1..4094 {
                              description 'The range of rewrite VLAN ID is 1-4094.' ;
                            }

                          }

                        }

                        ncd:revise-date 2022-07-26 ;
                      }

                      container traffic-statistics-params {
                        if-feature ac-traffic-statistics ;

                        leaf unicast-inrate-bps {
                          type uint64 {
                            range 1..18446744073709551615 {
                              description 'The range of unicast input bytes.' ;
                            }

                          }

                          description 'The unicast input bytes rate.' ;
                          units bps ;
                        }

                        leaf unicast-inrate-pps {
                          type uint32 {
                            range 1..4294967295 {
                              description 'The range of unicast input packets rate.' ;
                            }

                          }

                          description 'The unicast input packets rate.' ;
                          units pps ;
                        }

                        leaf broadcast-inrate-bps {
                          type uint64 {
                            range 1..18446744073709551615 {
                              description 'The range of broadcast input bytes.' ;
                            }

                          }

                          description 'The broadcast input bytes rate.' ;
                          units bps ;
                        }

                        leaf broadcast-inrate-pps {
                          type uint32 {
                            range 1..4294967295 {
                              description 'The range of broadcast input packets rate.' ;
                            }

                          }

                          description 'The broadcast input packets rate.' ;
                          units pps ;
                        }

                        leaf drop-inrate-bps {
                          type uint64 {
                            range 1..18446744073709551615 {
                              description 'The range of drop input bytes.' ;
                            }

                          }

                          description 'The drop input bytes rate.' ;
                          units bps ;
                        }

                        leaf drop-inrate-pps {
                          type uint32 {
                            range 1..4294967295 {
                              description 'The range of drop input packets rate.' ;
                            }

                          }

                          description 'The drop input packets rate.' ;
                          units pps ;
                        }

                        description 'The traffic statistics parameters of ethernet access.' ;
                        ncd:revise-date 2024-06-28 ;
                      }

                    }

                  }

                }

              }

            }

            container i-vpls-smart-vlan-bind {
              status obsolete {
                ncd:revise-date 2023-08-16 ;
              }

              description 'I-VPLS smart VLAN binding instance info.' ;
              list smart-vlan-bind {
                description 'I-VPLS smart VLAN binding instance info.' ;
                key smart-vlan-id ;
                leaf smart-vlan-id {
                  description 'Smart VLAN ID.' ;
                  type uint32 {
                    range 1..16777215 {
                      description 'The length of smart VLAN ID.' ;
                    }

                  }

                  status obsolete {
                    ncd:revise-date 2023-08-16 ;
                  }

                }

                leaf encapsulation {
                  description 'Specify encapsulation mode for smart VLAN.' ;
                  type enumeration {
                    enum i-sid {
                      value 1 ;
                      description 'The type of smart VLAN is I-SID' ;
                    }

                  }

                  status obsolete {
                    ncd:revise-date 2023-08-16 ;
                  }

                }

                container backbone {
                  description 'The binding of B-VPLS instance.' ;
                  presence backbone ;
                  leaf b-vpls-instance-name {
                    description 'The name of B-VPLS instance.' ;
                    type string {
                      length 1..32 {
                        description 'The length of instance name.' ;
                      }

                    }

                    mandatory true ;
                    status obsolete {
                      ncd:revise-date 2023-08-16 ;
                    }

                  }

                  status obsolete {
                    ncd:revise-date 2023-08-16 ;
                  }

                }

                status obsolete {
                  ncd:revise-date 2023-08-16 ;
                }

              }

            }

            container i-vpls-service-delimiter {
              description 'The normalized identifier among all PEs of the I-VPLS.' ;
              list service-delimiter {
                description 'The normalized identifier among all PEs of the I-VPLS.' ;
                key 'b-vpls-instance-name delimiter-id' ;
                leaf b-vpls-instance-name {
                  description 'The name of B-VPLS instance.' ;
                  type string {
                    length 1..31 {
                      description 'The length of instance name.' ;
                    }

                  }

                }

                leaf delimiter-id {
                  description 'Service delimiter ID.' ;
                  type uint32 {
                    range 1..16777214 {
                      description 'The length of delimiter ID.' ;
                    }

                  }

                }

                container encapsulation-as-i-sid {
                  description 'Specify delimiter encapsulation mode.' ;
                  presence backbone ;
                  leaf i-sid {
                    description 'The Service Instance ID (I-SID) for PBB I-Component.' ;
                    type empty ;

                    mandatory true ;
                  }

                  leaf source-bmac {
                    description 'The source B-MAC address.' ;
                    type ncd:mac-address-none-zero ;

                  }

                  leaf bum-bmac {
                    description 'The destination B-MAC address for BUM traffic.' ;
                    type ncd:mac-address-none-zero ;

                  }

                }

              }

              ncd:revise-date 2022-07-26 ;
            }

            container traffic-statistics-params {
              description 'The traffic statistics parameters of I-VPLS instance.' ;
              if-feature instances-traffic-statistics ;

              leaf traffic-enable {
                type enumeration {
                  enum disable {
                    value 0 ;
                    description 'The traffic statistics status of I-VPLS service is disable.' ;
                  }

                  enum enable {
                    value 1 ;
                    description 'The traffic statistics status of I-VPLS service is enable.' ;
                  }

                }

                description 'The traffic statistics status of I-VPLS service.' ;
                default disable ;
              }

              leaf unicast-inrate-bps {
                type uint64 {
                  range 1..18446744073709551615 {
                    description 'The range of unicast input bytes.' ;
                  }

                }

                description 'The unicast input bytes rate.' ;
                units bps ;
              }

              leaf unicast-inrate-pps {
                type uint32 {
                  range 1..4294967295 {
                    description 'The range of unicast input packets rate.' ;
                  }

                }

                description 'The unicast input packets rate.' ;
                units pps ;
              }

              leaf broadcast-inrate-bps {
                type uint64 {
                  range 1..18446744073709551615 {
                    description 'The range of broadcast input bytes.' ;
                  }

                }

                description 'The broadcast input bytes rate.' ;
                units bps ;
              }

              leaf broadcast-inrate-pps {
                type uint32 {
                  range 1..4294967295 {
                    description 'The range of broadcast input packets rate.' ;
                  }

                }

                description 'The broadcast input packets rate.' ;
                units pps ;
              }

              leaf drop-inrate-bps {
                type uint64 {
                  range 1..18446744073709551615 {
                    description 'The range of drop input bytes.' ;
                  }

                }

                description 'The drop input bytes rate.' ;
                units bps ;
              }

              leaf drop-inrate-pps {
                description 'The drop input packets rate.' ;
                type uint32 {
                  range 1..4294967295 {
                    description 'The range of drop input packets rate.' ;
                  }

                }

                units pps ;
              }

              ncd:revise-date 2024-06-28 ;
            }

          }

          ncd:revise-date 2018-07-25 ;
        }

        container ring-tree-instances {
          description 'The ring-tree instances configuration info.' ;
          list ring-tree-instance {
            description 'The ring-tree instance configuration info.' ;
            key instance-name ;
            leaf instance-name {
              description 'The name of the ring-tree instance.' ;
              type string {
                length 1..32 {
                  description 'The length of instance name.' ;
                }

              }

            }

            leaf description {
              description 'The description of the ring-tree instance.' ;
              type ncd:string-with-blank {
                length 1..104 {
                  description 'The description range of instance.' ;
                }

              }

            }

            leaf shutdown {
              description 'The enable status of the ring-tree instance.' ;
              type enumeration {
                enum disable {
                  value 0 ;
                  description 'The status of the ring-tree instance is disable.' ;
                }

                enum enable {
                  value 1 ;
                  description 'The status of the ring-tree instance is enable.' ;
                }

              }

              default enable ;
            }

            leaf mtu {
              description 'The MTU value of the ring-tree instance.' ;
              type uint16 {
                range 60..65535 {
                  description 'The range of MTU.' ;
                }

              }

              default 1500 ;
            }

            leaf switch-cmd {
              description 'Switch command of ring-tree APS.' ;
              type enumeration {
                enum clear {
                  value 1 ;
                  description 'Ring-tree APS switch command is clear.' ;
                }

                enum lock-out {
                  value 2 ;
                  description 'Ring-tree APS switch command is lock out of protect.' ;
                }

                enum fs-p {
                  value 3 ;
                  description 'Ring-tree APS switch command is force switch of protect.' ;
                }

                enum ms-p {
                  value 4 ;
                  description 'Ring-tree APS switch command is manual switch of protect.' ;
                }

                enum ms-w {
                  value 5 ;
                  description 'Ring-tree APS switch command is manual switch of work.' ;
                }

                enum exercise {
                  value 7 ;
                  description 'Ring-tree APS switch command is exercise.' ;
                }

              }

              ncd:revise-date 2019-09-02 ;
            }

            container revertive-mode-params {
              description 'The params of revertive-mode.' ;
              leaf revertive-mode {
                description 'The revertive-mode of the ring-tree instance.' ;
                type enumeration {
                  enum non-revertive {
                    value 0 ;
                    description 'The revertive-mode is non-revertive.' ;
                  }

                  enum revertive {
                    value 1 ;
                    description 'The revertive-mode is revertive.' ;
                  }

                }

                default revertive ;
              }

              leaf wtr-time {
                type uint8 {
                  range 0..12 {
                    description 'The length of WTR time in minute.' ;
                  }

                }

                description 'Set minutes in WTR. Requires setting wtr-second-with-minute node simultaneously. The range is 0-12(minutes).' ;
                default 5 ;
                units min ;
              }

              leaf wtr-second-with-minute {
                type uint8 {
                  range 0..59 {
                    description 'The length of WTR second time in minute.' ;
                  }

                }

                description 'Set seconds in WTR. Requires setting wtr-time node simultaneously. The range is 0-59(seconds).' ;
                units second ;
                if-feature wtr-second ;

                ncd:revise-date 2024-08-13 ;
              }

              leaf second {
                type uint32 {
                  range 0..720 {
                    description 'The length of WTR time in second.' ;
                  }

                }

                if-feature wtr-second ;

                description 'Set seconds in WTR. Cannot be configured simultaneously with wtr-time node or wtr-second-with-minute node. The range is 0-720(seconds). ' ;
                units second ;
                ncd:revise-date 2023-12-12 ;
              }

            }

            container traffic-statistics-params {
              description 'The traffic statistics parameters of ring-tree instance.' ;
              leaf traffic-enable {
                description 'The traffic statistics status of ring-tree service.' ;
                type enumeration {
                  enum disable {
                    value 0 ;
                    description 'The traffic statistics status of ring-tree service is disable.' ;
                  }

                  enum enable {
                    value 1 ;
                    description 'The traffic statistics status of ring-tree service is enable.' ;
                  }

                }

                default disable ;
              }

            }

            container ring-tree-pw-bind {
              description 'Ring-tree PW binding instance info.' ;
              list pw-instance-bind {
                description 'PW binding instance configuration info.' ;
                key pw-name ;
                leaf pw-name {
                  description 'The name of the PW in the bind.' ;
                  type ncd:ifname ;

                }

              }

            }

            container ring-tree-ac-bind {
              description 'Ring-tree AC binding instance info.' ;
              list ac-instance-bind {
                description 'AC binding instance configuration info.' ;
                key ac-name ;
                leaf ac-name {
                  description 'The name of the AC in the bind.' ;
                  type ncd:ifname ;

                }

                leaf description {
                  description 'The description of the interface.' ;
                  type ncd:string-with-blank {
                    length 1..104 {
                      description 'The description range of interface.' ;
                    }

                  }

                }

                choice ac-type {
                  description 'The access type of ring-tree instance and  the ring-tree only supports Ethernet access.' ;
                  case ethernet {
                    description 'The ethernet access type.' ;
                    container ethernet-params {
                      description 'Ethernet access type parameters.' ;
                      presence ethernet-params ;
                      leaf ethernet {
                        description 'Ethernet access type.' ;
                        type empty ;

                        mandatory true ;
                      }

                      leaf track-name {
                        description 'The name of the track object which bind to the AC.' ;
                        type string {
                          length 1..31 {
                            description 'The length of track name.' ;
                          }

                        }

                      }

                      leaf traffic-enable {
                        description 'The traffic statistics enable flag of the ethernet parameter.' ;
                        type enumeration {
                          enum disable {
                            value 0 ;
                            description 'The traffic statistics flag is disable.' ;
                          }

                          enum enable {
                            value 1 ;
                            description 'The traffic statistics flag is enable.' ;
                          }

                        }

                        default disable ;
                      }

                      leaf node-role {
                        description 'The node-role of ring-tree instance.' ;
                        type enumeration {
                          enum common-leaf {
                            value 0 ;
                            description 'The node-role of ring-tree is common-leaf.' ;
                          }

                          enum work-root {
                            value 1 ;
                            description 'The node-role of ring-tree is work-root.' ;
                          }

                          enum protect-root {
                            value 2 ;
                            description 'The node-role of ring-tree is protect-root.' ;
                          }

                          enum work-leaf {
                            value 3 ;
                            description 'The node-role of ring-tree is work-leaf.' ;
                          }

                          enum protect-leaf {
                            value 4 ;
                            description 'The node-role of ring-tree is protect-leaf.' ;
                          }

                        }

                        default common-leaf ;
                      }

                      container ingress-adjust-push-params {
                        description 'The ingress adjust push parameters of the ethernet parameter.' ;
                        leaf ingress-adjust-push {
                          description 'The ingress adjust push flag of the ethernet parameter.' ;
                          type enumeration {
                            enum disable {
                              value 0 ;
                              description 'The ingress adjust push flag of the ethernet parameter is disable.' ;
                            }

                            enum enable {
                              value 1 ;
                              description 'The ingress adjust push flag of the ethernet parameter is enable.' ;
                            }

                          }

                          default disable ;
                        }

                        leaf push-vlan-id {
                          description 'The ingress adjust push VLAN ID of the ethernet parameter.' ;
                          type uint16 {
                            range 1..4094 {
                              description 'The range of push VLAN ID is 1-4094.' ;
                            }

                          }

                        }

                      }

                      container ingress-adjust-rewrite-params {
                        description 'The ingress adjust rewrite parameters of the ethernet parameter.' ;
                        leaf ingress-adjust-rewrite {
                          description 'The ingress adjust rewrite flag of the ethernet parameter.' ;
                          type enumeration {
                            enum disable {
                              value 0 ;
                              description 'The ingress adjust rewrite flag of the ethernet parameter is disable.' ;
                            }

                            enum enable {
                              value 1 ;
                              description 'The ingress adjust rewrite flag of the ethernet parameter is enable.' ;
                            }

                          }

                          default disable ;
                        }

                        leaf rewrite-vlan-id {
                          description 'The ingress adjust rewrite VLAN ID of the ethernet parameter.' ;
                          type uint16 {
                            range 1..4094 {
                              description 'The range of rewrite VLAN ID is 1-4094.' ;
                            }

                          }

                        }

                      }

                      leaf ingress-adjust-drop-tagged-frames {
                        description 'The ingress adjust drop tagged frames flag of the ethernet.' ;
                        type enumeration {
                          enum disable {
                            value 0 ;
                            description 'The ingress adjust drop tagged frames flag is disable.' ;
                          }

                          enum enable {
                            value 1 ;
                            description 'The ingress adjust drop tagged frames flag is enable.' ;
                          }

                        }

                        default disable ;
                      }

                      leaf ingress-adjust-tag-as-payload {
                        description 'The ingress tag as payload flag of the ethernet parameter.' ;
                        type enumeration {
                          enum disable {
                            value 0 ;
                            description 'The ingress tag as payload flag is disable.' ;
                          }

                          enum all {
                            value 1 ;
                            description 'The ingress tag as payload flag is from outer most.' ;
                          }

                          enum from-sub-layer {
                            value 2 ;
                            description 'The ingress tag as payload flag is from sub layer.' ;
                          }

                        }

                        default disable ;
                      }

                    }

                  }

                }

              }

            }

          }

          ncd:revise-date 2018-09-07 ;
        }

        container l2vpn-p2p-services {
          description 'The L2VPN P2P instances configuration info.' ;
          list l2vpn-p2p-service {
            description 'The L2VPN P2P instance configuration info.' ;
            key instance-name ;
            leaf instance-name {
              description 'The name of the L2VPN P2P instance, it must be a number of 1-4294967295.' ;
              type string {
                length 1..10 {
                  description 'The length of instance name.' ;
                }

              }

            }

            leaf instance-description {
              description 'The description of the instance.' ;
              type ncd:string-with-blank {
                length 1..104 {
                  description 'The description range of instance.' ;
                }

              }

            }

            leaf encapsulation {
              description 'The encapsulation of instance.' ;
              type enumeration {
                enum tagged {
                  value 4 ;
                  description 'The encapsulation is tagged.' ;
                }

                enum raw {
                  value 5 ;
                  description 'The encapsulation is raw.' ;
                }

              }

              default raw ;
            }

            container traffic-statistics-params {
              description 'The traffic statistics of L2VPN service.' ;
              leaf traffic-enable {
                description 'The traffic statistics status of P2P service.' ;
                type enumeration {
                  enum disable {
                    value 0 ;
                    description 'The traffic statistics status of P2P service is disable.' ;
                  }

                  enum enable {
                    value 1 ;
                    description 'The traffic statistics status of P2P service is enable.' ;
                  }

                }

                default disable ;
              }

              ncd:revise-date 2021-06-07 ;
            }

            container ds-mode-params {
              description 'The DS mode of the instance.' ;
              presence ds-mode-params ;
              leaf ds-mode {
                description 'The DS service mode.' ;
                type enumeration {
                  enum uniform {
                    value 1 ;
                    description 'DS mode is uniform.' ;
                  }

                  enum pipe {
                    value 2 ;
                    description 'DS mode is pipe.' ;
                  }

                  enum shortPipe {
                    value 3 ;
                    description 'DS mode is shortPipe.' ;
                  }

                }

                mandatory true ;
              }

              leaf service-class {
                description 'The DS service class.' ;
                type enumeration {
                  enum be {
                    value 1 ;
                    description 'The DS service class is be.' ;
                  }

                  enum af1 {
                    value 2 ;
                    description 'The DS service class is af1.' ;
                  }

                  enum af2 {
                    value 3 ;
                    description 'The DS service class is af2.' ;
                  }

                  enum af3 {
                    value 4 ;
                    description 'The DS service class is af3.' ;
                  }

                  enum af4 {
                    value 5 ;
                    description 'The DS service class is af4.' ;
                  }

                  enum ef {
                    value 6 ;
                    description 'The DS service class is ef.' ;
                  }

                  enum cs6 {
                    value 7 ;
                    description 'The DS service class is cs6.' ;
                  }

                  enum cs7 {
                    value 8 ;
                    description 'The DS service class is cs7.' ;
                  }

                }

              }

              leaf colour {
                description 'The DS packet colour.' ;
                type enumeration {
                  enum green {
                    value 1 ;
                    description 'The DS packet colour is green.' ;
                  }

                  enum yellow {
                    value 2 ;
                    description 'The DS packet colour is yellow.' ;
                  }

                  enum red {
                    value 3 ;
                    description 'The DS packet colour is red.' ;
                  }

                }

              }

            }

            container static-srv6-evpn {
              description "Static SRv6 EVPN's parameters." ;
              presence static-srv6-evpn ;
              leaf mode {
                description 'The static SRv6 EVPN mode of P2P service.' ;
                type enumeration {
                  enum static-srv6-evpn {
                    value 5 ;
                    description 'The mode is static SRv6 EVPN.' ;
                  }

                }

                mandatory true ;
              }

              leaf traffic-enable {
                type enumeration {
                  enum disable {
                    value 0 ;
                    description 'The traffic statistics status of static SRv6 EVPN is disable.' ;
                  }

                  enum enable {
                    value 1 ;
                    description 'The traffic statistics status of static SRv6 EVPN is enable.' ;
                  }

                }

                description 'The traffic statistics status of static SRv6 EVPN.' ;
                default disable ;
                ncd:revise-date 2023-12-11 ;
              }

              container vpws-id-params {
                description 'VPWS ID parameters.' ;
                presence vpws-id-params ;
                leaf local-vpws-id {
                  description 'The local VPWS ID.' ;
                  type uint32 {
                    range 1..4294967294 {
                      description 'The range of local VPWS ID.' ;
                    }

                  }

                  mandatory true ;
                }

                leaf remote-vpws-id {
                  description 'The remote VPWS ID.' ;
                  type uint32 {
                    range 1..4294967294 {
                      description 'The range of remote VPWS ID.' ;
                    }

                  }

                  mandatory true ;
                }

              }

              container srv6-tunnel-params {
                description 'Configure SRv6 tunnel params.' ;
                leaf srv6-best-effort {
                  description 'Select SRv6 BE.' ;
                  type empty ;

                }

                leaf srv6-traffic-engineer {
                  description 'Select SRv6 TE.' ;
                  type empty ;

                }

                ncd:revise-date 2022-03-15 ;
              }

              container srv6-local-sid-params {
                description 'The SRv6 local SID parameters.' ;
                leaf local-sid {
                  description 'The SRv6 local SID.' ;
                  type ncd:ipv6-address-none-zero ;

                }

              }

              container srv6-locator-params {
                description 'The SRv6 locator parameters.' ;
                leaf srv6-locator-name {
                  description 'The SRv6 locator name.' ;
                  type string {
                    length 1..31 {
                      description 'The length of SRv6 locator name.' ;
                    }

                  }

                }

              }

              container srv6-remote-sid-params {
                description 'The SRv6 remote SID parameters.' ;
                list srv6-remote-sid-param {
                  description 'The SRv6 remote SID parameter.' ;
                  key remote-sid ;
                  leaf remote-sid {
                    description 'The remote SRv6 SID value.' ;
                    type ncd:ipv6-address-none-zero ;

                  }

                  leaf role {
                    description 'The remote SRv6 SID role.' ;
                    type enumeration {
                      enum normal {
                        value 0 ;
                        description 'The remote SID role is normal.' ;
                      }

                      enum backup {
                        value 1 ;
                        description 'The remote SID role is backup.' ;
                      }

                      enum by-pass {
                        value 2 ;
                        description 'The remote SID role is by-pass.' ;
                      }

                    }

                    default normal ;
                  }

                  leaf local-wtr-time {
                    status obsolete {
                      ncd:revise-date 2021-11-01 ;
                    }

                    description 'Wait to restore time (default:3min).It uses the local ESI wtr.' ;
                    type uint8 {
                      range 0..12 {
                        description 'The length of wtr-time.' ;
                      }

                    }

                    units min ;
                    default 3 ;
                  }

                  leaf wtr-time {
                    type uint8 {
                      range 0..12 {
                        description 'The length of WTR time in minute.' ;
                      }

                    }

                    description 'Set minutes in WTR. Requires setting wtr-second-with-minute node simultaneously. The range is 0-12(minutes).' ;
                    units min ;
                    default 3 ;
                    ncd:revise-date 2021-11-01 ;
                  }

                  leaf wtr-second-with-minute {
                    type uint8 {
                      range 0..59 {
                        description 'The length of WTR second time in minute.' ;
                      }

                    }

                    description 'Set seconds in WTR. Requires setting wtr-time node simultaneously. The range is 0-59(seconds).' ;
                    units second ;
                    ncd:revise-date 2024-08-13 ;
                  }

                  leaf second {
                    type uint32 {
                      range 0..720 {
                        description 'The length of WTR time in second.' ;
                      }

                    }

                    description 'Set seconds in WTR. Cannot be configured simultaneously with wtr-time node or wtr-second-with-minute node. The range is 0-720(seconds). ' ;
                    units second ;
                    ncd:revise-date 2023-12-12 ;
                  }

                  container tunnel-params {
                    description 'The tunnel parameters.' ;
                    presence tunnel-params ;
                    choice type {
                      description 'Peer type.' ;
                      mandatory true ;
                      case ipv4 {
                        description 'Peer type of IPv4.' ;
                        leaf ipv4-peer {
                          description 'The peer address of IPv4 type.' ;
                          type ncd:ipv4-address-none-zero ;

                          mandatory true ;
                        }

                      }

                      case ipv6 {
                        description 'Peer type of IPv6.' ;
                        leaf ipv6-peer {
                          description 'The peer address of IPv6 type.' ;
                          type ncd:ipv6-address-none-zero ;

                          mandatory true ;
                        }

                      }

                    }

                    leaf color {
                      description 'Config color parameter.' ;
                      type uint32 {
                        range 1..4294967295 {
                          description 'The value of color.' ;
                        }

                      }

                      mandatory true ;
                    }

                  }

                  container bfd-params {
                    description 'Configure BFD parameter.' ;
                    presence bfd-params ;
                    leaf bfd {
                      description 'Configure BFD.' ;
                      type enumeration {
                        enum disable {
                          value 0 ;
                          description 'Disable BFD.' ;
                        }

                        enum enable {
                          value 1 ;
                          description 'Enable BFD.' ;
                        }

                      }

                      default disable ;
                    }

                    leaf template {
                      description 'Configure template name.' ;
                      type string {
                        length 1..31 {
                          description 'The length of BFD template name.' ;
                        }

                      }

                    }

                    container discriminator-params {
                      description 'Discriminator parameters for EVPN BFD.' ;
                      presence discriminator-params ;
                      leaf ld {
                        description 'Local discriminator for EVPN BFD,the range of this parameter depends on the device,default range 1-4294967295.' ;
                        type uint32 {
                          range 1..4294967295 {
                            description 'Local discriminator for EVPN BFD,the range of this parameter depends on the device,default range 1-4294967295.' ;
                          }

                        }

                        mandatory true ;
                      }

                      leaf rd {
                        description 'Remote discriminator for EVPN BFD.' ;
                        type uint32 {
                          range 1..4294967295 {
                            description 'Remote discriminator for EVPN BFD.' ;
                          }

                        }

                        mandatory true ;
                      }

                    }

                  }

                }

              }

            }

            container p2p-ac-bind {
              description 'P2P AC binding instance info.' ;
              list ac-instance-bind {
                description 'AC binding instance configuration info.' ;
                key ac-name ;
                leaf ac-name {
                  description 'The name of the AC interface.' ;
                  type ncd:ifname {
                    length 1..31 {
                      description 'The length of AC name.' ;
                    }

                  }

                }

                choice ac-type {
                  description 'The access type of P2P instance.' ;
                  case ethernet {
                    description 'The ethernet access type.' ;
                    container ethernet-params {
                      description 'Ethernet access type parameters.' ;
                      presence ethernet-params ;
                      leaf ethernet {
                        description 'Ethernet access type.' ;
                        type empty ;

                        mandatory true ;
                      }

                      leaf ingress-adjust-tag-as-payload {
                        description 'The ingress tag as payload flag of the ethernet parameter.' ;
                        type enumeration {
                          enum disable {
                            value 0 ;
                            description 'The ingress tag as payload flag is disable.' ;
                          }

                          enum all {
                            value 1 ;
                            description 'All of tags are payload.' ;
                          }

                          enum from-sub-layer {
                            value 2 ;
                            description 'Payload from sub-layer tag.' ;
                          }

                        }

                        default disable ;
                      }

                      leaf ingress-adjust-drop-tagged-frames {
                        description 'The ingress adjust drop tagged frames flag of the ethernet.' ;
                        type enumeration {
                          enum disable {
                            value 0 ;
                            description 'The ingress adjust drop tagged frames flag is disable.' ;
                          }

                          enum enable {
                            value 1 ;
                            description 'The ingress adjust drop tagged frames flag is enable.' ;
                          }

                        }

                        ncd:revise-date 2023-03-10 ;
                      }

                      leaf oam-mapping {
                        description 'The oam-mapping flag of the ethernet parameter.' ;
                        type enumeration {
                          enum disable {
                            value 0 ;
                            description 'The oam-mapping flag of the ethernet parameter is disable.' ;
                          }

                          enum enable {
                            value 1 ;
                            description 'The oam-mapping flag of the ethernet parameter is enable.' ;
                          }

                        }

                        default disable ;
                        ncd:revise-date 2021-11-01 ;
                      }

                      leaf track-name {
                        description 'The name of the track object which bind to the AC.' ;
                        type string {
                          length 1..31 {
                            description 'The length of the track name.' ;
                          }

                        }

                        ncd:revise-date 2021-11-01 ;
                      }

                      leaf traffic-enable {
                        description 'The traffic statistics enable flag of the ethernet parameter.' ;
                        type enumeration {
                          enum disable {
                            value 0 ;
                            description 'The traffic statistics flag is disable.' ;
                          }

                          enum enable {
                            value 1 ;
                            description 'The traffic statistics flag is enable.' ;
                          }

                        }

                        default disable ;
                        ncd:revise-date 2021-06-07 ;
                      }

                      container ingress-adjust-push-params {
                        description 'The ingress adjust push parameters of the ethernet parameter.' ;
                        leaf ingress-adjust-push {
                          description 'The ingress adjust push flag of the ethernet parameter.' ;
                          type enumeration {
                            enum disable {
                              value 0 ;
                              description 'The ingress adjust push flag of the ethernet parameter is disable.' ;
                            }

                            enum enable {
                              value 1 ;
                              description 'The ingress adjust push flag of the ethernet parameter is enable.' ;
                            }

                          }

                          default disable ;
                        }

                        leaf push-vlan-id {
                          description 'The ingress adjust push VLAN ID of the ethernet parameter.' ;
                          type uint16 {
                            range 1..4094 {
                              description 'The range of push VLAN ID is 1-4094.' ;
                            }

                          }

                        }

                      }

                      container ingress-adjust-rewrite-params {
                        description 'The ingress adjust rewrite parameters of the ethernet parameter.' ;
                        leaf ingress-adjust-rewrite {
                          description 'The ingress adjust rewrite flag of the ethernet parameter.' ;
                          type enumeration {
                            enum disable {
                              value 0 ;
                              description 'The ingress adjust rewrite flag of the ethernet parameter is disable.' ;
                            }

                            enum enable {
                              value 1 ;
                              description 'The ingress adjust rewrite flag of the ethernet parameter is enable.' ;
                            }

                          }

                          default disable ;
                        }

                        leaf rewrite-vlan-id {
                          description 'The ingress adjust rewrite VLAN ID of the ethernet parameter.' ;
                          type uint16 {
                            range 1..4094 {
                              description 'The range of rewrite VLAN ID is 1-4094.' ;
                            }

                          }

                        }

                      }

                      container l2protocol-control-policy {
                        description 'L2protocol packet filtering function.' ;
                        leaf abm {
                          description 'All bridge multicast frame protocol packet filtering.' ;
                          type enumeration {
                            enum tunnelled {
                              value 0 ;
                              description 'All bridge multicast frame protocol packet filtering is tunnelled.' ;
                            }

                            enum dropped {
                              value 1 ;
                              description 'All bridge multicast frame protocol packet filtering is dropped.' ;
                            }

                            enum terminated {
                              value 2 ;
                              description 'All bridge multicast frame protocol packet filtering is terminated.' ;
                            }

                          }

                        }

                        leaf dot1x {
                          description '802.1x protocol frame packet filtering.' ;
                          type enumeration {
                            enum tunnelled {
                              value 0 ;
                              description '802.1x protocol frame packet filtering is tunnelled.' ;
                            }

                            enum dropped {
                              value 1 ;
                              description '802.1x protocol frame packet filtering is dropped.' ;
                            }

                            enum terminated {
                              value 2 ;
                              description '802.1x protocol frame packet filtering is terminated.' ;
                            }

                          }

                        }

                        leaf dot3x {
                          description '802.3x protocol frame packet filtering.' ;
                          type enumeration {
                            enum tunnelled {
                              value 0 ;
                              description '802.3x protocol frame packet filtering is tunnelled.' ;
                            }

                            enum dropped {
                              value 1 ;
                              description '802.3x protocol frame packet filtering is dropped.' ;
                            }

                            enum terminated {
                              value 2 ;
                              description '802.3x protocol frame packet filtering is terminated.' ;
                            }

                          }

                        }

                        leaf garp {
                          description 'GARP protocol packet filtering.' ;
                          type enumeration {
                            enum tunnelled {
                              value 0 ;
                              description 'GARP protocol packet filtering is tunnelled.' ;
                            }

                            enum dropped {
                              value 1 ;
                              description 'GARP protocol packet filtering is dropped.' ;
                            }

                            enum terminated {
                              value 2 ;
                              description 'GARP protocol packet filtering is terminated.' ;
                            }

                          }

                        }

                        leaf gmrp {
                          description 'GMRP protocol packet filtering.' ;
                          type enumeration {
                            enum tunnelled {
                              value 0 ;
                              description 'GMRP protocol packet filtering is tunnelled.' ;
                            }

                            enum dropped {
                              value 1 ;
                              description 'GMRP protocol packet filtering is dropped.' ;
                            }

                            enum terminated {
                              value 2 ;
                              description 'GMRP protocol packet filtering is terminated.' ;
                            }

                          }

                        }

                        leaf gvrp {
                          description 'GVRP protocol packet filtering.' ;
                          type enumeration {
                            enum tunnelled {
                              value 0 ;
                              description 'GVRP protocol packet filtering is tunnelled.' ;
                            }

                            enum dropped {
                              value 1 ;
                              description 'GVRP protocol packet filtering is dropped.' ;
                            }

                            enum terminated {
                              value 2 ;
                              description 'GVRP protocol packet filtering is terminated.' ;
                            }

                          }

                        }

                        leaf cisco {
                          description 'CISCO protocol packet filtering.' ;
                          type enumeration {
                            enum tunnelled {
                              value 0 ;
                              description 'CISCO protocol packet filtering is tunnelled.' ;
                            }

                            enum dropped {
                              value 1 ;
                              description 'CISCO protocol packet filtering is dropped.' ;
                            }

                            enum terminated {
                              value 2 ;
                              description 'CISCO protocol packet filtering is terminated.' ;
                            }

                          }

                        }

                        leaf dldp {
                          description 'DLDP protocol packet filtering.' ;
                          type enumeration {
                            enum tunnelled {
                              value 0 ;
                              description 'DLDP protocol packet filtering is tunnelled.' ;
                            }

                            enum dropped {
                              value 1 ;
                              description 'DLDP protocol packet filtering is dropped.' ;
                            }

                            enum terminated {
                              value 2 ;
                              description 'DLDP protocol packet filtering is terminated.' ;
                            }

                          }

                        }

                        leaf efm {
                          description 'EFM protocol packet filtering.' ;
                          type enumeration {
                            enum tunnelled {
                              value 0 ;
                              description 'EFM protocol packet filtering is tunnelled.' ;
                            }

                            enum dropped {
                              value 1 ;
                              description 'EFM protocol packet filtering is dropped.' ;
                            }

                            enum terminated {
                              value 2 ;
                              description 'EFM protocol packet filtering is terminated.' ;
                            }

                          }

                        }

                        leaf cfm {
                          description 'CFM protocol packet filtering.' ;
                          type enumeration {
                            enum tunnelled {
                              value 0 ;
                              description 'EFM protocol packet filtering is tunnelled.' ;
                            }

                            enum dropped {
                              value 1 ;
                              description 'EFM protocol packet filtering is dropped.' ;
                            }

                            enum terminated {
                              value 2 ;
                              description 'EFM protocol packet filtering is terminated.' ;
                            }

                          }

                        }

                        leaf pvst {
                          description 'PVST protocol packet filtering.' ;
                          type enumeration {
                            enum tunnelled {
                              value 0 ;
                              description 'PVST protocol packet filtering is tunnelled.' ;
                            }

                            enum dropped {
                              value 1 ;
                              description 'PVST protocol packet filtering is dropped.' ;
                            }

                            enum terminated {
                              value 2 ;
                              description 'PVST protocol packet filtering is terminated.' ;
                            }

                          }

                        }

                        leaf zdp {
                          description 'ZDP protocol packet filtering.' ;
                          type enumeration {
                            enum tunnelled {
                              value 0 ;
                              description 'ZDP protocol packet filtering is tunnelled.' ;
                            }

                            enum dropped {
                              value 1 ;
                              description 'ZDP protocol packet filtering is dropped.' ;
                            }

                            enum terminated {
                              value 2 ;
                              description 'ZDP protocol packet filtering is terminated.' ;
                            }

                          }

                        }

                        leaf lacp {
                          description 'LACP protocol packet filtering.' ;
                          type enumeration {
                            enum tunnelled {
                              value 0 ;
                              description 'LACP protocol packet filtering is tunnelled.' ;
                            }

                            enum dropped {
                              value 1 ;
                              description 'LACP protocol packet filtering is dropped.' ;
                            }

                            enum terminated {
                              value 2 ;
                              description 'LACP protocol packet filtering is terminated.' ;
                            }

                          }

                        }

                        leaf lldp {
                          description 'LLDP protocol packet filtering.' ;
                          type enumeration {
                            enum tunnelled {
                              value 0 ;
                              description 'LLDP protocol packet filtering is tunnelled.' ;
                            }

                            enum dropped {
                              value 1 ;
                              description 'LLDP protocol packet filtering is dropped.' ;
                            }

                            enum terminated {
                              value 2 ;
                              description 'LLDP protocol packet filtering is terminated.' ;
                            }

                          }

                        }

                        leaf stp {
                          description 'STP protocol packet filtering.' ;
                          type enumeration {
                            enum tunnelled {
                              value 0 ;
                              description 'STP protocol packet filtering is tunnelled.' ;
                            }

                            enum dropped {
                              value 1 ;
                              description 'STP protocol packet filtering is dropped.' ;
                            }

                            enum terminated {
                              value 2 ;
                              description 'STP protocol packet filtering is terminated.' ;
                            }

                            enum tunnelled-monitored {
                              value 3 ;
                              description 'STP protocol packet filtering is tunnelled-monitored.' ;
                            }

                          }

                        }

                        leaf erps {
                          description 'ERPS protocol packet filtering.' ;
                          type enumeration {
                            enum tunnelled {
                              value 0 ;
                              description 'ERPS protocol packet filtering is tunnelled.' ;
                            }

                            enum dropped {
                              value 1 ;
                              description 'ERPS protocol packet filtering is dropped.' ;
                            }

                            enum terminated {
                              value 2 ;
                              description 'ERPS protocol packet filtering is terminated.' ;
                            }

                          }

                        }

                        leaf udld {
                          description 'UDLD protocol packet filtering.' ;
                          type enumeration {
                            enum tunnelled {
                              value 0 ;
                              description 'UDLD protocol packet filtering is tunnelled.' ;
                            }

                            enum dropped {
                              value 1 ;
                              description 'UDLD protocol packet filtering is dropped.' ;
                            }

                            enum terminated {
                              value 2 ;
                              description 'UDLD protocol packet filtering is terminated.' ;
                            }

                          }

                        }

                        leaf vtp {
                          description 'VTP protocol packet filtering.' ;
                          type enumeration {
                            enum tunnelled {
                              value 0 ;
                              description 'VTP protocol packet filtering is tunnelled.' ;
                            }

                            enum dropped {
                              value 1 ;
                              description 'VTP protocol packet filtering is dropped.' ;
                            }

                            enum terminated {
                              value 2 ;
                              description 'VTP protocol packet filtering is terminated.' ;
                            }

                          }

                        }

                        leaf zesr {
                          description 'ZESR protocol packet filtering.' ;
                          type enumeration {
                            enum tunnelled {
                              value 0 ;
                              description 'ZESR protocol packet filtering is tunnelled.' ;
                            }

                            enum dropped {
                              value 1 ;
                              description 'ZESR protocol packet filtering is dropped.' ;
                            }

                            enum terminated {
                              value 2 ;
                              description 'ZESR protocol packet filtering is terminated.' ;
                            }

                          }

                        }

                        leaf l2bfd {
                          description 'L2BFD protocol packet filtering.' ;
                          type enumeration {
                            enum tunnelled {
                              value 0 ;
                              description 'L2BFD protocol packet filtering is tunnelled.' ;
                            }

                            enum terminated {
                              value 2 ;
                              description 'L2BFD protocol packet filtering is terminated.' ;
                            }

                          }

                        }

                        leaf mac-control {
                          description 'MAC-control protocol packet filtering.' ;
                          type enumeration {
                            enum tunnelled {
                              value 0 ;
                              description 'MAC-control protocol packet filtering is tunnelled.' ;
                            }

                            enum dropped {
                              value 1 ;
                              description 'MAC-control protocol packet filtering is dropped.' ;
                            }

                            enum terminated {
                              value 2 ;
                              description 'MAC-control protocol packet filtering is terminated.' ;
                            }

                          }

                          ncd:revise-date 2023-03-25 ;
                        }

                        container user-protocol-template {
                          description 'The template of user protocol.' ;
                          presence user-protocol-template ;
                          leaf user-protocol-name {
                            description 'The class name of user protocol.' ;
                            type string {
                              length 1..31 {
                                description 'The length of user protocol class name.' ;
                              }

                            }

                            mandatory true ;
                          }

                          leaf user-protocol-action {
                            description 'User protocol template action.' ;
                            type enumeration {
                              enum tunnelled {
                                value 0 ;
                                description 'User protocol template action is tunnelled.' ;
                              }

                              enum dropped {
                                value 1 ;
                                description 'User protocol template action is dropped.' ;
                              }

                              enum terminated {
                                value 2 ;
                                description 'User protocol template action is terminated.' ;
                              }

                            }

                            mandatory true ;
                          }

                        }

                        ncd:revise-date 2021-06-07 ;
                      }

                    }

                  }

                }

              }

            }

          }

          ncd:revise-date 2020-12-18 ;
        }

      }

      container pw-list-params {
        if-feature pw-list ;

        description 'The PW list configuration info.' ;
        list pw-list {
          description 'The PW list configuration info.' ;
          key list-id ;
          leaf list-id {
            description 'The PW list identification.The maximum value is controlled by the parameters of performance.' ;
            type uint32 {
              range 1..1024 {
                description 'The value of PW list identification.' ;
              }

            }

          }

          container master-pw-info {
            description 'Master PW configuration info of PW list. It can configure one master PW in one PW list.' ;
            presence master-pw-info ;
            leaf pw-name {
              description 'Master PW name of PW list.' ;
              type ncd:ifname {
                length 1..31 {
                  description 'The length of PW name.' ;
                }

              }

              mandatory true ;
            }

          }

          container slave-pw {
            description 'Slave PW configuration info of PW list.' ;
            list slave-pw-info {
              description 'Slave PW configuration info of PW list. The maximum number of slave PW is 128 in one PW list.' ;
              key pw-name ;
              leaf pw-name {
                description 'Slave PW name of PW list.' ;
                type ncd:ifname {
                  length 1..31 {
                    description 'The length of PW name.' ;
                  }

                }

              }

            }

          }

        }

      }

    }

  }

  container operation {
    config false ;
    description 'L2VPN module operation info.' ;
    container l2vpn {
      description 'L2VPN module operation root node.' ;
      container re-negotiate {
        if-feature operation-re-negotiate ;

        description 'L2VPN re-negotiate command.' ;
        presence re-negotiate ;
        list negotiate-pw {
          description 'PW re-negotiate.' ;
          key pw-name ;
          leaf pw-name {
            description 'The name of the PW.' ;
            type ncd:ifname ;

          }

          leaf negotiate {
            description 'Trigger control word re-negotiate.' ;
            type enumeration {
              enum disable {
                value 0 ;
                description 'The re-negotiate is disable.' ;
              }

              enum enable {
                value 1 ;
                description 'The re-negotiate is enable.' ;
              }

            }

            mandatory true ;
          }

          leaf control-word {
            description 'Re-negotiate control word.' ;
            type enumeration {
              enum disable {
                value 0 ;
                description 'Re-negotiate control word is disable.' ;
              }

              enum enable {
                value 1 ;
                description 'Re-negotiate control word is enable.' ;
              }

            }

          }

        }

      }

      container control-word {
        if-feature operation-control-word ;

        description 'L2VPN control word L-bit insert function.' ;
        presence control-word ;
        list control-lbit {
          description 'L2VPN control word L-bit insert function.' ;
          key pw-name ;
          leaf pw-name {
            description 'The name of the PW.' ;
            type ncd:ifname ;

          }

          leaf lbit-insert {
            description 'L-bit insert function. This command is only supported in TDM.' ;
            type enumeration {
              enum start {
                value 1 ;
                description 'The L-bit insert function start.' ;
              }

              enum stop {
                value 2 ;
                description 'The L-bit insert function stop.' ;
              }

            }

            mandatory true ;
          }

          leaf hold-time {
            description 'Manually L-bit insert hold time.' ;
            type uint32 {
              range 0..4294967295 {
                description 'The hold time range is 0 to 4294967295.' ;
              }

            }

            units s ;
            default 0 ;
          }

        }

      }

      container clear {
        description 'L2VPN traffic statistics clear.' ;
        container instance-statistics {
          description 'Clear the instance traffic statistics.' ;
          list instances {
            description 'Instances info of clear instance traffic statistics.' ;
            key instance-name ;
            leaf instance-name {
              description 'The instance name of clear the instance traffic statistics.' ;
              type string {
                length 1..32 {
                  description 'The length of instance name.' ;
                }

              }

            }

          }

        }

        container pw-statistics {
          description 'Clear the PW traffic statistics.' ;
          list pw-info {
            description 'PW info of clear PW traffic statistics.' ;
            key pw-name ;
            leaf pw-name {
              description 'The PW name of clear the PW traffic statistics.' ;
              type ncd:ifname ;

            }

          }

        }

        container ac-statistics {
          if-feature clear-ac-statistic ;

          description 'Clear the AC traffic statistics.' ;
          list ac-info {
            description 'AC info of clear AC traffic statistics.' ;
            key ac-name ;
            leaf ac-name {
              description 'The AC name of clear the AC traffic statistics.' ;
              type ncd:ifname ;

            }

          }

        }

        container l2vpn-statistics {
          description 'Clear the L2VPN traffic statistics.' ;
          leaf all {
            description 'Clear the L2VPN all traffic statistics.' ;
            type empty ;

          }

        }

      }

    }

  }

  rpc pwe3-signal-session {
    status obsolete {
      ncd:revise-date 2023-09-09 ;
    }

    description 'PWE3 signal session info.' ;
    input {
      container pwe3-sessions {
        description 'PWE3 sessions info.' ;
        list pwe3-session {
          description 'PWE3 session info.' ;
          key 'peer local-router-id' ;
          leaf peer {
            description 'Specify the session peer address.' ;
            type ncd:ipv4-address-none-zero ;

          }

          leaf local-router-id {
            description 'Specify the session local router ID.' ;
            type ncd:ipv4-address-none-zero ;

          }

        }

      }

    }

  }

}
