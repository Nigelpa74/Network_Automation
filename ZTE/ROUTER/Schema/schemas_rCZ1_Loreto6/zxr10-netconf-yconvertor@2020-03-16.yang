module zxr10-netconf-yconvertor {
  namespace 'http://www.zte.com.cn/zxr10/netconf/schema/rosng/netconf-yconvertor'
            ;
  prefix nc-yconvertor ;
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The inner netconf module for yconvertor.'
              ;
  revision 2020-03-16 ;
  container configuration {
    description 'Configuration model.'
                ;
    container netconf-yconvertor {
      description 'Yconvertor configuration model.'
                  ;
      leaf config-time {
        description 'Time of yconvertor configuration changed.'
                    ;
        type string {
          length 0..31 ;
        }
      }
    }
    container netconf-private {
      description 'Private configuration model.'
                  ;
      leaf config-time {
        description 'Time of private configuration changed.'
                    ;
        type string {
          length 0..31 ;
        }
      }
    }
  }
}
