module zxr10-ppp {
  namespace "http://www.zte.com.cn/zxr10/netconf/schema/rosng/ppp" ;
  prefix ppp ;
  yang-version 1 ;
  import zxr10-netconf-defs {
    prefix ncd ;
    revision-date 2013-11-22 ;
  }

  organization "ZTE Corporation" ;
  contact "ZTE Corporation
  Nanjing Institute of ZTE Corporation
  No.68 Zijinghua Rd. Yuhuatai District, Nanjing, China
  Tel: +86-25-52870000" ;
  description 'The netconf module to describe Point-to-Point Protocol(PPP)' ;
  revision 2025-07-29 {
    description 'Add a leaf of address(configuration/ppp/ipcp/ipcpattr)' ;
  }

  revision 2024-07-10 {
    description 'Add a container of auth-success-msgs(configuration/ppp/auth-success-msgs)' ;
  }

  revision 2023-12-15 {
    description 'Add the list of mplscp(configuration/ppp/mplscp/mplscpmode)' ;
  }

  revision 2023-09-19 {
    description 'Add a container of global(configuration/ppp/global)' ;
  }

  revision 2022-03-07 {
    description 'Add the enum item of authtype(configuration/ppp/authen/authenchap/authtype)
Modify description of the enum item of authtype(configuration/ppp/authen/authenchap/authtype)' ;
  }

  revision 2021-08-05 {
    description 'Add a container of user-ip(configuration/ppp/user-ip)' ;
  }

  revision 2021-03-16 {
    description 'Change length of pap unencrypted-password(configuration/ppp/pap/papconfig/password-choice/unencrypted-case/unencrypted-password) from 64 to 128.
Change length of pap encrypted-password(configuration/ppp/pap/papconfig/password-choice/encrypted-case/encrypted-password) from 200 to 236.
Change length of chap unencrypted-password(configuration/ppp/authen/authenchap/chappassword-choice/unencrypted-case/unencrypted-password) from 64 to 128.
Change length of chap encrypted-password(configuration/ppp/authen/authenchap/chappassword-choice/encrypted-case/encrypted-password) from 200 to 236.
Change length of auth-global clear-password(configuration/ppp/auth-global/auth/password-choice/clear-case/clear-password) from 64 to 128.
Change length of auth-global encrypted-password(configuration/ppp/auth-global/auth/password-choice/encrypted-case/encrypted-password) from 200 to 236.' ;
  }

  revision 2021-01-25 {
    description 'Change length of pap unencrypted-password(configuration/ppp/pap/papconfig/password-choice/unencrypted-case/unencrypted-password) from 31 to 64.
Change length of pap encrypted-password(configuration/ppp/pap/papconfig/password-choice/encrypted-case/encrypted-password) from 120 to 200.
Change length of chap unencrypted-password(configuration/ppp/authen/authenchap/chappassword-choice/unencrypted-case/unencrypted-password) from 31 to 64.' ;
  }

  revision 2020-10-22 {
    description 'Add a container of auth-global(configuration/ppp/auth-global)' ;
  }

  revision 2020-06-16 {
    description 'Add a container of rasend(configuration/ppp/rasend)' ;
  }

  revision 2020-05-26 {
    description 'Change length of bindipv4pool(configuration/ppp/ippool/ipattr/bindipv4pool) from 32 to 64
Change length of bindipv6pool(configuration/ppp/ippool/ipattr/bindipv6pool) from 31 to 64' ;
  }

  revision 2018-10-09 {
    description 'Modify description of primaryaddr(configuration/ppp/ipcpdns/dnsconfig/primaryaddr)
Modify description of secondaryaddr(configuration/ppp/ipcpdns/dnsconfig/secondaryaddr)
Modify description of primaryaddr(configuration/ppp/ipcpwins/winsconfig/primaryaddr)
Modify description of secondaryaddr(configuration/ppp/ipcpwins/winsconfig/secondaryaddr)
Modify description of ipv4addr(configuration/ppp/peeraddress/ipcppeeraddress/ipv4addr)' ;
  }

  revision 2017-07-21 {
    description 'Add a feature of ppp-aim-pool
Add a container of domain(configuration/ppp/aimpool)' ;
  }

  revision 2017-04-17 {
    description 'The feature of ppp-lifetime newly supports project 15K;
The feature of ppp-domain newly supports project 15K;' ;
  }

  revision 2016-08-18 {
    description 'Add a feature of ppp-domain
Add a container of domain(configuration/ppp/domain)
Add the enum item of authtype(state/ppp/ppp-instance/pppstate/authtype)' ;
  }

  revision 2016-08-10 {
    description 'Add the enum item of authtype(configuration/ppp/authen/authenchap/authtype)' ;
  }

  revision 2016-01-08 {
    description 'Delete the default-value of maxecho(configuration/ppp/lcp/lcpattr/maxecho)
Add the reset-value of maxecho(configuration/ppp/lcp/lcpattr/maxecho)
Delete the default-value of value(configuration/ppp/echo/keepalive/value)
Add the reset-value of value(configuration/ppp/echo/keepalive/value)' ;
  }

  revision 2015-10-12 {
    description 'Change length of bindipv6pool(configuration/ppp/ippool/ipattr/bindipv6pool) from 32 to 31' ;
  }

  revision 2015-07-03 {
    description 'Add a container of lifetime(configuration/ppp/lifetime)
Add a feature of ppp-lifetime' ;
  }

  revision 2015-04-01 {
    description 'Modify description of serverflag(configuration/ppp/ipv6dns/ipv6dns/serverflag)
Add the mandatory of epd(configuration/ppp/epd/epd/epd)
Add the reset-value of authtype(configuration/ppp/authen/authenchap/authtype)
Add the reset-value of chapusername(configuration/ppp/authen/authenchap/chapusername)
Add the reset-value of unencrypted-password(configuration/ppp/authen/authenchap/unencrypted-password)
Add the reset-value of encrypted-password(configuration/ppp/authen/authenchap/encrypted-password)
Add the reset-value of bindipv4pool(configuration/ppp/ippool/ipattr/bindipv4pool)
Add the reset-value of bindipv6pool(configuration/ppp/ippool/ipattr/bindipv6pool)
Add the reset-value of bindauthtemp(configuration/ppp/ippool/ipattr/bindauthtemp)
Add the reset-value of secondaryaddr(configuration/ppp/ipcpdns/dnsconfig/secondaryaddr)
Add the reset-value of secondaryaddr(configuration/ppp/ipcpwins/winsconfig/secondaryaddr)' ;
  }

  revision 2015-03-16 {
    description 'Add a container of neighborroute(configuration/ppp/neighborroute)
Add a container of peeraddress(configuration/ppp/peeraddress)
Add a container of compress(configuration/ppp/compress)' ;
  }

  revision 2015-01-08 {
    description 'delete a leaf of bridge(configuration/ppp/bcp/bcpattr/bridge)
chang some case of proper nouns,such as PPP,IPCP,LCP,EPD,DNS,WINS,PAP,CHAP' ;
  }

  revision 2014-10-29 {
    description 'Change length of epd(configuration/ppp/epd/epd/) from 16 to 32' ;
  }

  revision 2014-05-13 {
    description 'Add a container of state(state/ppp/ppp-instance/pppstate)
Add a typedef of PPP state(ppp-state-type)' ;
  }

  revision 2014-05-07 {
    description 'Change value of chap(configuration/ppp/authen/authenchap/authtype) from 0 to 1
Change value of pap(configuration/ppp/authen/authenchap/authtype) from 1 to 2' ;
  }

  revision 2014-02-12 {
    description 'The initial version' ;
  }

  feature ppp-lifetime {
    description 'Set PPP lifetime' ;
  }

  feature ppp-domain {
    description 'Set PPP domain' ;
  }

  feature ppp-aim-pool {
    description 'Set PPP AIM pool' ;
  }

  feature ppp-rasend {
    description 'Set PPP rasend' ;
  }

  feature ppp-user-ip {
    description 'Set the status of using IP address from user' ;
    ncd:revise-date 2021-08-05 ;
  }

  feature ppp-user-connect-queue {
    description 'Set PPP user connect queue ' ;
    ncd:revise-date 2023-09-19 ;
  }

  typedef ppp-state-type {
    description 'PPP correlation state type' ;
    type enumeration {
      enum INITIAL {
        value 0 ;
        description 'INITIAL state' ;
      }

      enum STARTING {
        value 1 ;
        description 'STARTING state' ;
      }

      enum CLOSED {
        value 2 ;
        description 'CLOSED state' ;
      }

      enum STOPPED {
        value 3 ;
        description 'STOPPED state' ;
      }

      enum CLOSING {
        value 4 ;
        description 'CLOSING state' ;
      }

      enum STOPPING {
        value 5 ;
        description 'STOPPING state' ;
      }

      enum REQ_SENT {
        value 6 ;
        description 'REQ_SENT state' ;
      }

      enum ACK_RCVD {
        value 7 ;
        description 'ACK_RCVD state' ;
      }

      enum ACK_SENT {
        value 8 ;
        description 'ACK_SENT state' ;
      }

      enum OPENED {
        value 9 ;
        description 'OPENED state' ;
      }

    }

  }

  feature ppp-mplscp-mode {
    description 'Set PPP MPLSCP mode' ;
    ncd:revise-date 2023-12-15 ;
  }

  feature ppp-auth-success-msg {
    description 'Set PPP auth-success-msg' ;
    ncd:revise-date 2024-07-10 ;
  }

  feature ppp-ipcp-address {
    description 'Set PPP ipcp address' ;
    ncd:revise-date 2025-07-29 ;
  }

  container configuration {
    description 'Describe the configuration of PPP' ;
    container ppp {
      description 'Configuration data of PPP' ;
      container lcp {
        description 'LCP correlation configuration' ;
        list lcpattr {
          description 'Configure LCP parameters' ;
          key ifname ;
          leaf ifname {
            description 'This value identifies the PPP interface name.This attribute is created by Interface Management' ;
            type ncd:ifname ;

          }

          leaf maxecho {
            description 'Set PPP keepalive granularity' ;
            type uint32 {
              range 1..10 ;

            }

          }

          leaf authtimeout {
            description 'Maximum time to wait for an authentication response' ;
            type uint32 {
              range 1..30 ;

            }

            units seconds ;
            default 5 ;
          }

          leaf negotiationtimeout {
            description 'Maximum time to wait for response during PPP negotiation' ;
            type uint32 {
              range 1..30 ;

            }

            units seconds ;
            default 5 ;
          }

        }

      }

      container authen {
        description 'authentation correlation configuration' ;
        list authenchap {
          description 'Configure CHAP authentication parameters' ;
          key ifname ;
          leaf ifname {
            description 'This value identifies the PPP interface name.This attribute is created by Interface Management' ;
            type ncd:ifname ;

          }

          leaf authtype {
            description 'Configure authentication type' ;
            type enumeration {
              enum chap {
                value 1 ;
                description 'Challenge handshake authentication protocol(CHAP)' ;
              }

              enum pap {
                value 2 ;
                description 'Password authentication protocol(PAP)' ;
              }

              enum chap-pap {
                value 3 ;
                description 'CHAP PAP adaptive authentication(CHAP first)' ;
              }

              enum pap-chap {
                value 4 ;
                description 'PAP CHAP adaptive authentication(PAP first)' ;
              }

            }

          }

          leaf chapusername {
            description 'Configure CHAP username' ;
            type string {
              length 1..159 ;

            }

          }

          choice chappassword-choice {
            description 'Configure CHAP password' ;
            case unencrypted-case {
              description 'Specify the unencrypted password' ;
              leaf unencrypted-password {
                description 'The unencrypted password' ;
                type string {
                  length 1..128 ;

                }

              }

            }

            case encrypted-case {
              description 'Specify the encrypted password' ;
              leaf encrypted-password {
                description 'The encrypted password' ;
                type string {
                  length 1..236 ;

                }

              }

            }

          }

        }

      }

      container ipcp {
        description 'IPCP correlation configuration' ;
        list ipcpattr {
          description 'Configure IPCP parameters' ;
          key ifname ;
          leaf ifname {
            description 'This value identifies the PPP interface name.This attribute is created by Interface Management' ;
            type ncd:ifname ;

          }

          leaf enable {
            description 'ppp ipcp enable' ;
            type enumeration {
              enum disable {
                value 0 ;
                description 'Disable IPCP' ;
              }

              enum enable {
                value 1 ;
                description 'Enable IPCP' ;
              }

            }

            default enable ;
          }

          leaf address {
            type enumeration {
              enum negotiate {
                value 0 ;
                description 'Ipcp negotiation with ip address' ;
              }

              enum ignore {
                value 1 ;
                description 'Ignore ipcp address' ;
              }

            }

            description 'Ipcp negotiation with ip address' ;
            default negotiate ;
            if-feature ppp-ipcp-address;

            ncd:revise-date 2025-07-29 ;
          }

        }

      }

      container bcp {
        description 'BCP correlation configuration' ;
        list bcpattr {
          description 'Configure BCP parameters' ;
          key ifname ;
          leaf ifname {
            description 'This value identifies the PPP interface name.This attribute is created by Interface Management' ;
            type ncd:ifname ;

          }

          leaf managementinline {
            description 'Enable management inline' ;
            type uint8 {
              range 0..1 ;

            }

            default 0 ;
          }

          leaf packetindicator {
            description 'Enable bridge control packet indicator' ;
            type uint8 {
              range 0..1 ;

            }

            default 0 ;
          }

          leaf taggedframe {
            description 'Enable IEEE 802 Tagged Frame' ;
            type uint8 {
              range 0..1 ;

            }

            default 0 ;
          }

        }

        list bcpenable {
          description 'Configure BCP enable' ;
          key ifname ;
          leaf ifname {
            description 'This value identifies the PPP interface name.This attribute is created by Interface Management' ;
            type ncd:ifname ;

          }

          leaf enable {
            description 'ppp bcp enable' ;
            type enumeration {
              enum disable {
                value 0 ;
                description 'Disable BCP' ;
              }

              enum enable {
                value 1 ;
                description 'Enable BCP' ;
              }

            }

            default disable ;
          }

        }

      }

      container epd {
        description 'EPD(End Point Discriminator) correlation configuration' ;
        list epd {
          description 'Configure the local endpoint discriminator' ;
          key ifname ;
          leaf ifname {
            description 'This value identifies the PPP interface name.This attribute is created by Interface Management' ;
            type ncd:ifname ;

          }

          leaf epd {
            description 'Configure the local endpoint discriminator' ;
            type string {
              length 1..32 ;

            }

            mandatory true ;
          }

        }

      }

      container ippool {
        description 'IP pool correlation configuration' ;
        list ipattr {
          description 'Configure IP address parameters' ;
          key ifname ;
          leaf ifname {
            description 'This value identifies the PPP interface name.This attribute is created by Interface Management' ;
            type ncd:ifname ;

          }

          leaf bindipv4pool {
            description 'Bind IPv4 pool' ;
            type string {
              length 1..64 ;

            }

          }

          leaf bindipv6pool {
            description 'Bind IPv6 pool' ;
            type string {
              length 1..64 ;

            }

          }

          leaf bindauthtemp {
            description 'Bind AAA authentication template' ;
            type uint16 {
              range 1..2128 ;

            }

          }

          leaf ipaccesstype {
            description 'Configure IP access type' ;
            type enumeration {
              enum dual {
                value 0 ;
                description 'IP dual stack access' ;
              }

              enum ipv4 {
                value 1 ;
                description 'IPv4 access' ;
              }

              enum ipv6 {
                value 2 ;
                description 'IPv6 access' ;
              }

            }

            default dual ;
          }

        }

      }

      container ipcpdns {
        description 'IPCP DNS correlation configuration' ;
        list dnsconfig {
          description 'Configure PPP IPCP DNS IP address' ;
          key ifname ;
          leaf ifname {
            description 'This value identifies the PPP interface name.This attribute is created by Interface Management' ;
            type ncd:ifname ;

          }

          leaf primaryaddr {
            description 'Configure primary DNS IP address. In particular, 0.0.0.0 cannot be configured, but 0.0.0.0 may be obtained.' ;
            type ncd:ipv4-address ;

            mandatory true ;
          }

          leaf secondaryaddr {
            description 'Configure secondary DNS IP address. In particular, 0.0.0.0 cannot be configured, but 0.0.0.0 may be obtained.' ;
            type ncd:ipv4-address ;

          }

        }

      }

      container ipcpwins {
        description 'IPCP WINS correlation configuration' ;
        list winsconfig {
          description 'Set PPP IPCP WINS IP adddress' ;
          key ifname ;
          leaf ifname {
            description 'This value identifies the PPP interface name.This attribute is created by Interface Management' ;
            type ncd:ifname ;

          }

          leaf primaryaddr {
            description 'Configure primary WINS IP address. In particular, 0.0.0.0 cannot be configured, but 0.0.0.0 may be obtained.' ;
            type ncd:ipv4-address ;

            mandatory true ;
          }

          leaf secondaryaddr {
            description 'Configure secondary WINS IP address. In particular, 0.0.0.0 cannot be configured, but 0.0.0.0 may be obtained.' ;
            type ncd:ipv4-address ;

          }

        }

      }

      container ipcppara {
        description 'IPCP correlation configuration' ;
        list ipcppara {
          description 'Configure IPCP parameters' ;
          key ifname ;
          leaf ifname {
            description 'This value identifies the PPP interface name.This attribute is created by Interface Management' ;
            type ncd:ifname ;

          }

          leaf dnsaccept {
            description 'Accept peer PPP IPCP DNS request' ;
            type uint8 {
              range 0..1 ;

            }

            default 0 ;
          }

          leaf dnssend {
            description 'Send PPP IPCP DNS request' ;
            type uint8 {
              range 0..1 ;

            }

            default 0 ;
          }

          leaf winsaccept {
            description 'Accept peer PPP IPCP WINS request' ;
            type uint8 {
              range 0..1 ;

            }

            default 0 ;
          }

          leaf winssend {
            description 'Send PPP IPCP WINS request' ;
            type uint8 {
              range 0..1 ;

            }

            default 0 ;
          }

        }

      }

      container mppp {
        description 'MPPP bind member correlation configuration' ;
        list bindmember {
          description 'MPPP bind member' ;
          key ifname ;
          leaf ifname {
            description 'This value identifies the PPP interface name.This attribute is created by Interface Management' ;
            type ncd:ifname ;

          }

          leaf multilink {
            description 'This value identifies the multilink interface name.' ;
            type ncd:ifname ;

            mandatory true ;
          }

        }

      }

      container pap {
        description 'PAP correlation configuration' ;
        list papconfig {
          description 'Configure PAP authentication parameters' ;
          key ifname ;
          leaf ifname {
            description 'This value identifies the PPP interface name.This attribute is created by Interface Management' ;
            type ncd:ifname ;

          }

          leaf username {
            description 'Configure PAP username' ;
            type string {
              length 1..159 ;

            }

            mandatory true ;
          }

          choice password-choice {
            description 'Configure PAP password' ;
            mandatory true ;
            case unencrypted-case {
              description 'Specify the unencrypted password' ;
              leaf unencrypted-password {
                description 'The unencrypted password' ;
                type string {
                  length 1..128 ;

                }

              }

            }

            case encrypted-case {
              description 'Specify the encrypted password' ;
              leaf encrypted-password {
                description 'The encrypted password' ;
                type string {
                  length 1..236 ;

                }

              }

            }

          }

        }

      }

      container ipv6dns {
        description 'IPv6 DNS correlation configuration' ;
        list ipv6dns {
          description 'Configure IPv6 DNS server address' ;
          key 'ifname serverflag' ;
          leaf ifname {
            description 'This value identifies the PPP interface name.This attribute is created by Interface Management' ;
            type ncd:ifname ;

          }

          leaf serverflag {
            description 'IPv6 secondary DNS server address' ;
            type uint8 {
              range 0..1 {
                description '0:primary server
1:secondary server' ;
              }

            }

          }

          leaf serveraddr {
            description 'IPv6 DNS server addr' ;
            type ncd:ipv6-address ;

            mandatory true ;
          }

        }

      }

      container nasporttype {
        description 'Nas-Port-Type correlation configuration' ;
        list nasporttype {
          description 'Configure NAS port type' ;
          key ifname ;
          leaf ifname {
            description 'This value identifies the PPP interface name.This attribute is created by Interface Management' ;
            type ncd:ifname ;

          }

          leaf nasporttype {
            description 'Configure NAS port type' ;
            type uint8 {
              range 0..255 ;

            }

            default 5 ;
          }

        }

      }

      container mplscp {
        description 'MPLSCP correlation configuration' ;
        list mplscp {
          description 'Configure MPLSCP parameters' ;
          key ifname ;
          leaf ifname {
            description 'This value identifies the PPP interface name.This attribute is created by Interface Management' ;
            type ncd:ifname ;

          }

          leaf enable {
            description 'ppp mplscp enable' ;
            type enumeration {
              enum disable {
                value 0 ;
                description 'Disable MPLSCP' ;
              }

              enum enable {
                value 1 ;
                description 'Enable MPLSCP' ;
              }

            }

            default disable ;
          }

        }

        list mplscpmode {
          if-feature ppp-mplscp-mode ;

          description 'Configure MPLSCP mode parameters' ;
          key ifname ;
          leaf ifname {
            type ncd:ifname ;

            description 'This value identifies the PPP interface name.This attribute is created by Interface Management' ;
          }

          leaf mode {
            type enumeration {
              enum dynamic {
                value 0 ;
                description 'MPLSCP dynamic mode' ;
              }

              enum static {
                value 1 ;
                description 'MPLSCP static mode' ;
              }

            }

            description 'ppp mplscp mode' ;
            default dynamic ;
          }

          ncd:revise-date 2023-12-15 ;
        }

      }

      container portrange {
        description 'portrange correlation configuration' ;
        list portrangeconfig {
          description 'Configure portrange poolname' ;
          key ifname ;
          leaf ifname {
            description 'This value identifies the PPP interface name.This attribute is created by Interface Management' ;
            type ncd:ifname ;

          }

          leaf poolname {
            description 'Portrange poolname' ;
            type string {
              length 1..31 ;

            }

            mandatory true ;
          }

        }

      }

      container bindvt {
        description 'bind VT(Virtual Template) correlation configuration' ;
        list v4vpn {
          description 'Bind IPv4 virtual_template interface' ;
          key ifname ;
          leaf ifname {
            description 'This value identifies the PPP interface name.This attribute is created by Interface Management' ;
            type ncd:ifname ;

          }

          leaf v4temp {
            description 'Virtual_template interface' ;
            type ncd:ifname ;

            mandatory true ;
          }

        }

        list v6vpn {
          description 'Bind IPv6 virtual_template interface' ;
          key ifname ;
          leaf ifname {
            description 'This value identifies the PPP interface name.This attribute is created by Interface Management' ;
            type ncd:ifname ;

          }

          leaf v6temp {
            description 'Virtual_template interface' ;
            type ncd:ifname ;

            mandatory true ;
          }

        }

      }

      container ipv6 {
        description 'IPv6 correlation configuration' ;
        list accesstype {
          description 'Configure IPv6 access type' ;
          key ifname ;
          leaf ifname {
            description 'This value identifies the PPP interface name.This attribute is created by Interface Management' ;
            type ncd:ifname ;

          }

          leaf accesstype {
            description 'IPv6 access type' ;
            type enumeration {
              enum slaac {
                value 0 ;
                description 'SLAAC access' ;
              }

              enum dhcpv6 {
                value 1 ;
                description 'DHCPv6 access' ;
              }

              enum dhcpv6-slaac {
                value 2 ;
                description 'DHCPv6-SLAAC access' ;
              }

            }

            mandatory true ;
          }

        }

      }

      container echo {
        description 'echo correlation configuration' ;
        list keepalive {
          description 'Configure PPP keepalive period' ;
          key ifname ;
          leaf ifname {
            description 'This value identifies the PPP interface name.This attribute is created by Interface Management' ;
            type ncd:ifname ;

          }

          leaf value {
            description 'Keepalive period (default 10 seconds)' ;
            type uint32 {
              range 0..32767 ;

            }

            units seconds ;
          }

        }

      }

      container priority {
        description 'Default router priority correlation configuration' ;
        list routerpriority {
          description 'Configure priority of default router which get by DHCP' ;
          key ifname ;
          leaf ifname {
            description 'This value identifies the PPP interface name.This attribute is created by Interface Management' ;
            type ncd:ifname ;

          }

          leaf value {
            description 'Default router priority(default 200)' ;
            type uint8 {
              range 1..254 ;

            }

            default 200 ;
          }

        }

      }

      container neighborroute {
        description 'PPP IPCP neighbor-route correlation configuration' ;
        list ipcpneighborroute {
          description 'Set PPP IPCP neighbor-route parameters' ;
          key ifname ;
          leaf ifname {
            description 'This value identifies the PPP interface name.This attribute is created by Interface Management' ;
            type ncd:ifname ;

          }

          leaf status {
            description 'The enable status of PPP IPCP neighbor-route' ;
            type enumeration {
              enum disable {
                value 0 ;
                description 'Disable PPP IPCP neighbor-route' ;
              }

              enum enable {
                value 1 ;
                description 'Enable PPP IPCP neighbor-route' ;
              }

            }

            default enable ;
          }

        }

      }

      container peeraddress {
        description 'PPP IPCP peer-address correlation configuration' ;
        list ipcppeeraddress {
          description 'Set PPP IPCP peer-address parameters' ;
          key ifname ;
          leaf ifname {
            description 'This value identifies the PPP interface name.This attribute is created by Interface Management' ;
            type ncd:ifname ;

          }

          leaf ipv4addr {
            description 'Set peer IP address. In particular, 0.0.0.0 cannot be configured, but 0.0.0.0 may be obtained.' ;
            type ncd:ipv4-address ;

            mandatory true ;
          }

        }

      }

      container compress {
        description 'PPP protocol compress correlation configuration' ;
        list protocolcompress {
          description 'Set protocol field compression parameters' ;
          key ifname ;
          leaf ifname {
            description 'This value identifies the PPP interface name.This attribute is created by Interface Management' ;
            type ncd:ifname ;

          }

          leaf status {
            description 'The enable status of protocol field compression' ;
            type enumeration {
              enum disable {
                value 0 ;
                description 'Disable protocol field compression' ;
              }

              enum enable {
                value 1 ;
                description 'Enable protocol field compression' ;
              }

            }

            default disable ;
          }

        }

      }

      container lifetime {
        if-feature ppp-lifetime ;

        description 'PPP lifetime correlation configuration' ;
        list lifetimeattr {
          description 'Set valid lifetime and preferred lifetime' ;
          key ifname ;
          leaf ifname {
            description 'This value identifies the PPP interface name.This attribute is created by Interface Management' ;
            type ncd:ifname ;

          }

          leaf validlifetime {
            description 'Set valid lifetime' ;
            type uint32 {
              range 0..4294967295 ;

            }

            units seconds ;
            default 2592000 ;
          }

          leaf preferredlifetime {
            description 'Set preferred lifetime' ;
            type uint32 {
              range 0..4294967295 ;

            }

            units seconds ;
            default 604800 ;
          }

        }

        ncd:revise-date 2015-07-03 ;
      }

      container domain {
        if-feature ppp-domain ;

        description 'PPP access domain correlation configuration' ;
        list accessdomain {
          description 'Set access domain name' ;
          key ifname ;
          leaf ifname {
            description 'This value identifies the PPP interface name.This attribute is created by Interface Management' ;
            type ncd:ifname ;

          }

          leaf domainname {
            description 'Specify access domain name' ;
            type string {
              length 1..31 ;

            }

          }

        }

        ncd:revise-date 2016-08-18 ;
      }

      container aimpool {
        if-feature ppp-aim-pool ;

        description 'Bind AIM(AAA Information Manage) pool correlation configuration' ;
        list bindaimpool {
          description 'Bind AIM pool' ;
          key ifname ;
          leaf ifname {
            description 'This value identifies the PPP interface name.This attribute is created by Interface Management' ;
            type ncd:ifname ;

          }

          leaf aimpooltype {
            description 'AIM pool type' ;
            type enumeration {
              enum ipv4 {
                value 1 ;
                description 'IPv4 pool' ;
              }

              enum ipv6 {
                value 2 ;
                description 'IPv6 pool' ;
              }

              enum dual {
                value 3 ;
                description 'IP dual stack pool' ;
              }

            }

          }

        }

        ncd:revise-date 2017-07-21 ;
      }

      container rasend {
        description 'Send ra packet correlation configuration' ;
        list delaytime {
          description 'Configure the delay time of sending the first RA packet' ;
          key ifname ;
          leaf ifname {
            description 'This value identifies the PPP interface name.This attribute is created by Interface Management' ;
            type ncd:ifname ;

          }

          leaf value {
            description 'Delay time period, its default value depends on the performance parameters.' ;
            type uint32 {
              range 0..30 ;

            }

            units seconds ;
            default 0 ;
          }

        }

        ncd:revise-date 2020-06-16 ;
      }

      container auth-global {
        description 'Authentication global configuration' ;
        list auth {
          description 'Configure authentication global user-name and password' ;
          key user-name ;
          leaf user-name {
            description 'Configure global user-name' ;
            type string {
              length 1..159 ;

            }

          }

          choice password-choice {
            description 'Configure global password' ;
            mandatory true ;
            case clear-case {
              description 'Configure clear password' ;
              leaf clear-password {
                description 'Clear password' ;
                type string {
                  length 1..128 ;

                }

                mandatory true ;
              }

            }

            case encrypted-case {
              description 'Configure encrypted password' ;
              leaf encrypted-password {
                description 'Encrypted password' ;
                type string {
                  length 1..236 ;

                }

                mandatory true ;
              }

            }

          }

        }

        ncd:revise-date 2020-10-22 ;
      }

      container user-ip {
        if-feature ppp-user-ip ;

        description 'User IP address correlation configuration' ;
        list user-ip {
          description 'Configure user IP address parameters' ;
          key ifname ;
          leaf ifname {
            description 'This value identifies the PPP interface name.This attribute is created by Interface Management' ;
            type ncd:ifname ;

          }

          leaf enable {
            description 'The enable status of using IP address from user' ;
            type enumeration {
              enum disable {
                value 0 ;
                description 'Disable user IP address' ;
              }

              enum enable {
                value 1 ;
                description 'Enable user IP address' ;
              }

            }

            default disable ;
          }

        }

        ncd:revise-date 2021-08-05 ;
      }

      container global {
        description 'Global configuration' ;
        leaf user-connect-queue {
          if-feature ppp-user-connect-queue ;

          description 'Configure user connect queue size.' ;
          type uint32 {
            range 0..4000 ;

          }

        }

        ncd:revise-date 2023-09-19 ;
      }

      container auth-success-msgs {
        list auth-success-msg {
          leaf ifname {
            type ncd:ifname ;

            description 'This value identifies the PPP interface name.This attribute is created by Interface Management' ;
          }

          description 'Configure auth-success-msg parameters' ;
          key ifname ;
          leaf message {
            type enumeration {
              enum empty {
                value 0 ;
                description 'The message field is zero octet.' ;
              }

              enum ok-format {
                description 'The message field is OK format.' ;
                value 1 ;
              }

              enum chap-success-format {
                value 2 ;
                description 'The message field is CHAP success format.' ;
              }

            }

            description 'Configure PPP auth-success-msg' ;
            default ok-format ;
          }

        }

        if-feature ppp-auth-success-msg ;

        description 'Auth success message configuration' ;
        ncd:revise-date 2024-07-10 ;
      }

    }

  }

  container operation {
    config false ;
    description 'Describe the operation of PPP' ;
    container ppp {
      description 'Operation data of PPP' ;
      container pppopen {
        description 'PPP open correlation operation' ;
        list renegotiation {
          description 'Set LCP renegotiation' ;
          key ifname ;
          leaf ifname {
            description 'This value identifies the PPP interface name.This attribute is created by Interface Management' ;
            type ncd:ifname ;

          }

          leaf pppopen {
            description 'Open PPP protocol' ;
            type uint8 {
              range 0..1 ;

            }

          }

        }

      }

    }

  }

  container state {
    config false ;
    description 'Describe the state of PPP' ;
    container ppp {
      description 'State data of PPP' ;
      container ppp-instance {
        description 'PPP correlation state' ;
        list pppstate {
          description 'PPP correlation state' ;
          key ifname ;
          leaf ifname {
            description 'This value identifies the PPP interface name.This attribute is created by Interface Management' ;
            type ncd:ifname ;

          }

          leaf lcp {
            description 'LCP state' ;
            type ppp-state-type ;

          }

          leaf ipcp {
            description 'IPCP state' ;
            type ppp-state-type ;

          }

          leaf bcp {
            description 'BCP state' ;
            type ppp-state-type ;

          }

          leaf ipv6cp {
            description 'IPv6CP state' ;
            type ppp-state-type ;

          }

          leaf mplscp {
            description 'MPLSCP state' ;
            type ppp-state-type ;

          }

          leaf mplscpmode {
            description 'MPLSCP mode type' ;
            type ppp-state-type ;

          }

          leaf osinlcp {
            description 'OSINLCP state' ;
            type ppp-state-type ;

          }

          leaf authtype {
            description 'authentication type' ;
            type enumeration {
              enum none {
                value 0 ;
                description 'Authentication type is not configured' ;
              }

              enum chap {
                value 1 ;
                description 'ppp authentication chap' ;
              }

              enum pap {
                value 2 ;
                description 'ppp authentication pap' ;
              }

              enum chap-pap {
                value 3 ;
                description 'CHAP PAP adaptive authentication' ;
              }

            }

          }

          leaf authstate {
            description 'authentication state' ;
            type enumeration {
              enum SUCCESS {
                value 0 ;
                description 'PPP_AUTH_SUCCESS' ;
              }

              enum FAILURE {
                value 1 ;
                description 'PPP_AUTH_FAILURE' ;
              }

              enum PROCESS {
                value 2 ;
                description 'PPP_AUTH_PROCESS: the flag of waiting for authentication server response' ;
              }

              enum INVALID {
                value 3 ;
                description 'PPP_AUTH_INVALID: authentication unreachable' ;
              }

            }

          }

        }

      }

    }

  }

}
