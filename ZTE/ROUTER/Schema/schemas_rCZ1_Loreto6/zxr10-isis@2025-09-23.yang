module zxr10-isis {
  namespace "http://www.zte.com.cn/zxr10/netconf/schema/rosng/isis" ;
  prefix isis ;
  yang-version 1 ;
  import zxr10-netconf-defs {
    prefix ncd ;
    revision-date 2013-11-22 ;
  }

  organization "ZTE Corporation" ;
  contact "ZTE Corporation
  Nanjing Institute of ZTE Corporation
  No.68 Zijinghua Rd. Yuhuatai District, Nanjing, China
  Tel: +86-25-52870000" ;
  description 'The netconf module to describe ISIS.This module describes a management information base for the IS-IS Routing protocol, as described in ISO 10589.' ;
  revision 2025-09-23 {
    description '1.Path:/configuration/route-isis/isis-instances/isis-instance/ipv4-microloop-prevention-te-tunnel/remote-change-delay-time.Add this leaf.
2.Path:/configuration/route-isis/isis-instances/isis-instance/ipv6-microloop-prevention-te-tunnel/remote-change-delay-time.Add this leaf.' ;
  }

  revision 2025-09-02 {
    description '1.Path:/configuration/route-isis/isis-instances/isis-instance/isis-attr/lsp-size-recieve.Correct spelling errors.
2.Path:/configuration/route-isis/isis-instances/isis-instance/lsp-gen-intervals.Correct spelling errors.
3.Path:/configuration/route-isis/isis-instances/isis-instance/lsp-gen-intervals/lsp-gen-interval.Correct spelling errors.
4.Path:/configuration/route-isis/isis-instances/isis-instance/redistributes/redis-ospf-protocol/redis-ospf/ospf.Correct spelling errors.
5.Path:/configuration/route-isis/isis-instances/isis-instance/redistributes/redis-other-protocols/redis-other-protocol/protocol.Correct spelling errors.
6.Path:/configuration/route-isis/isis-instances/isis-instance/isis-intfs/isis-intf-attr/retransmit-intervals/retransmit-interval/retran-interval.Correct spelling errors.
7.Path:/configuration/route-isis/isis-instances/isis-instance/authen-keychains/authen-keychain/keychain-name.Correct spelling errors.
8.Path:/state/route-isis/isis-peer-routerids.Correct spelling errors.
9.Path:/state/route-isis/isis-peer-routerids/isis-peer-routerid.Correct spelling errors.
10.Path:/state/route-isis/isis-instances.Correct spelling errors.
11.Path:/state/route-isis/isis-instances/isis-instance.Correct spelling errors.' ;
  }

  revision 2025-06-25 {
    description '1.Path:/configuration/isis:global-config/isis:memory-overload-protection.Add this leaf.' ;
  }

  revision 2025-06-03 {
    description '1.srv6-adjacency-set-feature add 高端路由器HighEndRouter.T8000 and 高端分组HighEndPacket.15K.' ;
  }

  revision 2025-05-13 {
    description '1.srv6-adjacency-set-feature. Add this feature, include PTN.6100, PTN.61-SSP, PTN.61V5_1, PC.MSE.
2.Path:/configuration/route-isis/isis-instances/isis-instance/srv6-locators/end-x-sid/adjacency-set. Container add srv6-adjacency-set-feature.' ;
  }

  revision 2025-04-25 {
    description '1.intf-ldp-sync-feature. Add this feature, include PC.MSE and PC.SWITCH.
2.Path:/configuration/route-isis/isis-instances/isis-instance/isis-intfs/isis-intf-attr/intf-ldp-sync-hold-times. Container add intf-ldp-sync-feature.
3.Path:/configuration/route-isis/isis-instances/isis-instance/isis-intfs/isis-intf-attr/intf-ipv6-ldp-sync-hold-times. Container add intf-ldp-sync-feature.' ;
  }

  revision 2025-04-15 {
    description '1.Path:/configuration/route-isis/isis-instances/isis-instance/multi-instance-iid-check. Add this container.' ;
  }

  revision 2025-04-07 {
    description '1.Path:/isis:configuration/isis:route-isis/isis:isis-instances/isis:isis-instance/isis:ipv6-redistributes/isis:redis-other-protocols/isis:redis-other-protocol/isis:protocol.
Add an enum type:nd-host.' ;
  }

  revision 2025-03-27 {
    description '1.Path:/configuration/route-isis/isis-instances/isis-instance/srv6-locators/end-x-sid/adjacency-set.Add this container.' ;
  }

  revision 2025-02-25 {
    description '1.Path:/configuration/route-isis/isis-instances/isis-instance/isis-intfs/isis-intf-attr/intf-ldp-sync-hold-times. Add this container.
2.Path:/configuration/route-isis/isis-instances/isis-instance/isis-intfs/isis-intf-attr/intf-ipv6-ldp-sync-hold-times. Add this container.' ;
  }

  revision 2025-02-24 {
    description '1.Path:/notification/adjacencies/adjacencyState. Add this list.' ;
  }

  revision 2025-02-11 {
    description '1.Path:/configuration/route-isis/isis-instances/isis-instance/ipv6-route-calculate/locator-update-delay/delay-time. Modify the default value of this leaf node.' ;
  }

  revision 2025-01-08 {
    description '1.Path:/isis:state/isis:route-isis/isis:isis-adjacencies/isis:isis-adjacency/isis:adj-hostname. Add this leaf.' ;
  }

  revision 2024-11-01 {
    description '1.Path:/configuration/route-isis/isis-instances/isis-instance/ipv6-route-calculate/locator-update-delay. Add this container.' ;
  }

  revision 2024-10-31 {
    description '1.Path:/notification/adjacencies/adjacency-period. Add this list.
2.Path:/notification/adjacencies/adjacency-number-period. Add this list.
3.Path:/notification/interfaces/interface-period. Add this list.' ;
  }

  revision 2024-09-13 {
    description '1.path:configuration/route-isis/isis-instances/isis-instance/ipv6-fa-summary-prefixs. Add this container.' ;
  }

  revision 2024-08-13 {
    description '1.Path:bier-lfa-feature. Add this features.' ;
  }

  revision 2024-01-04 {
    description '1.path:configuration/route-isis/isis-instances/isis-instance/isis-attr/maximum-paths.Add a default value PerfID and modify a leaf description
2.path:configuration/route-isis/isis-instances/isis-instance/isis-attr/ipv6-maximum-paths.Add a default value PerfID and modify a leaf description' ;
  }

  revision 2023-09-01 {
    description '1.path:configuration/route-isis/isis-instances/isis-instance/ipv4-tilfa-inter-level-protect. Add this container.
2.path:configuration/route-isis/isis-instances/isis-instance/ipv6-tilfa-inter-level-protect. Add this container.' ;
  }

  revision 2023-07-26 {
    description '1.Path:/configuration/route-isis/isis-instances/isis-isis/isis-instances/isis-instance/bier-info.Add this container.
2.Path:/configuration/route-isis/isis-instances/isis-isis/isis-instances/isis-instance/ipv4-bier.The state of this container is changed from current to obsolete.
3.Path:/configuration/route-isis/isis-instances/isis-isis/isis-instances/isis-instance/ipv6-bier.The state of this container is changed from current to obsolete.' ;
  }

  revision 2023-06-07 {
    description '1.Path:/notification/adjacencies/adjacencyNum. Add this leaf.
2.Path:/notification/interfaces. Add this container.' ;
  }

  revision 2023-05-24 {
    description '1.Path:/notification. Add this container.
2.Path:/notification/adjacencies. Add this container.' ;
  }

  revision 2023-05-07 {
    description '1.path:configuration/route-isis/isis-instances/isis-instance/isis-intfs/isis-intf-attr/ip-reachability-suppress. Add this container.
2.path:configuration/route-isis/isis-instances/isis-instance/isis-intfs/isis-intf-attr/ipv6-reachability-suppress. Add this container.' ;
  }

  revision 2023-05-06 {
    description '1.path:configuration/route-isis/isis-instances/isis-instance/isis-intfs/isis-intf-attr/ipv4-bfd-negotiation/min-rx.Modify the value range to 0..65535.
2.path:configuration/route-isis/isis-instances/isis-instance/isis-intfs/isis-intf-attr/ipv4-bfd-negotiation/min-tx.Modify the value range to 0..65535.
3.path:configuration/route-isis/isis-instances/isis-instance/isis-intfs/isis-intf-attr/ipv6-bfd-negotiation/min-rx.Modify the value range to 0..65535.
4.path:configuration/route-isis/isis-instances/isis-instance/isis-intfs/isis-intf-attr/ipv6-bfd-negotiation/min-tx.Modify the value range to 0..65535.' ;
  }

  revision 2023-02-28 {
    description '1.Path:/configuration/route-isis/isis-instances/isis-instance/fast-reroute-link-suppress-block. Add this container.
2.Path:/configuration/route-isis/isis-instances/isis-instance/ipv6-fast-reroute-link-suppress-block. Add this container.' ;
  }

  revision 2023-02-22 {
    description '1.Path:/configuration/route-isis/isis-instances/isis-isis/isis-instances/isis-instance/slice-source-prefixs.Add this container.' ;
  }

  revision 2023-02-21 {
    description '1.Path:/configuration/route-isis/isis-instances/isis-instance/srv6-locators/srv6-locator/metric.Add this container.
2.Path:/configuration/route-isis/isis-instances/isis-instance/srv6-locators/srv6-locator/tag.Add this container.' ;
  }

  revision 2023-02-20 {
    description '1.Path:frr feature, micr-sr-feature, te-link-feature, bfd-feature, reverse-metric-feature, remote-lfa-feature. Add these features.
2.Path:/configuration/route-isis/isis-instances/isis-instance/frr-priority/ti-lfa-priority. Add frr-feature.
3.Path:/configuration/route-isis/isis-instances/isis-instance/frr-tilfa/frr-tilfa. Add frr-feature.
4.Path:/configuration/route-isis/isis-instances/isis-instance/ipv6-frr-tilfa/frr-tilfa. Add frr-feature.
5.Path:/configuration/route-isis/isis-instances/isis-instance/microloop-prevention-segment-routing/delay-time. Add micr-sr-feature.
6.Path:/configuration/route-isis/isis-instances/isis-instance/ipv6-microloop-prevention-segment-routing/delay-time. Add micr-sr-feature.
7.Path:/configuration/route-isis/isis-instances/isis-instance/microloop-prevention-segment-routing/mpls-state. Add micr-sr-feature.
8.Path:/configuration/route-isis/isis-instances/isis-instance/ipv6-microloop-prevention-segment-routing/mpls-state. Add micr-sr-feature.
9.Path:/configuration/route-isis/isis-instances/isis-instance/isis-attr/te-link-loss-anomalous-attach-sd. Add te-link-feature.
10.Path:/configuration/route-isis/isis-instances/isis-instance/iipv6-frr-tilfa/frr-tilfa. Add frr-feature.
11.Path:/configuration/route-isis/isis-instances/isis-instance/ipv6-microloop-prevention-segment-routing/srv6-state. Add micr-sr-feature.
12.Path:/configuration/route-isis/isis-instances/isis-instance/isis-ipv6-router-id/ipv6-router-id. Add frr-feature.
13.Path:/configuration/route-isis/isis-instances/isis-instance/isis-intfs/isis-intf-attr/bfd-mode. Add bfd-feature.
14.Path:/configuration/route-isis/isis-instances/isis-instance/isis-intfs/isis-intf-attr/fast-reroute-tilfa-block. Add frr-feature.
15.Path:/configuration/route-isis/isis-instances/isis-instance/isis-intfs/isis-intf-attr/ipv6-fast-reroute-tilfa-block. Add frr-feature.
16.Path:/configuration/route-isis/isis-instances/isis-instance/isis-intfs/isis-intf-attr/revise-metric. Add reverse-metric-feature.
17.Path:/configuration/route-isis/isis-instances/isis-instance/isis-intfs/isis-intf-attr/static-remote-lfas. Add remote-lfa-feature.' ;
  }

  revision 2022-12-31 {
    description '1.Path:/configuration/route-isis/isis-instances/isis-instance/frr-policy/policy-type/route-map. Add this case.
2.Path:/configuration/route-isis/isis-instances/isis-instance/frr-policy/policy-type/route-policy. Add this case.
3.Path:/configuration/route-isis/isis-instances/isis-instance/ipv6-frr-policy/policy-type/route-map. Add this case.
4.Path:/configuration/route-isis/isis-instances/isis-instance/ipv6-frr-policy/policy-type/route-policy. Add this case.' ;
  }

  revision 2022-12-29 {
    description '1.Path:/configuration/route-isis/isis-instances/isis-instance/bgp-link-states/bgp-ls/level-2-leak-ignore.Add this leaf.' ;
  }

  revision 2022-12-28 {
    description '1.Path:/configuration/route-isis/isis-instances/isis-instance/prefix-log.Add this container.
2.Path:/configuration/route-isis/isis-instances/isis-instance/ipv6-prefix-log.Add this container.' ;
  }

  revision 2022-12-09 {
    description '1.Path:/configuration/route-isis/isis-instances/isis-instance/redistributes/redis-isis-protocol/redis-isis/with-bier.Add this leaf.
2.Path:/configuration/route-isis/isis-instances/isis-instance/ipv6-redistributes/redis-isis-protocol/redis-isis/with-bier.Add this leaf.' ;
  }

  revision 2022-12-08 {
    description '1.Path:/configuration/route-isis/isis-instances/isis-instance/ipv6-route-calculate/egress-protection.Add this container.' ;
  }

  revision 2022-11-26 {
    description '1.Path:/configuration/route-isis/isis-instances/isis-instance/ipv4-distances/policy.Add this container.
2.Path:/configuration/route-isis/isis-instances/isis-instance/ipv6-distances/policy.Add this container.' ;
  }

  revision 2022-10-30 {
    description '1.Path:/configuration/route-isis/isis-instances/isis-instance/ipv4-microloop-prevention-te-tunnel.Add this container.
2.Path:/configuration/route-isis/isis-instances/isis-instance/ipv6-microloop-prevention-te-tunnel.Add this container.' ;
  }

  revision 2022-08-16 {
    description '1.Path:/configuration/route-isis/isis-instances/isis-instance/multi-instance. Add this container.' ;
  }

  revision 2022-07-20 {
    description '1.Path:/configuration/route-isis/isis-instances/isis-instance/default-info/default-info-branches/prefix-list-branch. Add this container.
2.Path:/configuration/route-isis/isis-instances/isis-instance/ipv6-def-info/default-info/prefix-list-branch. Add this container.
3.Path:/configuration/route-isis/isis-instances/isis-instance/srv6-compress. Modify container pc-feature to sr-feature.' ;
  }

  revision 2022-07-13 {
    description '1.Path:/configuration/route-isis/isis-instances/isis-instance/ipv4-sr-prefix-sid-consistent-in-lsp. Add this container.
2.Path:/configuration/route-isis/isis-instances/isis-instance/ipv6-sr-prefix-sid-consistent-in-lsp. Add this container.' ;
  }

  revision 2022-06-28 {
    description '1.Path:/configuration/route-isis/isis-instances/isis-instance/srv6-locators/srv6-locator/end-m-sids. Add this container.' ;
  }

  revision 2022-06-16 {
    description '1.Path:/configuration/route-isis/isis-instances/isis-instance/frr-remote-srlg-protection. Add this container.
2.Path:/configuration/route-isis/isis-instances/isis-instance/ipv6-frr-remote-srlg-protection. Add this container.
3.Path:/configuration/route-isis/isis-instances/isis-instance/srlg-parameters. Add this container.' ;
  }

  revision 2022-06-13 {
    description '1.Path:/configuration/route-isis/isis-instances/isis-instance/srv6-compress. Add this container.' ;
  }

  revision 2022-06-04 {
    description '1.Path:/configuration/route-isis/isis-instances/isis-isis/isis-instances/isis-instance/ipv6-l2-bundle. Add this container.' ;
  }

  revision 2022-05-31 {
    description '1.Path:/configuration/route-isis/isis-instances/isis-instance/ipv4-direct-prefix-inter-area-l1tol2. Add this container.
2.Path:/configuration/route-isis/isis-instances/isis-instance/ipv4-direct-prefix-inter-area-l2tol1. Add this container.
3.Path:/configuration/route-isis/isis-instances/isis-instance/ipv6-direct-prefix-inter-area-l1tol2. Add this container.
4.Path:/configuration/route-isis/isis-instances/isis-instance/ipv6-direct-prefix-inter-area-l2tol1. Add this container.' ;
  }

  revision 2022-05-13 {
    description '1.Path:/configuration/route-isis/isis-instances/isis-isis/isis-instances/isis-instance/isis-intfs/isis-intf-attr/link-damped-lag-detect-down-para. Add this container.
2.Path:/configuration/route-isis/isis-instances/isis-isis/isis-instances/isis-instance/isis-intfs/isis-intf-attr/ipv6-link-damped-lag-detect-down-para. Add this container.
3.Path:/configuration/route-isis/isis-instances/isis-isis/isis-instances/isis-instance/isis-intfs/isis-intf-attr/link-damped-bfd-down-para. Add this container.
4.Path:/configuration/route-isis/isis-instances/isis-isis/isis-instances/isis-instance/isis-intfs/isis-intf-attr/ipv6-link-damped-bfd-down-para. Add this container.' ;
  }

  revision 2022-04-08 {
    description '1.Path:/configuration/route-isis/isis-instances/isis-instance/srv6-locators/srv6-locator/end-sid/auto-compressed-sid. Add this container.
2.Path:/configuration/route-isis/isis-instances/isis-instance/srv6-locators/srv6-locator/end-sid/auto-multi-sids. Add this container.
3.Path:/configuration/route-isis/isis-instances/isis-instance/srv6-locators/srv6-locator/end-sid/auto-multi-compressed-sids. Add this container.
4.Path:/configuration/route-isis/isis-instances/isis-instance/srv6-locators/srv6-locator/end-x-sid/auto-compressed-sid. Add this container.
5.Path:/configuration/route-isis/isis-instances/isis-instance/srv6-locators/srv6-locator/end-x-sid/auto-multi-sids. Add this container.
6.Path:/configuration/route-isis/isis-instances/isis-instance/srv6-locators/srv6-locator/end-x-sid/auto-multi-compressed-sids. Add this container.' ;
  }

  revision 2022-03-28 {
    description '1.Modify bier-feature. Add 15K and T8000 project label.' ;
  }

  revision 2021-12-17 {
    description '1.Path:/state/route-isis/isis-instances. Add this container.
2.Path:/state/route-isis/isis-adjacencies/isis-adjacency/adj-circuit-id. Add this leaf.
3.Path:/configuration/route-isis/isis-instances/isis-instance/isis-intfs/isis-intf-attr/hello-padding/hello-padding-type. Add this leaf.
4.Path:/state/route-isis/isis-adjacencies/isis-adjacency.Add new select adj-system-id.' ;
  }

  revision 2021-10-17 {
    description '1.Path:/configuration/route-isis/isis-instances/isis-isis/isis-instances/isis-instance/prefix-independent-converge. Add this container.
2.Path:/configuration/route-isis/isis-instances/isis-isis/isis-instances/isis-instance/ipv6-prefix-independent-converge. Add this container.' ;
  }

  revision 2021-09-16 {
    description '1.Path:/configuration/route-isis/isis-instances/isis-instance/srv6-locators/srv6-locator/end-sid/auto/usd. This leaf cancels mandatory attribute.
2.Path:/configuration/route-isis/isis-instances/isis-instance/srv6-locators/srv6-locator/end-sid/compressed-sids/compressed-sid/usd. This leaf cancels mandatory attribute.
3.Path:/configuration/route-isis/isis-instances/isis-instance/srv6-locators/srv6-locator/end-sid/sids/sid/usd. This leaf cancels mandatory attribute.
4.Path:/configuration/route-isis/isis-instances/isis-instance/srv6-locators/srv6-locator/end-x-sid/auto/usd. This leaf cancels mandatory attribute.
5.Path:/configuration/route-isis/isis-instances/isis-instance/srv6-locators/srv6-locator/end-x-sid/compressed-sids/compressed-sid/usd. This leaf cancels mandatory attribute.
6.Path:/configuration/route-isis/isis-instances/isis-instance/srv6-locators/srv6-locator/end-x-sid/sids/sid/usd. This leaf cancels mandatory attribute.
7.Path:/configuration/route-isis/isis-instances/isis-instance/srv6-locators/srv6-locator/end-sid/auto/psp. This leaf cancels mandatory attribute.
8.Path:/configuration/route-isis/isis-instances/isis-instance/srv6-locators/srv6-locator/end-sid/compressed-sids/compressed-sid/psp. This leaf cancels mandatory attribute.
9.Path:/configuration/route-isis/isis-instances/isis-instance/srv6-locators/srv6-locator/end-sid/sids/sid/psp. This leaf cancels mandatory attribute.
10.Path:/configuration/route-isis/isis-instances/isis-instance/srv6-locators/srv6-locator/end-x-sid/auto/psp. This leaf cancels mandatory attribute.
11.Path:/configuration/route-isis/isis-instances/isis-instance/srv6-locators/srv6-locator/end-x-sid/compressed-sids/compressed-sid/psp. This leaf cancels mandatory attribute.
12.Path:/configuration/route-isis/isis-instances/isis-instance/srv6-locators/srv6-locator/end-x-sid/sids/sid/psp. This leaf cancels mandatory attribute.
13.Path:/configuration/route-isis/isis-instances/isis-instance/srv6-locators/srv6-locator/end-sid/auto/usp. This leaf cancels mandatory attribute.
14.Path:/configuration/route-isis/isis-instances/isis-instance/srv6-locators/srv6-locator/end-sid/compressed-sids/compressed-sid/usp. This leaf cancels mandatory attribute.
15.Path:/configuration/route-isis/isis-instances/isis-instance/srv6-locators/srv6-locator/end-sid/sids/sid/usp. This leaf cancels mandatory attribute.
16.Path:/configuration/route-isis/isis-instances/isis-instance/srv6-locators/srv6-locator/end-x-sid/auto/usp. This leaf cancels mandatory attribute.
17.Path:/configuration/route-isis/isis-instances/isis-instance/srv6-locators/srv6-locator/end-x-sid/compressed-sids/compressed-sid/usp. This leaf cancels mandatory attribute.
18.Path:/configuration/route-isis/isis-instances/isis-instance/srv6-locators/srv6-locator/end-x-sid/sids/sid/usp. This leaf cancels mandatory attribute.
19.Path:/configuration/route-isis/isis-instances/isis-isis/isis-instances/isis-instance/isis-intfs/isis-intf-attr/flapping-damping. Add delay-time range from 5 to 3600;
20.Path:/configuration/route-isis/isis-instances/isis-isis/isis-instances/isis-instance/isis-intfs/isis-intf-attr/flapping-damping/detect-parameter. Add interval range from 10 to 300.Add threshold range from 3 to 10.' ;
  }

  revision 2021-06-07 {
    description '1.Path:/configuration/route-isis/isis-instances/isis-isis/isis-instances/isis-instance/link-advertise-delay. Add this container.
2.Path:/configuration/route-isis/isis-instances/isis-isis/isis-instances/isis-instance/ipv6-link-advertise-delay. Add this container.
3.Path:/configuration/route-isis/isis-instances/isis-instance/spf-calculation-policy. Add this container.
4.Path:/configuration/route-isis/isis-instances/isis-instance/isis-attr/ipv6-spf-calculation-policy. Add this container.' ;
  }

  revision 2021-06-03 {
    description '1.Path:/configuration/route-isis/isis-instances/isis-instance/srv6-locators/srv6-locator/end-sid/auto/usd. Add this leaf.
2.Path:/configuration/route-isis/isis-instances/isis-instance/srv6-locators/srv6-locator/end-sid/compressed-sids/compressed-sid/usd. Add this leaf.
3.Path:/configuration/route-isis/isis-instances/isis-instance/srv6-locators/srv6-locator/end-sid/sids/sid/usd. Add this leaf.
4.Path:/configuration/route-isis/isis-instances/isis-instance/srv6-locators/srv6-locator/end-x-sid/auto/usd. Add this leaf.
5.Path:/configuration/route-isis/isis-instances/isis-instance/srv6-locators/srv6-locator/end-x-sid/compressed-sids/compressed-sid/usd. Add this leaf.
6.Path:/configuration/route-isis/isis-instances/isis-instance/srv6-locators/srv6-locator/end-x-sid/sids/sid/usd. Add this leaf.' ;
  }

  revision 2021-05-12 {
    description '1.Path:/configuration/route-isis/isis-instances/isis-isis/isis-instances/isis-instance/ldp-sync-hold-times. Add this container.
2.Path:/configuration/route-isis/isis-instances/isis-isis/isis-instances/isis-instance/ldp-sync-metrics. Add this container.
3.Path:/configuration/route-isis/isis-instances/isis-isis/isis-instances/isis-instance/ipv6-ldp-sync-hold-times. Add this container.
4.Path:/configuration/route-isis/isis-instances/isis-isis/isis-instances/isis-instance/ipv6-ldp-sync-metrics. Add this container.' ;
  }

  revision 2021-04-21 {
    description '1.Path:/configuration/route-isis/isis-instances/isis-isis/isis-instances/isis-instance/ipv4-summary-policys. Add this container.
2.Path:/configuration/route-isis/isis-instances/isis-isis/isis-instances/isis-instance/ipv6-summary-policys. Add this container.' ;
  }

  revision 2021-03-30 {
    description '1.Path:/configuration/route-isis/isis-instances/isis-attr/ipv4-distances/distance-with-rmp. Add this list.
2.Path:/configuration/route-isis/isis-instances/isis-attr/ipv6-distances/distance-with-rmp. Add this list.
3.Path:/isis:configuration/isis:route-isis/isis:isis-instances/isis:isis-instance/isis:srv6-locators. Add this container.' ;
  }

  revision 2021-03-16 {
    description '1.Modify sr-feature. Add 61V5_1 project label.' ;
  }

  revision 2021-03-03 {
    description '1.Path:/configuration/route-isis/isis-instances/isis-isis/isis-instances/isis-instance/isis-attr/crypto-authen-keychain-hmac-md5.Add this leaf.' ;
  }

  revision 2021-03-02 {
    description '1.Path:/configuration/route-isis/isis-instances/isis-isis/isis-instances/isis-instance/isis-intfs/isis-intf-attr/bfd-mode. Add this leaf.' ;
  }

  revision 2021-02-25 {
    description '1.Path:/configuration/route-isis/isis-instances/isis-instance/spf-intervals/spf-interval/interval. The default value is changed , and customized by the performance parameter.
2.Path:/configuration/route-isis/isis-instances/isis-instance/spf-intervals/spf-interval/init-delay. The default value is changed , and customized by the performance parameter.
3.Path:/configuration/route-isis/isis-instances/isis-instance/spf-intervals/spf-interval/wait-first-second. The default value is changed , and customized by the performance parameter.
4.Path:/configuration/route-isis/isis-instances/isis-instance/lsp-gen-intervals/lsp-gen-interval/init-delay. The default value is changed , and customized by the performance parameter.
5.Path:/configuration/route-isis/isis-instances/isis-instance/lsp-gen-intervals/lsp-gen-interval/max-delay. The default value is changed , and customized by the performance parameter.
6.Path:/configuration/route-isis/isis-instances/isis-instance/lsp-gen-intervals/lsp-gen-interval/wait-first-second. The default value is changed , and customized by the performance parameter.
7.Path:/configuration/route-isis/isis-instances/isis-instance/ipv6-spf-intervals/ipv6-spf-interval/interval. The default value is changed , and customized by the  performance parameter.
8.Path:/configuration/route-isis/isis-instances/isis-instance/ipv6-spf-intervals/ipv6-spf-interval/init-delay. The default value is changed , and customized by the  performance parameter.
9.Path:/configuration/route-isis/isis-instances/isis-instance/ipv6-spf-intervals/ipv6-spf-interval/wait-first-second. The default value is changed , and customized by the  performance parameter.' ;
  }

  revision 2021-02-24 {
    description '1.Path:/configuration/route-isis/isis-instances/isis-instance/isis-attr/auto-metric-ref-bandwidth. Modify the max value of this leaf node.
2.Path:/configuration/route-isis/isis-instances/isis-instance/isis-attr/ipv6-auto-metric-ref-bw. Modify the max value of this leaf node.' ;
  }

  revision 2021-02-23 {
    description '1.Path:/isis:configuration/isis:route-isis/isis:isis-instances/isis:isis-instance/isis:ipv4-frr-state/multi-home. Add this leaf.
2.Path:/isis:configuration/isis:route-isis/isis:isis-instances/isis:isis-instance/isis:ipv6-frr-state/multi-home. Add this leaf.
3.Path:/isis:configuration/isis:route-isis/isis:isis-instances/isis:isis-instance/isis:ipv4-frr-state/state. The leaf state was reset mandatory.
4.Path:/isis:configuration/isis:route-isis/isis:isis-instances/isis:isis-instance/isis:ipv6-frr-state/state. The leaf state was reset mandatory.' ;
  }

  revision 2021-02-05 {
    description '1.Path:/configuration/route-isis/isis-instances/isis-isis/isis-instances/isis-instance/isis-attr/prefix-attribute-advertise.Add this leaf.
2.Path:/configuration/route-isis/isis-instances/isis-isis/isis-instances/isis-instance/isis-attr/ipv6-prefix-attribute-advertise. Add this leaf.
3.Path:/configuration/global-config/ipv4-external-prefix-calculate-low-preference. Add this leaf.
4.Path:/configuration/global-config/ipv6-external-prefix-calculate-low-preference. Add this leaf.' ;
  }

  revision 2021-01-15 {
    description '1.Path:/configuration/route-isis/isis-instances/isis-isis/isis-instances/isis-instance/isis-attr/te-link-loss. Add this leaf.' ;
  }

  revision 2020-12-11 {
    description '1.Path:/isis:configuration/isis:route-isis/isis:isis-instances/isis:isis-instance/isis:isis-intfs/isis:isis-intf-attr/isis:fast-reroute-srlgs. The state of this container is changed from current to obsolete.
2.Path:/isis:configuration/isis:route-isis/isis:isis-instances/isis:isis-instance/isis:isis-intfs/isis:isis-intf-attr/isis:frr-srlgs. Add this container.' ;
  }

  revision 2020-12-10 {
    description '1.Path:/isis:configuration/isis:route-isis/isis:isis-instances/isis:isis-instance/isis:ipv6-redistributes/isis:redis-other-protocols/isis:redis-other-protocol/isis:protocol.
Add an enum type:nptv6.
2.Path:/configuration/route-isis/isis-instances/isis-isis/isis-instances/isis-instance/isis-attr/te-link-bandwidth. Add this leaf.' ;
  }

  revision 2020-11-13 {
    description '1.Path:/configuration/route-isis/isis-instances/isis-isis/isis-instances/isis-instance/isis-intfs/isis-intf-attr/fast-reroute-tilfa-block. Add this container.
2.Path:/configuration/route-isis/isis-instances/isis-isis/isis-instances/isis-instance/isis-intfs/isis-intf-attr/ipv6-fast-reroute-tilfa-block. Add this container.' ;
  }

  revision 2020-11-09 {
    description '1.Path:/configuration/route-isis/isis-instances/isis-isis/isis-instances/isis-instance/isis-ipv6-router-id. Add this container.' ;
  }

  revision 2020-10-16 {
    description '1.Path:/configuration/route-isis/isis-instances/isis-isis/isis-instances/isis-instance/ipv6-flex-algorithms. Add this container.' ;
  }

  revision 2020-10-13 {
    description '1.Path:/configuration/route-isis/isis-instances/isis-isis/isis-instances/isis-instance/isis-attr/adjacency-hold-time. Add this leaf.
2.Path:/configuration/route-isis/isis-instances/isis-isis/isis-instances/isis-instance/isis-attr/lsp-hold-time. Add this leaf.' ;
  }

  revision 2020-09-24 {
    description '1.Path:/configuration/route-isis/isis-instances/isis-instance/bier The state of this container is changed from current to obsolete.
2.Path:/configuration/route-isis/isis-instances/isis-instance/ipv4-bier. Add this container.
3.Path:/configuration/route-isis/isis-instances/isis-instance/ipv6-bier. Add this container.' ;
  }

  revision 2020-09-09 {
    description '1.Path:/configuration/route-isis/isis-instances/isis-instance/set-ol-bit/link-block. The state of this container is changed from current to obsolete.
2.Path:/configuration/route-isis/isis-instances/isis-instance/set-ol-bit/ol-link-block-attr. Add this container.' ;
  }

  revision 2020-08-26 {
    description '1.Path:/configuration/route-isis/isis-instances/isis-isis/isis-instances/isis-instance/ipv6-traffic-eng. Add this container.' ;
  }

  revision 2020-07-15 {
    description '1.Path:/configuration/route-isis/isis-instances/isis-isis/isis-instances/isis-instance/isis-intfs/isis-intf-attr/ipv4-bfd-template. Add this container.
2.Path:/configuration/route-isis/isis-instances/isis-isis/isis-instances/isis-instance/isis-intfs/isis-intf-attr/ipv6-bfd-template. Add this container.' ;
  }

  revision 2020-07-09 {
    description '1.Path:/configuration/global-config. Add this container.' ;
  }

  revision 2020-07-01 {
    description '1.Path:/configuration/route-isis/isis-instances/isis-instance/authentications/authentication/encrypted-pwd. Modify The length of this leaf node.
2.Path:/configuration/route-isis/isis-instances/isis-instance/isis-intfs/isis-intf-attr/authentications/authentication/encrypted-pwd. Modify The length of this leaf node.' ;
  }

  revision 2020-06-24 {
    description '1.Path:/configuration/route-isis/isis-instances/isis-attr/segment-routing-ipv6/end-sid. The state of this container is changed from current to obsolete.' ;
  }

  revision 2020-05-25 {
    description '1.Path:/configuration/route-isis/isis-instances/isis-instance/set-ol-bit/link-block. Add this container.
2.The length of routemap-name has changed.
3.The length of prefix has changed.
4.The length of prefix-list-name has changed.' ;
  }

  revision 2020-05-16 {
    description '1.Path:/configuration/route-isis/isis-instances/isis-attr/segment-routing-ipv6/end-sid/index. Add this list.
2.Path:/configuration/route-isis/isis-instances/isis-attr/segment-routing-ipv6/end-sid/non-psp.The state of this leaf is changed from current to obsolete.
3.Path:/configuration/route-isis/isis-instances/isis-attr/segment-routing-ipv6/end-sid/style. The state of this choice is changed from current to obsolete.' ;
  }

  revision 2020-04-23 {
    description '1.Path:/isis:configuration/isis:route-isis/isis:isis-instances/isis:isis-instance/isis:microloop-prevention-policy. Add this container.
2.Path:/isis:configuration/isis:route-isis/isis:isis-instances/isis:isis-instance/isis:frr-policy. Add this container.
3.Path:/isis:configuration/isis:route-isis/isis:isis-instances/isis:isis-instance/isis:ipv6-microloop-prevention-policy. Add this container.
4.Path:/isis:configuration/isis:route-isis/isis:isis-instances/isis:isis-instance/isis:ipv6-frr-policy. Add this container.' ;
  }

  revision 2020-04-15 {
    description '1.Path:/configuration/route-isis/isis-instances/isis-isis/isis-instances/isis-instance/isis-attr/te-link-loss-anomalous-attach-sd. Add this leaf.' ;
  }

  revision 2020-04-09 {
    description '1.Path:/configuration/route-isis/isis-instances/isis-attr/description. Add this leaf.
2.Path:/configuration/route-isis/isis-instances/isis-attr/segment-routing-mpls-adj-sid. Add this leaf.
3.Path:/configuration/route-isis/isis-instances/isis-attr/ipv6-segment-routing-mpls-adj-sid. Add this leaf.' ;
  }

  revision 2020-03-31 {
    description '1.Path:/isis:configuration/isis:route-isis/isis:isis-instances/isis:isis-instance/isis:isis-intfs/isis:isis-intf-attr/isis:fast-reroute-srlgs. Add this container.' ;
  }

  revision 2020-03-30 {
    description '1.Path:/configuration/route-isis/isis-instances/isis-instance/set-ol-bit. Add on-start-up-invalid-branch case.' ;
  }

  revision 2020-03-11 {
    description '1.Path:/configuration/route-isis/isis-instances/isis-attr/hostname-string. Add this leaf.' ;
  }

  revision 2020-02-11 {
    description '1.Path:/configuration/route-isis/isis-instances/isis-instance/aiis. Add this container.
2.Path:/configuration/route-isis/isis-instances/isis-instance/flex-algorithms. Add this container.' ;
  }

  revision 2020-01-07 {
    description '1.Path:/configuration/route-isis/isis-instances/isis-isis/isis-instances/isis-instance/isis-intfs/isis-intf-attr/reverse-metric. Add this container.' ;
  }

  revision 2019-12-13 {
    description '1.Path:/configuration/route-isis/isis-instances/isis-isis/isis-instances/isis-instance/isis-intfs/isis-intf-attr/flapping-damping. Add this container.
2.Path:/configuration/route-isis/isis-instances/isis-isis/isis-instances/isis-instance/isis-intfs/isis-intf-attr/flapping-damping/detect-parameter. Add this container.' ;
  }

  revision 2019-10-30 {
    description '1.Path:/configuration/route-isis/isis-instances/isis-instance/te-link-delay. Add this container.' ;
  }

  revision 2019-09-27 {
    description '1.Path:/configuration/route-isis/isis-instances/isis-instance/segment-routing-mpls/entropy-label. Add this container.
2.Path:/configuration/route-isis/isis-instances/isis-instance/ipv6-segment-routing-mpls/ipv6-entropy-label. Add this container.' ;
  }

  revision 2019-09-18 {
    description '1.Path:/configuration/route-isis/isis-instances/isis-isis/isis-instances/isis-instance/isis-intfs/isis-intf-attr/link-damped-bfd-down. Add this container.
2.Path:/configuration/route-isis/isis-instances/isis-isis/isis-instances/isis-instance/isis-intfs/isis-intf-attr/ipv6-link-damped-bfd-down. Add this container.' ;
  }

  revision 2019-09-02 {
    description '1.Path:/configuration/route-isis/isis-instances/isis-instance/frr-priority. Add ti-lfa-priority leaf.' ;
  }

  revision 2019-08-13 {
    description '1.Path:/configuration/route-isis/isis-instances/isis-isis/isis-instances/isis-instance/isis-intfs/isis-intf-attr/ipv6-metrics. Add this container.' ;
  }

  revision 2019-08-08 {
    description '1.Path:/configuration/route-isis/isis-instances/isis-isis/isis-instances/isis-instance/isis-intfs/isis-intf-attr/link-damped-link-sd. Add this container.
2.Path:/configuration/route-isis/isis-instances/isis-isis/isis-instances/isis-instance/isis-intfs/isis-intf-attr/ipv6-link-damped-link-sd. Add this container.
3.Path:/configuration/route-isis/isis-instances/isis-isis/isis-instances/isis-instance/isis-intfs/isis-intf-attr/link-damped-lag-detect-down. Add this container.
4.Path:/configuration/route-isis/isis-instances/isis-isis/isis-instances/isis-instance/isis-intfs/isis-intf-attr/ipv6-link-damped-lag-detect-down. Add this container.' ;
  }

  revision 2019-08-05 {
    description '1.Path:/configuration/route-isis/isis-instances/isis-instance/route-leak-l1tol2. Add without-prefix-sid leaf.
2.Path:/configuration/route-isis/isis-instances/isis-instance/route-leak-l1tol2. Add host-only leaf.
3.Path:/configuration/route-isis/isis-instances/isis-instance/route-leak-l2tol1. Add without-prefix-sid leaf.
4.Path:/configuration/route-isis/isis-instances/isis-instance/route-leak-l2tol1. Add host-only leaf.
5.Path:/configuration/route-isis/isis-instances/isis-instance/redistributes/redis-isis-protocol/redis-isis. Add without-prefix-sid leaf.
6.Path:/configuration/route-isis/isis-instances/isis-instance/redistributes/redis-isis-protocol/redis-isis. Add host-only leaf.
7.Path:/configuration/route-isis/isis-instances/isis-instance/redistributes/redis-ospf-protocol/redis-ospf. Add without-prefix-sid leaf.
8.Path:/configuration/route-isis/isis-instances/isis-instance/redistributes/redis-ospf-protocol/redis-ospf. Add host-only leaf.
9.Path:/configuration/route-isis/isis-instances/isis-instance/redistributes/redis-other-protocols/redis-other-protocol. Add without-prefix-sid leaf.
10.Path:/configuration/route-isis/isis-instances/isis-instance/redistributes/redis-other-protocols/redis-other-protocol. Add host-only leaf.
11.Path:/configuration/route-isis/isis-instances/isis-instance/ipv6-route-leak-l1tol2. Add without-prefix-sid leaf.
12.Path:/configuration/route-isis/isis-instances/isis-instance/ipv6-route-leak-l1tol2. Add host-only leaf.
13.Path:/configuration/route-isis/isis-instances/isis-instance/ipv6-route-leak-l2tol1. Add without-prefix-sid leaf.
14.Path:/configuration/route-isis/isis-instances/isis-instance/ipv6-route-leak-l2tol1. Add host-only leaf.
15.Path:/configuration/route-isis/isis-instances/isis-instance/ipv6-redistributes/redis-isis-protocol/redis-isis. Add without-prefix-sid leaf.
16.Path:/configuration/route-isis/isis-instances/isis-instance/ipv6-redistributes/redis-isis-protocol/redis-isis. Add host-only leaf.
17.Path:/configuration/route-isis/isis-instances/isis-instance/ipv6-redistributes/redis-ospf-protocol/redis-ospf. Add without-prefix-sid leaf.
18.Path:/configuration/route-isis/isis-instances/isis-instance/ipv6-redistributes/redis-ospf-protocol/redis-ospf. Add host-only leaf.
19.Path:/configuration/route-isis/isis-instances/isis-instance/ipv6-redistributes/redis-other-protocols/redis-other-protocol. Add without-prefix-sid leaf.
20.Path:/configuration/route-isis/isis-instances/isis-instance/ipv6-redistributes/redis-other-protocols/redis-other-protocol. Add host-only leaf.' ;
  }

  revision 2019-07-26 {
    description '1.Path:/configuration/route-isis/isis-instances/isis-instance/ipv6-microloop-prevention-segment-routing. Add this container.' ;
  }

  revision 2019-07-23 {
    description '1.Path:/configuration/route-isis/isis-instances/isis-instance/ipv6-frr-ti-lfa-sr-mpls. Add this container.
2.Path:/configuration/route-isis/isis-instances/isis-instance/frr-ti-lfa.Add strategy leaf.
3.Path:/configuration/route-isis/isis-instances/isis-instance/ipv6-frr-ti-lfa.Add strategy leaf.' ;
  }

  revision 2019-07-02 {
    description '1.Path:/configuration/route-isis/isis-instances/isis-isis/isis-instances/isis-instance/isis-intfs/isis-intf-attr/link-damped-metric. Add this container.
2.Path:/configuration/route-isis/isis-instances/isis-isis/isis-instances/isis-instance/isis-intfs/isis-intf-attr/ipv6-link-damped-metric. Add this container.
3.Path:/configuration/route-isis/isis-instances/isis-isis/isis-instances/isis-instance/isis-intfs/isis-intf-attr/link-metric. The state of this container is changed from current to obsolete.
4.Path:/configuration/route-isis/isis-instances/isis-isis/isis-instances/isis-instance/isis-intfs/isis-intf-attr/link-damping. The state of this container is changed from current to obsolete.
5.Path:/configuration/route-isis/isis-instances/isis-isis/isis-instances/isis-instance/isis-intfs/isis-intf-attr/mt-ipv6-link-damping. The state of this container is changed from current to obsolete.' ;
  }

  revision 2019-04-11 {
    description '1.Path:/configuration/route-isis/isis-instances/isis-isis/isis-instances/isis-instance/isis-intfs/isis-intf-attr/link-damped-adj-establish. Add this container.
2.Path:/configuration/route-isis/isis-instances/isis-isis/isis-instances/isis-instance/isis-intfs/isis-intf-attr/ipv6-link-damped-adj-establish. Add this container.
3.Path:/configuration/route-isis/isis-instances/isis-isis/isis-instances/isis-instance/isis-intfs/isis-intf-attr/link-damped-revert-interval. Add this container.
4.Path:/configuration/route-isis/isis-instances/isis-isis/isis-instances/isis-instance/isis-intfs/isis-intf-attr/ipv6-link-damped-revert-interval. Add this container.' ;
  }

  revision 2019-03-18 {
    description '1.Path:/configuration/route-isis/isis-instances/isis-instance/segment-routing-ipv6/ipv6-sr-mpls-mapping-server.The state of this container is changed from current to obsolete.' ;
  }

  revision 2019-01-28 {
    description '1.Path:/configuration/route-isis/isis-instances/isis-instance/ipv6-segment-routing-mpls.Add this container.
2.Add sr-feature.' ;
  }

  revision 2019-01-08 {
    description '1.Path:/configuration/route-isis/isis-instances/isis-instance/microloop-prevention-segment-routing. Add this container.' ;
  }

  revision 2018-10-19 {
    description '1.Path:/configuration/route-isis/isis-instances/isis-instance/segment-routing-ipv6. The state of this container is changed from obsolete to current.
2.Path:/configuration/route-isis/isis-instances/isis-instance/ipv6-frr-ti-lfa. The state of this container is changed from obsolete to current.
3.Path:/configuration/route-isis/isis-instances/isis-instance/bgp-link-states/bgp-ls/instance-id. Add this container.' ;
  }

  revision 2018-09-11 {
    description '1.Path:/state/route-isis/isis-peer-routerids/isis-peer-routerid. Add this container.
2.Path:/state/route-isis/isis-adjacencies/isis-adjacency/adj-id. Add this leaf.
3.Path:/state/route-isis/isis-adjacencies/isis-adjacency/adj-2way-state. Add this leaf.
4.Path:/state/route-isis/isis-adjacencies/isis-adjacency/adj-last-uptime. Add this leaf.
5.Path:/configuration/route-isis/isis-instances/isis-instance/microloop-prevention-rlfa.Add this container.
6.Path:/configuration/route-isis/isis-instances/isis-instance/ipv6-microloop-prevention-link-up. Add this container.' ;
  }

  revision 2018-09-07 {
    description '1.Path:/configuration/route-isis/isis-instances/isis-instance/segment-routing-ipv6. Add this container.
2.Path:/configuration/route-isis/isis-instances/isis-instance/segment-routing-ipv6. The state of this container is changed from current to obsolete.
3.Path:/configuration/route-isis/isis-instances/isis-instance/frr-ti-lfa. Add this container.
4.Path:/configuration/route-isis/isis-instances/isis-instance/ipv6-frr-ti-lfa. Add this container.
5.Path:/configuration/route-isis/isis-instances/isis-instance/ipv6-frr-ti-lfa. The state of this container is changed from current to obsolete.
6.Path:/configuration/route-isis/isis-instances/isis-instance/segment-routing-mpls/sr-mpls-mapping-server. Add this container.
7.Path:/configuration/route-isis/isis-instances/isis-isis/isis-instances/isis-instance/isis-intfs/isis-intf-attr/link-metric/inc-metric. The default value is changed from increase-value to maximum-value.
8.Path:/configuration/route-isis/isis-instances/isis-isis/isis-instances/isis-instance/isis-intfs/isis-intf-attr/link-metric/inc-metric/increase-value/inc-value. The default value is abolished.
9.Path:/state/route-isis/isis-adjacencies/isis-adjacency. Add some selects.
10.Path:/state/route-isis/isis-circuits/isis-circuit. Add some selects.
11.Path:/configuration/route-isis/isis-instances/isis-intfs/ipv4-bfd-negotiation/min-tx. The range is changed , and customized by the  performance parameter.
12.Path:/configuration/route-isis/isis-instances/isis-intfs/ipv4-bfd-negotiation/min-rx. The range is changed , and customized by the  performance parameter.
13.Path:/configuration/route-isis/isis-instances/isis-intfs/ipv6-bfd-negotiation/min-tx. The range is changed , and customized by the  performance parameter.
14.Path:/configuration/route-isis/isis-instances/isis-intfs/ipv6-bfd-negotiation/min-rx. The range is changed , and customized by the  performance parameter.' ;
  }

  revision 2017-08-25 {
    description '1.Path:/configuration/route-isis/isis-instances/isis-instance/bier. Add this container.
2.Add pc-feature. This feature only use for PC.' ;
  }

  revision 2017-07-18 {
    description '1.Path:/configuration/route-isis/isis-instances/rlfa-exclude-ldp-not-sync. Add this container.
2.Add rlfa-exclude-ldp-not-sync.' ;
  }

  revision 2017-06-27 {
    description '1.Path:/configuration/route-isis/isis-instances/isis-intfs/metrics/metric-value. The minimum value of sub-node is changed from 1 into 0.' ;
  }

  revision 2017-06-06 {
    description '1.Path:/configuration/route-isis/isis-instances/isis-intfs/link-damping. Add this container.
2.Path:/configuration/route-isis/isis-instances/isis-intfs/mt-ipv6-link-damping. Add this container.
3.Add link-damping.
3.Add mt-ipv6-link-damping.' ;
  }

  revision 2016-12-07 {
    description '1.Path:/configuration/route-isis/isis-instances/isis-instance/segment-routing-mpls.Add this container.
2.Add sr-feature.' ;
  }

  revision 2016-09-19 {
    description '1.Path:/configuration/route-isis/isis-instances/isis-instance/microloop-prevention-rlfa.Add this container.' ;
  }

  revision 2016-08-04 {
    description '1.Path:/configuration/route-isis/isis-instances/isis-instance/def-info-learns.Add this container;
2.Path:/configuration/route-isis/isis-instances/isis-instance/default-info/default-info-branches/def-rib-match.Add this container;
3.Path:/configuration/route-isis/isis-instances/isis-instance/ipv6-def-info.Add this container;
4.Path:/configuration/route-isis/isis-instances/isis-instance/ipv6-def-info-learns.Add this container;
5.Path:/configuration/route-isis/isis-instances/isis-instance/ipv6-mpls-ldp-sync. Add this container;
6.Path:/configuration/route-isis/isis-instances/isis-instance/authen-keychains. Add this container;
7.Path:/configuration/route-isis/isis-instances/isis-intfs/isis-intf-attr/ipv6-mpls-ldps .Add this container.
8.Path:/configuration/route-isis/isis-instances/isis-intfs/isis-intf-attr/authen-keychains .Add this container.
9.Path:/configuration/route-isis/isis-instances/isis-intfs/isis-intf-attr/intf-hello-padding .Add this container.
10.Path:/configuration/route-isis/isis-instances/isis-instance/isis-attr.Add ipv6-auto-metric-state leaf.
11.Path:/configuration/route-isis/isis-instances/isis-instance/isis-attr.Add ipv6-auto-metric-ref-bw leaf.
12.Path:/configuration/route-isis/isis-instances/isis-instance/metrics.Add this container;
13.Path:/configuration/route-isis/isis-instances/isis-instance/ipv6-metrics.Add this container.' ;
  }

  revision 2016-03-16 {
    description 'Path:/configuration/route-isis/isis-instances/isis-instance/bgp-link-states. Add this container.' ;
  }

  revision 2015-09-22 {
    description '1.Path:/configuration/route-isis/isis-instances/isis-instance/router-id/router-id.Add this container;
2.Path:/configuration/route-isis/isis-instances/isis-instance/remote-lfa-state.Add this container;
3.Path:/configuration/route-isis/isis-instances/isis-instance/remote-lfa-max-metrics.Add this container;
4.Path:/configuration/route-isis/isis-instances/isis-instance/frr-priority. Add this container;
5.Path:/configuration/route-isis/isis-instances/isis-intfs/isis-intf-attr/fast-remote-lfa-block .Add this container.' ;
  }

  revision 2015-08-11 {
    description '1.Path: /configuration/route-isis/isis-instances/isis-instance/ipv4-distribute-list. Add this container' ;
  }

  revision 2015-08-04 {
    description "Change config flag of state node and it's sub-node from true into false." ;
  }

  revision 2015-07-21 {
    description '1.The path:/configuration/route-isis/isis-instances/isis-instance/isis-attr.Add auto-metric-state leaf.
2.The path:/configuration/route-isis/isis-instances/isis-instance/isis-attr.Add auto-metric-ref-bandwidth leaf.
3.The path:/configuration/route-isis/isis-instances/isis-intfs/isis-intf-attr/ipv4-bfd-negotiation. Add this container.
4.The path:/configuration/route-isis/isis-instances/isis-intfs/isis-intf-attr/ipv6-bfd-negotiation. Add this container.
5.The path:/configuration/route-isis/isis-instances/isis-instance/track-objects. Add this container.' ;
  }

  revision 2015-04-02 {
    description 'The path:/state/route-isis/isis/isis-adjacencies/isis-adjacency.
The isis-adjacency list add adj-vrf-name leaf.' ;
  }

  revision 2015-03-10 {
    description 'The path:/state/route-isis/isis/isis-adjacencies/isis-adjacency.
The isis-adjacency list add adj-system-type leaf and adj-extended-circ-id leaf.' ;
  }

  revision 2015-03-09 {
    description '1.Path: /configuration/route-isis/isis-instances/isis-instance/ipv4-redis-prefix-limits. Add this container
2.Path: /configuration/route-isis/isis-instances/isis-instance/ipv6-redis-prefix-limits. Add this container' ;
  }

  revision 2015-01-09 {
    description '1.Path:/configuration/route-isis/isis-instances/isis-instance/isis-intfs/isis-intf-attr/link-metric.Add this container' ;
  }

  revision 2014-11-03 {
    description 'The path:/configuration/route-isis/isis-instances/isis-intfs/isis-intf-attr/static-remote-lfas. Add this container.' ;
  }

  revision 2014-10-21 {
    description '1.Path:/configuration/route-isis/isis-instances/isis-instance/isis-attr/ipv6-distance. This leaf is out of use.
2.Path:/configuration/route-isis/isis-instances/isis-instance/isis-attr/distance.This leaf is out of use.
3.Path:/configuration/route-isis/isis-instances/isis-instance/ipv4-distances.
  Add this container.
4.Path:/configuration/route-isis/isis-instances/isis-instance/ipv6-distances.
  Add this container.' ;
  }

  revision 2014-10-14 {
    description 'Path:/isis:configuration/isis:route-isis/isis:isis-instances/isis:isis-instance/isis:ipv6-redistributes/isis:redis-other-protocols/isis:redis-other-protocol/isis:protocol
Add an enum type:dhcp-pd.' ;
  }

  revision 2014-07-04 {
    description 'The path:/configuration/route-isis/isis-instances/isis-instance/restart-t2-timers/restart-t2-timer/t2-timer
The default value of t2-timer changed from 60 into 330.' ;
  }

  revision 2014-06-19 {
    description '1.Modify some descriptions, which had mistakes or were imperfect.
2.The leaf t3-timer-value was set mandatory.
3.The range of tag-number changed from 0..4294967295 into 1..4294967295.
4.The type of leaf auto changed from boolean into empty.
5.The type of leaf wait-for-bgp changed from boolean into empty.
6.Modify mesh-group model.
7.Modify set-ol-bit model.
8.Modify redistribute model.' ;
  }

  revision 2014-05-05 {
    description '1.Modify some spelling mistakes.
2.Add description on some enum items which description was lack.
3.Change the type of adj-snpa-address from string into string-all.
  Change the type of circuit-state from string into string-all.
  Change the type of adj-state from string into string-all.
4.The type of level in redistributes change from uint8 into enumeration.
5.The range of circuit-l1-dr modify from 0-17 into 1-17.
6.Add default value on interval leaf of spf-interval.
  Add default value on metric-style.
7.Add two typedef:isis-level and isis-state.' ;
  }

  revision 2014-04-18 {
    description 'Change the object of system-id from container to list.
The leaf of state in route-leak-l2tol1 is set mandatory.
The leaf of state in ipv6-route-leak-l2tol1 is set mandatory.' ;
  }

  revision 2013-10-30 {
    description 'The initial version.' ;
  }

  feature sr-feature {
    description 'Only for the use of 15K ,T8K and PC.' ;
    status current ;

  }

  feature pc-feature {
    description 'Router and switch PC feature.' ;
    status current ;

  }

  feature aii-feature {
    description 'Router and switch aii feature.' ;
    status current ;

  }

  feature bier-feature {
    description 'Router and switch bier feature.' ;
    status current ;

  }

  feature bier-lfa-feature {
    description 'Exclude 15K and T8K.' ;
    status current ;

    ncd:revise-date 2024-08-13 ;
  }

  feature frr-feature {
    description 'Fast reroute feature.' ;
    status current ;

    ncd:revise-date 2023-02-20 ;
  }

  feature reverse-metric-feature {
    description 'Reverse metric feature.' ;
    status current ;

    ncd:revise-date 2023-02-20 ;
  }

  feature micr-sr-feature {
    description 'Microloop prevention segment routing feature.' ;
    status current ;

    ncd:revise-date 2023-02-20 ;
  }

  feature te-link-feature {
    description 'Te link loss feature.' ;
    status current ;

    ncd:revise-date 2023-02-20 ;
  }

  feature bfd-feature {
    description 'Bfd mode feature.' ;
    status current ;

    ncd:revise-date 2023-02-20 ;
  }

  feature remote-lfa-feature {
    description 'Static remote lfa feature.' ;
    status current ;

    ncd:revise-date 2023-02-20 ;
  }

  feature intf-ldp-sync-feature {
    description 'Interface LDP-ISIS synchronization feature.' ;
    status current ;

    ncd:revise-date 2025-04-25 ;
  }

  feature srv6-adjacency-set-feature {
    description 'SRv6 adjacency set feature.' ;
    status current ;

    ncd:revise-date 2025-05-13 ;
  }

  typedef isis-level {
    description 'Level(s) will be effected on.' ;
    type enumeration {
      enum level-1 {
        value 1 ;
        description 'Level-1 will be effected on.' ;
        status current ;

      }

      enum level-2 {
        value 2 ;
        description 'Level-2 will be effected on.' ;
        status current ;

      }

      enum level-1-2 {
        value 3 ;
        description 'Level-1-2 will be effected on.' ;
        status current ;

      }

    }

  }

  typedef isis-state {
    description 'The state of some isis attributes.' ;
    type enumeration {
      enum disable {
        value 0 ;
        description 'The state is off.' ;
        status current ;

      }

      enum enable {
        value 1 ;
        description 'The state is on.' ;
        status current ;

      }

    }

  }

  container configuration {
    description 'Configuration.' ;
    container route-isis {
      description 'Route ISIS configuration.' ;
      container isis-instances {
        description 'ISIS instance information.' ;
        list isis-instance {
          description 'The information of ISIS instance.' ;
          key process-id ;
          leaf process-id {
            description 'ISIS process ID' ;
            type uint32 {
              range 0..65535 ;

            }

            config true ;
            mandatory false ;
          }

          leaf vrf-name {
            description 'VPN routing/forwarding instance (VRF) name.' ;
            type string {
              length 1..32 ;

            }

            config true ;
            mandatory false ;
          }

          container multi-instance {
            description 'Configure multiple instance.' ;
            leaf instance-id {
              description 'Instance ID.' ;
              type uint32 {
                range 1..65535 ;

              }

              config true ;
              mandatory false ;
            }

            config true ;
            ncd:revise-date 2022-08-16 ;
          }

          container system-ids {
            description 'System id.' ;
            list system-id {
              description 'System-ID.' ;
              key isis-system-id ;
              max-elements 1 ;
              leaf isis-system-id {
                description 'A system ID for an ISIS instance.' ;
                type ncd:mac-address ;

                config true ;
                mandatory false ;
              }

              leaf range {
                description 'The range of system-ID.' ;
                type uint8 {
                  range 0..32 ;

                }

                default 0 ;
                config true ;
                mandatory false ;
              }

              config true ;
            }

            config true ;
          }

          container authentications {
            description 'Authentication information.' ;
            presence "encrypted password" ;
            list authentication {
              description 'Authentication information.' ;
              key level ;
              leaf level {
                description 'Level(s) will be effected on.' ;
                type uint8 {
                  range 0..2 ;

                }

                config true ;
                mandatory false ;
              }

              choice authen-word {
                description 'Password' ;
                case word {
                  description 'Word case.' ;
                  leaf authen-pwd {
                    description 'The clear password.' ;
                    type string {
                      length 1..100 ;

                    }

                    config true ;
                    mandatory true ;
                  }

                }

                case clear {
                  description 'Authentication clear password case.' ;
                  leaf clear-pwd {
                    description 'Specify the clear password.' ;
                    type string {
                      length 1..100 ;

                    }

                    config true ;
                    mandatory true ;
                  }

                }

                case encrypted-word {
                  description 'The label of encrypted password' ;
                  leaf encrypted-pwd {
                    description 'Authentication encrypted password' ;
                    type string {
                      length 24..192 ;

                    }

                    config true ;
                    mandatory true ;
                  }

                }

                config true ;
                mandatory false ;
              }

              config true ;
            }

            config true ;
          }

          container authentication-types {
            description 'Authentication type.' ;
            presence "authen type" ;
            list authen-type {
              description 'Authentication type' ;
              key level ;
              leaf level {
                description 'Level(s) would be effected on.' ;
                type uint8 {
                  range 0..2 ;

                }

                config true ;
                mandatory false ;
              }

              leaf authen-type {
                description 'Authentication type.' ;
                type enumeration {
                  enum md5 {
                    value 1 ;
                    status current ;

                  }

                  enum text {
                    value 2 ;
                    status current ;

                  }

                }

                default text ;
                config true ;
                mandatory false ;
              }

              config true ;
            }

            config true ;
          }

          container areas {
            description 'Areas.' ;
            list area {
              description 'Area address information.' ;
              key area-addr ;
              max-elements 3 ;
              leaf area-addr {
                description 'ISIS area address' ;
                type ncd:area-id ;

                config true ;
                mandatory false ;
              }

              config true ;
            }

            config true ;
          }

          container isis-attr {
            description 'ISIS attribution.' ;
            leaf isis-protocol-state {
              description 'Flag of that system is enable.' ;
              type isis-state ;

              default enable ;
              config true ;
              mandatory false ;
            }

            leaf is-type {
              description 'Level(s) of the ISIS instance.' ;
              type isis-level ;

              default level-1-2 ;
              config true ;
              mandatory false ;
            }

            leaf i-spf {
              description 'Flag of the i-spf is enable.' ;
              type boolean ;

              config true ;
              mandatory false ;
            }

            leaf distance {
              description 'IPv4 management distance.This leaf is out of use. The value of output is invalid.' ;
              type uint8 {
                range 1..255 ;

              }

              default 115 ;
              config true ;
              mandatory false ;
            }

            leaf maximum-paths {
              description 'Maximum of paths to one destination.' ;
              type uint32 {
                range 1..128 ;

              }

              default 1 ;
              config true ;
              mandatory false ;
            }

            leaf lsp-size-originate {
              description 'LSP MTU' ;
              type uint16 {
                range 512..7680 ;

              }

              units byte ;
              default 1492 ;
              config true ;
              mandatory false ;
            }

            leaf lsp-size-recieve {
              description 'The size of LSP can be received.' ;
              type uint16 {
                range 512..7680 ;

              }

              units byte ;
              default 1492 ;
              config true ;
              mandatory false ;
            }

            leaf snp-authentication-state {
              description 'Flag of the ISIS instance whether support SNP authentication.' ;
              type enumeration {
                enum disable-snp-authentication {
                  value 0 ;
                  description 'Config disable-snp-authentication.' ;
                  status current ;

                }

                enum enable-snp-authentication {
                  value 1 ;
                  description 'Config enable-snp-authentication.' ;
                  status current ;

                }

              }

              default enable-snp-authentication ;
              config true ;
              mandatory false ;
            }

            leaf ignore-lsp-errors {
              description 'Flag of the system whether would ignore LSP checksum error.' ;
              type isis-state ;

              default enable ;
              config true ;
              mandatory false ;
            }

            leaf lsp-refresh-time {
              description 'LSP refresh interval.' ;
              type uint16 {
                range 1..65535 ;

              }

              units second ;
              default 900 ;
              config true ;
              mandatory false ;
            }

            leaf max-lsp-lifetime {
              description 'Max LSP life time.' ;
              type uint16 {
                range 1..65535 ;

              }

              units second ;
              default 1200 ;
              config true ;
              mandatory false ;
            }

            leaf restart-state {
              description 'Flag of the system whether enable GR.' ;
              type isis-state ;

              config true ;
              mandatory false ;
            }

            leaf snmp-context {
              description 'ISIS mib context name' ;
              type string {
                length 1..30 ;

              }

              config true ;
              mandatory false ;
            }

            leaf local-mt-state {
              description 'Flag of that IGP-MT is enable.' ;
              type isis-state ;

              config true ;
              mandatory false ;
            }

            leaf fast-reroute-type {
              description 'FRR type' ;
              type enumeration {
                enum down-stream-path {
                  value 1 ;
                  status current ;

                }

              }

              config true ;
              mandatory false ;
            }

            leaf hostname-dynamic {
              description 'Dynamic hostname.' ;
              type isis-state ;

              default enable ;
              config true ;
              mandatory false ;
            }

            leaf fast-flood-num {
              description 'Number of the fast flooding LSPs.' ;
              type uint8 {
                range 1..15 ;

              }

              config true ;
              mandatory false ;
            }

            leaf ipv6-frr-type {
              description 'IPv6 fast-reroute type.' ;
              type enumeration {
                enum down-stream-path {
                  value 1 ;
                  description 'The FRR type is down-stream-path.' ;
                  status current ;

                }

              }

              config true ;
              mandatory false ;
            }

            leaf ipv6-distance {
              description 'ISIS IPv6 management distance.This leaf is out of use. The value of output is invalid.' ;
              type uint8 {
                range 1..255 ;

              }

              default 115 ;
              config true ;
              mandatory false ;
            }

            leaf ipv6-maximum-paths {
              description 'Maximum of paths to one destination of IPv6.' ;
              type uint32 {
                range 1..128 ;

              }

              default 1 ;
              config true ;
              mandatory false ;
            }

            leaf ipv6-set-ol-bit {
              description 'Set IPv6 OL bit.' ;
              type boolean ;

              config true ;
              mandatory false ;
            }

            leaf mpls-ldp-auto-config {
              description 'The state of mpls ldp auto-config.' ;
              type isis-state ;

              config true ;
              mandatory false ;
            }

            leaf auto-metric-state {
              description 'Whether adjust IS-IS interface metric according to bandwidth.' ;
              type isis-state ;

              default disable ;
              config true ;
              mandatory false ;
              ncd:revise-date 2015-07-21 ;
            }

            leaf auto-metric-ref-bandwidth {
              description 'Use reference bandwidth to assign IS-IS metric' ;
              type uint32 {
                range 1..2147483648 ;

              }

              default 100 ;
              config true ;
              mandatory false ;
              ncd:revise-date 2015-07-21 ;
            }

            leaf ipv6-auto-metric-state {
              description 'Whether adjust IS-IS IPv6 interface metric according to bandwidth.' ;
              type isis-state ;

              default disable ;
              config true ;
              mandatory false ;
              ncd:revise-date 2016-08-04 ;
            }

            leaf ipv6-auto-metric-ref-bw {
              description 'Use reference bandwidth to assign IS-IS IPv6 metric' ;
              type uint32 {
                range 1..2147483648 ;

              }

              default 100 ;
              config true ;
              mandatory false ;
              ncd:revise-date 2016-08-04 ;
            }

            leaf hostname-string {
              description 'ISIS hostname for instance' ;
              type string {
                length 1..64 ;

              }

              config true ;
              mandatory false ;
              ncd:revise-date 2020-03-11 ;
            }

            leaf description {
              description 'Description of process.' ;
              type string {
                length 1..63 ;

              }

              config true ;
              mandatory false ;
              ncd:revise-date 2020-04-09 ;
            }

            leaf segment-routing-mpls-adj-sid {
              if-feature sr-feature ;

              description 'Add the application mode of segment-routing-mpls-adj-sid.' ;
              type enumeration {
                enum hybrid {
                  value 1 ;
                  description 'Hybrid mode.' ;
                  status current ;

                }

                enum static {
                  value 0 ;
                  description 'Static mode.' ;
                  status current ;

                }

              }

              default hybrid ;
              config true ;
              mandatory false ;
              ncd:revise-date 2020-04-09 ;
            }

            leaf ipv6-segment-routing-mpls-adj-sid {
              if-feature sr-feature ;

              description 'Add the application mode of ipv6-segment-routing-mpls-adj-sid.' ;
              type enumeration {
                enum hybrid {
                  value 1 ;
                  description 'Hybrid mode.' ;
                  status current ;

                }

                enum static {
                  value 0 ;
                  description 'Static mode.' ;
                  status current ;

                }

              }

              default hybrid ;
              config true ;
              mandatory false ;
              ncd:revise-date 2020-04-09 ;
            }

            leaf te-link-loss-anomalous-attach-sd {
              if-feature te-link-feature {
                ncd:revise-date 2023-02-20 ;
              }

              description 'Advertise te link loss anomalous attached with sd.' ;
              type enumeration {
                enum disable {
                  value 0 ;
                  description 'Disable advertise te link loss anomalous attached with sd.' ;
                  status current ;

                }

                enum attach-sd {
                  value 1 ;
                  description 'Advertise te link loss anomalous attached with sd.' ;
                  status current ;

                }

              }

              default disable ;
              config true ;
              mandatory false ;
              ncd:revise-date 2020-04-15 ;
            }

            leaf adjacency-hold-time {
              description 'Adjacency hold time.' ;
              type uint16 {
                range 0..65535 ;

              }

              units second ;
              default 0 ;
              config true ;
              mandatory false ;
              ncd:revise-date 2020-10-13 ;
            }

            leaf lsp-hold-time {
              description 'Lsp hold time' ;
              type uint16 {
                range 0..65535 ;

              }

              units second ;
              default 0 ;
              config true ;
              mandatory false ;
              ncd:revise-date 2020-10-13 ;
            }

            leaf te-link-bandwidth {
              description 'Advertise te link bandwidth.' ;
              type isis-state ;

              default disable ;
              config true ;
              mandatory false ;
              ncd:revise-date 2020-12-10 ;
            }

            leaf te-link-loss {
              description 'Advertise te link bandwidth.' ;
              type isis-state ;

              default disable ;
              config true ;
              mandatory false ;
              ncd:revise-date 2021-01-15 ;
            }

            leaf prefix-attribute-advertise {
              description 'Set ipv4 prefix-attribute advertise mode' ;
              type enumeration {
                enum auto {
                  value 0 ;
                  description 'Some prefix with prefix-attribute sub-TLV according to scenario' ;
                  status current ;

                }

                enum all {
                  value 1 ;
                  description 'All prefix with prefix-attribute sub-TLV' ;
                  status current ;

                }

                enum none {
                  value 2 ;
                  description 'None prefix with prefix-attribute sub-TLV' ;
                  status current ;

                }

              }

              default auto ;
              config true ;
              mandatory false ;
              ncd:revise-date 2021-02-05 ;
            }

            leaf ipv6-prefix-attribute-advertise {
              description 'Set ipv6 prefix-attribute advertise mode' ;
              type enumeration {
                enum auto {
                  value 0 ;
                  description 'Some prefix with prefix-attribute sub-TLV according to scenario' ;
                  status current ;

                }

                enum all {
                  value 1 ;
                  description 'All prefix with prefix-attribute sub-TLV' ;
                  status current ;

                }

                enum none {
                  value 2 ;
                  description 'None prefix with prefix-attribute sub-TLV' ;
                  status current ;

                }

              }

              default auto ;
              config true ;
              mandatory false ;
              ncd:revise-date 2021-02-05 ;
            }

            leaf crypto-authen-keychain-hmac-md5 {
              description 'Configure generic cryptographic authentication based on HMAC-MD5 algorithm of keychain.' ;
              type isis-state ;

              default disable ;
              config true ;
              mandatory false ;
              ncd:revise-date 2021-03-03 ;
            }

            config true ;
          }

          container hello-padding {
            description 'Hello padding.' ;
            presence "hello padding" ;
            leaf hello-padding-type {
              description 'Hello PDU padding type.' ;
              type enumeration {
                enum hello-padding {
                  value 0 ;
                  description 'Can pad multi-point and point to point.' ;
                  status current ;

                }

                enum multi-point {
                  value 1 ;
                  description 'Can pad multi-point.' ;
                  status current ;

                }

                enum point-to-point {
                  value 2 ;
                  description 'Can pad point-to-point.' ;
                  status current ;

                }

              }

              config true ;
              mandatory true ;
            }

            config true ;
          }

          container metric-style {
            description 'Metric style.' ;
            presence "metric style" ;
            leaf metric-style {
              description 'Metric style. The default value is narrow.' ;
              type enumeration {
                enum narrow {
                  value 1 ;
                  description 'The style of metric is narrow.' ;
                  status current ;

                }

                enum wide {
                  value 2 ;
                  description 'The style of metric is wide.' ;
                  status current ;

                }

              }

              config true ;
              mandatory true ;
            }

            config true ;
          }

          container restart-t3-timer {
            description 'GR T3 timer.' ;
            choice t3-timer {
              description 'Attribution of T3 timer.' ;
              case t3-type-adjacency {
                description 'T3 type is adjacency.' ;
                leaf adjacency {
                  description 'Flag of that GR T3 is setup.' ;
                  type enumeration {
                    enum adjacency {
                      value 1 ;
                      description 'The type of T3 is adjacency.' ;
                      status current ;

                    }

                  }

                  config true ;
                  mandatory false ;
                }

              }

              case t3-type-manual {
                description 'T3 type is manual.' ;
                leaf manual {
                  description 'Flag of that GR t3 is setup.The default value of t3-type is manual.' ;
                  type enumeration {
                    enum manual {
                      value 2 ;
                      description 'The type of T3 is manual.' ;
                      status current ;

                    }

                  }

                  config true ;
                  mandatory true ;
                }

                leaf t3-timer-value {
                  description 'The value of GR T3 configured.' ;
                  type uint16 {
                    range 1..65535 ;

                  }

                  units second ;
                  config true ;
                  mandatory true ;
                }

              }

              config true ;
              mandatory false ;
            }

            config true ;
          }

          container default-info {
            description 'Control distribution of default information.' ;
            presence "default information" ;
            leaf default-info-originate {
              description 'ISIS redistribution default route information flag.' ;
              type boolean ;

              config true ;
              mandatory true ;
            }

            container default-info-branches {
              description 'Default route info branches.' ;
              presence "always branch" ;
              container always-branch {
                description 'Config default information always attribution.' ;
                presence always ;
                leaf always {
                  description 'Always redistribute the default routes.' ;
                  type boolean ;

                  config true ;
                  mandatory true ;
                }

                leaf always-level {
                  description 'Level(s) on which the system will always redistribute the default route.' ;
                  type isis-level ;

                  default level-2 ;
                  config true ;
                  mandatory false ;
                }

                leaf always-metric {
                  description 'Metric of the default redistributed routes.' ;
                  type uint32 {
                    range 0..4261412864 ;

                  }

                  default 0 ;
                  config true ;
                  mandatory false ;
                }

                leaf always-metric-style {
                  description "Type of the default always redistributed routes' metric." ;
                  type enumeration {
                    enum internal {
                      value 2 ;
                      status current ;

                    }

                  }

                  default internal ;
                  config true ;
                  mandatory false ;
                }

                config true ;
              }

              container conditional-branch {
                description 'Config default route conditional attribution.' ;
                leaf default-info-level {
                  description 'Level(s) of the default route.' ;
                  type isis-level ;

                  default level-2 ;
                  config true ;
                  mandatory false ;
                }

                leaf default-info-metric {
                  description 'Metric of the default route.' ;
                  type uint32 {
                    range 0..4261412864 ;

                  }

                  default 0 ;
                  config true ;
                  mandatory false ;
                }

                leaf default-info-metric-style {
                  description "Type of the default routes' metric." ;
                  type enumeration {
                    enum external {
                      value 1 ;
                      status current ;

                    }

                    enum internal {
                      value 2 ;
                      status current ;

                    }

                  }

                  default internal ;
                  config true ;
                  mandatory false ;
                }

                config true ;
              }

              container def-rib-match {
                description 'Config default route default-rib-match attribution.' ;
                presence def-rib-match ;
                leaf state {
                  description 'Advertise default route matched with RIB.' ;
                  type boolean ;

                  config true ;
                  mandatory true ;
                }

                leaf level {
                  description 'Level(s) on which the system will advertise default route matched with RIB.' ;
                  type isis-level ;

                  default level-2 ;
                  config true ;
                  mandatory false ;
                }

                leaf metric {
                  description 'Metric of the default route matched with RIB.' ;
                  type uint32 {
                    range 0..4261412864 ;

                  }

                  default 0 ;
                  config true ;
                  mandatory false ;
                }

                leaf metric-style {
                  description "Type of the default routes' metric." ;
                  type enumeration {
                    enum external {
                      value 1 ;
                      status current ;

                    }

                    enum internal {
                      value 2 ;
                      status current ;

                    }

                  }

                  default internal ;
                  config true ;
                  mandatory false ;
                }

                config true ;
                ncd:revise-date 2016-08-04 ;
              }

              container prefix-list-branch {
                description 'Config IPv4 default route prefix list attribution.' ;
                presence prefix-list-branch ;
                leaf prefix-list-name {
                  description 'Length of a prefix list name(1-169 characters).' ;
                  type string {
                    length 1..169 {
                      description 'Length of a prefix list name(1-169 characters).' ;
                    }

                  }

                  config true ;
                  mandatory true ;
                }

                leaf level {
                  description 'Level(s) on which the system will advertise default route matched with prefix list.' ;
                  type isis-level ;

                  default level-2 ;
                  config true ;
                  mandatory false ;
                }

                leaf metric {
                  description 'Metric of the default route matched with prefix list.' ;
                  type uint32 {
                    range 0..4261412864 ;

                  }

                  default 0 ;
                  config true ;
                  mandatory false ;
                }

                leaf metric-style {
                  description 'Metric type of the default routes matched with prefix list.' ;
                  type enumeration {
                    enum external {
                      value 1 ;
                      status current ;

                    }

                    enum internal {
                      value 2 ;
                      status current ;

                    }

                  }

                  default internal ;
                  config true ;
                  mandatory false ;
                }

                config true ;
                ncd:revise-date 2022-07-20 ;
              }

              config true ;
            }

            config true ;
            ncd:revise-date 2025-09-23 ;
          }

          container spf-intervals {
            description 'Attributes of SPF interval.' ;
            presence "spf interval" ;
            list spf-interval {
              description 'ISIS SPF execution interval.' ;
              key level ;
              leaf level {
                description 'Level(s) will be effected on.' ;
                type uint8 {
                  range 0..2 ;

                }

                config true ;
                mandatory false ;
              }

              leaf interval {
                description 'SPF execution interval.The default value is for reference only, different devices are different.' ;
                type uint16 {
                  range 1..120 ;

                }

                units second ;
                default 10 ;
                config true ;
                mandatory false ;
              }

              leaf init-delay {
                description 'Initial delay before a SPF calculation in ms.The default value is for reference only, different devices are different.' ;
                type uint32 {
                  range 0..120000 ;

                }

                units millisecond ;
                default 5500 ;
                config true ;
                mandatory false ;
              }

              leaf wait-first-second {
                description 'Secondary delay before a SPF calculation in ms.The default value is for reference only, different devices are different.' ;
                type uint32 {
                  range 1..120000 ;

                }

                units millisecond ;
                default 5500 ;
                config true ;
                mandatory false ;
              }

              config true ;
            }

            config true ;
          }

          container lsp-gen-intervals {
            description 'Attributes of LSP generation interval.' ;
            presence "max delay" ;
            list lsp-gen-interval {
              description 'LSP generation interval.' ;
              key level ;
              leaf level {
                description 'Level(s) will be effected on.' ;
                type uint8 {
                  range 0..2 ;

                }

                config true ;
                mandatory false ;
              }

              leaf init-delay {
                description 'Initial waiting time in milliseconds.The default value is for reference only, different devices are different.' ;
                type uint32 {
                  range 0..120000 ;

                }

                units millisecond ;
                default 50 ;
                config true ;
                mandatory false ;
              }

              leaf max-delay {
                description 'LSP Max generation interval in seconds.The default value is for reference only, different devices are different.' ;
                type uint16 {
                  range 1..120 ;

                }

                units second ;
                default 5 ;
                config true ;
                mandatory false ;
              }

              leaf wait-first-second {
                description 'Delay time between 1st and 2nd LSP generation in ms.The default value is for reference only, different devices are different.' ;
                type uint32 {
                  range 1..120000 ;

                }

                units millisecond ;
                default 5000 ;
                config true ;
                mandatory false ;
              }

              config true ;
            }

            config true ;
          }

          container summary-addrs {
            description 'Configure IP address summaries,' ;
            list summary-address {
              description 'ISIS IPv4 summary' ;
              key 'ip-address net-mask' ;
              leaf ip-address {
                description 'Summary IP address.' ;
                type ncd:ipv4-address ;

                config true ;
                mandatory false ;
              }

              leaf net-mask {
                description 'Summary net mask.' ;
                type ncd:ipv4-mask ;

                config true ;
                mandatory false ;
              }

              leaf metric-value {
                description 'Specify the metric for summary routes.' ;
                type uint32 {
                  range 0..4261412864 ;

                }

                default 0 ;
                config true ;
                mandatory false ;
              }

              leaf level {
                description 'Level(s) will be effected on.' ;
                type isis-level ;

                default level-1-2 ;
                config true ;
                mandatory false ;
              }

              config true ;
            }

            config true ;
          }

          container ipv4-prefix-priorities {
            description 'Configure the IPv4 prefix priority.' ;
            container acls {
              description 'Acl branch.' ;
              list acl {
                description 'Specify acl-list to indicate priority.' ;
                key 'level rule acl-name' ;
                leaf level {
                  description 'Level(s) will be effected on by prefix priority.' ;
                  type uint8 {
                    range 0..2 ;

                  }

                  config true ;
                  mandatory false ;
                }

                leaf rule {
                  description 'ISIS prefix priority rule.' ;
                  type enumeration {
                    enum critical {
                      value 1 ;
                      status current ;

                    }

                    enum high {
                      value 2 ;
                      status current ;

                    }

                    enum medium {
                      value 3 ;
                      status current ;

                    }

                  }

                  config true ;
                  mandatory false ;
                }

                leaf acl-name {
                  description 'ISIS prefix priority acl-list name.' ;
                  type string {
                    length 1..31 ;

                  }

                  config true ;
                  mandatory false ;
                }

                config true ;
              }

              config true ;
            }

            container tags {
              description 'Tag branch.' ;
              list tag {
                description 'Specify a tag to indicate priority.' ;
                key 'level rule tag-number' ;
                leaf level {
                  description 'Level(s) will be effected on by prefix priority.' ;
                  type uint8 {
                    range 0..2 ;

                  }

                  config true ;
                  mandatory false ;
                }

                leaf rule {
                  description 'ISIS prefix priority rule.' ;
                  type enumeration {
                    enum critical {
                      value 1 ;
                      status current ;

                    }

                    enum high {
                      value 2 ;
                      status current ;

                    }

                    enum medium {
                      value 3 ;
                      status current ;

                    }

                  }

                  config true ;
                  mandatory false ;
                }

                leaf tag-number {
                  description 'The number of isis prefix priority tag.' ;
                  type uint32 {
                    range 1..4294967295 ;

                  }

                  config true ;
                  mandatory false ;
                }

                config true ;
              }

              config true ;
            }

            config true ;
          }

          container route-leak-l1tol2 {
            description 'Route-leak level-1 into level-2.' ;
            presence "route leak state" ;
            leaf routemap-name {
              description 'The name of route map.' ;
              type string {
                length 1..200 ;

              }

              config true ;
              mandatory false ;
            }

            leaf state {
              description "The state of route-leak level-1 into level-2.The default value is enable.It's value can not be modified." ;
              type enumeration {
                enum enable {
                  value 1 ;
                  description 'The state of route-leak level-1 into level-2 is enable.' ;
                  status current ;

                }

              }

              config true ;
              mandatory true ;
            }

            leaf without-prefix-sid {
              description 'Leak optional parameters without-prefix-sid.' ;
              type isis-state ;

              default disable ;
              config true ;
              mandatory false ;
              ncd:revise-date 2019-08-05 ;
            }

            leaf host-only {
              description 'Leak optional parameters host-only.' ;
              type isis-state ;

              default disable ;
              config true ;
              mandatory false ;
              ncd:revise-date 2019-08-05 ;
            }

            config true ;
          }

          container route-leak-l2tol1 {
            description 'Route-leak level-2 into level-1.' ;
            presence route-leak ;
            leaf routemap-name {
              description 'The name of route map.' ;
              type string {
                length 1..200 ;

              }

              config true ;
              mandatory false ;
            }

            leaf state {
              description 'Set route leak level-2 into level-1.' ;
              type isis-state ;

              config true ;
              mandatory true ;
            }

            leaf without-prefix-sid {
              description 'Leak optional parameters without-prefix-sid.' ;
              type isis-state ;

              default disable ;
              config true ;
              mandatory false ;
              ncd:revise-date 2019-08-05 ;
            }

            leaf host-only {
              description 'Leak optional parameters host-only.' ;
              type isis-state ;

              default disable ;
              config true ;
              mandatory false ;
              ncd:revise-date 2019-08-05 ;
            }

            config true ;
          }

          container ipv6-route-leak-l1tol2 {
            description 'IPv6 route-leak level-1 into level-2.' ;
            presence ipv6-route-leak ;
            leaf routemap-name {
              description 'Route map name.' ;
              type string {
                length 1..200 ;

              }

              config true ;
              mandatory false ;
            }

            leaf state {
              description "The state of IPv6 route-leak level-1 into level-2.The default value is enable.It's value can not be modified." ;
              type enumeration {
                enum enable {
                  value 1 ;
                  description 'The state of IPv6 route-leak level-1 into level-2 is enable.' ;
                  status current ;

                }

              }

              config true ;
              mandatory true ;
            }

            leaf without-prefix-sid {
              description 'IPv6 leak optional parameters without-prefix-sid.' ;
              type isis-state ;

              default disable ;
              config true ;
              mandatory false ;
              ncd:revise-date 2019-08-05 ;
            }

            leaf host-only {
              description 'IPv6 leak optional parameters host-only.' ;
              type isis-state ;

              default disable ;
              config true ;
              mandatory false ;
              ncd:revise-date 2019-08-05 ;
            }

            config true ;
          }

          container ipv6-route-leak-l2tol1 {
            description 'IPv6 route-leak level-2 into level-1.' ;
            presence "ipv6 route-leak" ;
            leaf routemap-name {
              description 'Route map name.' ;
              type string {
                length 1..200 ;

              }

              config true ;
              mandatory false ;
            }

            leaf state {
              description 'Enable route-leak level-2 into level-1.' ;
              type isis-state ;

              config true ;
              mandatory true ;
            }

            leaf without-prefix-sid {
              description 'IPv6 leak optional parameters without-prefix-sid.' ;
              type isis-state ;

              default disable ;
              config true ;
              mandatory false ;
              ncd:revise-date 2019-08-05 ;
            }

            leaf host-only {
              description 'IPv6 leak optional parameters host-only.' ;
              type isis-state ;

              default disable ;
              config true ;
              mandatory false ;
              ncd:revise-date 2019-08-05 ;
            }

            config true ;
          }

          container ipv4-direct-prefix-inter-area-l1tol2 {
            description 'IPv4 direct prefix inter-area route leak level-1 into level-2.' ;
            leaf state {
              description 'The state of direct prefix inter-area route leak.' ;
              type isis-state ;

              default enable ;
              config true ;
              mandatory false ;
            }

            choice policy {
              description 'Direct prefix inter-area route leak policy' ;
              case host-only-branch {
                description 'Direct prefix inter-area route leak policy host-only branch.' ;
                leaf host-only {
                  description 'Direct prefix inter-area route leak policy host-only.' ;
                  type empty ;

                  config true ;
                  mandatory false ;
                }

              }

              case routemap-branch {
                description 'Direct prefix inter-area route leak policy route map branch.' ;
                leaf routemap-name {
                  description 'The name of route map.' ;
                  type string {
                    length 1..200 ;

                  }

                  config true ;
                  mandatory false ;
                }

              }

              config true ;
              mandatory false ;
            }

            config true ;
            ncd:revise-date 2022-05-31 ;
          }

          container ipv4-direct-prefix-inter-area-l2tol1 {
            description 'IPv4 direct prefix inter-area route leak level-2 into level-1.' ;
            leaf state {
              description 'The state of direct prefix inter-area route leak.' ;
              type isis-state ;

              config true ;
              mandatory false ;
            }

            choice policy {
              description 'Direct prefix inter-area route leak policy' ;
              case host-only-branch {
                description 'Direct prefix inter-area route leak policy host-only branch.' ;
                leaf host-only {
                  description 'Direct prefix inter-area route leak policy host-only.' ;
                  type empty ;

                  config true ;
                  mandatory false ;
                }

              }

              case routemap-branch {
                description 'Direct prefix inter-area route leak policy route map branch.' ;
                leaf routemap-name {
                  description 'The name of route map.' ;
                  type string {
                    length 1..200 ;

                  }

                  config true ;
                  mandatory false ;
                }

              }

              config true ;
              mandatory false ;
            }

            config true ;
            ncd:revise-date 2022-05-31 ;
          }

          container ipv6-direct-prefix-inter-area-l1tol2 {
            description 'IPv6 direct prefix inter-area route leak level-1 into level-2.' ;
            leaf state {
              description 'The state of direct prefix inter-area route leak.' ;
              type isis-state ;

              default enable ;
              config true ;
              mandatory false ;
            }

            choice policy {
              description 'Direct prefix inter-area route leak policy' ;
              case host-only-branch {
                description 'Direct prefix inter-area route leak policy host-only branch.' ;
                leaf host-only {
                  description 'Direct prefix inter-area route leak policy host-only.' ;
                  type empty ;

                  config true ;
                  mandatory false ;
                }

              }

              case routemap-branch {
                description 'Direct prefix inter-area route leak policy route map branch.' ;
                leaf routemap-name {
                  description 'The name of route map.' ;
                  type string {
                    length 1..200 ;

                  }

                  config true ;
                  mandatory false ;
                }

              }

              config true ;
              mandatory false ;
            }

            config true ;
            ncd:revise-date 2022-05-31 ;
          }

          container ipv6-direct-prefix-inter-area-l2tol1 {
            description 'IPv6 direct prefix inter-area route leak level-2 into level-1.' ;
            leaf state {
              description 'The state of direct prefix inter-area route leak.' ;
              type isis-state ;

              config true ;
              mandatory false ;
            }

            choice policy {
              description 'Direct prefix inter-area route leak policy' ;
              case host-only-branch {
                description 'Direct prefix inter-area route leak policy host-only branch.' ;
                leaf host-only {
                  description 'Direct prefix inter-area route leak policy host-only.' ;
                  type empty ;

                  config true ;
                  mandatory false ;
                }

              }

              case routemap-branch {
                description 'Direct prefix inter-area route leak policy route map branch.' ;
                leaf routemap-name {
                  description 'The name of route map.' ;
                  type string {
                    length 1..200 ;

                  }

                  config true ;
                  mandatory false ;
                }

              }

              config true ;
              mandatory false ;
            }

            config true ;
            ncd:revise-date 2022-05-31 ;
          }

          container redistributes {
            description 'Redistribute information from another routing protocol.' ;
            container redis-isis-protocol {
              description 'Redistribute protocol is ISIS.' ;
              list redis-isis {
                description 'Redistribute protocol is ISIS.' ;
                key 'isis isis-process-id' ;
                leaf isis {
                  description 'Redistribute protocol is ISIS.' ;
                  type enumeration {
                    enum isis {
                      value 3 ;
                      description 'The type of protocol is ISIS.' ;
                      status current ;

                    }

                  }

                  config true ;
                  mandatory false ;
                }

                leaf isis-process-id {
                  description 'Redistribute process ID.' ;
                  type uint32 {
                    range 0..65535 ;

                  }

                  config true ;
                  mandatory false ;
                }

                leaf level {
                  description 'Level(s) will be effected on.' ;
                  type isis-level ;

                  default level-2 ;
                  config true ;
                  mandatory false ;
                }

                leaf metric-style {
                  description 'OSPF/ISIS exterior metric type for redistribution.' ;
                  type enumeration {
                    enum external {
                      value 1 ;
                      description 'The metric-style is external.' ;
                      status current ;

                    }

                    enum internal {
                      value 2 ;
                      description 'The metric-style is internal.' ;
                      status current ;

                    }

                  }

                  default internal ;
                  config true ;
                  mandatory false ;
                }

                leaf routemap-name {
                  description 'Route map reference.' ;
                  type string {
                    length 1..200 ;

                  }

                  config true ;
                  mandatory false ;
                }

                choice metric-value {
                  description 'The redistribute metric value.' ;
                  default isis-branch ;
                  case originate-branch {
                    description 'The original metric case.' ;
                    leaf with-originate-metric {
                      description 'Using original metric' ;
                      type empty ;

                      config true ;
                      mandatory false ;
                    }

                  }

                  case isis-branch {
                    description 'ISIS config metric case' ;
                    leaf metric {
                      description 'ISIS config metric' ;
                      type uint32 {
                        range 0..4261412864 ;

                      }

                      default 0 ;
                      config true ;
                      mandatory false ;
                    }

                  }

                  config true ;
                  mandatory false ;
                }

                leaf without-prefix-sid {
                  description 'Redistribute optional parameters without-prefix-sid.' ;
                  type isis-state ;

                  default disable ;
                  config true ;
                  mandatory false ;
                  ncd:revise-date 2019-08-05 ;
                }

                leaf host-only {
                  description 'Redistribute optional parameters host-only.' ;
                  type isis-state ;

                  default disable ;
                  config true ;
                  mandatory false ;
                  ncd:revise-date 2019-08-05 ;
                }

                leaf with-bier {
                  description 'Redistribute route with BIER information.' ;
                  type isis-state ;

                  default disable ;
                  config true ;
                  mandatory false ;
                  ncd:revise-date 2022-12-09 ;
                }

                config true ;
              }

              config true ;
            }

            container redis-ospf-protocol {
              description 'The redistribute protocol is OSPF.' ;
              list redis-ospf {
                description 'Redistribute protocol is OSPF.' ;
                key 'ospf ospf-process-id' ;
                leaf ospf {
                  description 'Redistribute protocol is OSPF.' ;
                  type enumeration {
                    enum ospf {
                      value 4 ;
                      description 'Redistribute protocol is OSPF.' ;
                      status current ;

                    }

                  }

                  config true ;
                  mandatory false ;
                }

                leaf ospf-process-id {
                  description 'Process ID of OSPF.' ;
                  type uint32 {
                    range 1..65535 ;

                  }

                  config true ;
                  mandatory false ;
                }

                leaf level {
                  description 'Level will be effected on.' ;
                  type isis-level ;

                  default level-2 ;
                  config true ;
                  mandatory false ;
                }

                leaf routemap-name {
                  description 'Redistributed route map name.' ;
                  type string {
                    length 1..200 ;

                  }

                  config true ;
                  mandatory false ;
                }

                leaf metric-style {
                  description 'OSPF exterior metric type for redistribution.' ;
                  type enumeration {
                    enum external {
                      value 1 ;
                      description 'The metric-style is external.' ;
                      status current ;

                    }

                    enum internal {
                      value 2 ;
                      description 'The metric-style is internal.' ;
                      status current ;

                    }

                  }

                  default internal ;
                  config true ;
                  mandatory false ;
                }

                choice metric-value {
                  description 'The redistribute metric value.' ;
                  default isis-branch ;
                  case isis-branch {
                    description 'ISIS config metric case.' ;
                    leaf metric {
                      description 'ISIS config metric' ;
                      type uint32 {
                        range 0..4261412864 ;

                      }

                      default 0 ;
                      config true ;
                      mandatory false ;
                    }

                  }

                  case originate-branch {
                    description 'The original metric case.' ;
                    leaf with-originate-metric {
                      description 'Using original metric.' ;
                      type empty ;

                      config true ;
                      mandatory false ;
                    }

                  }

                  config true ;
                  mandatory false ;
                }

                leaf without-prefix-sid {
                  description 'Redistribute optional parameters without-prefix-sid.' ;
                  type isis-state ;

                  default disable ;
                  config true ;
                  mandatory false ;
                  ncd:revise-date 2019-08-05 ;
                }

                leaf host-only {
                  description 'Redistribute optional parameters host-only.' ;
                  type isis-state ;

                  default disable ;
                  config true ;
                  mandatory false ;
                  ncd:revise-date 2019-08-05 ;
                }

                config true ;
              }

              config true ;
            }

            container redis-other-protocols {
              description 'Redistribute protocol is neither ISIS nor OSPF.' ;
              list redis-other-protocol {
                description 'Redistribute protocol is neither ISIS nor OSPF.' ;
                key protocol ;
                leaf protocol {
                  description 'Redistribution protocol.' ;
                  type enumeration {
                    enum bgp {
                      value 1 ;
                      description 'The type of protocol is bgp.' ;
                      status current ;

                    }

                    enum connected {
                      value 2 ;
                      description 'Connected routes.' ;
                      status current ;

                    }

                    enum rip {
                      value 5 ;
                      description 'The type of protocol is rip.' ;
                      status current ;

                    }

                    enum static {
                      value 6 ;
                      description 'The type of protocol is static.' ;
                      status current ;

                    }

                    enum nat {
                      value 8 ;
                      description 'NAT routes.' ;
                      status current ;

                    }

                    enum natpt {
                      value 9 ;
                      description 'Port-address Translation routes.' ;
                      status current ;

                    }

                    enum ps-busi-addr {
                      value 10 ;
                      description 'Ps-busi-addr routes.' ;
                      status current ;

                    }

                    enum ps-user-addr {
                      value 11 ;
                      description 'Ps-user-addr routes.' ;
                      status current ;

                    }

                    enum subscriber-aggregation {
                      value 12 ;
                      description "Bras subscriber's aggregation routes." ;
                      status current ;

                    }

                    enum subscriber-host {
                      value 13 ;
                      description 'Subscriber host.' ;
                      status current ;

                    }

                    enum user-special {
                      value 14 ;
                      description 'User-special routes.' ;
                      status current ;

                    }

                    enum sl-nat64-ipv4 {
                      value 16 ;
                      description 'The type of protocol is sl-nat64-ipv6.' ;
                      status current ;

                    }

                  }

                  config true ;
                  mandatory false ;
                }

                leaf level {
                  description 'Level(s) will be effected on.' ;
                  type isis-level ;

                  default level-2 ;
                  config true ;
                  mandatory false ;
                }

                leaf metric-style {
                  description 'ISIS exterior metric type for redistribution.' ;
                  type enumeration {
                    enum external {
                      value 1 ;
                      description 'The metric-style is external.' ;
                      status current ;

                    }

                    enum internal {
                      value 2 ;
                      description 'The metric-style is internal.' ;
                      status current ;

                    }

                  }

                  default internal ;
                  config true ;
                  mandatory false ;
                }

                leaf routemap-name {
                  description 'Redistributed route map reference' ;
                  type string {
                    length 1..200 ;

                  }

                  config true ;
                  mandatory false ;
                }

                choice metric-value {
                  description 'The redistribute metric value.' ;
                  default isis-branch ;
                  case isis-branch {
                    description 'ISIS config metric case.' ;
                    leaf metric {
                      description 'ISIS config metric' ;
                      type uint32 {
                        range 0..4261412864 ;

                      }

                      default 0 ;
                      config true ;
                      mandatory false ;
                    }

                  }

                  case originate-branch {
                    description 'The original metric case.' ;
                    leaf with-originate-metric {
                      description 'Using original metric.' ;
                      type empty ;

                      config true ;
                      mandatory false ;
                    }

                  }

                  config true ;
                  mandatory false ;
                }

                leaf without-prefix-sid {
                  description 'Redistribute optional parameters without-prefix-sid.' ;
                  type isis-state ;

                  default disable ;
                  config true ;
                  mandatory false ;
                  ncd:revise-date 2019-08-05 ;
                }

                leaf host-only {
                  description 'Redistribute optional parameters host-only.' ;
                  type isis-state ;

                  default disable ;
                  config true ;
                  mandatory false ;
                  ncd:revise-date 2019-08-05 ;
                }

                config true ;
              }

              config true ;
            }

            config true ;
          }

          container multi-topology {
            description 'Multi-topology.' ;
            leaf state {
              description 'Multiply topology enable flag.' ;
              type isis-state ;

              config true ;
              mandatory false ;
            }

            config true ;
          }

          container ipv6-distribute-list {
            description 'IPv6 distribution instance.' ;
            presence "ipv6 distribute list" ;
            leaf routemap-name {
              description 'Routemap name used in IPv6 distribution.' ;
              type string {
                length 1..200 ;

              }

              config true ;
              mandatory true ;
            }

            config true ;
          }

          container ipv6-spf-intervals {
            description 'Attributes of IPv6 SPF interval.' ;
            presence "spf interval" ;
            list ipv6-spf-interval {
              description 'IPv6 SPF interval.' ;
              key level ;
              leaf level {
                description 'Level(s) will be effected on.' ;
                type uint8 {
                  range 0..2 ;

                }

                config true ;
                mandatory false ;
              }

              leaf interval {
                description 'ISIS SPF execution interval.The default value is for reference only, different devices are different.' ;
                type uint16 {
                  range 1..120 ;

                }

                units second ;
                default 10 ;
                config true ;
                mandatory false ;
              }

              leaf init-delay {
                description 'The initial waiting delay before first SPF in milliseconds.The default value is for reference only, different devices are different.' ;
                type uint32 {
                  range 0..120000 ;

                }

                units millisecond ;
                default 5500 ;
                config true ;
                mandatory false ;
              }

              leaf second-delay {
                description 'Minimum wait between first and second SPF in ms.The default value is for reference only, different devices are different.' ;
                type uint32 {
                  range 1..120000 ;

                }

                units millisecond ;
                default 5500 ;
                config true ;
                mandatory false ;
              }

              config true ;
            }

            config true ;
          }

          container ipv6-summary-prefixs {
            description 'IPv6 summary prefix.' ;
            list ipv6-summary-prefix {
              description 'IPv6 summary prefix.' ;
              key 'ipv6-prefix prefix-len' ;
              leaf ipv6-prefix {
                description 'IPv6 summary address.' ;
                type ncd:ipv6-address ;

                config true ;
                mandatory false ;
              }

              leaf prefix-len {
                description 'Prefix length of summary.' ;
                type uint8 ;

                config true ;
                mandatory false ;
              }

              leaf metric {
                description 'Specify metric value for summary prefix.' ;
                type uint32 {
                  range 0..4261412864 ;

                }

                default 0 ;
                config true ;
                mandatory false ;
              }

              leaf level {
                description 'Level(s) will be effected on.' ;
                type isis-level ;

                default level-1-2 ;
                config true ;
                mandatory false ;
              }

              config true ;
            }

            config true ;
          }

          container ipv6-frr-state {
            description 'Set ISIS IPv6 fast-reroute.' ;
            presence "ipv6 FRR" ;
            leaf state {
              description 'The flag of IPv6 FRR.' ;
              type isis-state ;

              config true ;
              mandatory false ;
            }

            leaf multi-home {
              description 'Fast-reroute selection state for IPv6 multi-homed prefixes.' ;
              type isis-state ;

              default disable ;
              config true ;
              mandatory false ;
              ncd:revise-date 2021-02-23 ;
            }

            config true ;
          }

          container ipv6-redistributes {
            description 'IPv6 redistribute.' ;
            container redis-isis-protocol {
              description 'Redistribute protocol is ISIS.' ;
              list redis-isis {
                description 'Redistribute protocol is ISIS.' ;
                key 'isis isis-process-id' ;
                leaf isis {
                  description 'Redistribution protocol.' ;
                  type enumeration {
                    enum isis {
                      value 3 ;
                      description 'The type of protocol is isis.' ;
                      status current ;

                    }

                  }

                  config true ;
                  mandatory false ;
                }

                leaf isis-process-id {
                  description 'Redistributed process ID.' ;
                  type uint32 {
                    range 0..65535 ;

                  }

                  config true ;
                  mandatory false ;
                }

                leaf level {
                  description 'Level(s) will be effected on.' ;
                  type isis-level ;

                  default level-2 ;
                  config true ;
                  mandatory false ;
                }

                leaf metric {
                  description 'Metric for redistributed routes' ;
                  type uint32 {
                    range 0..4261412864 ;

                  }

                  default 0 ;
                  config true ;
                  mandatory false ;
                }

                leaf routemap-name {
                  description 'Redistributed route map name.' ;
                  type string {
                    length 1..200 ;

                  }

                  config true ;
                  mandatory false ;
                }

                leaf without-prefix-sid {
                  description 'IPv6 redistribute optional parameters without-prefix-sid.' ;
                  type isis-state ;

                  default disable ;
                  config true ;
                  mandatory false ;
                  ncd:revise-date 2019-08-05 ;
                }

                leaf host-only {
                  description 'IPv6 redistribute optional parameters host-only.' ;
                  type isis-state ;

                  default disable ;
                  config true ;
                  mandatory false ;
                  ncd:revise-date 2019-08-05 ;
                }

                leaf with-bier {
                  description 'IPv6 redistribute route with BIER information.' ;
                  type isis-state ;

                  default disable ;
                  config true ;
                  mandatory false ;
                  ncd:revise-date 2022-12-09 ;
                }

                config true ;
              }

              config true ;
            }

            container redis-other-protocols {
              description 'Redistribute protocol is neither ISIS nor OSPF.' ;
              list redis-other-protocol {
                description 'Redistribute protocol is not ISIS or OSPF.' ;
                key protocol ;
                leaf protocol {
                  description 'Redistribution protocol.' ;
                  type enumeration {
                    enum bgp {
                      value 1 ;
                      description 'The type of protocol is bgp.' ;
                      status current ;

                    }

                    enum connected {
                      value 2 ;
                      description 'The type of protocol is connect.' ;
                      status current ;

                    }

                    enum rip {
                      value 5 ;
                      description 'The type of protocol is rip.' ;
                      status current ;

                    }

                    enum static {
                      value 6 ;
                      description 'The type of protocol is static.' ;
                      status current ;

                    }

                    enum dhcp-pd {
                      value 7 ;
                      description 'The type of protocol is dhcp-pd.' ;
                      status current ;

                    }

                    enum subscriber-host {
                      value 13 ;
                      description 'The type of protocol is subscriber-host.' ;
                      status current ;

                    }

                    enum sl-nat64-ipv6 {
                      value 15 ;
                      description 'The type of protocol is ipv6 sl-nat64.' ;
                      status current ;

                    }

                    enum sf-nat64 {
                      value 17 ;
                      description 'The type of protocol is sf-nat64.' ;
                      status current ;

                    }

                    enum aftr {
                      value 18 ;
                      description 'The type of protocol is aftr.' ;
                      status current ;

                    }

                    enum nptv6 {
                      value 23 ;
                      description 'The type of protocol is nptv6.' ;
                      status current ;

                    }

                    enum nd-host {
                      value 24 ;
                      status current ;

                      description 'The type of protocol is ND-HOST.' ;
                    }

                  }

                  config true ;
                  mandatory false ;
                }

                leaf level {
                  description 'Level(s) will be effected on.' ;
                  type isis-level ;

                  default level-2 ;
                  config true ;
                  mandatory false ;
                }

                leaf metric {
                  description 'Metric for redistributed routes.' ;
                  type uint32 {
                    range 0..4261412864 ;

                  }

                  default 0 ;
                  config true ;
                  mandatory false ;
                }

                leaf routemap-name {
                  description 'Redistributed route map name.' ;
                  type string {
                    length 1..200 ;

                  }

                  config true ;
                  mandatory false ;
                }

                leaf without-prefix-sid {
                  description 'IPv6 redistribute optional parameters without-prefix-sid.' ;
                  type isis-state ;

                  default disable ;
                  config true ;
                  mandatory false ;
                  ncd:revise-date 2019-08-05 ;
                }

                leaf host-only {
                  description 'IPv6 redistribute optional parameters host-only.' ;
                  type isis-state ;

                  default disable ;
                  config true ;
                  mandatory false ;
                  ncd:revise-date 2019-08-05 ;
                }

                config true ;
              }

              config true ;
            }

            container redis-ospf-protocol {
              description 'Redistribute protocol is  OSPF.' ;
              list redis-ospf {
                description 'Redistribute protocol is OSPF.' ;
                key 'ospf ospf-process-id' ;
                leaf ospf {
                  description 'Redistribute protocol is OSPF.' ;
                  type enumeration {
                    enum ospf {
                      value 4 ;
                      status current ;

                    }

                  }

                  config true ;
                  mandatory false ;
                }

                leaf ospf-process-id {
                  description 'Process ID of OSPF.' ;
                  type uint32 {
                    range 1..65535 ;

                  }

                  config true ;
                  mandatory false ;
                }

                leaf level {
                  description 'Level will be effected on.' ;
                  type isis-level ;

                  default level-2 ;
                  config true ;
                  mandatory false ;
                }

                leaf metric {
                  description 'The metric of redistributed routes.' ;
                  type uint32 {
                    range 0..4261412864 ;

                  }

                  default 0 ;
                  config true ;
                  mandatory false ;
                }

                leaf routemap-name {
                  description 'The name of route-map.' ;
                  type string {
                    length 1..200 ;

                  }

                  config true ;
                  mandatory false ;
                }

                leaf without-prefix-sid {
                  description 'IPv6 redistribute optional parameters without-prefix-sid.' ;
                  type isis-state ;

                  default disable ;
                  config true ;
                  mandatory false ;
                  ncd:revise-date 2019-08-05 ;
                }

                leaf host-only {
                  description 'IPv6 redistribute optional parameters host-only.' ;
                  type isis-state ;

                  default disable ;
                  config true ;
                  mandatory false ;
                  ncd:revise-date 2019-08-05 ;
                }

                config true ;
              }

              config true ;
            }

            config true ;
          }

          container ipv6-prefix-priorities {
            description 'Configure the IPv6 prefix priority.' ;
            container acls {
              description 'Specify acl-list to indicate priority.' ;
              list acl {
                description 'Specify acl-list to indicate priority.' ;
                key 'level rule acl-name' ;
                leaf level {
                  description 'Level(s) will be effected on by prefix priority.' ;
                  type uint8 {
                    range 0..2 ;

                  }

                  config true ;
                  mandatory false ;
                }

                leaf rule {
                  description 'Prefix-priority rule.' ;
                  type enumeration {
                    enum critical {
                      value 1 ;
                      status current ;

                    }

                    enum high {
                      value 2 ;
                      status current ;

                    }

                    enum medium {
                      value 3 ;
                      status current ;

                    }

                  }

                  config true ;
                  mandatory false ;
                }

                leaf acl-name {
                  description 'Acl name.' ;
                  type string {
                    length 1..31 ;

                  }

                  config true ;
                  mandatory false ;
                }

                config true ;
              }

              config true ;
            }

            container tags {
              description 'Specify a tag to indicate priority.' ;
              list tag {
                description 'Specify a tag to indicate priority.' ;
                key 'level rule tag-number' ;
                leaf level {
                  description 'Level(s) will be effected on by prefix priority.' ;
                  type uint8 {
                    range 0..2 ;

                  }

                  config true ;
                  mandatory false ;
                }

                leaf rule {
                  description 'Prefix-priority rule.' ;
                  type enumeration {
                    enum critical {
                      value 1 ;
                      status current ;

                    }

                    enum high {
                      value 2 ;
                      status current ;

                    }

                    enum medium {
                      value 3 ;
                      status current ;

                    }

                  }

                  config true ;
                  mandatory false ;
                }

                leaf tag-number {
                  description 'Config tag number.' ;
                  type uint32 {
                    range 1..4294967295 ;

                  }

                  config true ;
                  mandatory false ;
                }

                config true ;
              }

              config true ;
            }

            config true ;
          }

          container mpls-traffic-engs {
            description 'The object of ISIS MPLS.' ;
            list mpls-traffic-eng {
              description 'ISIS traffic engineering.' ;
              key level ;
              leaf level {
                description 'Level(s) will be effected on.' ;
                type enumeration {
                  enum level-1 {
                    value 1 ;
                    description 'Mpls traffic-eng on level 1.' ;
                    status current ;

                  }

                  enum level-2 {
                    value 2 ;
                    description 'Mpls traffic-eng on level 2.' ;
                    status current ;

                  }

                }

                config true ;
                mandatory false ;
              }

              config true ;
            }

            config true ;
          }

          container mpls-ldp-sync {
            description 'Configure LDP-ISIS synchronization.' ;
            presence "mpls ldp sync" ;
            leaf level {
              description 'Level(s) will be effected on.' ;
              type uint8 {
                range 0..2 ;

              }

              config true ;
              mandatory true ;
            }

            config true ;
          }

          container ipv4-frr-state {
            description 'IPv4 fast reroute state.' ;
            presence "frr state" ;
            leaf state {
              description 'The state of IPv4 FRR.' ;
              type isis-state ;

              config true ;
              mandatory false ;
            }

            leaf multi-home {
              description 'Fast-reroute selection state for multi-homed prefixes.' ;
              type isis-state ;

              default disable ;
              config true ;
              mandatory false ;
              ncd:revise-date 2021-02-23 ;
            }

            config true ;
          }

          container restart-t2-timers {
            description 'GR t2 timer.' ;
            list restart-t2-timer {
              description 'ISIS GR t2 timer.' ;
              key level ;
              leaf level {
                description 'Level(s) will be effected on.' ;
                type uint8 {
                  range 0..2 ;

                }

                config true ;
                mandatory false ;
              }

              leaf t2-timer {
                description 'The value of T2 timer.' ;
                type uint16 {
                  range 5..65535 ;

                }

                units second ;
                default 330 ;
                config true ;
                mandatory false ;
              }

              config true ;
            }

            config true ;
          }

          container set-ol-bit {
            description 'Set overload bit.' ;
            presence "set overload bit" ;
            leaf ol-set-flag {
              description 'The flag of setting OL bit.' ;
              type boolean ;

              config true ;
              mandatory true ;
            }

            container suppress-type {
              description 'If overload-bit set, suppress the following types.' ;
              presence "suppress type" ;
              leaf ol-suppress-type {
                description 'If overload-bit set, suppress the following types.' ;
                type enumeration {
                  enum external {
                    value 1 ;
                    description 'IP prefixes learned from other protocols.' ;
                    status current ;

                  }

                  enum interlevel {
                    value 2 ;
                    description 'IP prefixes learned from another ISIS level.' ;
                    status current ;

                  }

                  enum all {
                    value 3 ;
                    description 'Both interlevel and external.' ;
                    status current ;

                  }

                }

                config true ;
                mandatory true ;
              }

              config true ;
            }

            container ol-link-block-attr {
              description 'Block link advertisement after reload' ;
              presence "link block attr" ;
              leaf link-block-attr {
                description 'Block link advertisement after reload' ;
                type empty ;

                config true ;
                mandatory true ;
              }

              config true ;
              ncd:revise-date 2020-09-09 ;
            }

            choice on-start-up {
              description 'Config OL attribution after restart.' ;
              case auto-branch {
                description 'Waiting for ISIS database synchronization.' ;
                leaf auto {
                  description 'Waiting for ISIS database synchronization.' ;
                  type empty ;

                  config true ;
                  mandatory true ;
                }

                leaf auto-time {
                  description 'Time in seconds to clear OL bit after reboot.' ;
                  type uint32 {
                    range 5..86400 ;

                  }

                  units second ;
                  config true ;
                  mandatory false ;
                }

              }

              case wait-for-bgp-branch {
                description 'Let BGP decide when to unset the OL bit.' ;
                leaf wait-for-bgp {
                  description 'Let BGP decide when to clear the OL bit.' ;
                  type empty ;

                  config true ;
                  mandatory true ;
                }

                leaf ol-bgp-time {
                  description 'Time in seconds to clear OL bit after reboot.' ;
                  type uint32 {
                    range 5..86400 ;

                  }

                  units second ;
                  config true ;
                  mandatory false ;
                }

              }

              case const-time-branch {
                description 'Time in seconds to unset OL bit after reboot.' ;
                leaf ol-const-time {
                  description 'Time in seconds to unset OL bit after reboot.' ;
                  type uint32 {
                    range 5..86400 ;

                  }

                  units second ;
                  config true ;
                  mandatory false ;
                }

              }

              case on-start-up-invalid-branch {
                description 'Shutdown on-start-up function' ;
                leaf on-start-up-invalid {
                  description 'Shutdown on-start-up function' ;
                  type empty ;

                  config true ;
                  mandatory true ;
                }

                ncd:revise-date 2020-03-30 ;
              }

              config true ;
              mandatory false ;
            }

            container link-block {
              description 'Block link advertisement after reload' ;
              status obsolete {
                ncd:revise-date 2020-09-09 ;
              }

              presence "link block" ;
              leaf ol-link-block {
                description 'Block link advertisement after reload' ;
                type empty ;

                config true ;
                mandatory true ;
              }

              config true ;
              ncd:revise-date 2020-05-25 ;
            }

            config true ;
          }

          container isis-intfs {
            description 'Attributes of isis interface.' ;
            list isis-intf-attr {
              description 'Information of ISIS interface.' ;
              key intf-name ;
              leaf intf-name {
                description 'The name of interface.' ;
                type ncd:ifname ;

                config true ;
                mandatory false ;
              }

              leaf circuit-type {
                description "Circuit's level." ;
                type enumeration {
                  enum level-1 {
                    value 1 ;
                    description 'level-1' ;
                    status current ;

                  }

                  enum level-2-only {
                    value 2 ;
                    description 'level-2' ;
                    status current ;

                  }

                  enum level-1-2 {
                    value 3 ;
                    description 'level-1-2' ;
                    status current ;

                  }

                }

                default level-1-2 ;
                config true ;
                mandatory false ;
              }

              leaf bfd-state {
                description 'Enable IPv4 bfd on this interface.' ;
                type isis-state ;

                config true ;
                mandatory false ;
              }

              leaf bfd-mode {
                if-feature bfd-feature {
                  ncd:revise-date 2023-02-20 ;
                }

                description 'Set bfd mode.' ;
                type enumeration {
                  enum standard {
                    value 0 ;
                    status current ;

                  }

                  enum strict {
                    value 1 ;
                    status current ;

                  }

                }

                default standard ;
                config true ;
                mandatory false ;
                ncd:revise-date 2021-03-02 ;
              }

              leaf fast-reroute-block {
                description 'Set interface ip fast-reroute attribute.' ;
                type boolean ;

                config true ;
                mandatory false ;
              }

              leaf ignore-mtu {
                description 'Ignore interface MTU.' ;
                type boolean ;

                config true ;
                mandatory false ;
              }

              leaf max-burst {
                description 'The maximum number of sent LSP each time.' ;
                type uint16 {
                  range 1..50 ;

                }

                default 1 ;
                config true ;
                mandatory false ;
              }

              leaf monitor-receive-interval {
                description 'Monitor ISIS packet receive interval.' ;
                type uint16 {
                  range 1..100 ;

                }

                units second ;
                default 10 ;
                config true ;
                mandatory false ;
              }

              leaf monitor-send-interval {
                description 'Monitor ISIS packet send interval.' ;
                type uint16 {
                  range 1..100 ;

                }

                units second ;
                default 10 ;
                config true ;
                mandatory false ;
              }

              leaf network-p2p {
                description 'Specify ISIS point-to-point network.' ;
                type boolean ;

                config true ;
                mandatory false ;
              }

              leaf passive-mode {
                description 'Control the interface routing update.' ;
                type enumeration {
                  enum disable {
                    value 0 ;
                    description 'Passive mode is off.' ;
                    status current ;

                  }

                  enum enable {
                    value 1 ;
                    description 'Passive mode is on.' ;
                    status current ;

                  }

                  enum with-original-metric {
                    value 2 ;
                    description 'Using original metric of the interface.' ;
                    status current ;

                  }

                }

                config true ;
                mandatory false ;
              }

              leaf ignore-ip-adj-check {
                description 'Ignore adjacency check.' ;
                type boolean ;

                config true ;
                mandatory false ;
              }

              leaf ipv6-bfd-state {
                description 'Enable ipv6 bfd on this interface.' ;
                type isis-state ;

                config true ;
                mandatory false ;
              }

              leaf ipv6-fast-reroute-block {
                description 'Interface IPv6 fast-reroute block.' ;
                type boolean ;

                config true ;
                mandatory false ;
              }

              leaf ignore-ipv6-adj-check {
                description 'Ignore IPv6 adjacency check.' ;
                type boolean ;

                config true ;
                mandatory false ;
              }

              leaf ignore-ip-subnet-check {
                description 'Ignore IP address subnet check.' ;
                type boolean ;

                config true ;
                mandatory false ;
              }

              container psnp-intervals {
                description 'Psnp interval.' ;
                presence "psnp interval" ;
                list psnp-interval {
                  description 'Psnp interval.' ;
                  key level ;
                  leaf level {
                    description 'Level(s) will be effected on.' ;
                    type uint8 {
                      range 0..2 ;

                    }

                    config true ;
                    mandatory false ;
                  }

                  leaf psnp-interval {
                    description 'PSNP transmission interval.' ;
                    type uint16 {
                      range 1..65535 ;

                    }

                    units second ;
                    default 3 ;
                    config true ;
                    mandatory false ;
                  }

                  config true ;
                }

                config true ;
              }

              container intf-mpls-ldps {
                description 'Configure MPLS LDP protocol parameters.' ;
                list intf-mpls-ldp-sync {
                  description 'Configure LDP-ISIS synchronization on interface.' ;
                  key level ;
                  leaf level {
                    description 'Level(s) will be effected on.' ;
                    type uint8 {
                      range 0..2 ;

                    }

                    config true ;
                    mandatory false ;
                  }

                  leaf disable {
                    description 'Disable the flag of ISIS interface mpls ldp synchronization flag.' ;
                    type boolean ;

                    config true ;
                    mandatory false ;
                  }

                  config true ;
                }

                config true ;
              }

              container retransmit-intervals {
                description 'Set per-lsp retransmission interval.' ;
                presence "retran interval" ;
                list retransmit-interval {
                  description 'Set per-lsp retransmission interval.' ;
                  key level ;
                  leaf level {
                    description 'Level(s) will be effected on.' ;
                    type uint8 {
                      range 0..2 ;

                    }

                    config true ;
                    mandatory false ;
                  }

                  leaf retran-interval {
                    description 'Lsp retransmission interval.' ;
                    type uint16 {
                      range 1..65535 ;

                    }

                    default 5 ;
                    config true ;
                    mandatory false ;
                  }

                  config true ;
                }

                config true ;
              }

              container restart-t1-retrys {
                description 'Set restart T1 retry.' ;
                presence "gr t1 retry" ;
                list restart-t1-retry {
                  description 'Set restart T1 retry.' ;
                  key level ;
                  leaf level {
                    description 'Level(s) will be effected on.' ;
                    type uint8 {
                      range 0..2 ;

                    }

                    config true ;
                    mandatory false ;
                  }

                  leaf t1-retry {
                    description 'GR T1 maximum retransmission times.' ;
                    type uint16 {
                      range 1..65535 ;

                    }

                    default 3 ;
                    config true ;
                    mandatory false ;
                  }

                  config true ;
                }

                config true ;
              }

              container restart-t1-timers {
                description 'Set restart T1 timer.' ;
                presence "t1 timer" ;
                list restart-t1-timer {
                  description 'Set restart T1 timer.' ;
                  key level ;
                  leaf level {
                    description 'Level(s) will be effected on.' ;
                    type uint8 {
                      range 0..2 ;

                    }

                    config true ;
                    mandatory false ;
                  }

                  leaf t1-timer {
                    description 'GR T1 timer interval.' ;
                    type uint16 {
                      range 1..65535 ;

                    }

                    units second ;
                    default 10 ;
                    config true ;
                    mandatory false ;
                  }

                  config true ;
                }

                config true ;
              }

              container priorities {
                description 'Set priority for designated router election.' ;
                presence priority ;
                list priority {
                  description 'Set priority for designated router election.' ;
                  key level ;
                  leaf level {
                    description 'Level(s) will be effected on.' ;
                    type uint8 {
                      range 0..2 ;

                    }

                    config true ;
                    mandatory false ;
                  }

                  leaf priority {
                    description 'Interface priority.' ;
                    type uint8 {
                      range 0..127 ;

                    }

                    default 64 ;
                    config true ;
                    mandatory false ;
                  }

                  config true ;
                }

                config true ;
              }

              container metrics {
                description 'Configure the metric for interface.' ;
                presence metric ;
                list metric {
                  description 'Configure the metric for interface.' ;
                  key level ;
                  leaf level {
                    description 'Level(s) will be effected on.' ;
                    type uint8 {
                      range 0..2 ;

                    }

                    config true ;
                    mandatory false ;
                  }

                  leaf metric-value {
                    description 'Interface metric value.' ;
                    type uint32 {
                      range 0..16777215 ;

                    }

                    config true ;
                    mandatory true ;
                  }

                  config true ;
                }

                config true ;
              }

              container lsp-intervals {
                description 'Information of LSP transmission interval.' ;
                presence "lsp interval" ;
                list lsp-interval {
                  description 'Set LSP transmission interval.' ;
                  key level ;
                  leaf level {
                    description 'Level(s) will be effected on.' ;
                    type uint8 {
                      range 0..2 ;

                    }

                    config true ;
                    mandatory false ;
                  }

                  leaf lsp-interval {
                    description 'LSP interval.' ;
                    type uint32 {
                      range 33..4294967040 ;

                    }

                    units millisecond ;
                    default 33 ;
                    config true ;
                    mandatory false ;
                  }

                  config true ;
                }

                config true ;
              }

              container hello-padding {
                description 'Circuit Hello padding.' ;
                presence "hello padding" ;
                leaf hello-padding-type {
                  description 'Circuit Hello PDU padding type.' ;
                  type enumeration {
                    enum enable {
                      value 1 ;
                      description 'ENABLE' ;
                      status current ;

                    }

                    enum dynamic {
                      value 2 ;
                      description 'DYNAMIC' ;
                      status current ;

                    }

                    enum disable {
                      value 3 ;
                      description 'DISABLE' ;
                      status current ;

                    }

                  }

                  config true ;
                  mandatory true ;
                }

                config true ;
                ncd:revise-date 2021-12-17 ;
              }

              container hello-multipliers {
                description 'Set multiplier for hello holding time.' ;
                presence "hello multi" ;
                list hello-multiplier {
                  description 'Set multiplier for hello holding time.' ;
                  key level ;
                  leaf level {
                    description 'Level(s) will be effected on.' ;
                    type uint8 {
                      range 0..2 ;

                    }

                    config true ;
                    mandatory false ;
                  }

                  leaf hello-multiplier {
                    description 'Hello multiplier.' ;
                    type uint16 {
                      range 3..1000 ;

                    }

                    default 3 ;
                    config true ;
                    mandatory false ;
                  }

                  config true ;
                }

                config true ;
              }

              container hello-intervals {
                description 'Hello-interval' ;
                presence "hello interval" ;
                list hello-interval {
                  description 'The interval of hello pdu transmit.' ;
                  key level ;
                  leaf level {
                    description 'Level(s) will be effected on.' ;
                    type uint8 {
                      range 0..2 ;

                    }

                    config true ;
                    mandatory false ;
                  }

                  leaf hello-interval {
                    description 'Hello-interval in seconds.' ;
                    type uint16 {
                      range 1..65535 ;

                    }

                    units second ;
                    default 10 ;
                    config true ;
                    mandatory false ;
                  }

                  config true ;
                }

                config true ;
              }

              container csnp-intervals {
                description 'Csnp interval.' ;
                presence "csnp interval" ;
                list csnp-interval {
                  description 'CSNP interval.' ;
                  key level ;
                  leaf level {
                    description 'Level(s) will be effected on.' ;
                    type uint8 {
                      range 0..2 ;

                    }

                    config true ;
                    mandatory false ;
                  }

                  leaf csnp-interval {
                    description 'CSNP interval.' ;
                    type uint16 {
                      range 1..65535 ;

                    }

                    units second ;
                    default 10 ;
                    config true ;
                    mandatory false ;
                  }

                  config true ;
                }

                config true ;
              }

              container authentication-types {
                description 'Authentication type of interface.' ;
                presence "auth type" ;
                list authentication-type {
                  description 'Authentication type.' ;
                  key level ;
                  leaf level {
                    description 'Level(s) will be effected on.' ;
                    type uint8 {
                      range 0..2 ;

                    }

                    config true ;
                    mandatory false ;
                  }

                  leaf auth-type {
                    description 'The type of authentication.' ;
                    type enumeration {
                      enum md5 {
                        value 1 ;
                        status current ;

                      }

                      enum text {
                        value 2 ;
                        status current ;

                      }

                    }

                    default text ;
                    config true ;
                    mandatory false ;
                  }

                  config true ;
                }

                config true ;
              }

              container intf-mtu {
                description 'Set ISIS MTU.' ;
                presence mtu ;
                leaf mtu {
                  description 'Interface mtu value.' ;
                  type uint32 {
                    range 512..4096 ;

                  }

                  config true ;
                  mandatory true ;
                }

                config true ;
              }

              container ip-router-isis {
                description 'Enable ISIS protocol on interface.' ;
                presence "ip router isis" ;
                leaf ipv4-isis-state {
                  description 'Enable IPv4 ISIS protocol.' ;
                  type isis-state ;

                  config true ;
                  mandatory false ;
                }

                config true ;
              }

              container ipv6-router-isis {
                description 'Enable ISIS IPv6 protocol on interface.' ;
                presence "ipv6 router isis" ;
                leaf ipv6-isis-state {
                  description 'Enable isis IPv6 on interface.' ;
                  type isis-state ;

                  config true ;
                  mandatory false ;
                }

                config true ;
              }

              container mesh-group {
                description 'Set ISIS mesh group information.' ;
                choice isis-mesh-group {
                  description 'ISIS mesh group branches.' ;
                  case group-number-branch {
                    description 'The branch of group number.' ;
                    leaf group-number {
                      description 'Mesh group number.' ;
                      type uint32 {
                        range 1..4294967295 {
                          description 'The range of group number.' ;
                        }

                      }

                      config true ;
                      mandatory false ;
                    }

                  }

                  case blocked-branch {
                    description 'The branch of blocking LSPs.' ;
                    leaf blocked {
                      description 'Block LSPs on this interface.' ;
                      type empty ;

                      config true ;
                      mandatory false ;
                    }

                  }

                  config true ;
                  mandatory false ;
                }

                config true ;
              }

              container authentications {
                description 'Set authentication on interface.' ;
                presence "encrypted password" ;
                list authentication {
                  description 'Set authentication on interface.' ;
                  key level ;
                  leaf level {
                    description 'Information of the level.' ;
                    type uint8 {
                      range 0..2 ;

                    }

                    config true ;
                    mandatory false ;
                  }

                  choice password {
                    description 'Config authentication.' ;
                    case word {
                      description 'Authentication word case.' ;
                      leaf auth-pwd {
                        description 'Password.' ;
                        type string {
                          length 1..100 ;

                        }

                        config true ;
                        mandatory true ;
                      }

                    }

                    case clear-word {
                      description 'Authentication clear word case.' ;
                      leaf clear-pwd {
                        description 'Clear password.' ;
                        type string {
                          length 1..100 ;

                        }

                        config true ;
                        mandatory true ;
                      }

                    }

                    case encrypted-word {
                      description 'Authentication encrypted password case.' ;
                      leaf encrypted-pwd {
                        description 'Encrypted password.' ;
                        type string {
                          length 24..192 ;

                        }

                        config true ;
                        mandatory true ;
                      }

                    }

                    config true ;
                    mandatory false ;
                  }

                  config true ;
                }

                config true ;
              }

              container tags {
                description "The interface's tag information." ;
                presence "tag info" ;
                list tag {
                  description 'Tag information' ;
                  key level ;
                  leaf level {
                    description 'Level(s) will be effected on.' ;
                    type uint8 {
                      range 0..2 ;

                    }

                    config true ;
                    mandatory false ;
                  }

                  leaf tag-value {
                    description 'The tag value.' ;
                    type uint32 {
                      range 1..4294967295 ;

                    }

                    config true ;
                    mandatory true ;
                  }

                  config true ;
                }

                config true ;
              }

              container mpls-ldp-auto-config {
                description 'The state of mpls ldp auto-config.' ;
                leaf state {
                  description 'The state of mpls ldp auto-config.' ;
                  type isis-state ;

                  config true ;
                  mandatory false ;
                }

                config true ;
              }

              container static-remote-lfas {
                if-feature remote-lfa-feature {
                  ncd:revise-date 2023-02-20 ;
                }

                description 'Static remote lfa' ;
                list static-remote-lfa-prefix {
                  if-feature remote-lfa-feature {
                    ncd:revise-date 2023-02-20 ;
                  }

                  description 'Static remote LFA with prefix' ;
                  key prefix ;
                  max-elements 31 ;
                  leaf prefix {
                    if-feature remote-lfa-feature ;

                    description 'Prefix' ;
                    type string {
                      length 1..169 ;

                    }

                    config true ;
                    mandatory false ;
                  }

                  leaf next-hop {
                    if-feature remote-lfa-feature {
                      ncd:revise-date 2023-02-20 ;
                    }

                    description 'Next hop' ;
                    type ncd:ipv4-address ;

                    config true ;
                    mandatory true ;
                  }

                  config true ;
                }

                container static-remote-lfa {
                  if-feature remote-lfa-feature {
                    ncd:revise-date 2023-02-20 ;
                  }

                  description 'Static remote LFA with no prefix' ;
                  presence nexthop ;
                  leaf next-hop {
                    if-feature remote-lfa-feature {
                      ncd:revise-date 2023-02-20 ;
                    }

                    description 'Next hop' ;
                    type ncd:ipv4-address ;

                    config true ;
                    mandatory true ;
                  }

                  config true ;
                }

                config true ;
              }

              container link-metric {
                description 'Configure the metric for interface in sd status' ;
                status obsolete {
                  ncd:revise-date 2019-07-02 ;
                }

                choice inc-metric {
                  description 'Configure the metric increase for interface in sd status' ;
                  default maximum-value ;
                  case increase-value {
                    description 'Configure the metric increase for interface in sd status' ;
                    leaf inc-value {
                      description 'increase value' ;
                      type uint16 {
                        range 100..10000 ;

                      }

                      config true ;
                      mandatory false ;
                    }

                  }

                  case maximum-value {
                    description 'set max metric when link in sd status' ;
                    leaf maximum {
                      description 'Set max maximum' ;
                      type empty ;

                      config true ;
                      mandatory false ;
                    }

                  }

                  config true ;
                  mandatory false ;
                }

                config true ;
              }

              container ipv4-bfd-negotiation {
                description 'IPv4 BFD time negotiation parameter' ;
                leaf min-tx {
                  description 'Minimum transmit interval in milliseconds.The default value is provided by the performance parameter.' ;
                  type uint32 {
                    range 0..65535 ;

                  }

                  units millisecond ;
                  config true ;
                  mandatory false ;
                }

                leaf min-rx {
                  description 'Minimum receive interval in milliseconds.The default value is provided by the performance parameter.' ;
                  type uint32 {
                    range 0..65535 ;

                  }

                  units millisecond ;
                  config true ;
                  mandatory false ;
                }

                leaf multiplier {
                  description 'Detect multiplier.The default value is provided by the performance parameter.' ;
                  type uint8 {
                    range 3..50 ;

                  }

                  config true ;
                  mandatory false ;
                }

                config true ;
                ncd:revise-date 2015-07-21 ;
              }

              container ipv6-bfd-negotiation {
                description 'IPv6 BFD time negotiation parameter' ;
                leaf min-tx {
                  description 'Minimum transmit interval in milliseconds.The default value is provided by the performance parameter.' ;
                  type uint32 {
                    range 0..65535 ;

                  }

                  units millisecond ;
                  config true ;
                  mandatory false ;
                }

                leaf min-rx {
                  description 'Minimum receive interval in milliseconds.The default value is provided by the performance parameter.' ;
                  type uint32 {
                    range 0..65535 ;

                  }

                  units millisecond ;
                  config true ;
                  mandatory false ;
                }

                leaf multiplier {
                  description 'Detect multiplier.The default value is provided by the performance parameter.' ;
                  type uint8 {
                    range 3..50 ;

                  }

                  config true ;
                  mandatory false ;
                }

                config true ;
                ncd:revise-date 2015-07-21 ;
              }

              container fast-remote-lfa-block {
                description 'Block interface IP remote-lfa capability' ;
                leaf level {
                  description 'Level(s) will be effected on.' ;
                  type uint8 {
                    range 0..2 ;

                  }

                  config true ;
                  mandatory false ;
                }

                config true ;
                ncd:revise-date 2015-09-22 ;
              }

              container ipv6-mpls-ldps {
                description 'Configure IPv6 MPLS LDP protocol parameters.' ;
                list ipv6-mpls-ldp-sync {
                  description 'Configure IPv6 LDP-ISIS synchronization on the interface.' ;
                  key level ;
                  leaf level {
                    description 'Level(s) will be effected on.' ;
                    type uint8 {
                      range 0..2 ;

                    }

                    config true ;
                    mandatory false ;
                  }

                  leaf disable {
                    description 'Disable ISIS mpls ldp synchronization on the interface.' ;
                    type boolean ;

                    config true ;
                    mandatory false ;
                  }

                  config true ;
                }

                config true ;
                ncd:revise-date 2016-08-04 ;
              }

              container authen-keychains {
                description 'Configure keychain authentication information.' ;
                list authen-keychain {
                  description 'Configure keychain authentication on the interface.' ;
                  key level ;
                  leaf level {
                    description 'Level(s) will be effected on.' ;
                    type uint8 {
                      range 0..2 ;

                    }

                    config true ;
                    mandatory false ;
                  }

                  leaf keychain-name {
                    description 'Keychain name associated to neighbor for authentication on the interface.' ;
                    type string {
                      length 1..31 {
                        description 'Name of a keychain (1-31 characters).' ;
                      }

                    }

                    config true ;
                    mandatory false ;
                  }

                  config true ;
                }

                config true ;
                ncd:revise-date 2016-08-04 ;
              }

              container link-damping {
                description 'Configure link damping for interface.' ;
                status obsolete {
                  ncd:revise-date 2019-07-02 ;
                }

                leaf damping-time {
                  description 'Set damping time for link damping.' ;
                  type uint32 {
                    range 1..3600 {
                      description 'The damping time value in seconds.' ;
                    }

                  }

                  units second ;
                  default 600 ;
                  config true ;
                  mandatory false ;
                }

                choice inc-metric {
                  description 'Set metric for link damping.' ;
                  default maximum-value ;
                  case increase-value {
                    description 'Set increase metric when link is damping.' ;
                    leaf inc-value {
                      description 'The increase metric value.' ;
                      type uint32 {
                        range 100..10000 {
                          description 'The increase metric value.' ;
                        }

                      }

                      config true ;
                      mandatory true ;
                    }

                  }

                  case maximum-value {
                    description 'Set maximum metric when link is damping.' ;
                    leaf maximum {
                      description 'Set max maximum.' ;
                      type empty ;

                      config true ;
                      mandatory false ;
                    }

                  }

                  config true ;
                  mandatory false ;
                }

                config true ;
                ncd:revise-date 2017-06-06 ;
              }

              container mt-ipv6-link-damping {
                description 'Configure link damping for interface.' ;
                status obsolete {
                  ncd:revise-date 2019-07-02 ;
                }

                leaf damping-time {
                  description 'Set damping time for link damping.' ;
                  type uint32 {
                    range 1..3600 {
                      description 'The damping time value in seconds.' ;
                    }

                  }

                  units second ;
                  default 600 ;
                  config true ;
                  mandatory false ;
                }

                choice inc-metric {
                  description 'Set metric for link damping.' ;
                  default maximum-value ;
                  case increase-value {
                    description 'Set increase metric when link is damping.' ;
                    leaf inc-value {
                      description 'The increase metric value.' ;
                      type uint32 {
                        range 100..10000 {
                          description 'The increase metric value.' ;
                        }

                      }

                      config true ;
                      mandatory true ;
                    }

                  }

                  case maximum-value {
                    description 'Set maximum metric when link is damping.' ;
                    leaf maximum {
                      description 'Set max maximum.' ;
                      type empty ;

                      config true ;
                      mandatory false ;
                    }

                  }

                  config true ;
                  mandatory false ;
                }

                config true ;
                ncd:revise-date 2017-06-06 ;
              }

              container link-damped-adj-establish {
                description 'Configure link damped for adjacency establish.' ;
                leaf adj-establish-status {
                  description 'Set link damped disable or enable for adjacency establish.' ;
                  type isis-state ;

                  default disable ;
                  config true ;
                  mandatory false ;
                }

                config true ;
                ncd:revise-date 2019-04-11 ;
              }

              container ipv6-link-damped-adj-establish {
                description 'Configure link damped for adjacency establish.' ;
                leaf adj-establish-status {
                  description 'Set link damped disable or enable for adjacency establish.' ;
                  type isis-state ;

                  default disable ;
                  config true ;
                  mandatory false ;
                }

                config true ;
                ncd:revise-date 2019-04-11 ;
              }

              container link-damped-revert-interval {
                description 'Configure link damped revert interval for interface.' ;
                leaf max-delay-time {
                  description 'Maximum delay before a link damped in seconds.' ;
                  type uint32 {
                    range 1..3600 {
                      description 'Maximum delay before a link damped in seconds.' ;
                    }

                  }

                  units second ;
                  default 600 ;
                  config true ;
                  mandatory false ;
                }

                leaf init-delay-time {
                  description 'Initial delay before a link damped in ms.' ;
                  type uint32 {
                    range 1..600000 {
                      description 'Range for delay time:1-600000(ms)' ;
                    }

                  }

                  units millisecond ;
                  default 3000 ;
                  config true ;
                  mandatory false ;
                }

                leaf second-delay-time {
                  description 'Secondary delay before a link damped in ms.' ;
                  type uint32 {
                    range 1..600000 {
                      description 'Range for delay time:1-600000(ms)' ;
                    }

                  }

                  units millisecond ;
                  default 3000 ;
                  config true ;
                  mandatory false ;
                }

                config true ;
                ncd:revise-date 2019-04-11 ;
              }

              container ipv6-link-damped-revert-interval {
                description 'Configure link damped revert interval for interface.' ;
                leaf max-delay-time {
                  description 'Maximum delay before a link damped in seconds.' ;
                  type uint32 {
                    range 1..3600 {
                      description 'Maximum delay before a link damped in seconds.' ;
                    }

                  }

                  units second ;
                  default 600 ;
                  config true ;
                  mandatory false ;
                }

                leaf init-delay-time {
                  description 'Initial delay before a link damped in ms.' ;
                  type uint32 {
                    range 1..600000 {
                      description 'Range for delay time:1-600000(ms)' ;
                    }

                  }

                  units millisecond ;
                  default 3000 ;
                  config true ;
                  mandatory false ;
                }

                leaf second-delay-time {
                  description 'Secondary delay before a link damped in ms.' ;
                  type uint32 {
                    range 1..600000 {
                      description 'Range for delay time:1-600000(ms)' ;
                    }

                  }

                  units millisecond ;
                  default 3000 ;
                  config true ;
                  mandatory false ;
                }

                config true ;
                ncd:revise-date 2019-04-11 ;
              }

              container link-damped-metric {
                description 'Configure the metric for link damped' ;
                choice inc-metric {
                  description 'Configure the increase metric for link damped' ;
                  default maximum-value ;
                  case increase-value {
                    description 'Configure the increase metric for link damped' ;
                    leaf inc-value {
                      description 'increase value' ;
                      type uint32 {
                        range 100..10000 ;

                      }

                      config true ;
                      mandatory false ;
                    }

                  }

                  case maximum-value {
                    description 'Set max metric when link damped' ;
                    leaf maximum {
                      description 'Set max maximum' ;
                      type empty ;

                      config true ;
                      mandatory false ;
                    }

                  }

                  config true ;
                  mandatory false ;
                }

                config true ;
                ncd:revise-date 2019-07-02 ;
              }

              container ipv6-link-damped-metric {
                description 'Configure the metric for link damped' ;
                choice inc-metric {
                  description 'Configure the increase metric for link damped' ;
                  default maximum-value ;
                  case increase-value {
                    description 'Configure the increase metric for link damped' ;
                    leaf inc-value {
                      description 'increase value' ;
                      type uint32 {
                        range 100..10000 ;

                      }

                      config true ;
                      mandatory false ;
                    }

                  }

                  case maximum-value {
                    description 'Set max metric when link damped' ;
                    leaf maximum {
                      description 'Set max maximum' ;
                      type empty ;

                      config true ;
                      mandatory false ;
                    }

                  }

                  config true ;
                  mandatory false ;
                }

                config true ;
                ncd:revise-date 2019-07-02 ;
              }

              container link-damped-link-sd {
                description 'Link SD suppression function switch.' ;
                leaf status {
                  description 'enable:open link SD suppression function switch;disable:shutdown link SD suppression function switch.' ;
                  type isis-state ;

                  default enable ;
                  config true ;
                  mandatory false ;
                }

                config true ;
                ncd:revise-date 2019-08-08 ;
              }

              container ipv6-link-damped-link-sd {
                description 'Link SD suppression function switch.' ;
                leaf status {
                  description 'enable:open link SD suppression function switch;disable:shutdown link SD suppression function switch.' ;
                  type isis-state ;

                  default enable ;
                  config true ;
                  mandatory false ;
                }

                config true ;
                ncd:revise-date 2019-08-08 ;
              }

              container link-damped-lag-detect-down {
                description 'Smartgroup link member interface detects the BFD down link suppression function switch.' ;
                leaf status {
                  description 'enable:open switch;disable:shutdown switch.' ;
                  type isis-state ;

                  default disable ;
                  config true ;
                  mandatory false ;
                }

                config true ;
                ncd:revise-date 2019-08-08 ;
              }

              container ipv6-link-damped-lag-detect-down {
                description 'Smartgroup link member interface detects the BFD down link suppression function switch.' ;
                leaf status {
                  description 'enable:open switch;disable:shutdown switch.' ;
                  type isis-state ;

                  default disable ;
                  config true ;
                  mandatory false ;
                }

                config true ;
                ncd:revise-date 2019-08-08 ;
              }

              container ipv6-metrics {
                description 'Configure the IPv6 metric for interface.' ;
                list ipv6-metric {
                  description 'Configure the IPv6 metric for interface.' ;
                  key level ;
                  leaf level {
                    description 'Level(s) will be effected on.' ;
                    type uint8 {
                      range 0..2 ;

                    }

                    config true ;
                    mandatory false ;
                  }

                  leaf metric-value {
                    description 'Interface IPv6 metric value.' ;
                    type uint32 {
                      range 0..16777215 ;

                    }

                    config true ;
                    mandatory true ;
                  }

                  config true ;
                }

                config true ;
                ncd:revise-date 2019-08-13 ;
              }

              container link-damped-bfd-down {
                description 'Link BFD down suppression function switch.' ;
                leaf status {
                  description 'enable:open link BFD down suppression function switch;disable:shutdown link BFD down suppression function switch.' ;
                  type isis-state ;

                  default enable ;
                  config true ;
                  mandatory false ;
                }

                config true ;
                ncd:revise-date 2019-09-18 ;
              }

              container ipv6-link-damped-bfd-down {
                description 'Link IPv6 BFD down suppression function switch.' ;
                leaf status {
                  description 'enable:open link IPv6 BFD down suppression function switch;disable:shutdown link IPv6 BFD down suppression function switch.' ;
                  type isis-state ;

                  default enable ;
                  config true ;
                  mandatory false ;
                }

                config true ;
                ncd:revise-date 2019-09-18 ;
              }

              container flapping-damping {
                description 'The damping set of isis adjacency up/down flapping.' ;
                leaf state {
                  description 'State of adjacency flapping damping.' ;
                  type isis-state ;

                  default enable ;
                  config true ;
                  mandatory false ;
                }

                leaf delay-time {
                  description 'Delay time for adjacency flapping damping.' ;
                  type uint32 {
                    range 5..3600 ;

                  }

                  default 60 ;
                  config true ;
                  mandatory false ;
                }

                container detect-parameter {
                  description 'Set detection parameters.' ;
                  leaf interval {
                    description 'Detect interval.' ;
                    type uint32 {
                      range 10..300 ;

                    }

                    default 60 ;
                    config true ;
                    mandatory false ;
                  }

                  leaf threshold {
                    description 'The number of adjacency down times within the detection time reaches the threshold.' ;
                    type uint8 {
                      range 3..10 ;

                    }

                    default 3 ;
                    config true ;
                    mandatory false ;
                  }

                  config true ;
                }

                config true ;
                ncd:revise-date 2019-12-13 ;
              }

              container reverse-metric {
                if-feature reverse-metric-feature {
                  ncd:revise-date 2023-02-20 ;
                }

                description 'In ISIS Interface mode, set attributes of reverse-metric.' ;
                leaf state {
                  if-feature reverse-metric-feature {
                    ncd:revise-date 2023-02-20 ;
                  }

                  description 'enable:open Reverse-Metric function switch; disable: shutdown Reverse-Metric function switch' ;
                  type isis-state ;

                  default disable ;
                  config true ;
                  mandatory false ;
                }

                leaf increase-value {
                  if-feature reverse-metric-feature {
                    ncd:revise-date 2023-02-20 ;
                  }

                  description 'Interface reverse-metric increase value' ;
                  type uint32 {
                    range 1..16777214 ;

                  }

                  default 16777214 ;
                  config true ;
                  mandatory false ;
                }

                config true ;
                ncd:revise-date 2020-01-07 ;
              }

              container fast-reroute-srlgs {
                status obsolete {
                  ncd:revise-date 2020-12-11 ;
                }

                list fast-reroute-srlg {
                  key value ;
                  leaf value {
                    description 'Configure the value of srlg.' ;
                    type int32 ;

                    config true ;
                    mandatory false ;
                  }

                  config true ;
                }

                config true ;
                ncd:revise-date 2020-03-31 ;
              }

              container ipv4-bfd-template {
                presence "template name" ;
                leaf template-name {
                  description 'Configure BFD interface template parameter' ;
                  type string {
                    length 1..31 ;

                  }

                  config true ;
                  mandatory true ;
                }

                config true ;
                ncd:revise-date 2020-07-15 ;
              }

              container ipv6-bfd-template {
                presence "template name" ;
                leaf template-name {
                  description 'Configure BFD interface template parameter' ;
                  type string {
                    length 1..31 ;

                  }

                  config true ;
                  mandatory true ;
                }

                config true ;
                ncd:revise-date 2020-07-15 ;
              }

              container fast-reroute-tilfa-block {
                if-feature frr-feature {
                  ncd:revise-date 2023-02-20 ;
                }

                description 'Block interface IP ti-lfa capability' ;
                leaf level {
                  if-feature frr-feature {
                    ncd:revise-date 2023-02-20 ;
                  }

                  description 'Level(s) will be effected on' ;
                  type uint8 {
                    range 0..2 ;

                  }

                  config true ;
                  mandatory false ;
                }

                config true ;
                ncd:revise-date 2020-11-13 ;
              }

              container ipv6-fast-reroute-tilfa-block {
                if-feature frr-feature {
                  ncd:revise-date 2023-02-20 ;
                }

                description 'Block interface IPv6 ti-lfa capability' ;
                leaf level {
                  if-feature frr-feature {
                    ncd:revise-date 2023-02-20 ;
                  }

                  description 'Level(s) will be effected on' ;
                  type uint8 {
                    range 0..2 ;

                  }

                  config true ;
                  mandatory false ;
                }

                config true ;
                ncd:revise-date 2020-11-13 ;
              }

              container frr-srlgs {
                description 'Configure FRR SRLG information on an interface.' ;
                list frr-srlg {
                  description 'Configure FRR SRLG information on an interface.' ;
                  key value ;
                  leaf value {
                    description 'Set the identifier of SRLG.' ;
                    type uint32 {
                      range 0..4294967295 ;

                    }

                    config true ;
                    mandatory false ;
                  }

                  config true ;
                }

                config true ;
                ncd:revise-date 2020-12-11 ;
              }

              container ipv6-link-damped-bfd-down-para {
                description 'Configure detection parameters that interface detects the BFD down.' ;
                leaf detect-interval {
                  description 'Detect interval.' ;
                  type uint32 {
                    range 1..300 ;

                  }

                  default 60 ;
                  config true ;
                  mandatory false ;
                }

                leaf threshold {
                  description 'The number of BFD down times within the detection time reaches the threshold.' ;
                  type uint32 {
                    range 1..10 ;

                  }

                  default 3 ;
                  config true ;
                  mandatory false ;
                }

                leaf resume-interval {
                  description 'Resume time for link damped.' ;
                  type uint32 {
                    range 1..3600 ;

                  }

                  default 120 ;
                  config true ;
                  mandatory false ;
                }

                config true ;
                ncd:revise-date 2022-05-13 ;
              }

              container ipv6-link-damped-lag-detect-down-para {
                description 'Configure detection parameters that smartgroup link member interface detects the BFD down.' ;
                leaf detect-interval {
                  description 'Detect interval.' ;
                  type uint32 {
                    range 1..300 ;

                  }

                  default 60 ;
                  config true ;
                  mandatory false ;
                }

                leaf threshold {
                  description 'The number of BFD down times within the detection time reaches the threshold.' ;
                  type uint32 {
                    range 1..10 ;

                  }

                  default 3 ;
                  config true ;
                  mandatory false ;
                }

                leaf resume-interval {
                  description 'Resume time for link damped.' ;
                  type uint32 {
                    range 1..3600 ;

                  }

                  default 120 ;
                  config true ;
                  mandatory false ;
                }

                config true ;
                ncd:revise-date 2022-05-13 ;
              }

              container link-damped-bfd-down-para {
                description 'Configure detection parameters that interface detects the BFD down.' ;
                leaf detect-interval {
                  description 'Detect interval.' ;
                  type uint32 {
                    range 1..300 ;

                  }

                  default 60 ;
                  config true ;
                  mandatory false ;
                }

                leaf threshold {
                  description 'The number of BFD down times within the detection time reaches the threshold.' ;
                  type uint32 {
                    range 1..10 ;

                  }

                  default 3 ;
                  config true ;
                  mandatory false ;
                }

                leaf resume-interval {
                  description 'Resume time for link damped.' ;
                  type uint32 {
                    range 1..3600 ;

                  }

                  default 120 ;
                  config true ;
                  mandatory false ;
                }

                config true ;
                ncd:revise-date 2022-05-13 ;
              }

              container link-damped-lag-detect-down-para {
                description 'Configure detection parameters that smartgroup link member interface detects the BFD down.' ;
                leaf detect-interval {
                  description 'Detect interval.' ;
                  type uint32 {
                    range 1..300 ;

                  }

                  default 60 ;
                  config true ;
                  mandatory false ;
                }

                leaf threshold {
                  description 'The number of BFD down times within the detection time reaches the threshold.' ;
                  type uint32 {
                    range 1..10 ;

                  }

                  default 3 ;
                  config true ;
                  mandatory false ;
                }

                leaf resume-interval {
                  description 'Resume time for link damped.' ;
                  type uint32 {
                    range 1..3600 ;

                  }

                  default 120 ;
                  config true ;
                  mandatory false ;
                }

                config true ;
                ncd:revise-date 2022-05-13 ;
              }

              container ip-reachability-suppress {
                description 'Suppress IS-IS IP reachability.' ;
                leaf state {
                  description 'State of suppress IS-IS IP reachability.' ;
                  type isis-state ;

                  default disable ;
                  config true ;
                  mandatory false ;
                }

                config true ;
                ncd:revise-date 2023-05-07 ;
              }

              container ipv6-reachability-suppress {
                description 'Suppress IS-IS IPv6 reachability.' ;
                leaf state {
                  description 'State of suppress IS-IS IPv6 reachability.' ;
                  type isis-state ;

                  default disable ;
                  config true ;
                  mandatory false ;
                }

                config true ;
                ncd:revise-date 2023-05-07 ;
              }

              container intf-ldp-sync-hold-times {
                description 'Configure LDP-ISIS synchronization hold time on interface.' ;
                list intf-ldp-sync-hold-time {
                  description 'Configure LDP-ISIS synchronization hold time on interface.' ;
                  key level ;
                  leaf level {
                    description 'Level(s) will be effected on.' ;
                    type uint8 {
                      range 0..2 ;

                    }

                    config true ;
                    mandatory false ;
                  }

                  choice hold-time {
                    description 'Set LDP-ISIS synchronization hold time in seconds on interface.' ;
                    mandatory true ;
                    case time {
                      description 'Set LDP-ISIS synchronization hold time in seconds on interface.' ;
                      leaf value {
                        description 'Set time value in seconds.' ;
                        type uint32 {
                          range 1..65535 ;

                        }

                        config true ;
                        mandatory true ;
                      }

                    }

                    case infinite {
                      description 'Set LDP-ISIS synchronization hold time infinite on interface.' ;
                      leaf infinite {
                        description 'Set time to infinite.' ;
                        type empty ;

                        config true ;
                        mandatory true ;
                      }

                    }

                    config true ;
                  }

                  config true ;
                }

                config true ;
                if-feature intf-ldp-sync-feature {
                  ncd:revise-date 2025-04-25 ;
                }

                ncd:revise-date 2025-02-25 ;
              }

              container intf-ipv6-ldp-sync-hold-times {
                description 'Configure IPv6 LDP-ISIS synchronization hold time on interface.' ;
                list intf-ipv6-ldp-sync-hold-time {
                  description 'Configure LDP-ISIS synchronization hold time on interface.' ;
                  key level ;
                  leaf level {
                    description 'Level(s) will be effected on.' ;
                    type uint8 {
                      range 0..2 ;

                    }

                    config true ;
                    mandatory false ;
                  }

                  choice hold-time {
                    description 'Set LDP-ISIS synchronization hold time in seconds on interface.' ;
                    mandatory true ;
                    case time {
                      description 'Set LDP-ISIS synchronization hold time in seconds on interface.' ;
                      leaf value {
                        description 'Set time value in seconds.' ;
                        type uint32 {
                          range 1..65535 ;

                        }

                        config true ;
                        mandatory true ;
                      }

                    }

                    case infinite {
                      description 'Set LDP-ISIS synchronization hold time infinite on interface.' ;
                      leaf infinite {
                        description 'Set time to infinite.' ;
                        type empty ;

                        config true ;
                        mandatory true ;
                      }

                    }

                    config true ;
                  }

                  config true ;
                }

                config true ;
                if-feature intf-ldp-sync-feature {
                  ncd:revise-date 2025-04-25 ;
                }

                ncd:revise-date 2025-02-25 ;
              }

              config true ;
            }

            config true ;
          }

          container ipv4-distances {
            description 'Administrative distance of IPv4 ISIS route.' ;
            presence distance ;
            list ipv4-distance {
              description 'Administrative distance of route.' ;
              key prefix-list-name ;
              max-elements 9 ;
              leaf prefix-list-name {
                description 'Name of a prefix list (1-169 characters).' ;
                type string {
                  length 1..169 {
                    description 'Name of a prefix list (1-169 characters).' ;
                  }

                }

                config true ;
                mandatory false ;
              }

              leaf distance {
                description 'Distance value.Range:1-255' ;
                type uint8 {
                  range 1..255 {
                    description 'Distance value.Range:1-255' ;
                  }

                }

                config true ;
                mandatory true ;
              }

              config true ;
            }

            container distance-without-prefix-list {
              description 'IPv4 distance without prefix-list name.' ;
              presence distance ;
              leaf distance {
                description 'Distance value.Range:1-255. Default:115' ;
                type uint8 {
                  range 1..255 ;

                }

                default 115 ;
                config true ;
                mandatory false ;
              }

              config true ;
            }

            list distance-with-rmp {
              description 'Administrative distance of route with route map.' ;
              key route-map-name ;
              max-elements 9 ;
              leaf route-map-name {
                description 'Name of a route map (1-200 characters).' ;
                type string {
                  length 1..200 {
                    description 'Name of a route map (1-200 characters).' ;
                  }

                }

                config true ;
                mandatory false ;
              }

              leaf distance {
                description 'Distance value.Range:1-255' ;
                type uint8 {
                  range 1..255 {
                    description 'Distance value.Range:1-255' ;
                  }

                }

                config true ;
                mandatory true ;
              }

              config true ;
              ncd:revise-date 2021-03-30 ;
            }

            container policy {
              description 'Configure policy of distance.' ;
              presence "ipv4 distance policy" ;
              choice policy-type {
                description 'Configure policy type of distance.' ;
                mandatory true ;
                case routemap-branch {
                  description 'Route map branch of distance policy.' ;
                  leaf routemap-name {
                    description 'The name of route map.' ;
                    type string {
                      length 1..200 ;

                    }

                    config true ;
                    mandatory true ;
                  }

                }

                config true ;
              }

              config true ;
              ncd:revise-date 2022-11-26 ;
            }

            config true ;
          }

          container ipv6-distances {
            description 'Administrative distance of IPv6 ISIS route.' ;
            presence "distance leaf" ;
            list ipv6-distance {
              description 'Administrative distance of IPv6 route.' ;
              key prefix-list-name ;
              max-elements 9 ;
              leaf prefix-list-name {
                description 'Name of a prefix list (1-169 characters).' ;
                type string {
                  length 1..169 {
                    description 'Name of a prefix list (1-169 characters).' ;
                  }

                }

                config true ;
                mandatory false ;
              }

              leaf distance {
                description 'Value of distance. Range:1-255.' ;
                type uint8 {
                  range 1..255 {
                    description 'Distance value.Range:1-255' ;
                  }

                }

                config true ;
                mandatory true ;
              }

              config true ;
            }

            container distance-without-prefix-list {
              description 'IPv6 distance without prefix-list name.' ;
              presence distance ;
              leaf distance {
                description 'Value of distance. Range:1-255.Default:115' ;
                type uint8 {
                  range 1..255 ;

                }

                default 115 ;
                config true ;
                mandatory false ;
              }

              config true ;
            }

            list distance-with-rmp {
              description 'Administrative distance of IPv6 route with route map.' ;
              key route-map-name ;
              max-elements 9 ;
              leaf route-map-name {
                description 'Name of a route map (1-200 characters).' ;
                type string {
                  length 1..200 {
                    description 'Name of a route map (1-200 characters).' ;
                  }

                }

                config true ;
                mandatory false ;
              }

              leaf distance {
                description 'Distance value.Range:1-255' ;
                type uint8 {
                  range 1..255 {
                    description 'Distance value.Range:1-255' ;
                  }

                }

                config true ;
                mandatory true ;
              }

              config true ;
              ncd:revise-date 2021-03-30 ;
            }

            container policy {
              description 'Configure policy of distance.' ;
              presence "ipv6 distance policy" ;
              choice policy-type {
                description 'Configure policy type of distance.' ;
                mandatory true ;
                case routemap-branch {
                  description 'Route map branch of distance policy.' ;
                  leaf routemap-name {
                    description 'The name of route map.' ;
                    type string {
                      length 1..200 ;

                    }

                    config true ;
                    mandatory true ;
                  }

                }

                config true ;
              }

              config true ;
              ncd:revise-date 2022-11-26 ;
            }

            config true ;
          }

          container ipv4-redis-prefix-limits {
            description 'IPv4 redistribute prefix limit' ;
            list ipv4-redis-prefix-limit {
              description 'IPv4 redistribute prefix limit' ;
              key level ;
              leaf level {
                description 'Level(s) will be effected on.' ;
                type uint8 {
                  range 0..2 ;

                }

                config true ;
                mandatory false ;
              }

              leaf prefix-limit {
                description 'Maximum number of IPv4 prefixes redistributed' ;
                type uint32 {
                  range 1..1000000 ;

                }

                config true ;
                mandatory true ;
              }

              config true ;
            }

            config true ;
          }

          container ipv6-redis-prefix-limits {
            description 'IPv6 redistribute prefix limit' ;
            list ipv6-redis-prefix-limit {
              description 'IPv6 redistribute prefix limit' ;
              key level ;
              leaf level {
                description 'Level(s) will be effected on.' ;
                type uint8 {
                  range 0..2 ;

                }

                config true ;
                mandatory false ;
              }

              leaf prefix-limit {
                description 'Maximum number of IPv6 prefixes redistributed' ;
                type uint32 {
                  range 1..1000000 ;

                }

                config true ;
                mandatory true ;
              }

              config true ;
            }

            config true ;
          }

          container track-objects {
            description 'Event tracking.' ;
            list track-object {
              description 'Event tracking.' ;
              key track-name ;
              leaf track-name {
                description 'The samgr name of the associated track detection' ;
                type string {
                  length 1..31 {
                    description 'The length of track-name is from 1 to 31 characters.' ;
                  }

                }

                config true ;
                mandatory false ;
              }

              config true ;
            }

            config true ;
            ncd:revise-date 2015-07-21 ;
          }

          container ipv4-distribute-list {
            description 'IPv4 distribution instance.' ;
            presence "ipv4 distribute list" ;
            leaf routemap-name {
              description 'Routemap name used in IPv4 distribution.' ;
              type string {
                length 1..200 ;

              }

              config true ;
              mandatory true ;
            }

            config true ;
            ncd:revise-date 2015-08-11 ;
          }

          container isis-router-id {
            if-feature frr-feature {
              ncd:revise-date 2023-02-20 ;
            }

            description 'Set auxiliary router-id for ISIS process' ;
            leaf router-id {
              if-feature frr-feature {
                ncd:revise-date 2023-02-20 ;
              }

              description 'ISIS auxiliary router-id in IP address format' ;
              type ncd:ipv4-address ;

              config true ;
              mandatory false ;
            }

            config true ;
            ncd:revise-date 2015-09-22 ;
          }

          container remote-lfa-state {
            description 'The state of remote LFA.' ;
            leaf level {
              description 'Level(s) will be effected on.' ;
              type uint8 {
                range 0..2 ;

              }

              config true ;
              mandatory false ;
            }

            config true ;
            ncd:revise-date 2015-09-22 ;
          }

          container remote-lfa-max-metrics {
            description 'Set maximum metric required to the release node' ;
            list remote-lfa-max-metric {
              description 'Set maximum metric required to the release node' ;
              key level ;
              leaf level {
                description 'Level(s) will be effected on.' ;
                type uint8 {
                  range 0..2 ;

                }

                config true ;
                mandatory false ;
              }

              leaf metric-value {
                description 'Maximum metric value.' ;
                type uint32 {
                  range 1..4261412864 ;

                }

                config true ;
                mandatory false ;
              }

              config true ;
            }

            config true ;
            ncd:revise-date 2015-09-22 ;
          }

          container frr-priority {
            description 'Set priority for FRR type' ;
            leaf lfa-priority {
              description 'LFA priority.Range:1-255. Default:115.' ;
              type uint8 {
                range 1..255 ;

              }

              default 115 ;
              config true ;
              mandatory false ;
            }

            leaf rlfa-priority {
              description 'Set remote-lfa priority. Range:1-255. Default:115' ;
              type uint8 {
                range 1..255 ;

              }

              default 115 ;
              config true ;
              mandatory false ;
            }

            leaf static-rlfa-priority {
              description 'Set static remote-lfa priority. Range:1-255. Default:115.' ;
              type uint8 {
                range 1..255 ;

              }

              default 115 ;
              config true ;
              mandatory false ;
            }

            leaf ti-lfa-priority {
              if-feature frr-feature {
                ncd:revise-date 2023-02-20 ;
              }

              description 'Set ti-lfa priority. Range:1-255. Default:115.' ;
              type uint8 {
                range 1..255 ;

              }

              default 115 ;
              config true ;
              mandatory false ;
              ncd:revise-date 2019-09-02 ;
            }

            config true ;
            ncd:revise-date 2015-09-22 ;
          }

          container bgp-link-states {
            description 'The object of ISIS BGP-LS.' ;
            list bgp-ls {
              description 'ISIS BGP-LS' ;
              key level ;
              leaf level {
                description 'Level(s) will be effected on.' ;
                type enumeration {
                  enum level-1 {
                    value 1 ;
                    description 'BGP-LS on level-1' ;
                    status current ;

                  }

                  enum level-2 {
                    value 2 ;
                    description 'BGP-LS on level-2' ;
                    status current ;

                  }

                }

                config true ;
                mandatory false ;
              }

              leaf instance-id {
                description 'The link-state data instance identifier' ;
                type int32 {
                  range 0..65535 ;

                }

                config true ;
                mandatory false ;
                ncd:revise-date 2018-10-19 ;
              }

              leaf level-2-leak-ignore {
                description 'Ignore the routes leaked by level-2.' ;
                type isis-state ;

                default disable ;
                config true ;
                mandatory false ;
                ncd:revise-date 2022-12-29 ;
              }

              config true ;
            }

            config true ;
            ncd:revise-date 2016-03-16 ;
          }

          container def-info-learns {
            description 'Learn of ISIS IPv4 default route.' ;
            list def-info-learn {
              description 'Learn of ISIS IPv4 default route.' ;
              key state ;
              leaf state {
                description 'Flag of the system whether would ignore the IPv4 default route.' ;
                type enumeration {
                  enum ignore {
                    value 1 ;
                    description 'Ignore learn of ISIS default route' ;
                    status current ;

                  }

                }

                config true ;
                mandatory false ;
              }

              leaf level {
                description 'Level(s) will be effected on.' ;
                type isis-level ;

                config true ;
                mandatory true ;
              }

              config true ;
            }

            config true ;
            ncd:revise-date 2016-08-04 ;
          }

          container ipv6-def-info {
            description 'Control distribution of IPv6 default route information.' ;
            presence "ipv6 default information" ;
            leaf def-info-originate {
              description 'ISIS redistribution default route information flag.' ;
              type boolean ;

              config true ;
              mandatory true ;
            }

            container default-info {
              description 'Default route attribution branches.' ;
              presence "always branch" ;
              container always {
                description 'Config IPv6 default information always attribution.' ;
                presence always ;
                leaf state {
                  description 'Always redistribute the default routes.' ;
                  type boolean ;

                  config true ;
                  mandatory true ;
                }

                leaf level {
                  description 'Level(s) on which the system will always redistribute the IPv6 default routes.' ;
                  type isis-level ;

                  default level-2 ;
                  config true ;
                  mandatory false ;
                }

                leaf metric {
                  description 'Metric of the IPv6 always redistributed default routes.' ;
                  type uint32 {
                    range 0..4261412864 ;

                  }

                  default 0 ;
                  config true ;
                  mandatory false ;
                }

                config true ;
              }

              container def-rib-match {
                description 'Config IPv6 default route matched with RIB attribution.' ;
                presence def-rib-match ;
                leaf state {
                  description 'Advertise default route matched with RIB.' ;
                  type boolean ;

                  config true ;
                  mandatory true ;
                }

                leaf level {
                  description 'Level(s) on which the system will advertise IPv6 default route matched with RIB.' ;
                  type isis-level ;

                  default level-2 ;
                  config true ;
                  mandatory false ;
                }

                leaf metric {
                  description 'Metric of the IPv6 default route matched with RIB.' ;
                  type uint32 {
                    range 0..4261412864 ;

                  }

                  default 0 ;
                  config true ;
                  mandatory false ;
                }

                config true ;
              }

              container prefix-list-branch {
                description 'Config IPv6 default route prefix list attribution.' ;
                presence prefix-list-branch ;
                leaf prefix-list-name {
                  description 'Length of a prefix list name(1-169 characters).' ;
                  type string {
                    length 1..169 {
                      description 'Length of a prefix list name(1-169 characters).' ;
                    }

                  }

                  config true ;
                  mandatory true ;
                }

                leaf level {
                  description 'Level(s) on which the system will advertise default route matched with prefix list.' ;
                  type isis-level ;

                  default level-2 ;
                  config true ;
                  mandatory false ;
                }

                leaf metric {
                  description 'Metric of the default route matched with prefix list.' ;
                  type uint32 {
                    range 0..4261412864 ;

                  }

                  default 0 ;
                  config true ;
                  mandatory false ;
                }

                config true ;
                ncd:revise-date 2022-07-20 ;
              }

              config true ;
            }

            config true ;
            ncd:revise-date 2016-08-04 ;
          }

          container ipv6-def-info-learns {
            description 'Learn of ISIS IPv6 default route.' ;
            list def-info-learn {
              description 'Learn of ISIS IPv6 default route.' ;
              key state ;
              leaf state {
                description 'Flag of the system whether would ignore the IPv6 default route.' ;
                type enumeration {
                  enum ignore {
                    value 1 ;
                    description 'Ignore learn of ISIS default route' ;
                    status current ;

                  }

                }

                config true ;
                mandatory false ;
              }

              leaf level {
                description 'Level(s) will be effected on.' ;
                type isis-level ;

                config true ;
                mandatory true ;
              }

              config true ;
            }

            config true ;
            ncd:revise-date 2016-08-04 ;
          }

          container ipv6-mpls-ldp-sync {
            description 'Configure IPv6 LDP-ISIS synchronization.' ;
            leaf level {
              description 'Level(s) will be effected on.' ;
              type uint8 {
                range 0..2 ;

              }

              config true ;
              mandatory false ;
            }

            config true ;
            ncd:revise-date 2016-08-04 ;
          }

          container authen-keychains {
            description 'Authentication keychain information.' ;
            list authen-keychain {
              description 'Configure keychain authentication.' ;
              key level ;
              leaf level {
                description 'Level(s) will be effected on.' ;
                type uint8 {
                  range 0..2 ;

                }

                config true ;
                mandatory false ;
              }

              leaf keychain-name {
                description 'Keychain name associated to neighbor for authentication.' ;
                type string {
                  length 1..31 {
                    description 'Name of a keychain (1-31 characters).' ;
                  }

                }

                config true ;
                mandatory false ;
              }

              config true ;
            }

            config true ;
            ncd:revise-date 2016-08-04 ;
          }

          container metrics {
            description 'Set IS-IS instance metric' ;
            list metric {
              description 'Set IS-IS instance metric' ;
              key level ;
              leaf level {
                description 'Level(s) will be effected on.' ;
                type uint8 {
                  range 0..2 ;

                }

                config true ;
                mandatory false ;
              }

              leaf metric-value {
                description 'Metric value.' ;
                type uint32 {
                  range 1..16777215 ;

                }

                default 10 ;
                config true ;
                mandatory false ;
              }

              config true ;
            }

            config true ;
            ncd:revise-date 2016-08-04 ;
          }

          container ipv6-metrics {
            description 'Set IS-IS instance IPv6 metric' ;
            list metric {
              description 'Set IS-IS instance IPv6 metric' ;
              key level ;
              leaf level {
                description 'Level(s) will be effected on.' ;
                type uint8 {
                  range 0..2 ;

                }

                config true ;
                mandatory false ;
              }

              leaf metric-value {
                description 'Metric value.' ;
                type uint32 {
                  range 1..16777215 ;

                }

                default 10 ;
                config true ;
                mandatory false ;
              }

              config true ;
            }

            config true ;
            ncd:revise-date 2016-08-04 ;
          }

          container microloop-prevention-rlfa {
            description 'Attributes of microloop prevention for remote-LFA.' ;
            leaf state {
              description 'State of microloop prevention for remote-LFA.' ;
              type isis-state ;

              default enable ;
              config true ;
              mandatory false ;
            }

            leaf delay-time {
              description 'Delay time in ms.' ;
              type uint32 {
                range 1..300000 {
                  description 'Range for delay time:1-300000(ms)' ;
                }

              }

              default 3000 ;
              config true ;
              mandatory false ;
            }

            config true ;
            ncd:revise-date 2016-09-19 ;
          }

          container segment-routing-mpls {
            if-feature sr-feature ;

            description 'Configure segment routing for MPLS dataplane.' ;
            leaf state {
              description 'State of segment routing for MPLS dataplane.' ;
              type isis-state ;

              default disable ;
              config true ;
              mandatory false ;
            }

            container sr-mpls-mapping-server {
              if-feature sr-feature ;

              description 'Configure segment routing mpls mapping-server.' ;
              leaf state {
                description 'Configure segment routing mpls mapping-server.' ;
                type isis-state ;

                default disable ;
                config true ;
                mandatory false ;
              }

              config true ;
              ncd:revise-date 2018-09-07 ;
            }

            container entropy-label {
              if-feature sr-feature ;

              description 'Configure segment routing mpls entropy label capability.' ;
              leaf state {
                description 'Configure segment routing mpls entropy label capability.' ;
                type isis-state ;

                default disable ;
                config true ;
                mandatory false ;
              }

              config true ;
              ncd:revise-date 2019-09-27 ;
            }

            config true ;
            ncd:revise-date 2016-12-07 ;
          }

          container rlfa-exclude-ldp-not-sync {
            description "Configure ISIS remote-lfa with excluding primary link which LDP doesn't sync" ;
            leaf state {
              description "Status of ISIS remote-lfa with excluding primary link which LDP doesn't sync" ;
              type isis-state ;

              default disable ;
              config true ;
              mandatory false ;
            }

            config true ;
            ncd:revise-date 2017-07-18 ;
          }

          container bier {
            if-feature pc-feature ;

            description 'Set IS-IS BIER info' ;
            status obsolete {
              ncd:revise-date 2020-09-24 ;
            }

            list sub-domain {
              if-feature pc-feature ;

              description 'Set IS-IS BIER sub-domain info' ;
              key sub-domain-id ;
              max-elements 255 ;
              leaf sub-domain-id {
                description 'BIER sub-domain identifier' ;
                type uint16 {
                  range 0..255 {
                    description 'BIER sub-domain-id range' ;
                  }

                }

                config true ;
                mandatory false ;
              }

              leaf level {
                if-feature pc-feature ;

                description 'Level(s) will be effected on.' ;
                type uint8 {
                  range 1..2 {
                    description 'Level will be effected on.' ;
                  }

                }

                config true ;
                mandatory true ;
              }

              config true ;
            }

            config true ;
            ncd:revise-date 2017-08-25 ;
          }

          container segment-routing-ipv6 {
            description 'Configure SRV6.' ;
            leaf state {
              description 'State of segment routing for IPV6 dataplane.' ;
              type isis-state ;

              default disable ;
              config true ;
              mandatory false ;
            }

            container end-sid {
              status obsolete {
                ncd:revise-date 2020-06-24 ;
              }

              list index {
                description 'Configure End SID Index' ;
                key value ;
                leaf value {
                  description 'Value of End SID index.' ;
                  type uint32 {
                    range 0..255 {
                      description 'Range for the value of index:0-255' ;
                    }

                  }

                  config true ;
                  mandatory false ;
                }

                container style {
                  description 'Specify the SRv6 END SID style' ;
                  choice style {
                    description 'Specify the SRv6 END SID style' ;
                    default auto-style ;
                    case auto-style {
                      description 'Specify the SRv6 END SID is auto' ;
                      leaf auto {
                        description 'Specify the SRv6 END SID is auto' ;
                        type empty ;

                        config true ;
                        mandatory false ;
                      }

                    }

                    case static-style {
                      description 'Specify the SRv6 END SID is static' ;
                      leaf sid {
                        description 'Specify the SRv6 END SID is static' ;
                        type empty ;

                        config true ;
                        mandatory true ;
                      }

                      leaf ipv6-addr {
                        description 'Static End SID' ;
                        type ncd:ipv6-address ;

                        config true ;
                        mandatory true ;
                      }

                    }

                    config true ;
                    mandatory false ;
                  }

                  config true ;
                }

                container flavors {
                  description 'Set the END SID behavior' ;
                  choice flavors {
                    description 'Set the END SID behavior' ;
                    case no-flavor {
                      description 'Set the END SID without flavor' ;
                      leaf no-flavor {
                        description 'Set the End SID without flavor.' ;
                        type empty ;

                        config true ;
                        mandatory false ;
                      }

                    }

                    case flavor {
                      description 'Set the END SID with flavor' ;
                      leaf psp {
                        description 'Set the End SID with PSP.' ;
                        type empty ;

                        config true ;
                        mandatory false ;
                      }

                      leaf usp {
                        description 'Set the End SID with USP.' ;
                        type empty ;

                        config true ;
                        mandatory false ;
                      }

                    }

                    config true ;
                    mandatory false ;
                  }

                  config true ;
                }

                config true ;
                ncd:revise-date 2020-05-16 ;
              }

              choice end-sid {
                description 'end sid' ;
                status obsolete {
                  ncd:revise-date 2020-05-16 ;
                }

                default auto-style ;
                case auto-style {
                  description 'auto' ;
                  leaf auto {
                    description 'auto' ;
                    type empty ;

                    config true ;
                    mandatory false ;
                  }

                }

                case static-style {
                  description 's id' ;
                  leaf sid {
                    type empty ;

                    config true ;
                    mandatory true ;
                  }

                  leaf ipv6-addr {
                    type ncd:ipv6-address ;

                    config true ;
                    mandatory true ;
                  }

                }

                config true ;
                mandatory false ;
              }

              leaf non-psp {
                status obsolete {
                  ncd:revise-date 2020-05-16 ;
                }

                type uint8 {
                  range 0..1 ;

                }

                default 0 ;
                config true ;
                mandatory false ;
              }

              config true ;
            }

            container ipv6-sr-mpls-mapping-server {
              description 'Configure ipv6 segment routing mpls mapping-server.' ;
              status obsolete {
                ncd:revise-date 2019-03-18 ;
              }

              leaf state {
                description 'Configure ipv6 segment routing mpls mapping-server.' ;
                type isis-state ;

                default disable ;
                config true ;
                mandatory false ;
              }

              config true ;
            }

            config true ;
            ncd:revise-date 2018-10-19 ;
          }

          container frr-ti-lfa {
            if-feature frr-feature {
              ncd:revise-date 2023-02-20 ;
            }

            description 'Configure fast-reroute ti-lfa sr-mpls.' ;
            list frr-ti-lfa {
              if-feature frr-feature {
                ncd:revise-date 2023-02-20 ;
              }

              description 'Configure fast-reroute ti-lfa sr-mpls.' ;
              key level ;
              leaf level {
                if-feature frr-feature ;

                description 'level' ;
                type uint8 {
                  range 0..2 {
                    description 'level' ;
                    reference "level" ;
                  }

                }

                config true ;
                mandatory false ;
              }

              leaf sr-type {
                if-feature frr-feature {
                  ncd:revise-date 2023-02-20 ;
                }

                description 'IPV4 sr-type' ;
                type enumeration {
                  enum sr-mpls {
                    value 1 ;
                    description 'sr-mpls' ;
                    status current ;

                  }

                }

                config true ;
                mandatory false ;
              }

              leaf strategy {
                if-feature frr-feature {
                  ncd:revise-date 2023-02-20 ;
                }

                description 'IPv4 SR MPLS TILFA protection type.' ;
                type enumeration {
                  enum default-strategy {
                    value 0 ;
                    description 'Configure TILFA default protection type.' ;
                    status current ;

                  }

                  enum node-protection {
                    value 1 ;
                    description 'Configure TILFA node protection type.' ;
                    status current ;

                  }

                }

                default default-strategy ;
                config true ;
                mandatory false ;
                ncd:revise-date 2019-07-23 ;
              }

              config true ;
            }

            config true ;
            ncd:revise-date 2018-09-07 ;
          }

          container ipv6-frr-ti-lfa {
            if-feature frr-feature {
              ncd:revise-date 2023-02-20 ;
            }

            description 'Configure IPV6 fast-reroute ti-lfa sr-mpls.' ;
            list ipv6-frr-ti-lfa {
              if-feature frr-feature {
                ncd:revise-date 2023-02-20 ;
              }

              description 'Configure IPV6 fast-reroute ti-lfa sr-mpls or srv6.' ;
              key level ;
              leaf level {
                if-feature frr-feature ;

                description 'level' ;
                type uint8 {
                  range 0..2 {
                    description 'level' ;
                    reference "level" ;
                  }

                }

                config true ;
                mandatory false ;
              }

              leaf sr-type {
                if-feature frr-feature {
                  ncd:revise-date 2023-02-20 ;
                }

                description 'IPV6 sr-type' ;
                type enumeration {
                  enum srv6 {
                    value 2 ;
                    description 'srv6' ;
                    status current ;

                  }

                }

                config true ;
                mandatory false ;
              }

              leaf strategy {
                if-feature frr-feature {
                  ncd:revise-date 2023-02-20 ;
                }

                description 'SRv6 TILFA protection type.' ;
                type enumeration {
                  enum default-strategy {
                    value 0 ;
                    description 'Configure TILFA default protection type.' ;
                    status current ;

                  }

                  enum node-protection {
                    value 1 ;
                    description 'Configure TILFA node protection type.' ;
                    status current ;

                  }

                }

                default default-strategy ;
                config true ;
                mandatory false ;
                ncd:revise-date 2019-07-23 ;
              }

              config true ;
            }

            config true ;
            ncd:revise-date 2018-10-19 ;
          }

          container ipv6-frr-ti-lfa-sr-mpls {
            if-feature frr-feature {
              ncd:revise-date 2023-02-20 ;
            }

            description 'Configure IPV6 fast-reroute ti-lfa sr-mpls.' ;
            list ipv6-frr-ti-lfa-sr-mpls {
              if-feature frr-feature {
                ncd:revise-date 2023-02-20 ;
              }

              description 'Configure IPV6 fast-reroute ti-lfa sr-mpls or srv6.' ;
              key level ;
              leaf level {
                if-feature frr-feature ;

                description 'level' ;
                type uint8 {
                  range 0..2 {
                    description 'level' ;
                    reference "level" ;
                  }

                }

                config true ;
                mandatory false ;
              }

              leaf strategy {
                if-feature frr-feature {
                  ncd:revise-date 2023-02-20 ;
                }

                description 'IPv6 SR MPLS TILFA protection type.' ;
                type enumeration {
                  enum default-strategy {
                    value 0 ;
                    description 'Configure TILFA default protection type.' ;
                    status current ;

                  }

                  enum node-protection {
                    value 1 ;
                    description 'Configure TILFA node protection type.' ;
                    status current ;

                  }

                }

                default default-strategy ;
                config true ;
                mandatory false ;
              }

              config true ;
            }

            config true ;
            ncd:revise-date 2019-07-23 ;
          }

          container microloop-prevention-link-up {
            description 'In the configuration of single topology or IPv4 mode of multi-topology , attributes of microloop prevention for link-up.' ;
            leaf state {
              description 'In the configuration of single topology or IPv4 mode of multi-topology , state of microloop prevention for link-up.' ;
              type isis-state ;

              default enable ;
              config true ;
              mandatory false ;
            }

            leaf delay-time {
              description 'Delay time in ms.' ;
              type uint32 {
                range 50..30000 {
                  description 'Range for delay time:50-300000(ms)' ;
                }

              }

              default 1000 ;
              config true ;
              mandatory false ;
            }

            config true ;
            ncd:revise-date 2018-09-11 ;
          }

          container ipv6-microloop-prevention-link-up {
            description 'In the configuration of multi-topology , attributes of microloop prevention for link-up.' ;
            leaf state {
              description 'In the configuration of multi-topology ,state of microloop prevention for link-up.' ;
              type isis-state ;

              default enable ;
              config true ;
              mandatory false ;
            }

            leaf delay-time {
              description 'Delay time in ms.' ;
              type uint32 {
                range 50..30000 {
                  description 'Range for delay time:50-300000(ms)' ;
                }

              }

              default 1000 ;
              config true ;
              mandatory false ;
            }

            config true ;
            ncd:revise-date 2018-09-11 ;
          }

          container microloop-prevention-segment-routing {
            if-feature micr-sr-feature {
              ncd:revise-date 2023-02-20 ;
            }

            description 'In the configuration of ISIS IPv4 mode ,  attributes of microloop prevention for segment-routing.' ;
            leaf mpls-state {
              if-feature micr-sr-feature {
                ncd:revise-date 2023-02-20 ;
              }

              description 'In the configuration of ISIS IPv4 mode , state of microloop prevention for segment-routing mpls.' ;
              type isis-state ;

              default disable ;
              config true ;
              mandatory false ;
            }

            leaf delay-time {
              if-feature micr-sr-feature {
                ncd:revise-date 2023-02-20 ;
              }

              description 'Delay time in ms.' ;
              type uint32 {
                range 1..300000 {
                  description 'Range for delay time:1-300000(ms)' ;
                }

              }

              default 3000 ;
              config true ;
              mandatory false ;
            }

            config true ;
            ncd:revise-date 2019-01-08 ;
          }

          container ipv6-microloop-prevention-segment-routing {
            if-feature micr-sr-feature {
              ncd:revise-date 2023-02-20 ;
            }

            description 'In the configuration of ISIS IPv6 mode ,  attributes of microloop prevention for segment-routing.' ;
            leaf mpls-state {
              if-feature micr-sr-feature {
                ncd:revise-date 2023-02-20 ;
              }

              description 'In the configuration of ISIS IPv6 mode , state of microloop prevention for segment-routing mpls.' ;
              type isis-state ;

              default disable ;
              config true ;
              mandatory false ;
            }

            leaf srv6-state {
              if-feature micr-sr-feature {
                ncd:revise-date 2023-02-20 ;
              }

              description 'In the configuration of ISIS IPv6 mode , state of microloop prevention for segment-routing srv6.' ;
              type isis-state ;

              default disable ;
              config true ;
              mandatory false ;
            }

            leaf delay-time {
              if-feature micr-sr-feature {
                ncd:revise-date 2023-02-20 ;
              }

              description 'IPv6 Delay time in ms.' ;
              type uint32 {
                range 1..300000 {
                  description 'Range for delay time:1-300000(ms)' ;
                }

              }

              default 3000 ;
              config true ;
              mandatory false ;
            }

            config true ;
            ncd:revise-date 2019-07-26 ;
          }

          container ipv6-segment-routing-mpls {
            if-feature sr-feature ;

            description 'Configure ipv6 segment routing for MPLS dataplane.' ;
            leaf state {
              description 'State of ipv6 segment routing for MPLS dataplane.' ;
              type isis-state ;

              default disable ;
              config true ;
              mandatory false ;
            }

            container ipv6-sr-mpls-mapping-server {
              if-feature sr-feature ;

              description 'Configure ipv6 segment routing mpls mapping-server.' ;
              leaf state {
                description 'Configure ipv6 segment routing mpls mapping-server.' ;
                type isis-state ;

                default disable ;
                config true ;
                mandatory false ;
              }

              config true ;
            }

            container ipv6-entropy-label {
              if-feature sr-feature ;

              description 'Configure ipv6 segment routing mpls entropy label capability.' ;
              leaf state {
                description 'Configure ipv6 segment routing mpls entropy label capability.' ;
                type isis-state ;

                default disable ;
                config true ;
                mandatory false ;
              }

              config true ;
              ncd:revise-date 2019-09-27 ;
            }

            config true ;
            ncd:revise-date 2019-01-28 ;
          }

          container te-link-delay {
            description 'ISIS link TE delay information notification function.' ;
            leaf state {
              description 'ISIS link TE delay information notification function switch.' ;
              type isis-state ;

              default disable ;
              config true ;
              mandatory false ;
            }

            config true ;
            ncd:revise-date 2019-10-30 ;
          }

          container aiis {
            if-feature aii-feature ;

            description 'Configure aii function.' ;
            list aii {
              description 'Configure aii function.' ;
              key value ;
              leaf value {
                description 'Configure the value of aii.' ;
                type uint32 {
                  range 1..4294967295 {
                    description 'Range for the value of aii:1-4294967295' ;
                  }

                }

                config true ;
                mandatory false ;
              }

              leaf level {
                description 'Command support level.' ;
                type uint8 {
                  range 0..2 {
                    description 'level' ;
                    reference "level" ;
                  }

                }

                config true ;
                mandatory false ;
              }

              config true ;
            }

            config true ;
            ncd:revise-date 2020-02-11 ;
          }

          container flex-algorithms {
            if-feature sr-feature ;

            description 'Configure flex-algorithm function.' ;
            list flex-algorithm {
              description 'Configure flex-algorithm function.' ;
              key value ;
              leaf value {
                description 'Configure the value of flex-algorithm.' ;
                type uint16 {
                  range 128..255 {
                    description 'Range for the value of flex-algorithm:128-255' ;
                  }

                }

                config true ;
                mandatory false ;
              }

              leaf level {
                description 'Command support level.' ;
                type uint8 {
                  range 0..2 {
                    description 'level' ;
                    reference "level" ;
                  }

                }

                config true ;
                mandatory false ;
              }

              config true ;
            }

            config true ;
            ncd:revise-date 2020-02-11 ;
          }

          container microloop-prevention-policy {
            description 'Configure microloop prevention policy.' ;
            presence "microloop prevention policy" ;
            choice policy-type {
              description 'Configure microloop prevention policy.' ;
              mandatory true ;
              case host-only {
                description 'Configure  microloop prevention policy base on host.' ;
                leaf host-only {
                  description 'Configure microloop prevention policy base on host.' ;
                  type enumeration {
                    enum host-only {
                      value 1 ;
                      description 'Host-only policy.' ;
                      status current ;

                    }

                  }

                  config true ;
                  mandatory true ;
                }

              }

              config true ;
            }

            config true ;
            ncd:revise-date 2020-04-23 ;
          }

          container frr-policy {
            description 'Configure fast-reroute policy.' ;
            presence "frr policy" ;
            choice policy-type {
              description 'Configure fast-reroute policy.' ;
              mandatory true ;
              case host-only {
                description 'Configure fast-reroute policy based on host-only.' ;
                leaf host-only {
                  description 'Configure fast-reroute policy based on host-only.' ;
                  type enumeration {
                    enum host-only {
                      value 1 ;
                      description 'Host-only policy.' ;
                      status current ;

                    }

                  }

                  config true ;
                  mandatory false ;
                }

              }

              case route-map {
                description 'Configure fast-reroute policy based on route-map.' ;
                leaf route-map {
                  description 'Configure fast-reroute policy based on route-map.' ;
                  type string {
                    length 1..200 ;

                  }

                  config true ;
                  mandatory false ;
                }

                ncd:revise-date 2022-12-31 ;
              }

              case route-policy {
                description 'Configure fast-reroute route policy based on route-map.' ;
                leaf route-policy {
                  description 'Configure fast-reroute route policy based on route-map.' ;
                  type string {
                    length 1..200 ;

                  }

                  config true ;
                  mandatory false ;
                }

                ncd:revise-date 2022-12-31 ;
              }

              config true ;
            }

            config true ;
            ncd:revise-date 2020-04-23 ;
          }

          container ipv6-microloop-prevention-policy {
            description 'Configure IPv6 microloop prevention policy.' ;
            presence "ipv6 microloop prevention policy" ;
            choice policy-type {
              description 'Configure IPv6 microloop prevention policy.' ;
              mandatory true ;
              case host-only {
                description 'Configure  microloop prevention policy base on host.' ;
                leaf host-only {
                  description 'Configure microloop prevention policy base on host.' ;
                  type enumeration {
                    enum host-only {
                      value 1 ;
                      description 'Host-only policy.' ;
                      status current ;

                    }

                  }

                  config true ;
                  mandatory true ;
                }

              }

              config true ;
            }

            config true ;
            ncd:revise-date 2020-04-23 ;
          }

          container ipv6-frr-policy {
            description 'Configure IPv6 fast-reroute policy.' ;
            presence "ipv6 frr policy" ;
            choice ipv6-policy-type {
              description 'Configure IPv6 fast-reroute policy.' ;
              mandatory true ;
              case host-only {
                description 'Configure IPv6 fast-reroute policy based on host-only.' ;
                leaf host-only {
                  description 'Configure IPv6 fast-reroute policy based on host-only.' ;
                  type enumeration {
                    enum host-only {
                      value 1 ;
                      description 'Host-only policy.' ;
                      status current ;

                    }

                  }

                  config true ;
                  mandatory false ;
                }

              }

              case route-map {
                description 'Configure IPv6 fast-reroute policy based on route-map.' ;
                leaf route-map {
                  description 'Configure IPv6 fast-reroute policy based on route-map.' ;
                  type string {
                    length 1..200 ;

                  }

                  config true ;
                  mandatory false ;
                }

                ncd:revise-date 2022-12-31 ;
              }

              case route-policy {
                description 'Configure IPv6 fast-reroute route policy based on route-map.' ;
                leaf route-policy {
                  description 'Configure IPv6 fast-reroute route policy based on route-map.' ;
                  type string {
                    length 1..200 ;

                  }

                  config true ;
                  mandatory false ;
                }

                ncd:revise-date 2022-12-31 ;
              }

              config true ;
            }

            config true ;
            ncd:revise-date 2020-04-23 ;
          }

          container ipv6-traffic-eng {
            description 'ISIS IPv6 traffic engineering.' ;
            list ipv6-traffic-eng {
              description 'ISIS IPv6 traffic engineering.' ;
              key level ;
              leaf level {
                description 'Level(s) will be effected on.' ;
                type enumeration {
                  enum level-1 {
                    value 1 ;
                    description 'IPv6 traffic-eng on level-1.' ;
                    status current ;

                  }

                  enum level-2 {
                    value 2 ;
                    description 'IPv6 traffic-eng on level-2.' ;
                    status current ;

                  }

                }

                config true ;
                mandatory false ;
              }

              config true ;
            }

            config true ;
            ncd:revise-date 2020-08-26 ;
          }

          container ipv4-bier {
            if-feature bier-feature ;

            description 'Set IS-IS IPv4 BIER info' ;
            status obsolete {
              ncd:revise-date 2023-07-26 ;
            }

            list sub-domain {
              if-feature bier-feature ;

              description 'Set IS-IS IPv4 BIER sub-domain info' ;
              status obsolete {
                ncd:revise-date 2023-07-26 ;
              }

              key 'sub-domain-id level' ;
              max-elements 255 ;
              leaf sub-domain-id {
                description 'BIER sub-domain identifier' ;
                status obsolete {
                  ncd:revise-date 2023-07-26 ;
                }

                type uint8 {
                  range 0..255 ;

                }

                config true ;
                mandatory false ;
              }

              leaf level {
                description 'Level(s) will be effected on.' ;
                status obsolete {
                  ncd:revise-date 2023-07-26 ;
                }

                type uint8 {
                  range 0..2 ;

                }

                config true ;
                mandatory false ;
              }

              config true ;
            }

            config true ;
            ncd:revise-date 2020-09-24 ;
          }

          container ipv6-bier {
            if-feature bier-feature ;

            description 'Set IS-IS IPv6 BIER info' ;
            status obsolete {
              ncd:revise-date 2023-07-26 ;
            }

            list sub-domain {
              if-feature bier-feature ;

              description 'Set IS-IS IPv6 BIER sub-domain info' ;
              status obsolete {
                ncd:revise-date 2023-07-26 ;
              }

              key 'sub-domain-id level' ;
              max-elements 255 ;
              leaf sub-domain-id {
                description 'BIER sub-domain identifier' ;
                status obsolete {
                  ncd:revise-date 2023-07-26 ;
                }

                type uint8 {
                  range 0..255 ;

                }

                config true ;
                mandatory false ;
              }

              leaf level {
                description 'Level(s) will be effected on.' ;
                status obsolete {
                  ncd:revise-date 2023-07-26 ;
                }

                type uint8 {
                  range 0..2 ;

                }

                config true ;
                mandatory false ;
              }

              config true ;
            }

            config true ;
            ncd:revise-date 2020-09-24 ;
          }

          container ipv6-flex-algorithms {
            if-feature sr-feature ;

            description 'Configure ipv6 flex-algorithm function.' ;
            list ipv6-flex-algorithm {
              description 'Configure ipv6 flex-algorithm function.' ;
              key value ;
              leaf value {
                description 'Configure the value of ipv6 flex-algorithm.' ;
                type uint16 {
                  range 128..255 {
                    description 'Range for the value of flex-algorithm:128-255' ;
                  }

                }

                config true ;
                mandatory false ;
              }

              leaf level {
                description 'Command support level.' ;
                type uint8 {
                  range 0..2 {
                    description 'level' ;
                  }

                }

                config true ;
                mandatory false ;
              }

              config true ;
            }

            config true ;
            ncd:revise-date 2020-10-16 ;
          }

          container isis-ipv6-router-id {
            if-feature frr-feature {
              ncd:revise-date 2023-02-20 ;
            }

            description 'Set auxiliary IPv6 router-id for ISIS process' ;
            leaf ipv6-router-id {
              if-feature frr-feature {
                ncd:revise-date 2023-02-20 ;
              }

              description 'ISIS auxiliary IPv6 router-id in IPv6 address format' ;
              type ncd:ipv6-address ;

              config true ;
              mandatory false ;
            }

            config true ;
            ncd:revise-date 2020-11-09 ;
          }

          container srv6-locators {
            if-feature sr-feature ;

            description 'SRv6 locator mode configuration.' ;
            list srv6-locator {
              description 'SRv6 locator mode configuration.' ;
              key locator-name ;
              leaf locator-name {
                description 'The name of locator.' ;
                type string {
                  length 1..31 ;

                }

                config true ;
                mandatory false ;
              }

              container end-sid {
                description 'End SID configuration.' ;
                container auto {
                  description 'Configure the SRv6 End SID automatically.' ;
                  presence "auto status" ;
                  leaf psp {
                    description 'The PSP attribute of auto End SID.' ;
                    type isis-state ;

                    default disable ;
                    config true ;
                    mandatory false ;
                  }

                  leaf usp {
                    description 'The USP attribute of auto End SID.' ;
                    type isis-state ;

                    default disable ;
                    config true ;
                    mandatory false ;
                  }

                  leaf usd {
                    description 'The USD attribute of auto End SID.' ;
                    type isis-state ;

                    default disable ;
                    config true ;
                    mandatory false ;
                    ncd:revise-date 2021-06-03 ;
                  }

                  config true ;
                }

                container auto-compressed-sid {
                  description 'Configure the SRv6 compressed End SID automatically.' ;
                  leaf psp {
                    description 'The PSP attribute of End SID.' ;
                    type isis-state ;

                    default disable ;
                    config true ;
                    mandatory false ;
                  }

                  leaf usp {
                    description 'The USP attribute of End SID.' ;
                    type isis-state ;

                    default disable ;
                    config true ;
                    mandatory false ;
                  }

                  leaf usd {
                    description 'The USD attribute of End SID.' ;
                    type isis-state ;

                    default disable ;
                    config true ;
                    mandatory false ;
                  }

                  config true ;
                  ncd:revise-date 2022-04-08 ;
                }

                container auto-multi-sids {
                  description 'Configure the SRv6 multiple End SID automatically.' ;
                  list auto-multi-sid {
                    description 'Configure the SRv6 multiple End SID automatically.' ;
                    key 'psp usp usd' ;
                    leaf psp {
                      description 'The PSP attribute of End SID.' ;
                      type isis-state ;

                      config true ;
                      mandatory false ;
                    }

                    leaf usp {
                      description 'The USP attribute of End SID.' ;
                      type isis-state ;

                      config true ;
                      mandatory false ;
                    }

                    leaf usd {
                      description 'The USD attribute of End SID.' ;
                      type isis-state ;

                      config true ;
                      mandatory false ;
                    }

                    config true ;
                  }

                  config true ;
                  ncd:revise-date 2022-04-08 ;
                }

                container auto-multi-compressed-sids {
                  description 'Configure the SRv6 multiple compressed End SID automatically.' ;
                  list auto-multi-compressed-sid {
                    description 'Configure the SRv6 multiple compressed End SID automatically.' ;
                    key 'encapsulation-type psp usp usd' ;
                    leaf encapsulation-type {
                      description 'The encapsulation type attribute of End SID.' ;
                      type enumeration {
                        enum uet-128 {
                          value 0 ;
                          status current ;

                        }

                        enum uet-32 {
                          value 1 ;
                          status current ;

                        }

                      }

                      config true ;
                      mandatory false ;
                    }

                    leaf psp {
                      description 'The PSP attribute of End SID.' ;
                      type isis-state ;

                      config true ;
                      mandatory false ;
                    }

                    leaf usp {
                      description 'The USP attribute of End SID.' ;
                      type isis-state ;

                      config true ;
                      mandatory false ;
                    }

                    leaf usd {
                      description 'The USD attribute of End SID.' ;
                      type isis-state ;

                      config true ;
                      mandatory false ;
                    }

                    config true ;
                  }

                  config true ;
                  ncd:revise-date 2022-04-08 ;
                }

                container sids {
                  description 'End SID static configuration.' ;
                  presence "func code" ;
                  list sid {
                    description 'End SID static configuration.' ;
                    key func-code ;
                    leaf func-code {
                      description 'The function code of End SID.' ;
                      type ncd:ipv6-address ;

                      config true ;
                      mandatory false ;
                    }

                    leaf psp {
                      description 'The PSP attribute of End SID.' ;
                      type isis-state ;

                      default disable ;
                      config true ;
                      mandatory false ;
                    }

                    leaf usp {
                      description 'The USP attribute of End SID.' ;
                      type isis-state ;

                      default disable ;
                      config true ;
                      mandatory false ;
                    }

                    leaf usd {
                      description 'The USD attribute of End SID.' ;
                      type isis-state ;

                      default disable ;
                      config true ;
                      mandatory false ;
                      ncd:revise-date 2021-06-03 ;
                    }

                    config true ;
                  }

                  config true ;
                }

                container compressed-sids {
                  description 'Compressed End SID static configuration.' ;
                  presence "compressed sid" ;
                  list compressed-sid {
                    description 'Compressed End SID static configuration.' ;
                    key func-code ;
                    leaf func-code {
                      description 'The function code of End SID.' ;
                      type ncd:ipv6-address ;

                      config true ;
                      mandatory false ;
                    }

                    leaf encapsulation-type {
                      description 'The encapsulation type attribute of End SID.' ;
                      type enumeration {
                        enum uet-128 {
                          value 0 ;
                          status current ;

                        }

                        enum uet-32 {
                          value 1 ;
                          status current ;

                        }

                      }

                      default uet-128 ;
                      config true ;
                      mandatory false ;
                    }

                    leaf psp {
                      description 'The PSP attribute of End SID.' ;
                      type isis-state ;

                      default disable ;
                      config true ;
                      mandatory false ;
                    }

                    leaf usp {
                      description 'The USP attribute of End SID.' ;
                      type isis-state ;

                      default disable ;
                      config true ;
                      mandatory false ;
                    }

                    leaf usd {
                      description 'The USD attribute of End SID.' ;
                      type isis-state ;

                      default disable ;
                      config true ;
                      mandatory false ;
                      ncd:revise-date 2021-06-03 ;
                    }

                    config true ;
                  }

                  config true ;
                }

                config true ;
              }

              container end-x-sid {
                description 'End.X SID configuration.' ;
                container auto {
                  description 'Configure the SRv6 End.X SID automatically.' ;
                  presence "auto status" ;
                  leaf psp {
                    description 'The PSP attribute of auto End.X SID.' ;
                    type isis-state ;

                    default disable ;
                    config true ;
                    mandatory false ;
                  }

                  leaf usp {
                    description 'The USP attribute of auto End.X SID.' ;
                    type isis-state ;

                    default disable ;
                    config true ;
                    mandatory false ;
                  }

                  leaf usd {
                    description 'The USD attribute of auto End.X SID.' ;
                    type isis-state ;

                    default disable ;
                    config true ;
                    mandatory false ;
                    ncd:revise-date 2021-06-03 ;
                  }

                  config true ;
                }

                container auto-compressed-sid {
                  description 'Configure the SRv6 compressed End.X SID automatically.' ;
                  leaf psp {
                    description 'The PSP attribute of End.X SID.' ;
                    type isis-state ;

                    default disable ;
                    config true ;
                    mandatory false ;
                  }

                  leaf usp {
                    description 'The USP attribute of End.X SID.' ;
                    type isis-state ;

                    default disable ;
                    config true ;
                    mandatory false ;
                  }

                  leaf usd {
                    description 'The USD attribute of End.X SID.' ;
                    type isis-state ;

                    default disable ;
                    config true ;
                    mandatory false ;
                  }

                  config true ;
                  ncd:revise-date 2022-04-08 ;
                }

                container auto-multi-sids {
                  description 'Configure the SRv6 multiple End.X SID automatically.' ;
                  list auto-multi-sid {
                    description 'Configure the SRv6 multiple End.X SID automatically.' ;
                    key 'psp usp usd' ;
                    leaf psp {
                      description 'The PSP attribute of End.X SID.' ;
                      type isis-state ;

                      config true ;
                      mandatory false ;
                    }

                    leaf usp {
                      description 'The USP attribute of End.X SID.' ;
                      type isis-state ;

                      config true ;
                      mandatory false ;
                    }

                    leaf usd {
                      description 'The USD attribute of End.X SID.' ;
                      type isis-state ;

                      config true ;
                      mandatory false ;
                    }

                    config true ;
                  }

                  config true ;
                  ncd:revise-date 2022-04-08 ;
                }

                container auto-multi-compressed-sids {
                  description 'Configure the SRv6 multiple compressed End.X SID automatically.' ;
                  list auto-multi-compressed-sid {
                    description 'Configure the SRv6 multiple compressed End.X SID automatically.' ;
                    key 'encapsulation-type psp usp usd' ;
                    leaf encapsulation-type {
                      description 'The encapsulation type attribute of End.X SID.' ;
                      type enumeration {
                        enum uet-128 {
                          value 0 ;
                          status current ;

                        }

                        enum uet-32 {
                          value 1 ;
                          status current ;

                        }

                      }

                      config true ;
                      mandatory false ;
                    }

                    leaf psp {
                      description 'The PSP attribute of End.X SID.' ;
                      type isis-state ;

                      config true ;
                      mandatory false ;
                    }

                    leaf usp {
                      description 'The USP attribute of End.X SID.' ;
                      type isis-state ;

                      config true ;
                      mandatory false ;
                    }

                    leaf usd {
                      description 'The USD attribute of End.X SID.' ;
                      type isis-state ;

                      config true ;
                      mandatory false ;
                    }

                    config true ;
                  }

                  config true ;
                  ncd:revise-date 2022-04-08 ;
                }

                container sids {
                  description 'End.X SID static configuration.' ;
                  presence "func code" ;
                  list sid {
                    description 'End.X SID static configuration.' ;
                    key func-code ;
                    leaf func-code {
                      description 'The function code of End.X SID.' ;
                      type ncd:ipv6-address ;

                      config true ;
                      mandatory false ;
                    }

                    choice neighbor {
                      description 'The information of neighbor associated with End.X SID.' ;
                      mandatory true ;
                      case interface {
                        description 'The branch of interface associated with End.X SID.' ;
                        container interface {
                          description 'The information of interface associated with End.X SID.' ;
                          leaf interface-name {
                            description 'The name of interface associated with End.X SID.' ;
                            type ncd:ifname ;

                            config true ;
                            mandatory true ;
                          }

                          config true ;
                        }

                      }

                      case router-id {
                        description 'The branch of router-id associated with End.X SID.' ;
                        container router-id {
                          description 'The information of router-id associated with End.X SID.' ;
                          leaf interface-name {
                            description 'The name of interface associated with End.X SID.' ;
                            type ncd:ifname ;

                            config true ;
                            mandatory true ;
                          }

                          leaf router-id {
                            description 'The IPv6 router-id of neighbor associated with End.X SID.' ;
                            type ncd:ipv6-address ;

                            config true ;
                            mandatory true ;
                          }

                          config true ;
                        }

                      }

                      case system-id {
                        description 'The branch of system-id associated with End.X SID.' ;
                        container system-id {
                          description 'The information of system-id associated with End.X SID.' ;
                          leaf interface-name {
                            description 'The name of interface associated with End.X SID.' ;
                            type ncd:ifname ;

                            config true ;
                            mandatory true ;
                          }

                          leaf system-id {
                            description 'The system-id of neighbor associated with End.X SID.' ;
                            type ncd:mac-address ;

                            config true ;
                            mandatory true ;
                          }

                          config true ;
                        }

                      }

                      config true ;
                    }

                    leaf psp {
                      description 'The PSP attribute of End.X SID.' ;
                      type isis-state ;

                      default disable ;
                      config true ;
                      mandatory false ;
                    }

                    leaf usp {
                      description 'The USP attribute of End.X SID.' ;
                      type isis-state ;

                      default disable ;
                      config true ;
                      mandatory false ;
                    }

                    leaf usd {
                      description 'The USD attribute of End.X SID.' ;
                      type isis-state ;

                      default disable ;
                      config true ;
                      mandatory false ;
                      ncd:revise-date 2021-06-03 ;
                    }

                    config true ;
                  }

                  config true ;
                }

                container compressed-sids {
                  description 'Compressed End.X SID static configuration.' ;
                  presence "func code" ;
                  list compressed-sid {
                    description 'Compress End.X SID static configuration.' ;
                    key func-code ;
                    leaf func-code {
                      description 'The function code of End.X SID.' ;
                      type ncd:ipv6-address ;

                      config true ;
                      mandatory false ;
                    }

                    choice neighbor {
                      description 'The information of neighbor associated with End.X SID.' ;
                      mandatory true ;
                      case interface {
                        description 'The branch of interface associated with End.X SID.' ;
                        container interface {
                          description 'The information of interface associated with End.X SID.' ;
                          leaf interface-name {
                            description 'The name of interface associated with End.X SID.' ;
                            type ncd:ifname ;

                            config true ;
                            mandatory true ;
                          }

                          config true ;
                        }

                      }

                      case router-id {
                        description 'The branch of router-id associated with End.X SID.' ;
                        container router-id {
                          description 'The information of router-id associated with End.X SID.' ;
                          leaf interface-name {
                            description 'The name of interface associated with End.X SID.' ;
                            type ncd:ifname ;

                            config true ;
                            mandatory true ;
                          }

                          leaf router-id {
                            description 'The IPv6 router-id of neighbor associated with End.X SID.' ;
                            type ncd:ipv6-address ;

                            config true ;
                            mandatory true ;
                          }

                          config true ;
                        }

                      }

                      case system-id {
                        description 'The branch of system-id associated with End.X SID.' ;
                        container system-id {
                          description 'The information of system-id associated with End.X SID.' ;
                          leaf interface-name {
                            description 'The name of interface associated with End.X SID.' ;
                            type ncd:ifname ;

                            config true ;
                            mandatory true ;
                          }

                          leaf system-id {
                            description 'The system-id of neighbor associated with End.X SID.' ;
                            type ncd:mac-address ;

                            config true ;
                            mandatory true ;
                          }

                          config true ;
                        }

                      }

                      config true ;
                    }

                    leaf encapsulation-type {
                      description 'The encapsulation type attribute of End.X SID.' ;
                      type enumeration {
                        enum uet-128 {
                          value 0 ;
                          status current ;

                        }

                        enum uet-32 {
                          value 1 ;
                          status current ;

                        }

                      }

                      default uet-128 ;
                      config true ;
                      mandatory false ;
                    }

                    leaf psp {
                      description 'The PSP attribute of End.X SID.' ;
                      type isis-state ;

                      default disable ;
                      config true ;
                      mandatory false ;
                    }

                    leaf usp {
                      description 'The USP attribute of End.X SID.' ;
                      type isis-state ;

                      default disable ;
                      config true ;
                      mandatory false ;
                    }

                    leaf usd {
                      description 'The USD attribute of End.X SID.' ;
                      type isis-state ;

                      default disable ;
                      config true ;
                      mandatory false ;
                      ncd:revise-date 2021-06-03 ;
                    }

                    config true ;
                  }

                  config true ;
                }

                container adjacency-set {
                  description 'A set of IS-IS neighbor adjacencies.' ;
                  leaf state {
                    description 'In the configuration of ISIS SRv6 Locator mode, state of the SID refers to a set of adjacencies.' ;
                    type isis-state ;

                    default disable ;
                    config true ;
                    mandatory false ;
                  }

                  config true ;
                  if-feature srv6-adjacency-set-feature {
                    ncd:revise-date 2025-05-13 ;
                  }

                }

                config true ;
              }

              container end-m-sids {
                description 'End.M SID configuration.' ;
                list end-m-sid {
                  description 'End.M SID configuration.' ;
                  key 'func-code protect-type protected-ipv6-prefix protected-prefix-len' ;
                  leaf func-code {
                    description 'The function code of the SRv6 End.M SID.' ;
                    type ncd:ipv6-address ;

                    config true ;
                    mandatory false ;
                  }

                  leaf protect-type {
                    description 'Specify protected type.' ;
                    type enumeration {
                      enum protected-locator {
                        value 2 ;
                        status current ;

                      }

                    }

                    config true ;
                    mandatory false ;
                  }

                  leaf protected-ipv6-prefix {
                    description 'Specify protected IPv6 prefix.' ;
                    type ncd:ipv6-address ;

                    config true ;
                    mandatory false ;
                  }

                  leaf protected-prefix-len {
                    description 'Specify protected prefix length.' ;
                    type ncd:ipv6-mask-length ;

                    config true ;
                    mandatory false ;
                  }

                  config true ;
                }

                config true ;
                ncd:revise-date 2022-06-28 ;
              }

              container metric {
                description 'Metric configuration.' ;
                presence metric ;
                leaf metric-value {
                  description 'Metric value.' ;
                  type uint32 {
                    range 0..16777215 ;

                  }

                  default 0 ;
                  config true ;
                  mandatory false ;
                }

                config true ;
                ncd:revise-date 2023-02-21 ;
              }

              container tag {
                description 'Admin tag configuration.' ;
                presence tag ;
                leaf tag-value {
                  description 'Tag value.' ;
                  type uint32 {
                    range 1..4294967295 ;

                  }

                  config true ;
                  mandatory false ;
                }

                config true ;
                ncd:revise-date 2023-02-21 ;
              }

              config true ;
            }

            config true ;
            ncd:revise-date 2021-03-30 ;
          }

          container srv6-compress {
            if-feature sr-feature {
              ncd:revise-date 2022-07-20 ;
            }

            description 'Configure the SRv6 with compressibility.' ;
            list encapsulation-types {
              description 'Configure the SRv6 compress encapsulation types.' ;
              key encapsulation-type ;
              leaf encapsulation-type {
                description 'Specify the compress encapsulation type.' ;
                type enumeration {
                  enum uet-32 {
                    value 1 ;
                    status current ;

                  }

                }

                config true ;
                mandatory false ;
              }

              config true ;
            }

            config true ;
            ncd:revise-date 2022-06-13 ;
          }

          container ipv4-summary-policys {
            description 'ISIS IPv4 route summary policy configuration.' ;
            list ipv4-summary-policy {
              description 'ISIS IPv4 route summary policy configuration.' ;
              key policy-type ;
              leaf policy-type {
                description 'ISIS IPv4 route summary policy type configuration.' ;
                type enumeration {
                  enum exclude-local-prefix {
                    value 1 ;
                    description 'Exclude ipv4 prefix of local interface.' ;
                    status current ;

                  }

                }

                config true ;
                mandatory false ;
              }

              leaf level {
                description 'Level(s) will be effected on.' ;
                type isis-level ;

                config true ;
                mandatory true ;
              }

              config true ;
            }

            config true ;
            ncd:revise-date 2021-04-21 ;
          }

          container ipv6-summary-policys {
            description 'ISIS IPv6 route summary policy configuration.' ;
            list ipv6-summary-policy {
              description 'ISIS IPv6 route summary policy configuration.' ;
              key policy-type ;
              leaf policy-type {
                description 'ISIS IPv6 route summary policy type configuration.' ;
                type enumeration {
                  enum exclude-local-prefix {
                    value 1 ;
                    description 'Exclude ipv6 prefix of local interface.' ;
                    status current ;

                  }

                }

                config true ;
                mandatory false ;
              }

              leaf level {
                description 'Level(s) will be effected on.' ;
                type isis-level ;

                config true ;
                mandatory true ;
              }

              config true ;
            }

            config true ;
            ncd:revise-date 2021-04-21 ;
          }

          container ldp-sync-hold-times {
            description 'Configure LDP-ISIS synchronization hold time.' ;
            list ldp-sync-hold-time {
              description 'Configure LDP-ISIS synchronization hold time.' ;
              key level ;
              leaf level {
                description 'Command support level.' ;
                type uint8 {
                  range 0..2 {
                    description 'level' ;
                  }

                }

                config true ;
                mandatory false ;
              }

              choice hold-time {
                description 'Set LDP-ISIS synchronization hold time in seconds.' ;
                default infinite ;
                case time {
                  description 'Set LDP-ISIS synchronization hold time in seconds.' ;
                  leaf value {
                    description 'time value.' ;
                    type uint32 {
                      range 1..65535 ;

                    }

                    config true ;
                    mandatory false ;
                  }

                }

                case infinite {
                  description 'Set LDP-ISIS synchronization hold time infinite.' ;
                  leaf infinite {
                    description 'Set to infinite.' ;
                    type empty ;

                    config true ;
                    mandatory false ;
                  }

                }

                config true ;
                mandatory false ;
              }

              config true ;
            }

            config true ;
            ncd:revise-date 2021-05-12 ;
          }

          container ldp-sync-metrics {
            description 'Configure LDP-ISIS synchronization increase metric.' ;
            list ldp-sync-metric {
              description 'Configure LDP-ISIS synchronization increase metric.' ;
              key level ;
              leaf level {
                description 'Command support level.' ;
                type uint8 {
                  range 0..2 {
                    description 'level' ;
                  }

                }

                config true ;
                mandatory false ;
              }

              choice metric {
                description 'Configure the increase metric for LDP-ISIS synchronization.' ;
                default maximum ;
                case increase {
                  description 'Configure the increase metric for LDP-ISIS synchronization.' ;
                  leaf value {
                    description 'increase value.' ;
                    type uint32 {
                      range 100..10000 ;

                    }

                    config true ;
                    mandatory false ;
                  }

                }

                case maximum {
                  description 'Set to maximum metric.' ;
                  leaf maximum {
                    description 'Set to maximum metric.' ;
                    type empty ;

                    config true ;
                    mandatory false ;
                  }

                }

                config true ;
                mandatory false ;
              }

              config true ;
            }

            config true ;
            ncd:revise-date 2021-05-12 ;
          }

          container ipv6-ldp-sync-hold-times {
            description 'Configure IPv6 LDP-ISIS synchronization hold time.' ;
            list ipv6-ldp-sync-hold-time {
              description 'Configure LDP-ISIS synchronization hold time.' ;
              key level ;
              leaf level {
                description 'Command support level.' ;
                type uint8 {
                  range 0..2 {
                    description 'level' ;
                  }

                }

                config true ;
                mandatory false ;
              }

              choice hold-time {
                description 'Set LDP-ISIS synchronization hold time in seconds.' ;
                default infinite ;
                case time {
                  description 'Set LDP-ISIS synchronization hold time in seconds.' ;
                  leaf value {
                    description 'time value.' ;
                    type uint32 {
                      range 1..65535 ;

                    }

                    config true ;
                    mandatory false ;
                  }

                }

                case infinite {
                  description 'Set LDP-ISIS synchronization hold time infinite.' ;
                  leaf infinite {
                    description 'Set to infinite.' ;
                    type empty ;

                    config true ;
                    mandatory false ;
                  }

                }

                config true ;
                mandatory false ;
              }

              config true ;
            }

            config true ;
            ncd:revise-date 2021-05-12 ;
          }

          container ipv6-ldp-sync-metrics {
            description 'Configure IPv6 LDP-ISIS synchronization increase metric.' ;
            list ipv6-ldp-sync-metric {
              description 'Configure LDP-ISIS synchronization increase metric.' ;
              key level ;
              leaf level {
                description 'Command support level.' ;
                type uint8 {
                  range 0..2 {
                    description 'level' ;
                  }

                }

                config true ;
                mandatory false ;
              }

              choice metric {
                description 'Configure the increase metric for LDP-ISIS synchronization.' ;
                default maximum ;
                case increase {
                  description 'Configure the increase metric for LDP-ISIS synchronization.' ;
                  leaf value {
                    description 'increase value.' ;
                    type uint32 {
                      range 100..10000 ;

                    }

                    config true ;
                    mandatory false ;
                  }

                }

                case maximum {
                  description 'Set to maximum metric.' ;
                  leaf maximum {
                    description 'Set to maximum metric.' ;
                    type empty ;

                    config true ;
                    mandatory false ;
                  }

                }

                config true ;
                mandatory false ;
              }

              config true ;
            }

            config true ;
            ncd:revise-date 2021-05-12 ;
          }

          container link-advertise-delay {
            description 'In the configuration of ISIS mode ,  attributes of link advertise delay.' ;
            container adj-establish {
              description 'In the configuration of ISIS mode ,  attributes of link advertise delay for adjacency establish.' ;
              leaf state {
                description 'In the configuration of ISIS mode , state of link advertise delay.' ;
                type isis-state ;

                default disable ;
                config true ;
                mandatory false ;
              }

              leaf delay-time {
                description 'Delay time in ms.' ;
                type uint32 {
                  range 50..300000 {
                    description 'Range for delay time:50-300000(ms)' ;
                  }

                }

                default 3000 ;
                config true ;
                mandatory false ;
              }

              config true ;
            }

            config true ;
            ncd:revise-date 2021-06-07 ;
          }

          container ipv6-link-advertise-delay {
            description 'In the configuration of ISIS IPv6 mode ,  attributes of link advertise delay.' ;
            container adj-establish {
              description 'In the configuration of ISIS IPv6 mode ,  attributes of link advertise delay for adjacency establish.' ;
              leaf state {
                description 'In the configuration of ISIS IPv6 mode , state of link advertise delay.' ;
                type isis-state ;

                default disable ;
                config true ;
                mandatory false ;
              }

              leaf delay-time {
                description 'IPv6 Delay time in ms.' ;
                type uint32 {
                  range 50..300000 {
                    description 'Range for delay time:50-300000(ms)' ;
                  }

                }

                default 3000 ;
                config true ;
                mandatory false ;
              }

              config true ;
            }

            config true ;
            ncd:revise-date 2021-06-07 ;
          }

          container spf-calculation-policy {
            description 'ISIS SPF calculation policy.' ;
            leaf overload-bit-unreachable {
              description 'Set the node with overload bit unreachable.' ;
              type isis-state ;

              default disable ;
              config true ;
              mandatory false ;
            }

            config true ;
            ncd:revise-date 2021-06-07 ;
          }

          container ipv6-spf-calculation-policy {
            description 'IS-IS IPv6 SPF calculation policy.' ;
            leaf overload-bit-unreachable {
              description 'Set the IPv6 node with overload bit unreachable.' ;
              type isis-state ;

              default disable ;
              config true ;
              mandatory false ;
            }

            config true ;
            ncd:revise-date 2021-06-07 ;
          }

          container prefix-independent-converge {
            description 'In the configuration of ISIS mode ,  attributes of prefix independent converge.' ;
            leaf state {
              description 'In the configuration of ISIS mode , state of prefix independent converge.' ;
              type isis-state ;

              default enable ;
              config true ;
              mandatory false ;
            }

            config true ;
            ncd:revise-date 2021-10-17 ;
          }

          container ipv6-prefix-independent-converge {
            description 'In the configuration of ISIS IPv6 mode ,  attributes of prefix independent converge.' ;
            leaf state {
              description 'In the configuration of ISIS IPv6 mode , state of prefix independent converge.' ;
              type isis-state ;

              default enable ;
              config true ;
              mandatory false ;
            }

            config true ;
            ncd:revise-date 2021-10-17 ;
          }

          container ipv4-sr-prefix-sid-consistent-in-lsp {
            description 'Specify the IPv4 prefix-sid for keeping consistent in the LSP.' ;
            leaf state {
              description 'The state of IPv4 prefix-sid keep consistent in LSP.' ;
              type isis-state ;

              default enable ;
              config true ;
              mandatory false ;
            }

            config true ;
            ncd:revise-date 2022-07-13 ;
          }

          container ipv6-sr-prefix-sid-consistent-in-lsp {
            description 'Specify the IPv6 prefix-sid for keeping consistent in the LSP.' ;
            leaf state {
              description 'The state of IPv6 prefix-sid keep consistent in LSP.' ;
              type isis-state ;

              default enable ;
              config true ;
              mandatory false ;
            }

            config true ;
            ncd:revise-date 2022-07-13 ;
          }

          container ipv6-l2-bundle {
            description 'Configure ISIS IPv6 L2 Bundle.' ;
            leaf state {
              description 'Configure ISIS IPv6 L2 Bundle State.' ;
              type isis-state ;

              default disable ;
              config true ;
              mandatory false ;
            }

            config true ;
            ncd:revise-date 2022-06-04 ;
          }

          container frr-remote-srlg-protection {
            description 'Configure ISIS fast-reroute remote SRLG protection.' ;
            leaf state {
              description 'Configure ISIS fast-reroute remote SRLG protection state.' ;
              type isis-state ;

              default disable ;
              config true ;
              mandatory false ;
            }

            config true ;
            ncd:revise-date 2022-06-16 ;
          }

          container ipv6-frr-remote-srlg-protection {
            description 'Configure ISIS IPv6 fast-reroute remote SRLG protection.' ;
            leaf state {
              description 'Configure ISIS IPv6 fast-reroute remote SRLG protection state.' ;
              type isis-state ;

              default disable ;
              config true ;
              mandatory false ;
            }

            config true ;
            ncd:revise-date 2022-06-16 ;
          }

          container srlg-parameters {
            description 'Configure SRLG parameters.' ;
            list srlg-parameter {
              description 'Configure SRLG parameter.' ;
              key srlg-id ;
              max-elements 16 ;
              leaf srlg-id {
                description 'SRLG identifier.' ;
                type uint32 {
                  range 0..4294967295 ;

                }

                config true ;
                mandatory false ;
              }

              leaf admin-weight {
                description 'Administrative weight.' ;
                type uint32 {
                  range 1..16777214 ;

                }

                config true ;
                mandatory true ;
              }

              config true ;
            }

            config true ;
            ncd:revise-date 2022-06-16 ;
          }

          container ipv4-microloop-prevention-te-tunnel {
            description 'In the configuration of ISIS IPv4 mode ,  attributes of microloop prevention for te-tunnel.' ;
            leaf state {
              description 'In the configuration of ISIS IPv4 mode , state of microloop prevention for te-tunnel.' ;
              type isis-state ;

              default disable ;
              config true ;
              mandatory false ;
            }

            leaf delay-time {
              description 'Delay time in ms.' ;
              type uint32 {
                range 1..300000 {
                  description 'Range for delay time:1-300000(ms)' ;
                }

              }

              default 3000 ;
              config true ;
              mandatory false ;
            }

            config true ;
            leaf remote-change-delay-time {
              type uint32 {
                range 50..300000 ;

              }

              description 'When the remote link changes, set the delay time in milliseconds.' ;
              default 1000 ;
              ncd:revise-date 2025-09-23 ;
            }

            ncd:revise-date 2022-10-30 ;
          }

          container ipv6-microloop-prevention-te-tunnel {
            description 'In the configuration of ISIS IPv6 mode ,  attributes of microloop prevention for te-tunnel.' ;
            leaf state {
              description 'In the configuration of ISIS IPv6 mode , state of microloop prevention for te-tunnel.' ;
              type isis-state ;

              default disable ;
              config true ;
              mandatory false ;
            }

            leaf delay-time {
              description 'Delay time in ms.' ;
              type uint32 {
                range 1..300000 {
                  description 'Range for delay time:1-300000(ms)' ;
                }

              }

              default 3000 ;
              config true ;
              mandatory false ;
            }

            config true ;
            leaf remote-change-delay-time {
              type uint32 {
                range 50..300000 ;

              }

              description 'When the remote link changes, set the delay time in milliseconds.' ;
              default 1000 ;
              ncd:revise-date 2025-09-23 ;
            }

            ncd:revise-date 2022-10-30 ;
          }

          container ipv6-route-calculate {
            description 'Configure ISIS IPv6 route calculate.' ;
            container egress-protection {
              description 'Configure ISIS IPv6 egress-protection.' ;
              leaf state {
                description 'In the configuration of ISIS IPv6 mode , state of route calculate delay for egress-protection.' ;
                type isis-state ;

                default disable ;
                config true ;
                mandatory false ;
              }

              leaf delay-time {
                description 'Delay time in ms.' ;
                type uint32 {
                  range 1..300000 {
                    description 'Range for delay time:1-300000(ms)' ;
                  }

                }

                default 60000 ;
                config true ;
                mandatory false ;
              }

              config true ;
            }

            container locator-update-delay {
              description 'Configure ISIS SRv6 locator-update delay.' ;
              leaf state {
                description 'State of route calculate delay for SRv6 locator-update.' ;
                type isis-state ;

                default disable ;
                config true ;
                mandatory false ;
              }

              leaf delay-time {
                description 'Delay time in ms.' ;
                type uint32 {
                  range 1..300000 ;

                }

                default 3000 ;
                config true ;
                mandatory false ;
              }

              config true ;
              ncd:revise-date 2024-11-01 ;
            }

            config true ;
            ncd:revise-date 2022-12-08 ;
          }

          container prefix-log {
            description 'Configure IS-IS IPv4 prefix log.' ;
            leaf state {
              description 'The state of IPv4 prefix log.' ;
              type isis-state ;

              default enable ;
              config true ;
              mandatory false ;
            }

            config true ;
            ncd:revise-date 2022-12-28 ;
          }

          container ipv6-prefix-log {
            description 'Configure IS-IS IPv6 prefix log.' ;
            leaf state {
              description 'The state of IPv6 prefix log.' ;
              type isis-state ;

              default enable ;
              config true ;
              mandatory false ;
            }

            config true ;
            ncd:revise-date 2022-12-28 ;
          }

          container slice-source-prefixs {
            description 'Slice source prefix configuration.' ;
            list slice-source-prefix {
              description 'Slice source prefix configuration.' ;
              key prefix-name ;
              leaf prefix-name {
                description 'The name of slice prefix.' ;
                type string {
                  length 1..63 ;

                }

                config true ;
                mandatory false ;
              }

              config true ;
            }

            config true ;
            ncd:revise-date 2023-02-22 ;
          }

          container fast-reroute-link-suppress-block {
            description 'Configure ISIS block suppress interface fast-reroute.' ;
            leaf state {
              description 'In the configuration of ISIS mode , state of fast-reroute link-suppress block.' ;
              type isis-state ;

              default disable ;
              config true ;
              mandatory false ;
            }

            config true ;
            ncd:revise-date 2023-02-28 ;
          }

          container ipv6-fast-reroute-link-suppress-block {
            description 'Configure ISIS IPv6 block suppress interface fast-reroute.' ;
            leaf state {
              description 'In the configuration of ISIS IPv6 mode , state of fast-reroute link-suppress block.' ;
              type isis-state ;

              default disable ;
              config true ;
              mandatory false ;
            }

            config true ;
            ncd:revise-date 2023-02-28 ;
          }

          container bier-info {
            description 'Configure IS-IS BIER info.' ;
            container ipv4-bier {
              description 'Configure IS-IS IPv4 BIER info.' ;
              container fast-reroute {
                if-feature bier-lfa-feature {
                  ncd:revise-date 2024-08-13 ;
                }

                description 'Configure IS-IS IPv4 BIER fast-reroute function.' ;
                container lfa {
                  if-feature bier-lfa-feature {
                    ncd:revise-date 2024-08-13 ;
                  }

                  description 'Configure IS-IS IPv4 BIER fast-reroute LFA function.' ;
                  container lfa-state {
                    if-feature bier-lfa-feature {
                      ncd:revise-date 2024-08-13 ;
                    }

                    description 'Configure IS-IS IPv4 BIER fast-reroute LFA function.' ;
                    choice state {
                      if-feature bier-lfa-feature {
                        ncd:revise-date 2024-08-13 ;
                      }

                      description 'In the configuration of ISIS IPv4 mode, state of  BIER fast-reroute LFA.' ;
                      default disable ;
                      case enable {
                        if-feature bier-lfa-feature {
                          ncd:revise-date 2024-08-13 ;
                        }

                        leaf enable {
                          if-feature bier-lfa-feature {
                            ncd:revise-date 2024-08-13 ;
                          }

                          description 'Enable.' ;
                          type empty ;

                          config true ;
                          mandatory false ;
                        }

                      }

                      case disable {
                        if-feature bier-lfa-feature {
                          ncd:revise-date 2024-08-13 ;
                        }

                        leaf disable {
                          if-feature bier-lfa-feature {
                            ncd:revise-date 2024-08-13 ;
                          }

                          description 'Disable.' ;
                          type empty ;

                          config true ;
                          mandatory false ;
                        }

                      }

                      config true ;
                      mandatory false ;
                    }

                    config true ;
                  }

                  config true ;
                }

                config true ;
              }

              container sub-domains {
                description 'Configure IS-IS IPv4 BIER sub-domains.' ;
                list sub-domain {
                  description 'Configure IS-IS IPv4 BIER sub-domain info.' ;
                  key 'sub-domain-id level' ;
                  max-elements 255 ;
                  leaf sub-domain-id {
                    description 'BIER sub-domain identifier.' ;
                    type uint8 {
                      range 0..255 ;

                    }

                    config true ;
                    mandatory false ;
                  }

                  leaf level {
                    description 'Level(s) will be effected on.' ;
                    type uint8 {
                      range 0..2 ;

                    }

                    config true ;
                    mandatory false ;
                  }

                  config true ;
                }

                config true ;
              }

              config true ;
            }

            container ipv6-bier {
              description 'Configure IS-IS IPv6 BIER info.' ;
              container fast-reroute {
                if-feature bier-lfa-feature {
                  ncd:revise-date 2024-08-13 ;
                }

                description 'Configure IS-IS IPv6 BIER fast-reroute function.' ;
                container lfa {
                  if-feature bier-lfa-feature {
                    ncd:revise-date 2024-08-13 ;
                  }

                  description 'Configure IS-IS IPv6 BIER fast-reroute LFA function.' ;
                  container lfa-state {
                    if-feature bier-lfa-feature {
                      ncd:revise-date 2024-08-13 ;
                    }

                    description 'Configure IS-IS IPv6 BIER fast-reroute LFA function.' ;
                    choice state {
                      if-feature bier-lfa-feature {
                        ncd:revise-date 2024-08-13 ;
                      }

                      description 'In the configuration of ISIS IPv6 mode, state of  BIER fast-reroute LFA.' ;
                      default disable ;
                      case enable {
                        if-feature bier-lfa-feature {
                          ncd:revise-date 2024-08-13 ;
                        }

                        leaf enable {
                          if-feature bier-lfa-feature {
                            ncd:revise-date 2024-08-13 ;
                          }

                          description 'Enable.' ;
                          type empty ;

                          config true ;
                          mandatory false ;
                        }

                      }

                      case disable {
                        if-feature bier-lfa-feature {
                          ncd:revise-date 2024-08-13 ;
                        }

                        leaf disable {
                          if-feature bier-lfa-feature {
                            ncd:revise-date 2024-08-13 ;
                          }

                          description 'Disable.' ;
                          type empty ;

                          config true ;
                          mandatory false ;
                        }

                      }

                      config true ;
                      mandatory false ;
                    }

                    config true ;
                  }

                  config true ;
                }

                config true ;
              }

              container sub-domains {
                description 'Configure IS-IS IPv6 BIER sub-domains.' ;
                list sub-domain {
                  description 'Configure IS-IS IPv6 BIER sub-domain info.' ;
                  key 'sub-domain-id level' ;
                  max-elements 255 ;
                  leaf sub-domain-id {
                    description 'BIER sub-domain identifier.' ;
                    type uint8 {
                      range 0..255 ;

                    }

                    config true ;
                    mandatory false ;
                  }

                  leaf level {
                    description 'Level(s) will be effected on.' ;
                    type uint8 {
                      range 0..2 ;

                    }

                    config true ;
                    mandatory false ;
                  }

                  config true ;
                }

                config true ;
              }

              config true ;
            }

            config true ;
            ncd:revise-date 2023-07-26 ;
          }

          container ipv4-tilfa-inter-level-protect {
            description 'Configure IS-IS IPv4 inter-level fast-reroute TI-LFA.' ;
            leaf level-1-state {
              description 'State of ISIS IPv4 inter-level protection in level-1.' ;
              type isis-state ;

              default disable ;
              config true ;
              mandatory false ;
            }

            config true ;
            ncd:revise-date 2023-09-01 ;
          }

          container ipv6-tilfa-inter-level-protect {
            description 'Configure IS-IS IPv6 inter-level fast-reroute TI-LFA.' ;
            leaf level-1-state {
              description 'State of ISIS IPv6 inter-level protection in level-1.' ;
              type isis-state ;

              default disable ;
              config true ;
              mandatory false ;
            }

            config true ;
            ncd:revise-date 2023-09-01 ;
          }

          container ipv6-fa-summary-prefixs {
            description 'IPv6 fa summary prefix.' ;
            list ipv6-fa-summary-prefix {
              description 'IPv6 fa summary prefix.' ;
              key 'ipv6-prefix prefix-len flex-algorithm' ;
              leaf ipv6-prefix {
                description 'IPv6 summary address.' ;
                type ncd:ipv6-address ;

                config true ;
                mandatory false ;
              }

              leaf prefix-len {
                description 'Prefix length of summary.' ;
                type uint8 ;

                config true ;
                mandatory false ;
              }

              leaf flex-algorithm {
                description 'The value of flex-algorithm.' ;
                type uint8 {
                  range 128..255 ;

                }

                config true ;
                mandatory false ;
              }

              leaf metric {
                description 'Specify metric value for summary prefix.' ;
                type uint32 {
                  range 0..4261412864 ;

                }

                default 0 ;
                config true ;
                mandatory false ;
              }

              leaf level {
                description 'Level(s) will be effected on.' ;
                type isis-level ;

                default level-1-2 ;
                config true ;
                mandatory false ;
              }

              config true ;
            }

            config true ;
          }

          config true ;
          container multi-instance-iid-check {
            leaf state {
              type isis-state ;

              description 'The state of multi-instance instance identifier check.' ;
              default enable ;
            }

            description 'Configure IS-IS multi-instance instance identifier check.' ;
            ncd:revise-date 2025-04-15 ;
          }

        }

        config true ;
      }

      config true ;
    }

    container global-config {
      description 'Route ISIS global config.' ;
      leaf p2p-comply-level-2 {
        description 'Comply P2P hello level-2 config.' ;
        type isis-state ;

        default disable ;
        config true ;
        mandatory false ;
      }

      leaf ipv4-external-prefix-calculate-low-preference {
        description 'Set IS-IS IPv4 external-prefix as low-preference when calculate' ;
        type isis-state ;

        default disable ;
        config true ;
        mandatory false ;
        ncd:revise-date 2021-02-05 ;
      }

      leaf ipv6-external-prefix-calculate-low-preference {
        description 'Set IS-IS IPv6 external-prefix as low-preference when calculate' ;
        type isis-state ;

        default disable ;
        config true ;
        mandatory false ;
        ncd:revise-date 2021-02-05 ;
      }

      leaf memory-overload-protection {
        description 'Configure IS-IS memory overload protection.' ;
        type isis-state ;

        default disable ;
        config true ;
        mandatory false ;
        ncd:revise-date 2025-06-25 ;
      }

      config true ;
      ncd:revise-date 2020-07-09 ;
    }

    config true ;
  }

  container state {
    config false ;
    container route-isis {
      description 'Route isis.' ;
      container isis-adjacencies {
        description 'The information of ISIS adjacency.' ;
        list isis-adjacency {
          description 'The information of ISIS adjacency.' ;
          key 'adj-process-id adj-intf-name adj-level adj-system-id adj-snpa-addr' ;
          leaf adj-process-id {
            description 'Process ID which adjacency belongs to.' ;
            type uint32 {
              range 0..65535 ;

            }

            config false ;
            mandatory false ;
          }

          leaf adj-intf-name {
            description 'The interface name of ISIS adjacency.' ;
            type string {
              length 0..32 ;

            }

            config false ;
            mandatory false ;
          }

          leaf adj-level {
            description "Adjacency's level." ;
            type uint8 {
              range 1..2 ;

            }

            config false ;
            mandatory false ;
          }

          leaf adj-system-id {
            description 'Adjacent system-ID' ;
            type ncd:mac-address ;

            config false ;
            mandatory false ;
          }

          leaf adj-snpa-addr {
            description 'Adjacent SNPA address.' ;
            type ncd:string-all {
              length 1..14 {
                description 'The SNPA of isis adjacency.' ;
              }

            }

            config false ;
            mandatory false ;
          }

          leaf adj-state {
            description 'Adjacent state.' ;
            type ncd:string-all {
              length 1..4 {
                description 'The state of isis adjacency.' ;
              }

            }

            config false ;
            mandatory false ;
          }

          leaf adj-hold-time {
            description 'Holding time of ISIS adjacency.' ;
            type uint16 {
              range 0..65535 {
                description 'Hold-time of isis adjacency.' ;
              }

            }

            config false ;
            mandatory false ;
          }

          leaf adj-priority {
            description 'Priority of ISIS adjacency.' ;
            type uint8 {
              range 0..127 {
                description 'The priority of isis adjacency.' ;
              }

            }

            config false ;
            mandatory false ;
          }

          leaf adj-mt-flag {
            description 'The multi-toplogy flag of isis adjacency' ;
            type uint8 {
              range 0..1 {
                description 'The multi-toplogy flag of isis adjacency.' ;
              }

            }

            config false ;
            mandatory false ;
          }

          leaf adj-system-type {
            description "Adjacency's system type." ;
            type isis-level ;

            config false ;
            mandatory false ;
          }

          leaf adj-extended-circ-id {
            description "Adjacency's extended circuit id." ;
            type uint32 ;

            config false ;
            mandatory false ;
          }

          leaf adj-circuit-id {
            description "If PPP,Adjacency's extended circuit id;
            If LAN,Adjacency's LAN id;" ;
            type string {
              length 1..17 ;

            }

            config false ;
            mandatory false ;
            ncd:revise-date 2021-12-17 ;
          }

          leaf adj-vrf-name {
            description "Adjacency's VRF name." ;
            type string {
              length 1..32 ;

            }

            config false ;
            mandatory false ;
            ncd:revise-date 2015-04-02 ;
          }

          leaf adj-id {
            description 'The ID of adjacency.' ;
            type string {
              length 28 ;

            }

            config false ;
            mandatory false ;
            ncd:revise-date 2018-09-11 ;
          }

          leaf adj-3way-state {
            description 'This is the 3way-state of ISIS adjacency, when the type of network is point-to-point(it is zero ,when network is not point-to-point).' ;
            type uint8 {
              range 0..2 {
                description 'The range of 3way-state is from 0 to 2.' ;
              }

            }

            config false ;
            mandatory false ;
            ncd:revise-date 2018-09-11 ;
          }

          leaf adj-last-uptime {
            description 'This is the time interval since the last adjacency was established.' ;
            type uint32 {
              range 0..4294967295 {
                description 'This is the time interval since the last adjacency was established.' ;
              }

            }

            config false ;
            mandatory false ;
            ncd:revise-date 2018-09-11 ;
          }

          leaf adj-hostname {
            description "Adjacency's hostname." ;
            type string {
              length 1..254 ;

            }

            config false ;
            mandatory false ;
            ncd:revise-date 2025-01-08 ;
          }

          config false ;
          ncd:select adj-process-id ;
          ncd:select adj-intf-name ;
          ncd:select adj-level ;
          ncd:select "adj-process-id adj-intf-name" ;
          ncd:select "adj-process-id adj-intf-name adj-level" ;
          ncd:select "adj-process-id adj-level" ;
          ncd:select "adj-intf-name adj-level" ;
          ncd:select "adj-process-id adj-intf-name adj-level adj-system-id" ;
          ncd:select "adj-process-id adj-intf-name adj-level adj-snpa-addr" ;
          ncd:select "adj-process-id adj-intf-name adj-level adj-system-id adj-snpa-addr" ;
          ncd:select adj-system-id ;
          ncd:select adj-hostname ;
        }

        config false ;
      }

      container isis-circuits {
        description 'The information of ISIS circuits.' ;
        list isis-circuit {
          description 'The information of ISIS circuits.' ;
          key 'circuit-process-id circuit-name' ;
          leaf circuit-process-id {
            description 'Process ID which the circuit belongs to.' ;
            type uint32 {
              range 0..65535 ;

            }

            config false ;
            mandatory false ;
          }

          leaf circuit-name {
            description 'The name of the circuit.' ;
            type ncd:string-all {
              length 1..32 {
                description 'ISIS interface name.' ;
              }

            }

            config false ;
            mandatory false ;
          }

          leaf circuit-type {
            description 'The type of the circuit.' ;
            type enumeration {
              enum L1 {
                value 1 ;
                status current ;

              }

              enum L2 {
                value 2 ;
                status current ;

              }

              enum L1L2 {
                value 3 ;
                status current ;

              }

            }

            config false ;
            mandatory false ;
          }

          leaf circuit-state {
            description 'The state of the circuit.' ;
            type ncd:string-all {
              length 1..7 {
                description 'The state of ISIS interface.' ;
              }

            }

            config false ;
            mandatory false ;
          }

          leaf circuit-id {
            description 'The ID of the circuit' ;
            type uint8 {
              range 0..255 {
                description 'Circuit id of the isis circuit.' ;
              }

            }

            config false ;
            mandatory false ;
          }

          leaf circuit-l1-dr {
            description 'The level-1 DR information of circuit.' ;
            type ncd:string-all {
              length 1..17 {
                description 'The flag of level-1 designated router of the isis circuit.' ;
              }

            }

            config false ;
            mandatory false ;
          }

          leaf circuit-l2-dr {
            description 'The level-2 DR information of circuit.' ;
            type ncd:string-all {
              length 1..17 {
                description 'The flag of level-2 designated router of the isis circuit.' ;
              }

            }

            config false ;
            mandatory false ;
          }

          leaf circuit-l1-priority {
            description 'Priority of the ISIS level-1 circuit.' ;
            type uint8 {
              range 0..127 {
                description "Range of circuit's priority." ;
              }

            }

            config false ;
            mandatory false ;
          }

          leaf circuit-l2-priority {
            description 'Priority of the ISIS level-2 circuit.' ;
            type uint8 {
              range 0..127 {
                description "Range of circuit's priority." ;
              }

            }

            config false ;
            mandatory false ;
          }

          config false ;
          ncd:select circuit-process-id ;
          ncd:select circuit-name ;
          ncd:select "circuit-process-id circuit-name" ;
        }

        config false ;
      }

      container isis-peer-routerids {
        description 'The information of the remote router id' ;
        list isis-peer-routerid {
          description 'The information of the remote router id' ;
          key 'process-id level peer-system-id' ;
          leaf process-id {
            description 'The process ID of the local ISIS instance' ;
            type uint32 {
              range 0..65535 ;

            }

            config false ;
            mandatory false ;
          }

          leaf instance-type {
            description 'The type of the local ISIS instance' ;
            type uint8 {
              range 0..1 ;

            }

            config false ;
            mandatory false ;
          }

          leaf vrf-name {
            description 'The vrf name of the local ISIS instance' ;
            type string {
              length 0..32 ;

            }

            config false ;
            mandatory false ;
          }

          leaf system-id {
            description 'The system id of the local ISIS instance' ;
            type ncd:mac-address ;

            config false ;
            mandatory false ;
          }

          leaf level {
            description 'The level of the remote router-id' ;
            type uint8 {
              range 1..2 ;

            }

            config false ;
            mandatory false ;
          }

          leaf peer-system-id {
            description 'The system id of the remote ISIS instance' ;
            type ncd:mac-address ;

            config false ;
            mandatory false ;
          }

          leaf peer-name {
            description 'The name of the remote ISIS' ;
            type string {
              length 0..254 ;

            }

            config false ;
            mandatory false ;
          }

          leaf peer-routerid {
            description 'The router id of the remote ISIS instance' ;
            type ncd:ipv4-address ;

            config false ;
            mandatory false ;
          }

          config false ;
          ncd:select process-id ;
          ncd:select level ;
          ncd:select peer-system-id ;
          ncd:select "process-id level" ;
          ncd:select "process-id peer-system-id" ;
          ncd:select "level peer-system-id" ;
          ncd:select "process-id level peer-system-id" ;
        }

        config false ;
        ncd:revise-date 2018-09-11 ;
      }

      container isis-instances {
        description 'The information of ISIS instance.' ;
        list isis-instance {
          description 'The information of ISIS instance.' ;
          key process-id ;
          leaf process-id {
            description 'The process ID of ISIS instance.' ;
            type uint32 {
              range 0..65535 ;

            }

            config false ;
            mandatory false ;
          }

          container isis-ipv4-routes {
            description 'The information of ISIS IPv4 route.' ;
            list isis-ipv4-route {
              description 'The information of ISIS IPv4 route.' ;
              key 'ipv4-address mask-len' ;
              leaf ipv4-address {
                description 'IPv4 address.' ;
                type ncd:ipv4-address ;

                config false ;
                mandatory false ;
              }

              leaf mask-len {
                description 'IPv4 address mask length.' ;
                type uint8 ;

                config false ;
                mandatory false ;
              }

              leaf route-type {
                description 'The route type of ISIS IPv4 route.' ;
                type string {
                  length 0..6 ;

                }

                config false ;
                mandatory false ;
              }

              leaf level {
                description 'The level of ISIS IPv4 route.' ;
                type uint8 {
                  range 1..2 ;

                }

                config false ;
                mandatory false ;
              }

              container nexthops {
                description 'The next hop of ISIS IPv4 route.' ;
                list nexthop {
                  description 'The next hop of ISIS IPv4 route.' ;
                  key 'next-hop out-interface' ;
                  leaf next-hop {
                    description 'The gateway of next hop.' ;
                    type ncd:ipv4-address ;

                    config false ;
                    mandatory false ;
                  }

                  leaf out-interface {
                    description 'The outgoing interface of next hop.' ;
                    type string {
                      length 0..64 ;

                    }

                    config false ;
                    mandatory false ;
                  }

                  leaf metric {
                    description 'The metric of next hop.' ;
                    type uint32 {
                      range 1..4294967295 ;

                    }

                    config false ;
                    mandatory false ;
                  }

                  config false ;
                }

                config false ;
              }

              config false ;
            }

            config false ;
          }

          container isis-ipv6-routes {
            description 'The information of ISIS IPv6 route.' ;
            list isis-ipv6-route {
              description 'The information of ISIS IPv6 route.' ;
              key 'ipv6-address mask-len' ;
              leaf ipv6-address {
                description 'IPv6 address.' ;
                type ncd:ipv6-address ;

                config false ;
                mandatory false ;
              }

              leaf mask-len {
                description 'IPv6 address mask length.' ;
                type uint8 ;

                config false ;
                mandatory false ;
              }

              leaf route-type {
                description 'The route type of ISIS IPv6 route.' ;
                type string {
                  length 0..6 ;

                }

                config false ;
                mandatory false ;
              }

              leaf level {
                description 'The level of ISIS IPv6 route.' ;
                type uint8 {
                  range 1..2 ;

                }

                config false ;
                mandatory false ;
              }

              container nexthops {
                description 'The next hop of ISIS IPv6 route.' ;
                list nexthop {
                  description 'The next hop of ISIS IPv6 route.' ;
                  key 'next-hop out-interface' ;
                  leaf next-hop {
                    description 'The gateway of next hop.' ;
                    type ncd:ipv6-address ;

                    config false ;
                    mandatory false ;
                  }

                  leaf out-interface {
                    description 'The outgoing interface of next hop.' ;
                    type string {
                      length 0..64 ;

                    }

                    config false ;
                    mandatory false ;
                  }

                  leaf metric {
                    description 'The metric of next hop.' ;
                    type uint32 {
                      range 1..4294967295 ;

                    }

                    config false ;
                    mandatory false ;
                  }

                  config false ;
                }

                config false ;
              }

              config false ;
            }

            config false ;
          }

          config false ;
        }

        config false ;
        ncd:revise-date 2021-12-17 ;
      }

      config false ;
    }

  }

  notification notification {
    description 'Notification of ISIS, only telemetry upload is supported.' ;
    container adjacencies {
      description 'ISIS adjacency.' ;
      config false ;
      list adjacency {
        description 'adjacency.' ;
        key 'process-id level intf-name system-id' ;
        leaf process-id {
          description 'ISIS process ID.' ;
          type uint32 {
            range 0..65535 ;

          }

          config false ;
          mandatory false ;
        }

        leaf level {
          description 'Level(s) will be effected on.' ;
          type enumeration {
            enum level-1 {
              value 1 ;
              description 'level-1' ;
              status current ;

            }

            enum level-2 {
              value 2 ;
              description 'level-2' ;
              status current ;

            }

          }

          config false ;
          mandatory false ;
        }

        leaf intf-name {
          description 'Interface name.' ;
          type ncd:ifname {
            length 1..31 {
              description 'The length of interface name from 1 to 31.' ;
            }

          }

          config false ;
          mandatory false ;
        }

        leaf system-id {
          description 'A system ID for an ISIS instance.' ;
          type ncd:mac-address ;

          config false ;
          mandatory false ;
        }

        leaf state {
          description 'The state of ISIS neighbor.' ;
          type enumeration {
            enum down {
              value 0 ;
              description 'The  state of ISIS neighbor is down.' ;
              status current ;

            }

            enum init {
              value 1 ;
              description 'The  state of ISIS neighbor is init.' ;
              status current ;

            }

            enum up {
              value 2 ;
              description 'The  state of ISIS neighbor is up.' ;
              status current ;

            }

          }

          config false ;
          mandatory false ;
        }

        config false ;
      }

      list adjacencyNum {
        description 'ISIS adjacency numbers.' ;
        key process-id ;
        leaf process-id {
          description 'ISIS process ID.' ;
          type uint32 {
            range 0..65535 ;

          }

          config false ;
          mandatory false ;
        }

        leaf totalNum {
          description 'ISIS adjacency total numbers.' ;
          type uint32 {
            range 0..4096 ;

          }

          config false ;
          mandatory false ;
        }

        leaf level1-up {
          description 'ISIS adjacency L1 up numbers.' ;
          type uint32 {
            range 0..4096 ;

          }

          config false ;
          mandatory false ;
        }

        leaf level1-init {
          description 'ISIS adjacency L1 init numbers.' ;
          type uint32 {
            range 0..4096 ;

          }

          config false ;
          mandatory false ;
        }

        leaf level2-up {
          description 'ISIS adjacency L2 up numbers.' ;
          type uint32 {
            range 0..4096 ;

          }

          config false ;
          mandatory false ;
        }

        leaf level2-init {
          description 'ISIS adjacency L2 init numbers.' ;
          type uint32 {
            range 0..4096 ;

          }

          config false ;
          mandatory false ;
        }

        config false ;
        ncd:revise-date 2023-06-07 ;
      }

      list adjacency-period {
        description 'Periodic sampling of ISIS adjacency, only telemetry upload is supported.' ;
        key 'process-id level intf-name system-id' ;
        leaf process-id {
          description 'ISIS process ID.' ;
          type uint32 {
            range 0..65535 ;

          }

          config false ;
          mandatory false ;
        }

        leaf level {
          description 'Level(s) will be effected on.' ;
          type enumeration {
            enum level-1 {
              value 1 ;
              description 'level-1' ;
              status current ;

            }

            enum level-2 {
              value 2 ;
              description 'level-2' ;
              status current ;

            }

          }

          config false ;
          mandatory false ;
        }

        leaf intf-name {
          description 'Interface name.' ;
          type ncd:ifname {
            length 1..31 {
              description 'The length of interface name from 1 to 31.' ;
            }

          }

          config false ;
          mandatory false ;
        }

        leaf system-id {
          description 'A system ID for an ISIS instance.' ;
          type ncd:mac-address ;

          config false ;
          mandatory false ;
        }

        leaf state {
          description 'The state of ISIS neighbor.' ;
          type enumeration {
            enum down {
              value 0 ;
              description 'The  state of ISIS neighbor is down.' ;
              status current ;

            }

            enum init {
              value 1 ;
              description 'The  state of ISIS neighbor is init.' ;
              status current ;

            }

            enum up {
              value 2 ;
              description 'The  state of ISIS neighbor is up.' ;
              status current ;

            }

          }

          config false ;
          mandatory false ;
        }

        config false ;
        ncd:revise-date 2024-10-31 ;
      }

      list adjacency-number-period {
        description 'Periodic sampling of ISIS adjacency numbers, only telemetry upload is supported.' ;
        key process-id ;
        leaf process-id {
          description 'ISIS process ID.' ;
          type uint32 {
            range 0..65535 ;

          }

          config false ;
          mandatory false ;
        }

        leaf total-number {
          description 'ISIS adjacency total numbers.' ;
          type uint32 {
            range 0..4096 ;

          }

          config false ;
          mandatory false ;
        }

        leaf level1-up {
          description 'ISIS adjacency L1 up numbers.' ;
          type uint32 {
            range 0..4096 ;

          }

          config false ;
          mandatory false ;
        }

        leaf level1-init {
          description 'ISIS adjacency L1 init numbers.' ;
          type uint32 {
            range 0..4096 ;

          }

          config false ;
          mandatory false ;
        }

        leaf level2-up {
          description 'ISIS adjacency L2 up numbers.' ;
          type uint32 {
            range 0..4096 ;

          }

          config false ;
          mandatory false ;
        }

        leaf level2-init {
          description 'ISIS adjacency L2 init numbers.' ;
          type uint32 {
            range 0..4096 ;

          }

          config false ;
          mandatory false ;
        }

        config false ;
        ncd:revise-date 2024-10-31 ;
      }

      list adjacencyState {
        description 'The state of ISIS adjacency.' ;
        key 'process-id level intf-name system-id' ;
        leaf process-id {
          description 'ISIS process ID.' ;
          type uint32 {
            range 0..65535 ;

          }

          config false ;
          mandatory false ;
        }

        leaf level {
          description 'Level(s) will be effected on.' ;
          type enumeration {
            enum level-1 {
              value 1 ;
              description 'level-1' ;
              status current ;

            }

            enum level-2 {
              value 2 ;
              description 'level-2' ;
              status current ;

            }

          }

          config false ;
          mandatory false ;
        }

        leaf intf-name {
          description 'Interface name.' ;
          type ncd:ifname {
            length 1..31 {
              description 'The length of interface name from 1 to 31.' ;
            }

          }

          config false ;
          mandatory false ;
        }

        leaf system-id {
          description 'A system ID for an ISIS instance.' ;
          type ncd:mac-address ;

          config false ;
          mandatory false ;
        }

        leaf state {
          description 'The state of ISIS neighbor.' ;
          type enumeration {
            enum down {
              value 0 ;
              description 'The  state of ISIS neighbor is down.' ;
              status current ;

            }

            enum init {
              value 1 ;
              description 'The  state of ISIS neighbor is init.' ;
              status current ;

            }

            enum up {
              value 2 ;
              description 'The  state of ISIS neighbor is up.' ;
              status current ;

            }

          }

          config false ;
          mandatory false ;
        }

        config false ;
        ncd:revise-date 2025-02-24 ;
      }

    }

    container interfaces {
      description 'ISIS interface.' ;
      config false ;
      list interface {
        description 'interface.' ;
        key 'process-id intf-name' ;
        leaf process-id {
          description 'ISIS process ID.' ;
          type uint32 {
            range 0..65535 ;

          }

          config false ;
          mandatory false ;
        }

        leaf intf-name {
          description 'Interface name.' ;
          type ncd:ifname {
            length 1..31 ;

          }

          config false ;
          mandatory false ;
        }

        leaf state {
          description 'The state of ISIS interface.' ;
          type enumeration {
            enum down {
              value 0 ;
              description 'The  state of ISIS interface is down.' ;
              status current ;

            }

            enum up {
              value 1 ;
              description 'The  state of ISIS interface is up.' ;
              status current ;

            }

            enum disable {
              value 2 ;
              description 'The  state of ISIS interface is disable.' ;
              status current ;

            }

            enum "up(SDdown)" {
              value 3 ;
              description 'The  state of ISIS interface is up(SDdown).' ;
              status current ;

            }

          }

          config false ;
          mandatory false ;
        }

        leaf level {
          description 'Level(s) will be effected on.' ;
          type enumeration {
            enum level-1-2 {
              value 0 ;
              description 'level-1-2' ;
              status current ;

            }

            enum level1 {
              value 1 ;
              description 'level1' ;
              status current ;

            }

            enum level2 {
              value 2 ;
              description 'level2' ;
              status current ;

            }

          }

          config false ;
          mandatory false ;
        }

        leaf ipv4-state {
          description 'The state of ISIS IPv4 interface.' ;
          type enumeration {
            enum down {
              value 1 ;
              description 'The  ipv4-state of ISIS interface is down.' ;
              status current ;

            }

            enum up {
              value 2 ;
              description 'The  ipv4-state of ISIS interface is up.' ;
              status current ;

            }

          }

          config false ;
          mandatory false ;
        }

        leaf ipv6-state {
          description 'The state of ISIS IPv6 interface.' ;
          type enumeration {
            enum down {
              value 1 ;
              description 'The  ipv6-state of ISIS interface is down.' ;
              status current ;

            }

            enum up {
              value 2 ;
              description 'The  ipv6-state of ISIS interface is up.' ;
              status current ;

            }

          }

          config false ;
          mandatory false ;
        }

        config false ;
      }

      list interface-period {
        description 'Periodic sampling of ISIS interface, only telemetry upload is supported.' ;
        key 'process-id intf-name' ;
        leaf process-id {
          description 'ISIS process ID.' ;
          type uint32 {
            range 0..65535 ;

          }

          config false ;
          mandatory false ;
        }

        leaf intf-name {
          description 'Interface name.' ;
          type ncd:ifname {
            length 1..31 ;

          }

          config false ;
          mandatory false ;
        }

        leaf state {
          description 'The state of ISIS interface.' ;
          type enumeration {
            enum down {
              value 0 ;
              description 'The  state of ISIS interface is down.' ;
              status current ;

            }

            enum up {
              value 1 ;
              description 'The  state of ISIS interface is up.' ;
              status current ;

            }

            enum disable {
              value 2 ;
              description 'The  state of ISIS interface is disable.' ;
              status current ;

            }

            enum "up(SDdown)" {
              value 3 ;
              description 'The  state of ISIS interface is up(SDdown).' ;
              status current ;

            }

          }

          config false ;
          mandatory false ;
        }

        leaf level {
          description 'Level(s) will be effected on.' ;
          type enumeration {
            enum level-1-2 {
              value 0 ;
              description 'level-1-2' ;
              status current ;

            }

            enum level1 {
              value 1 ;
              description 'level1' ;
              status current ;

            }

            enum level2 {
              value 2 ;
              description 'level2' ;
              status current ;

            }

          }

          config false ;
          mandatory false ;
        }

        leaf ipv4-state {
          description 'The state of ISIS IPv4 interface.' ;
          type enumeration {
            enum down {
              value 1 ;
              description 'The  ipv4-state of ISIS interface is down.' ;
              status current ;

            }

            enum up {
              value 2 ;
              description 'The  ipv4-state of ISIS interface is up.' ;
              status current ;

            }

          }

          config false ;
          mandatory false ;
        }

        leaf ipv6-state {
          description 'The state of ISIS IPv6 interface.' ;
          type enumeration {
            enum down {
              value 1 ;
              description 'The  ipv6-state of ISIS interface is down.' ;
              status current ;

            }

            enum up {
              value 2 ;
              description 'The  ipv6-state of ISIS interface is up.' ;
              status current ;

            }

          }

          config false ;
          mandatory false ;
        }

        config false ;
        ncd:revise-date 2024-10-31 ;
      }

      ncd:revise-date 2023-06-07 ;
    }

    ncd:revise-date 2023-05-24 ;
  }

}
