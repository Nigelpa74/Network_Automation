module zxr10-flexe-oam {
  namespace "http://www.zte.com.cn/zxr10/netconf/schema/rosng/flexe-oam" ;
  prefix flexe-oam ;
  yang-version 1 ;
  import zxr10-netconf-defs {
    prefix ncd ;
    revision-date 2017-03-30 ;
  }

  organization "ZTE Corporation" ;
  contact "ZTE Corporation
  Nanjing Institute of ZTE Corporation
  No.68 Zijinghua Rd. Yuhuatai District, Nanjing, China
  Tel: +86-25-52870000" ;
  revision 2023-06-27 {
    description '1. Modify the leaf name configuration/flexe-oam/megs/meg/meg-type/mep/mep/one-dm-cfg to one-dm;
2. Modify the leaf name configuration/flexe-oam/megs/meg/meg-type/mep/mep/one-way-period to one-dm-period;
3. Modify the leaf name configuration/flexe-oam/megs/meg/meg-type/mep/mep/two-dm-cfg to two-dm;
4. Modify the leaf name configuration/flexe-oam/megs/meg/meg-type/mep/mep/two-way-period to two-dm-period.' ;
  }

  revision 2023-06-20 {
    description 'Add TCM
1. Add TCM to configuration/flexe-oam/megs/meg;
' ;
  }

  revision 2023-03-09 {
    description '1.Modify the range of configuration/flexe-oam/megs/meg/meg-type/mep/loss-threshold from 9-12 to 8-12;
2.Modify the range of configuration/flexe-oam/megs/meg/meg-type/mep/exc-threshold from 7-8 to 6-8;
3.Modify the range of configuration/flexe-oam/megs/meg/meg-type/mip/loss-threshold from 9-12 to 8-12;
4.Modify the range of configuration/flexe-oam/megs/meg/meg-type/mip/exc-threshold from 7-8 to 6-8;' ;
  }

  revision 2023-02-01 {
    description '1.Add feature spn which is available for PC.MSE product.
2.Add state/flexe-oam/detect-alarm-infos/detect-alarm-info.
3.Add configuration/flexe-oam/megs/meg/meg-type/mep/mep/csf.
4.Add configuration/flexe-oam/megs/meg/meg-type/mep/mep/sd.
5.Add configuration/flexe-oam/megs/meg/meg-type/mep/mep/sf.
6.Add configuration/flexe-oam/megs/meg/meg-type/mep/mep/one-dm-cfg.
7.Add configuration/flexe-oam/megs/meg/meg-type/mep/mep/one-way-period.
8.Add configuration/flexe-oam/megs/meg/meg-type/mep/mep/two-dm-cfg.
9.Add configuration/flexe-oam/megs/meg/meg-type/mep/mep/two-way-period.
10.Add configuration/flexe-oam/megs/meg/meg-type/mip/mip/sd.
11.Add configuration/flexe-oam/megs/meg/meg-type/mip/mip/sf.
12.Add configuration/flexe-oam/megs/meg/meg-type/mip/mip/sd-propagate.' ;
  }

  revision 2020-08-25 {
    description '1.Add configuration/flexe-oam/megs/meg/meg-type/mep/mep/subclient-period.
1.Add feature subclient-period which is available for PTN6100,PTN6700 and PTN65V5 product.' ;
  }

  revision 2019-07-30 {
    description '1.Add feature sd-propagate which is available for PTN6100,PTN6700 and PTN65V5 product.
2.Add configuration/flexe-oam/megs/meg/meg-type/mep/mep/sd-propagate.' ;
  }

  revision 2019-04-16 {
    description '1.Add feature cs-type which is available for PTN6100 product.
2.Add configuration/flexe-oam/megs/meg/meg-type/mep/mep/cs-type.' ;
  }

  revision 2019-04-02 {
    description '1 Modify range for configuration/flexe-oam/megs/meg/meg-type/mep/mep/local-mep
2 Modify range for configuration/flexe-oam/megs/meg/meg-type/mep/mep/peer-mep' ;
  }

  revision 2019-02-20 {
    description '1 Modify range for configuration/flexe-oam/megs/meg/meg-type/mep/mep/loss-threshold.
2 Add configuration/flexe-oam/megs/meg/meg-type/mep/mep/loss-mantissa.
3 Add configuration/flexe-oam/megs/meg/meg-type/mep/mep/exc-mantissa.
4 Add configuration/flexe-oam/megs/meg/meg-type/mep/mep/exc-threshold.
5 Add configuration/flexe-oam/megs/meg/meg-type/mip/mip/loss-mantissa.
6 Add configuration/flexe-oam/megs/meg/meg-type/mip/mip/loss-threshold.
7 Add configuration/flexe-oam/megs/meg/meg-type/mip/mip/exc-mantissa.
8 Add configuration/flexe-oam/megs/meg/meg-type/mip/mip/exc-threshold.' ;
  }

  revision 2019-01-17 {
    description '1.Add feature cc-bip-status which is available for PTN6100,PTN6700 and PTN65V5 product.
2.Add an enumeration value auto for configuration/flexe-oam/megs/meg/mep/block-period and configuration/flexe-oam/megs/meg/mip/block-period.
3.Add configuration/flexe-oam/megs/meg/mep/cc-bip and configuration/flexe-oam/megs/meg/mip/cc-bip.' ;
  }

  revision 2018-07-17 {
    description 'Initial version.' ;
  }

  feature sequence-number {
    description 'The fixed sequence number of base block.' ;
  }

  feature cc-bip-status {
    description 'The switch for turning on or off the CC and BIP function(default:enable).' ;
  }

  feature cs-type {
    description 'The test type of CS function.' ;
  }

  feature sd-propagate {
    description 'The switch for turning on or off the SD propagate function(default:disable).' ;
  }

  feature subclient_period {
    description 'The subclient OAM period.' ;
  }

  feature spn {
    description 'MTN Channel OAM function.' ;
    ncd:revise-date 2023-02-01 ;
  }

  feature tcm {
    description 'TCM OAM function.' ;
    ncd:revise-date 2023-06-20 ;
  }

  typedef mep-type {
    type enumeration {
      enum source {
        value 1 ;
        description 'Source MEP.' ;
      }

      enum destination {
        value 2 ;
        description 'Destination MEP.' ;
      }

      enum bidirectional {
        value 3 ;
        description 'Bidirection MEP.' ;
      }

    }

    description 'The type of MEP, including source MEP, destination MEP and bidirectional MEP.' ;
  }

  container configuration {
    description 'Configuration model Info.' ;
    container flexe-oam {
      description 'FlexE OAM megs configuration.' ;
      container global {
        description 'Configure global Info of FlexE OAM.' ;
        leaf oam-switch {
          description 'The switch for turning on or off FlexE OAM function(default:enable).' ;
          type enumeration {
            enum disable {
              value 0 ;
              description 'Turn off FlexE OAM function.' ;
            }

            enum enable {
              value 1 ;
              description 'Turn on FlexE OAM function.' ;
            }

          }

          default enable ;
        }

        leaf rdi-to-sf-switch {
          description 'The switch for turning on or off FlexE OAM RDI transform to sf function(default:enable).' ;
          type enumeration {
            enum disable {
              value 0 ;
              description 'Turn off FlexE OAM RDI transform to sf function.' ;
            }

            enum enable {
              value 1 ;
              description 'Turn on FlexE OAM RDI transform to sf function.' ;
            }

          }

          default enable ;
        }

      }

      container megs {
        description 'Configure FlexE OAM megs.' ;
        list meg {
          description 'Configure FlexE OAM megs.' ;
          key meg-index ;
          leaf meg-index {
            description 'Meg index,ranges from 1 to 65535.' ;
            type uint16 {
              range 1..65535 {
                description 'The value of meg index.' ;
              }

            }

          }

          leaf ifname {
            description 'The FlexE client interface binded by OAM.' ;
            type ncd:ifname {
              length 1..31 {
                description 'The range of interface name length.' ;
              }

            }

            mandatory true ;
          }

          choice meg-type {
            description 'Configure MEP or MIP parameters of MEG.' ;
            case mep {
              description 'MEP parameters.' ;
              container mep {
                description 'MEP parameters.' ;
                presence mep ;
                leaf local-mep {
                  description 'The local MEP.' ;
                  type string {
                    length 1..15 {
                      description 'The string length ranges from 1 to 15.' ;
                    }

                  }

                }

                leaf local-mep-type {
                  description 'The type of local MEP, including source MEP, destination MEP and bidirectional MEP(default:bidirectional MEP).' ;
                  type mep-type ;

                  default bidirectional ;
                }

                leaf peer-mep {
                  description 'The peer MEP.' ;
                  type string {
                    length 1..15 {
                      description 'The string length ranges from 1 to 15.' ;
                    }

                  }

                }

                leaf base-block {
                  description 'The switch for turning on or off base block function(default:disable).' ;
                  type enumeration {
                    enum disable {
                      value 0 ;
                      description 'Disable base block.' ;
                    }

                    enum enable {
                      value 1 ;
                      description 'Enable base block.' ;
                    }

                  }

                  default disable ;
                }

                leaf block-period {
                  description 'The base block period,including 16k,32k,64k,512k and auto(default:16k).' ;
                  type enumeration {
                    enum 16k {
                      value 1 ;
                      description 'The block period is 16k.' ;
                    }

                    enum 32k {
                      value 5 ;
                      description 'The block period is 32k.' ;
                    }

                    enum 64k {
                      value 2 ;
                      description 'The block period is 64k.' ;
                    }

                    enum 512k {
                      value 4 ;
                      description 'The block period is 512k.' ;
                    }

                    enum auto {
                      value 6 ;
                      description 'The block period is auto.' ;
                    }

                  }

                  default 16k ;
                }

                leaf bip-check {
                  description 'Include or exclude OAM block in BIP check (default:include).' ;
                  type enumeration {
                    enum include {
                      value 1 ;
                      description 'Include OAM in BIP check.' ;
                    }

                    enum exclude {
                      value 0 ;
                      description 'Exclude OAM in BIP check.' ;
                    }

                  }

                  default include ;
                }

                leaf circle-sequence {
                  description 'The switch for turning on or off circle sequence function in the base block(default:enable).' ;
                  type enumeration {
                    enum enable {
                      value 1 ;
                      description 'Enable the function of circle sequence in the base code block' ;
                    }

                    enum disable {
                      value 0 ;
                      description 'Disable the function of circle sequence in the base code block' ;
                    }

                  }

                  default enable ;
                }

                leaf cv {
                  description 'The switch for turning on or off the CV function(default:disable).' ;
                  type enumeration {
                    enum enable {
                      value 1 ;
                      description 'Enable the CV function.' ;
                    }

                    enum disable {
                      value 0 ;
                      description 'Disable the CV function.' ;
                    }

                  }

                  default disable ;
                }

                leaf cv-period {
                  description 'The period of sending packets in CV function(default:10s).' ;
                  type enumeration {
                    enum 1s {
                      value 1 ;
                      description 'Packet send period:1s(default:10s)' ;
                    }

                    enum 10s {
                      value 2 ;
                      description 'Packet send period:10s(default:10s)' ;
                    }

                    enum 1min {
                      value 3 ;
                      description 'Packet send period:1min(default:10s)' ;
                    }

                  }

                  default 10s ;
                }

                leaf cs {
                  description 'The switch for turning on or off the CS function(default:disable).' ;
                  type enumeration {
                    enum enable {
                      value 1 ;
                      description 'Enable the CS function(default:disable).' ;
                    }

                    enum disable {
                      value 0 ;
                      description 'Disable the CS function(default:disable).' ;
                    }

                  }

                  default disable ;
                }

                leaf cs-period {
                  description 'The period of sending packets in CS function(default:10s).' ;
                  type enumeration {
                    enum 1s {
                      value 1 ;
                      description 'Packet send period:1s(default:10s)' ;
                    }

                    enum 10s {
                      value 2 ;
                      description 'Packet send period:10s(default:10s)' ;
                    }

                    enum 1min {
                      value 3 ;
                      description 'Packet send period:1min(default:10s)' ;
                    }

                  }

                  default 10s ;
                }

                leaf loss-threshold {
                  description 'The exponent of the packet loss threshold(default:9).' ;
                  type uint8 {
                    range 8..12 {
                      description 'This parameter ranges from 8 to 12(default:9).' ;
                    }

                  }

                  default 9 ;
                }

                leaf sequence-number {
                  if-feature sequence-number ;

                  description 'The fixed sequence number of base block that ranging from 0 to 15(default:0).' ;
                  type uint8 {
                    range 0..15 {
                      description 'The fixed sequence number of base block ranging from 0 to 15(default:0)' ;
                    }

                  }

                  default 0 ;
                }

                leaf cc-bip {
                  if-feature cc-bip-status ;

                  description 'The switch for turning on or off the CC and BIP function(default:enable).' ;
                  type enumeration {
                    enum disable {
                      value 0 ;
                      description 'Disable the CC and BIP function(default:enable).' ;
                    }

                    enum enable {
                      value 1 ;
                      description 'Enable the CC and BIP function(default:enable).' ;
                    }

                  }

                  default enable ;
                  ncd:revise-date 2019-01-17 ;
                }

                leaf loss-mantissa {
                  description 'The mantissa of the packet loss threshold(default:1).' ;
                  type uint8 {
                    range 1..9 {
                      description 'This parameter ranges from 1 to 9(default:1).' ;
                    }

                  }

                  default 1 ;
                  ncd:revise-date 2019-02-20 ;
                }

                leaf exc-mantissa {
                  description 'The mantissa of the packet EXC threshold(default:1).' ;
                  type uint8 {
                    range 1..9 {
                      description 'This parameter ranges from 1 to 9(default:1).' ;
                    }

                  }

                  default 1 ;
                  ncd:revise-date 2019-02-20 ;
                }

                leaf exc-threshold {
                  description 'The exponent of the packet EXC threshold(default:7).' ;
                  type uint8 {
                    range 6..8 {
                      description 'This parameter ranges from 6 to 8(default:7).' ;
                    }

                  }

                  default 7 ;
                  ncd:revise-date 2019-02-20 ;
                }

                leaf cs-type {
                  if-feature cs-type ;

                  description 'The test type of CS function(default:unequipped).' ;
                  type enumeration {
                    enum unequipped {
                      value 1 ;
                      description 'The CS type is signal unequipped(default:unequipped).' ;
                    }

                    enum eth {
                      value 2 ;
                      description 'The CS type is ETH service(default:unequipped).' ;
                    }

                    enum sdh {
                      value 3 ;
                      description 'The CS type is SDH service(default:unequipped).' ;
                    }

                    enum fc {
                      value 4 ;
                      description 'The CS type is FC service(default:unequipped).' ;
                    }

                    enum cpri {
                      value 5 ;
                      description 'The CS type is CPRI service(default:unequipped).' ;
                    }

                  }

                  default unequipped ;
                  ncd:revise-date 2019-04-16 ;
                }

                leaf sd-propagate {
                  if-feature sd-propagate ;

                  description 'The switch for turning on or off the SD propagate function(default:disable).' ;
                  type enumeration {
                    enum enable {
                      value 1 ;
                      description 'Enable the SD propagate function(default:disable).' ;
                    }

                    enum disable {
                      value 0 ;
                      description 'Disable the SD propagate function(default:disable).' ;
                    }

                  }

                  default disable ;
                  ncd:revise-date 2019-07-30 ;
                }

                leaf subclient-period {
                  if-feature subclient_period ;

                  description 'The subclient OAM period.' ;
                  type enumeration {
                    enum auto {
                      value 1 ;
                      description 'The subclient OAM period is auto.' ;
                    }

                  }

                  default auto ;
                  ncd:revise-date 2020-08-25 ;
                }

                leaf csf {
                  if-feature spn ;

                  description 'The switch for turning on or off the CSF function(default:disable).' ;
                  type enumeration {
                    enum disable {
                      value 0 ;
                      description 'Disable CSF function.' ;
                    }

                    enum enable {
                      value 1 ;
                      description 'Enable CSF function.' ;
                    }

                  }

                  default disable ;
                  ncd:revise-date 2023-02-01 ;
                }

                leaf sd {
                  if-feature spn ;

                  description 'The switch for turning on or off the SD function(default:disable).' ;
                  type enumeration {
                    enum disable {
                      value 0 ;
                      description 'Disable SD function.' ;
                    }

                    enum enable {
                      value 1 ;
                      description 'Enable SD function.' ;
                    }

                  }

                  default disable ;
                  ncd:revise-date 2023-02-01 ;
                }

                leaf sf {
                  if-feature spn ;

                  description 'The switch for turning on or off the SF function(default:disable).' ;
                  type enumeration {
                    enum disable {
                      value 0 ;
                      description 'Disable SF function.' ;
                    }

                    enum enable {
                      value 1 ;
                      description 'Enable SF function.' ;
                    }

                  }

                  default disable ;
                  ncd:revise-date 2023-02-01 ;
                }

                leaf one-dm {
                  if-feature spn ;

                  description 'The switch for turning on or off the one-way DM function(default:disable).' ;
                  type enumeration {
                    enum disable {
                      value 0 ;
                      description 'Disable one-way DM function.' ;
                    }

                    enum enable {
                      value 1 ;
                      description 'Enable one-way DM function.' ;
                    }

                  }

                  default disable ;
                  ncd:revise-date 2023-02-01 ;
                }

                leaf one-dm-period {
                  if-feature spn ;

                  description 'The period of sending packets of one-way DM function,including 1s,10s and 60s(default:10s).' ;
                  type enumeration {
                    enum 1s {
                      value 1 ;
                      description 'The period of one-way DM.' ;
                    }

                    enum 10s {
                      value 2 ;
                      description 'The period of one-way DM.' ;
                    }

                    enum 1min {
                      value 3 ;
                      description 'The period of one-way DM.' ;
                    }

                  }

                  default 10s ;
                  ncd:revise-date 2023-02-01 ;
                }

                leaf two-dm {
                  if-feature spn ;

                  description 'The switch for turning on or off the two-way DM function(default:disable).' ;
                  type enumeration {
                    enum disable {
                      value 0 ;
                      description 'Disable two-way DM function.' ;
                    }

                    enum enable {
                      value 1 ;
                      description 'Enable two-way DM function.' ;
                    }

                  }

                  default disable ;
                  ncd:revise-date 2023-02-01 ;
                }

                leaf two-dm-period {
                  if-feature spn ;

                  description 'The period of sending packets of two-way DM function,including 1s,10s and 60s(default:10s).' ;
                  type enumeration {
                    enum 1s {
                      value 1 ;
                      description 'The period of two-way DM.' ;
                    }

                    enum 10s {
                      value 2 ;
                      description 'The period of two-way DM.' ;
                    }

                    enum 1min {
                      value 3 ;
                      description 'The period of two-way DM.' ;
                    }

                  }

                  default 10s ;
                  ncd:revise-date 2023-02-01 ;
                }

                container tcm {
                  leaf tcm {
                    type enumeration {
                      enum disable {
                        value 0 ;
                        description 'Disable TCM function.' ;
                      }

                      enum enable {
                        value 1 ;
                        description 'Enable TCM function.' ;
                      }

                    }

                    default disable ;
                    description 'The status of TCM,including enable and disable(default:disable).' ;
                  }

                  leaf level {
                    type enumeration {
                      enum tcm0 {
                        value 0 ;
                        description 'TCM level 0.' ;
                      }

                      enum tcm1 {
                        value 1 ;
                        description 'TCM level 1.' ;
                      }

                      enum tcm2 {
                        value 2 ;
                        description 'TCM level 2.' ;
                      }

                    }

                    default tcm0 ;
                    description 'TCM level,including tcm0,tcm1 and tcm2(default:tcm0).' ;
                  }

                  if-feature tcm ;

                  description 'TCM(Tandem Connection Monitoring) function.' ;
                  ncd:revise-date 2023-06-20 ;
                }

              }

            }

            case mip {
              description 'MIP parameters.' ;
              container mip {
                presence mip ;
                leaf base-block {
                  description 'The switch for turning on or off base block function(default:disable).' ;
                  type enumeration {
                    enum disable {
                      value 0 ;
                      description 'Disable base block.' ;
                    }

                    enum enable {
                      value 1 ;
                      description 'Enable base block.' ;
                    }

                  }

                  default disable ;
                }

                leaf block-period {
                  description 'The base block period,including 16k,32k,64k,512k and auto(default:16k).' ;
                  type enumeration {
                    enum 16k {
                      value 1 ;
                      description 'The block period is 16k.' ;
                    }

                    enum 32k {
                      value 5 ;
                      description 'The block period is 32k.' ;
                    }

                    enum 64k {
                      value 2 ;
                      description 'The block period is 64k.' ;
                    }

                    enum 512k {
                      value 4 ;
                      description 'The block period is 512k.' ;
                    }

                    enum auto {
                      value 6 ;
                      description 'The block period is auto.' ;
                    }

                  }

                  default 16k ;
                }

                leaf bip-check {
                  description 'Include or exclude OAM block in BIP check (default:include).' ;
                  type enumeration {
                    enum include {
                      value 1 ;
                      description 'Include OAM in BIP check.' ;
                    }

                    enum exclude {
                      value 0 ;
                      description 'Exclude OAM in BIP check.' ;
                    }

                  }

                  default include ;
                }

                leaf circle-sequence {
                  description 'The switch for turning on or off circle sequence function in the base block(default:enable).' ;
                  type enumeration {
                    enum enable {
                      value 1 ;
                      description 'Enable the function of circle sequence in the base code block' ;
                    }

                    enum disable {
                      value 0 ;
                      description 'Disable the function of circle sequence in the base code block' ;
                    }

                  }

                  default enable ;
                }

                leaf sequence-number {
                  if-feature sequence-number ;

                  description 'The fixed sequence number of base block that ranging from 0 to 15(default:0).' ;
                  type uint8 {
                    range 0..15 {
                      description 'The fixed sequence number of base block ranging from 0 to 15(default:0)' ;
                    }

                  }

                  default 0 ;
                }

                leaf cc-bip {
                  if-feature cc-bip-status ;

                  description 'The switch for turning on or off the CC and BIP function(default:enable).' ;
                  type enumeration {
                    enum disable {
                      value 0 ;
                      description 'Disable the CC and BIP function(default:enable).' ;
                    }

                    enum enable {
                      value 1 ;
                      description 'Enable the CC and BIP function(default:enable).' ;
                    }

                  }

                  default enable ;
                  ncd:revise-date 2019-01-17 ;
                }

                leaf loss-mantissa {
                  description 'The mantissa of the packet loss threshold(default:1).' ;
                  type uint8 {
                    range 1..9 {
                      description 'This parameter ranges from 1 to 9(default:1).' ;
                    }

                  }

                  default 1 ;
                  ncd:revise-date 2019-02-20 ;
                }

                leaf loss-threshold {
                  description 'The exponent of the packet loss threshold(default:9).' ;
                  type uint8 {
                    range 8..12 {
                      description 'This parameter ranges from 8 to 12(default:9).' ;
                    }

                  }

                  default 9 ;
                  ncd:revise-date 2019-02-20 ;
                }

                leaf exc-mantissa {
                  description 'The mantissa of the packet EXC threshold(default:1).' ;
                  type uint8 {
                    range 1..9 {
                      description 'This parameter ranges from 1 to 9(default:1).' ;
                    }

                  }

                  default 1 ;
                  ncd:revise-date 2019-02-20 ;
                }

                leaf exc-threshold {
                  description 'The exponent of the packet EXC threshold(default:7).' ;
                  type uint8 {
                    range 6..8 {
                      description 'This parameter ranges from 6 to 8(default:7).' ;
                    }

                  }

                  default 7 ;
                  ncd:revise-date 2019-02-20 ;
                }

                leaf subclient-period {
                  if-feature subclient_period ;

                  description 'The subclient OAM period.' ;
                  type enumeration {
                    enum auto {
                      value 1 ;
                      description 'The subclient OAM period is auto.' ;
                    }

                  }

                  default auto ;
                  ncd:revise-date 2020-08-25 ;
                }

                leaf sd {
                  if-feature spn ;

                  description 'SD function opening mark' ;
                  type enumeration {
                    enum disable {
                      value 0 ;
                      description 'disable sd' ;
                    }

                    enum enable {
                      value 1 ;
                      description 'enable sd' ;
                    }

                  }

                  default disable ;
                  ncd:revise-date 2023-02-01 ;
                }

                leaf sf {
                  if-feature spn ;

                  description 'SF function opening mark' ;
                  type enumeration {
                    enum disable {
                      value 0 ;
                      description 'disable sf' ;
                    }

                    enum enable {
                      value 1 ;
                      description 'enable sf' ;
                    }

                  }

                  default disable ;
                  ncd:revise-date 2023-02-01 ;
                }

                leaf sd-propagate {
                  if-feature spn ;

                  description 'The switch for turning on or off the SD propagate function(default:disable).' ;
                  type enumeration {
                    enum disable {
                      value 0 ;
                      description 'Disable the SD propagate function(default:disable).' ;
                    }

                    enum enable {
                      value 1 ;
                      description 'Enable the SD propagate function(default:disable).' ;
                    }

                  }

                  default disable ;
                  ncd:revise-date 2023-02-01 ;
                }

              }

            }

          }

        }

      }

    }

  }

  container operation {
    config false ;
    container flexe-oam {
      container dms {
        list dm {
          description 'On demand dm function.' ;
          key index ;
          leaf index {
            description 'OAM index.' ;
            type uint16 {
              range 1..65535 {
                description 'This oam index ranges from 1 to 65535.' ;
              }

            }

            mandatory true ;
          }

          choice dm-switch {
            description 'The switch for enable or disable the DM function(default:disable).' ;
            case enable {
              description 'Turn on the DM function.' ;
              leaf enable {
                description 'Turn on the DM function.' ;
                type empty ;

              }

              leaf type {
                description 'The type of DM function.' ;
                type enumeration {
                  enum one-way {
                    value 1 ;
                    description 'One-way on demand dm type' ;
                  }

                  enum two-way {
                    value 2 ;
                    description 'Twao-way on demand dm type' ;
                  }

                }

                mandatory true ;
              }

              leaf period {
                description 'The sending period of on-demand DM packets(default:10s).' ;
                type enumeration {
                  enum 1s {
                    value 1 ;
                    description 'Packet send period:1s(default:10s)' ;
                  }

                  enum 10s {
                    value 2 ;
                    description 'Packet send period:10s(default:10s)' ;
                  }

                  enum 1min {
                    value 3 ;
                    description 'Packet send period:1min(default:10s)' ;
                  }

                }

                default 10s ;
              }

              leaf send-time {
                description 'Duration time of on-demand DM(default:600s).' ;
                type uint32 {
                  range 300..86400 {
                    description 'This parameter ranges from 300s to 86400s(default:600s).' ;
                  }

                }

                units s ;
                default 600 ;
              }

              leaf report-interval {
                description "The report interval of the DM test result,the default value is 0s which means don't upsend results until the test stopped." ;
                type uint32 {
                  range 0..86400 {
                    description 'This parameter ranges from 0 to 86400(default:0).' ;
                  }

                }

                units s ;
                default 0 ;
              }

              leaf serial-number {
                description 'The serial number of DM.' ;
                type ncd:terminal-based-uint32 ;

              }

            }

            case disable {
              description 'Turn off the DM function.' ;
              leaf disable {
                description 'Turn off the DM function.' ;
                type empty ;

              }

            }

          }

        }

      }

    }

  }

  container state {
    config false ;
    description 'FlexE OAM state model info' ;
    container flexe-oam {
      description 'FlexE OAM state info' ;
      container detect-alarm-infos {
        if-feature spn ;

        description 'Detect Alarm info' ;
        list detect-alarm-info {
          description 'Detect Alarm info' ;
          key meg-index ;
          leaf meg-index {
            description 'Meg index,ranges from 1 to 65535.' ;
            type uint16 ;

          }

          leaf detect-state {
            description 'The OAM detect state(default:INIT).' ;
            type enumeration {
              enum INIT {
                value 0 ;
                description 'The OAM detect state.' ;
              }

              enum UP {
                value 1 ;
                description 'The OAM detect state.' ;
              }

              enum DOWN {
                value 2 ;
                description 'The OAM detect state.' ;
              }

            }

            default INIT ;
          }

          leaf alarm-indicate {
            description 'The OAM alarm(default:no_alarm).' ;
            type enumeration {
              enum no_alarm {
                value 0 ;
                description 'The OAM alarm.' ;
              }

              enum CS_LF {
                value 1 ;
                description 'The OAM alarm.' ;
              }

              enum CS_RF {
                value 2 ;
                description 'The OAM alarm.' ;
              }

              enum SF {
                value 3 ;
                description 'The OAM alarm.' ;
              }

              enum SD {
                value 4 ;
                description 'The OAM alarm.' ;
              }

              enum API_Mismatch {
                value 5 ;
                description 'The OAM alarm.' ;
              }

              enum CS_Mismatch {
                value 6 ;
                description 'The OAM alarm.' ;
              }

            }

            default no_alarm ;
          }

          leaf cs-type {
            description 'The test type of CS function(default:unequipped).' ;
            type enumeration {
              enum unequipped {
                value 1 ;
                description 'The CS type is signal unequipped(default:unequipped).' ;
              }

              enum eth {
                value 2 ;
                description 'The CS type is ETH service(default:unequipped).' ;
              }

              enum sdh {
                value 3 ;
                description 'The CS type is SDH service(default:unequipped).' ;
              }

              enum fc {
                value 4 ;
                description 'The CS type is FC service(default:unequipped).' ;
              }

              enum cpri {
                value 5 ;
                description 'The CS type is CPRI service(default:unequipped).' ;
              }

            }

            default unequipped ;
          }

        }

      }

    }

    ncd:revise-date 2023-02-01 ;
  }

  notification dm-event {
    list dm-result {
      description 'The test result is reported periodically according to the configured reporting interval in the DM test.' ;
      key index ;
      leaf index {
        config false ;
        description 'OAM index.' ;
        type uint16 {
          range 1..65535 {
            description 'This oam index ranges from 1 to 65535.' ;
          }

        }

        mandatory true ;
      }

      leaf delay {
        description 'The delay data of DM test(units: ns).' ;
        type uint64 ;

        units ns ;
      }

      leaf delay-variation {
        description 'The delay variation of DM test(units: ns).' ;
        type uint64 ;

        units ns ;
      }

      leaf average-delay {
        description 'The average delay of DM test(units: ns).' ;
        type uint64 ;

        units ns ;
      }

      leaf average-delay-variation {
        description 'The average delay variation of DM test(units: ns).' ;
        type uint64 ;

        units ns ;
      }

      leaf min-delay {
        description 'The minimal delay of DM test(units: ns).' ;
        type uint64 ;

        units ns ;
      }

      leaf max-delay {
        description 'The maximal delay of DM test(units: ns).' ;
        type uint64 ;

        units ns ;
      }

      leaf min-delay-variation {
        description 'The manimal delay of DM test(units: ns).' ;
        type uint64 ;

        units ns ;
      }

      leaf max-delay-variation {
        description 'The maximal delay of DM test(units: ns).' ;
        type uint64 ;

        units ns ;
      }

    }

  }

}
