module zxr10-interfaces-dev-upn {
  namespace 'http://www.zte.com.cn/zxr10/netconf/schema/rosng/interfaces-dev-upn'
            ;
  prefix interfaces-dev-upn ;
  import zxr10-interfaces {
    prefix interface ;
    revision-date 2015-10-16 ;
  }
  import zxr10-netconf-defs {
    prefix ncd ;
    revision-date 2014-06-24 ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The interfaces netconf file in 15k.'
              ;
  revision 2022-11-18 {
    description 'Delete the leaf /configuration/interfaces/interface-configurat'
              + 'ion/interface/description;'
                ;
  }
  revision 2021-02-23 {
    description 'Add the enum type value per-designation of the leaf /configura'
              + 'tion/interfaces/interface-configuration/interface/load-sharing'
              + '/policy.'
                ;
  }
  revision 2017-12-21 {
    description 'Initial version.'
                ;
  }
  deviation '/interface:configuration/interface:interfaces/interface:interface-'
          + 'configuration/interface:interface/interface:track-trigger/interfac'
          + 'e:track-status'
            {
    description 'Block,shutdown or reverse the interface.'
                ;
    deviate replace {
      type enumeration {
        enum block {
          value 1 ;
          description 'Block interface'
                      ;
        }
        enum shutdown {
          value 2 ;
          description 'Shutdown interface'
                      ;
        }
        enum reverse {
          value 3 ;
          description 'Reverse interface'
                      ;
        }
      }
    }
  }
  deviation '/interface:configuration/interface:interfaces/interface:interface-'
          + 'configuration/interface:interface/interface:load-sharing/interface'
          + ':policy'
            {
    description 'The load sharing policy of the interface'+"\n"
              + ''+"\n"
              + 'Only particular interfaces support load sharing. For interface'
              + 's that do not support load sharing, this node is not present.'
                ;
    deviate replace {
      type enumeration {
        enum per-destination {
          value 0 ;
          description 'The device distributes the packets based on the destinat'
                    + 'ion address.'
                      ;
        }
        enum per-packet {
          value 1 ;
          description 'The device distributes the packets based on the packets.'
                      ;
        }
        enum per-designation {
          value 3 ;
          description 'The device distributes the packets based on the designat'
                    + 'ion.'
                      ;
        }
      }
    }
  }
}
