module zxr10-ospfv3 {
  namespace "http://www.zte.com.cn/zxr10/netconf/schema/rosng/ospfv3" ;
  prefix ospfv3 ;
  yang-version 1 ;
  import zxr10-netconf-defs {
    prefix ncd ;
    revision-date 2013-11-22 ;
  }

  organization "ZTE Corporation" ;
  contact "ZTE Corporation
  Nanjing Institute of ZTE Corporation
  No.68 Zijinghua Rd. Yuhuatai District, Nanjing, China
  Tel: +86-25-52870000" ;
  description 'The netconf module of describing OSPFv3.' ;
  revision 2025-08-18 {
    description 'Modify the misspelled descriptions.' ;
  }

  revision 2025-07-21 {
    description 'modify a leaf name:
/ospfv3:notification/ospfv3:interfaces/ospfv3:virtual-links/ospfv3:virtual-link/ospfv3:process-id' ;
  }

  revision 2025-06-30 {
    description 'Add a container:
/ospfv3:configuration/ospfv3:ospfv3/ospfv3:global
Add a leaf:
/ospfv3:configuration/ospfv3:ospfv3/ospfv3:global/ospfv3:memory-overload-protection' ;
  }

  revision 2025-05-14 {
    description 'add a feature:
srv6-adjacency-set.include PTN.6100, PTN.61-SSP, PTN.61V5_1, PC.MSE.
this leaf add srv6-adjacency-set feature:
/ospfv3:configuration/ospfv3:ospfv3/ospfv3:processes/ospfv3:process/ospfv3:segment-routing/ospfv3:srv6/ospfv3:locators/ospfv3:locator/ospfv3:adjacency-set' ;
  }

  revision 2025-04-22 {
    description 'Expend enumeration value:
/ospfv3:configuration/ospfv3:ospfv3/ospfv3:processes/ospfv3:process/ospfv3:redistribute/ospfv3:redistribute-other/ospfv3:redistribute-other/ospfv3:protocol' ;
  }

  revision 2025-03-05 {
    description 'Add new leaf:
/ospfv3:configuration/ospfv3:ospfv3/ospfv3:processes/ospfv3:process/ospfv3:segment-routing/ospfv3:srv6/ospfv3:locators/ospfv3:locator/ospfv3:adjacency-set' ;
  }

  revision 2025-02-05 {
    description 'Add a container:
/ospfv3:notification/ospfv3:sample
Add a container:
/ospfv3:notification/ospfv3:sample/ospfv3:neighbors
Add a container:
/ospfv3:notification/ospfv3:sample/ospfv3:neighbors/ospfv3:normal-nbrs
Add a list:
/ospfv3:notification/ospfv3:sample/ospfv3:neighbors/ospfv3:normal-nbrs/ospfv3:normal-nbr
Add a leaf:
/ospfv3:notification/ospfv3:sample/ospfv3:neighbors/ospfv3:normal-nbrs/ospfv3:normal-nbr/ospfv3:proc-id
Add a leaf:
/ospfv3:notification/ospfv3:sample/ospfv3:neighbors/ospfv3:normal-nbrs/ospfv3:normal-nbr/ospfv3:area-ip
Add a leaf:
/ospfv3:notification/ospfv3:sample/ospfv3:neighbors/ospfv3:normal-nbrs/ospfv3:normal-nbr/ospfv3:if-name
Add a leaf:
/ospfv3:notification/ospfv3:sample/ospfv3:neighbors/ospfv3:normal-nbrs/ospfv3:normal-nbr/ospfv3:nbr-id
Add a leaf:
/ospfv3:notification/ospfv3:sample/ospfv3:neighbors/ospfv3:normal-nbrs/ospfv3:normal-nbr/ospfv3:nbr-state
Add a container:
/ospfv3:notification/ospfv3:sample/ospfv3:nbr-cnts
Add a list:
/ospfv3:notification/ospfv3:sample/ospfv3:nbr-cnts/ospfv3:nbr-cnt
Add a leaf:
/ospfv3:notification/ospfv3:sample/ospfv3:nbr-cnts/ospfv3:nbr-cnt/ospfv3:proc-id
Add a leaf:
/ospfv3:notification/ospfv3:sample/ospfv3:nbr-cnts/ospfv3:nbr-cnt/ospfv3:total-nbr-cnt
Add a leaf:
/ospfv3:notification/ospfv3:sample/ospfv3:nbr-cnts/ospfv3:nbr-cnt/ospfv3:full-nbr-cnt' ;
  }

  revision 2024-07-15 {
    description 'Add a container:
/ospfv3:configuration/ospfv3:ospfv3/ospfv3:processes/ospfv3:process/ospfv3:summary-prefixs/ospfv3:summary-prefix/ospfv3:tag
Add two leafs:
/ospfv3:configuration/ospfv3:ospfv3/ospfv3:processes/ospfv3:process/ospfv3:summary-prefixs/ospfv3:summary-prefix/ospfv3:tag/ospfv3:tag
/ospfv3:configuration/ospfv3:ospfv3/ospfv3:processes/ospfv3:process/ospfv3:summary-prefixs/ospfv3:summary-prefix/ospfv3:tag/ospfv3:tag-flag' ;
  }

  revision 2024-05-22 {
    description 'Add new leaf:
/ospfv3:configuration/ospfv3:ospfv3/ospfv3:processes/ospfv3:process/ospfv3:segment-routing/ospfv3:srv6/ospfv3:locator-fixed-length/ospfv3:capability' ;
  }

  revision 2024-03-06 {
    description 'Add new enumeration value:
/ospfv3:configuration/ospfv3:ospfv3/ospfv3:processes/ospfv3:process/ospfv3:domain-ids/ospfv3:domain-id/ospfv3:type
Add new container:
/ospfv3:configuration/ospfv3:ospfv3/ospfv3:processes/ospfv3:process/ospfv3:vpn-instance-capability
Add new leaf:
/ospfv3:configuration/ospfv3:ospfv3/ospfv3:processes/ospfv3:process/ospfv3:vpn-instance-capability/ospfv3:abr-capability' ;
  }

  revision 2024-01-10 {
    description 'add list:
/ospfv3:configuration/ospfv3:ospfv3/ospfv3:processes/ospfv3:process/ospfv3:segment-routing/ospfv3:srv6/ospfv3:locators/ospfv3:locator/ospfv3:end-x-sids/ospfv3:end-x-sid-compress
add leafs:
/ospfv3:configuration/ospfv3:ospfv3/ospfv3:processes/ospfv3:process/ospfv3:segment-routing/ospfv3:srv6/ospfv3:compress
/ospfv3:configuration/ospfv3:ospfv3/ospfv3:processes/ospfv3:process/ospfv3:segment-routing/ospfv3:srv6/ospfv3:locators/ospfv3:locator/ospfv3:end-x-sids/ospfv3:end-x-sid-compress/ospfv3:func-code
/ospfv3:configuration/ospfv3:ospfv3/ospfv3:processes/ospfv3:process/ospfv3:segment-routing/ospfv3:srv6/ospfv3:locators/ospfv3:locator/ospfv3:end-x-sids/ospfv3:end-x-sid-compress/ospfv3:interface-name
/ospfv3:configuration/ospfv3:ospfv3/ospfv3:processes/ospfv3:process/ospfv3:segment-routing/ospfv3:srv6/ospfv3:locators/ospfv3:locator/ospfv3:end-x-sids/ospfv3:end-x-sid-compress/ospfv3:neighbor-id
/ospfv3:configuration/ospfv3:ospfv3/ospfv3:processes/ospfv3:process/ospfv3:segment-routing/ospfv3:srv6/ospfv3:locators/ospfv3:locator/ospfv3:end-x-sids/ospfv3:end-x-sid-compress/ospfv3:psp
/ospfv3:configuration/ospfv3:ospfv3/ospfv3:processes/ospfv3:process/ospfv3:segment-routing/ospfv3:srv6/ospfv3:locators/ospfv3:locator/ospfv3:end-x-sids/ospfv3:end-x-sid-compress/ospfv3:usp
/ospfv3:configuration/ospfv3:ospfv3/ospfv3:processes/ospfv3:process/ospfv3:segment-routing/ospfv3:srv6/ospfv3:locators/ospfv3:locator/ospfv3:end-x-sids/ospfv3:end-x-sid-compress/ospfv3:usd
/ospfv3:configuration/ospfv3:ospfv3/ospfv3:processes/ospfv3:process/ospfv3:segment-routing/ospfv3:srv6/ospfv3:locators/ospfv3:locator/ospfv3:end-x-sids/ospfv3:end-x-sid-compress/ospfv3:encap-type
add a list:
/ospfv3:configuration/ospfv3:ospfv3/ospfv3:processes/ospfv3:process/ospfv3:segment-routing/ospfv3:srv6/ospfv3:locators/ospfv3:locator/ospfv3:end-x-multi-sid-autos/ospfv3:end-x-multi-sid-auto-compress
add leafs:
/ospfv3:configuration/ospfv3:ospfv3/ospfv3:processes/ospfv3:process/ospfv3:segment-routing/ospfv3:srv6/ospfv3:locators/ospfv3:locator/ospfv3:end-x-multi-sid-autos/ospfv3:end-x-multi-sid-auto-compress/ospfv3:encap-type
/ospfv3:configuration/ospfv3:ospfv3/ospfv3:processes/ospfv3:process/ospfv3:segment-routing/ospfv3:srv6/ospfv3:locators/ospfv3:locator/ospfv3:end-x-multi-sid-autos/ospfv3:end-x-multi-sid-auto-compress/ospfv3:psp
/ospfv3:configuration/ospfv3:ospfv3/ospfv3:processes/ospfv3:process/ospfv3:segment-routing/ospfv3:srv6/ospfv3:locators/ospfv3:locator/ospfv3:end-x-multi-sid-autos/ospfv3:end-x-multi-sid-auto-compress/ospfv3:usp
/ospfv3:configuration/ospfv3:ospfv3/ospfv3:processes/ospfv3:process/ospfv3:segment-routing/ospfv3:srv6/ospfv3:locators/ospfv3:locator/ospfv3:end-x-multi-sid-autos/ospfv3:end-x-multi-sid-auto-compress/ospfv3:usd
add a list:
/ospfv3:configuration/ospfv3:ospfv3/ospfv3:processes/ospfv3:process/ospfv3:segment-routing/ospfv3:srv6/ospfv3:locators/ospfv3:locator/ospfv3:end-multi-sid-autos/ospfv3:end-multi-sid-auto-compress
add leaves:
/ospfv3:configuration/ospfv3:ospfv3/ospfv3:processes/ospfv3:process/ospfv3:segment-routing/ospfv3:srv6/ospfv3:locators/ospfv3:locator/ospfv3:end-multi-sid-autos/ospfv3:end-multi-sid-auto-compress/ospfv3:psp
/ospfv3:configuration/ospfv3:ospfv3/ospfv3:processes/ospfv3:process/ospfv3:segment-routing/ospfv3:srv6/ospfv3:locators/ospfv3:locator/ospfv3:end-multi-sid-autos/ospfv3:end-multi-sid-auto-compress/ospfv3:usp
/ospfv3:configuration/ospfv3:ospfv3/ospfv3:processes/ospfv3:process/ospfv3:segment-routing/ospfv3:srv6/ospfv3:locators/ospfv3:locator/ospfv3:end-multi-sid-autos/ospfv3:end-multi-sid-auto-compress/ospfv3:usd
/ospfv3:configuration/ospfv3:ospfv3/ospfv3:processes/ospfv3:process/ospfv3:segment-routing/ospfv3:srv6/ospfv3:locators/ospfv3:locator/ospfv3:end-multi-sid-autos/ospfv3:end-multi-sid-auto-compress/ospfv3:encap-type
add a list:
/ospfv3:configuration/ospfv3:ospfv3/ospfv3:processes/ospfv3:process/ospfv3:segment-routing/ospfv3:srv6/ospfv3:locators/ospfv3:locator/ospfv3:end-sids/ospfv3:end-sid-compress
add leaves:
/ospfv3:configuration/ospfv3:ospfv3/ospfv3:processes/ospfv3:process/ospfv3:segment-routing/ospfv3:srv6/ospfv3:locators/ospfv3:locator/ospfv3:end-sids/ospfv3:end-sid-compress/ospfv3:func-code
/ospfv3:configuration/ospfv3:ospfv3/ospfv3:processes/ospfv3:process/ospfv3:segment-routing/ospfv3:srv6/ospfv3:locators/ospfv3:locator/ospfv3:end-sids/ospfv3:end-sid-compress/ospfv3:psp
/ospfv3:configuration/ospfv3:ospfv3/ospfv3:processes/ospfv3:process/ospfv3:segment-routing/ospfv3:srv6/ospfv3:locators/ospfv3:locator/ospfv3:end-sids/ospfv3:end-sid-compress/ospfv3:usp
/ospfv3:configuration/ospfv3:ospfv3/ospfv3:processes/ospfv3:process/ospfv3:segment-routing/ospfv3:srv6/ospfv3:locators/ospfv3:locator/ospfv3:end-sids/ospfv3:end-sid-compress/ospfv3:usd
/ospfv3:configuration/ospfv3:ospfv3/ospfv3:processes/ospfv3:process/ospfv3:segment-routing/ospfv3:srv6/ospfv3:locators/ospfv3:locator/ospfv3:end-sids/ospfv3:end-sid-compress/ospfv3:encap-type' ;
  }

  revision 2024-01-03 {
    description 'Add a default Value PerfID and modify a leaf description:
/ospfv3:configuration/ospfv3:ospfv3/ospfv3:processes/ospfv3:process/ospfv3:maximum-paths</description>' ;
  }

  revision 2023-09-22 {
    description 'Modify the misspelled descriptions.' ;
  }

  revision 2023-05-29 {
    description 'Add new enumeration value:
/ospfv3:state/ospfv3:ospfv3/ospfv3:interfaces/ospfv3:normal-interfaces/ospfv3:normal-interface/ospfv3:ldp-link-state' ;
  }

  revision 2023-05-17 {
    description 'Add a container:
/ospfv3:notification/ospfv3:nbr-cnts
Add a list:
/ospfv3:notification/ospfv3:nbr-cnts/ospfv3:nbr-cnt
Add a leaf:
/ospfv3:notification/ospfv3:nbr-cnts/ospfv3:nbr-cnt/ospfv3:proc-id
Add a leaf:
/ospfv3:notification/ospfv3:nbr-cnts/ospfv3:nbr-cnt/ospfv3:total-nbr-cnt
Add a leaf:
/ospfv3:notification/ospfv3:nbr-cnts/ospfv3:nbr-cnt/ospfv3:full-nbr-cnt' ;
  }

  revision 2023-05-08 {
    description 'modify leafs:
/ospfv3:configuration/ospfv3:ospfv3/ospfv3:processes/ospfv3:process/ospfv3:segment-routing/ospfv3:srv6/ospfv3:locators/ospfv3:locator/ospfv3:end-sids/ospfv3:end-sid/ospfv3:psp
/ospfv3:configuration/ospfv3:ospfv3/ospfv3:processes/ospfv3:process/ospfv3:segment-routing/ospfv3:srv6/ospfv3:locators/ospfv3:locator/ospfv3:end-sids/ospfv3:end-sid/ospfv3:usp
/ospfv3:configuration/ospfv3:ospfv3/ospfv3:processes/ospfv3:process/ospfv3:segment-routing/ospfv3:srv6/ospfv3:locators/ospfv3:locator/ospfv3:end-x-sids/ospfv3:end-x-sid/ospfv3:psp
/ospfv3:configuration/ospfv3:ospfv3/ospfv3:processes/ospfv3:process/ospfv3:segment-routing/ospfv3:srv6/ospfv3:locators/ospfv3:locator/ospfv3:end-x-sids/ospfv3:end-x-sid/ospfv3:usp' ;
  }

  revision 2023-05-06 {
    description 'modify a leaf
/ospfv3:configuration/ospfv3:ospfv3/ospfv3:processes/ospfv3:process/ospfv3:maximum-paths' ;
  }

  revision 2023-04-07 {
    description 'Add a leaf:
/ospfv3:configuration/ospfv3:ospfv3/ospfv3:processes/ospfv3:process/ospfv3:areas/ospfv3:area/ospfv3:interfaces/ospfv3:interface/ospfv3:link-sd/ospfv3:capability' ;
  }

  revision 2023-03-27 {
    description 'Add a leaf:
/ospfv3:configuration/ospfv3:ospfv3/ospfv3:processes/ospfv3:process/ospfv3:rfc1583-value' ;
  }

  revision 2023-03-24 {
    description 'Add some containers:
/ospfv3:configuration/ospfv3:ospfv3/ospfv3:processes/ospfv3:process/ospfv3:segment-routing/ospfv3:srv6/ospfv3:locators/ospfv3:locator/ospfv3:end-x-multi-sid-autos
/ospfv3:configuration/ospfv3:ospfv3/ospfv3:processes/ospfv3:process/ospfv3:segment-routing/ospfv3:srv6/ospfv3:locators/ospfv3:locator/ospfv3:end-multi-sid-autos
Add some lists:
/ospfv3:configuration/ospfv3:ospfv3/ospfv3:processes/ospfv3:process/ospfv3:segment-routing/ospfv3:srv6/ospfv3:locators/ospfv3:locator/ospfv3:end-x-multi-sid-autos/ospfv3:end-x-multi-sid-auto
/ospfv3:configuration/ospfv3:ospfv3/ospfv3:processes/ospfv3:process/ospfv3:segment-routing/ospfv3:srv6/ospfv3:locators/ospfv3:locator/ospfv3:end-multi-sid-autos/ospfv3:end-multi-sid-auto
Add some leafs:
/ospfv3:configuration/ospfv3:ospfv3/ospfv3:processes/ospfv3:process/ospfv3:segment-routing/ospfv3:srv6/ospfv3:locators/ospfv3:locator/ospfv3:end-sids/ospfv3:end-sid/ospfv3:usd
/ospfv3:configuration/ospfv3:ospfv3/ospfv3:processes/ospfv3:process/ospfv3:segment-routing/ospfv3:srv6/ospfv3:locators/ospfv3:locator/ospfv3:end-sid-auto/ospfv3:end-sid-auto/ospfv3:usd
/ospfv3:configuration/ospfv3:ospfv3/ospfv3:processes/ospfv3:process/ospfv3:segment-routing/ospfv3:srv6/ospfv3:locators/ospfv3:locator/ospfv3:end-x-sids/ospfv3:end-x-sid/ospfv3:usd
/ospfv3:configuration/ospfv3:ospfv3/ospfv3:processes/ospfv3:process/ospfv3:segment-routing/ospfv3:srv6/ospfv3:locators/ospfv3:locator/ospfv3:end-x-sid-auto/ospfv3:end-x-sid-auto/ospfv3:usd
/ospfv3:configuration/ospfv3:ospfv3/ospfv3:processes/ospfv3:process/ospfv3:segment-routing/ospfv3:srv6/ospfv3:locators/ospfv3:locator/ospfv3:end-x-multi-sid-autos/ospfv3:end-x-multi-sid-auto/ospfv3:psp
/ospfv3:configuration/ospfv3:ospfv3/ospfv3:processes/ospfv3:process/ospfv3:segment-routing/ospfv3:srv6/ospfv3:locators/ospfv3:locator/ospfv3:end-x-multi-sid-autos/ospfv3:end-x-multi-sid-auto/ospfv3:usp
/ospfv3:configuration/ospfv3:ospfv3/ospfv3:processes/ospfv3:process/ospfv3:segment-routing/ospfv3:srv6/ospfv3:locators/ospfv3:locator/ospfv3:end-x-multi-sid-autos/ospfv3:end-x-multi-sid-auto/ospfv3:usd
/ospfv3:configuration/ospfv3:ospfv3/ospfv3:processes/ospfv3:process/ospfv3:segment-routing/ospfv3:srv6/ospfv3:locators/ospfv3:locator/ospfv3:end-multi-sid-autos/ospfv3:end-multi-sid-auto/ospfv3:psp
/ospfv3:configuration/ospfv3:ospfv3/ospfv3:processes/ospfv3:process/ospfv3:segment-routing/ospfv3:srv6/ospfv3:locators/ospfv3:locator/ospfv3:end-multi-sid-autos/ospfv3:end-multi-sid-auto/ospfv3:usp
/ospfv3:configuration/ospfv3:ospfv3/ospfv3:processes/ospfv3:process/ospfv3:segment-routing/ospfv3:srv6/ospfv3:locators/ospfv3:locator/ospfv3:end-multi-sid-autos/ospfv3:end-multi-sid-auto/ospfv3:usd' ;
  }

  revision 2023-03-17 {
    description 'Modify a container to presence:
/ospfv3:configuration/ospfv3:ospfv3/ospfv3:processes/ospfv3:process/ospfv3:slice-source-prefix
Add a list:
/ospfv3:configuration/ospfv3:ospfv3/ospfv3:processes/ospfv3:process/ospfv3:slice-source-prefix/ospfv3:slice-source-prefixs' ;
  }

  revision 2023-02-17 {
    description 'Modify project label' ;
  }

  revision 2023-02-03 {
    description 'Add some containers:
/ospfv3:configuration/ospfv3:ospfv3/ospfv3:processes/ospfv3:process/ospfv3:areas/ospfv3:area/ospfv3:interfaces/ospfv3:interface/ospfv3:bfd-flap-detect
/ospfv3:configuration/ospfv3:ospfv3/ospfv3:processes/ospfv3:process/ospfv3:areas/ospfv3:area/ospfv3:interfaces/ospfv3:interface/ospfv3:bfd-flap-detect/ospfv3:detect-parameter
/ospfv3:configuration/ospfv3:ospfv3/ospfv3:processes/ospfv3:process/ospfv3:areas/ospfv3:area/ospfv3:interfaces/ospfv3:interface/ospfv3:lag-flap-detect
/ospfv3:configuration/ospfv3:ospfv3/ospfv3:processes/ospfv3:process/ospfv3:areas/ospfv3:area/ospfv3:interfaces/ospfv3:interface/ospfv3:lag-flap-detect/ospfv3:detect-parameter
Add some choices:
/ospfv3:configuration/ospfv3:ospfv3/ospfv3:processes/ospfv3:process/ospfv3:areas/ospfv3:area/ospfv3:interfaces/ospfv3:interface/ospfv3:bfd-flap-detect/ospfv3:cost
/ospfv3:configuration/ospfv3:ospfv3/ospfv3:processes/ospfv3:process/ospfv3:areas/ospfv3:area/ospfv3:interfaces/ospfv3:interface/ospfv3:lag-flap-detect/ospfv3:cost
Add some cases:
/ospfv3:configuration/ospfv3:ospfv3/ospfv3:processes/ospfv3:process/ospfv3:areas/ospfv3:area/ospfv3:interfaces/ospfv3:interface/ospfv3:bfd-flap-detect/ospfv3:cost/ospfv3:increase-value
/ospfv3:configuration/ospfv3:ospfv3/ospfv3:processes/ospfv3:process/ospfv3:areas/ospfv3:area/ospfv3:interfaces/ospfv3:interface/ospfv3:bfd-flap-detect/ospfv3:cost/ospfv3:maximum
/ospfv3:configuration/ospfv3:ospfv3/ospfv3:processes/ospfv3:process/ospfv3:areas/ospfv3:area/ospfv3:interfaces/ospfv3:interface/ospfv3:lag-flap-detect/ospfv3:cost/ospfv3:increase-value
/ospfv3:configuration/ospfv3:ospfv3/ospfv3:processes/ospfv3:process/ospfv3:areas/ospfv3:area/ospfv3:interfaces/ospfv3:interface/ospfv3:lag-flap-detect/ospfv3:cost/ospfv3:maximum
Add some leafs:
/ospfv3:configuration/ospfv3:ospfv3/ospfv3:processes/ospfv3:process/ospfv3:areas/ospfv3:area/ospfv3:interfaces/ospfv3:interface/ospfv3:bfd-flap-detect/ospfv3:cost/ospfv3:increase-value/ospfv3:increase-value
/ospfv3:configuration/ospfv3:ospfv3/ospfv3:processes/ospfv3:process/ospfv3:areas/ospfv3:area/ospfv3:interfaces/ospfv3:interface/ospfv3:bfd-flap-detect/ospfv3:cost/ospfv3:maximum/ospfv3:maximum
/ospfv3:configuration/ospfv3:ospfv3/ospfv3:processes/ospfv3:process/ospfv3:areas/ospfv3:area/ospfv3:interfaces/ospfv3:interface/ospfv3:lag-flap-detect/ospfv3:cost/ospfv3:increase-value/ospfv3:increase-value
/ospfv3:configuration/ospfv3:ospfv3/ospfv3:processes/ospfv3:process/ospfv3:areas/ospfv3:area/ospfv3:interfaces/ospfv3:interface/ospfv3:lag-flap-detect/ospfv3:cost/ospfv3:maximum/ospfv3:maximum
/ospfv3:configuration/ospfv3:ospfv3/ospfv3:processes/ospfv3:process/ospfv3:areas/ospfv3:area/ospfv3:interfaces/ospfv3:interface/ospfv3:bfd-flap-detect/ospfv3:detect-parameter/ospfv3:detect-interval
/ospfv3:configuration/ospfv3:ospfv3/ospfv3:processes/ospfv3:process/ospfv3:areas/ospfv3:area/ospfv3:interfaces/ospfv3:interface/ospfv3:bfd-flap-detect/ospfv3:detect-parameter/ospfv3:threshold
/ospfv3:configuration/ospfv3:ospfv3/ospfv3:processes/ospfv3:process/ospfv3:areas/ospfv3:area/ospfv3:interfaces/ospfv3:interface/ospfv3:bfd-flap-detect/ospfv3:detect-parameter/ospfv3:resume-interval
/ospfv3:configuration/ospfv3:ospfv3/ospfv3:processes/ospfv3:process/ospfv3:areas/ospfv3:area/ospfv3:interfaces/ospfv3:interface/ospfv3:lag-flap-detect/ospfv3:detect-parameter/ospfv3:detect-interval
/ospfv3:configuration/ospfv3:ospfv3/ospfv3:processes/ospfv3:process/ospfv3:areas/ospfv3:area/ospfv3:interfaces/ospfv3:interface/ospfv3:lag-flap-detect/ospfv3:detect-parameter/ospfv3:threshold
/ospfv3:configuration/ospfv3:ospfv3/ospfv3:processes/ospfv3:process/ospfv3:areas/ospfv3:area/ospfv3:interfaces/ospfv3:interface/ospfv3:lag-flap-detect/ospfv3:detect-parameter/ospfv3:resume-interval' ;
  }

  revision 2023-01-17 {
    description 'Add a leaf:
/ospfv3:configuration/ospfv3:ospfv3/ospfv3:processes/ospfv3:process/ospfv3:areas/ospfv3:area/ospfv3:interfaces/ospfv3:interface/ospfv3:wait-interval' ;
  }

  revision 2023-01-16 {
    description 'Modify some leaves:
/ospfv3:configuration/ospfv3:ospfv3/ospfv3:processes/ospfv3:process/ospfv3:segment-routing/ospfv3:srv6/ospfv3:locators/ospfv3:locator/ospfv3:end-sids/ospfv3:end-sid/ospfv3:psp
/ospfv3:configuration/ospfv3:ospfv3/ospfv3:processes/ospfv3:process/ospfv3:segment-routing/ospfv3:srv6/ospfv3:locators/ospfv3:locator/ospfv3:end-sids/ospfv3:end-sid/ospfv3:usp
/ospfv3:configuration/ospfv3:ospfv3/ospfv3:processes/ospfv3:process/ospfv3:segment-routing/ospfv3:srv6/ospfv3:locators/ospfv3:locator/ospfv3:end-x-sids/ospfv3:end-x-sid/ospfv3:psp
/ospfv3:configuration/ospfv3:ospfv3/ospfv3:processes/ospfv3:process/ospfv3:segment-routing/ospfv3:srv6/ospfv3:locators/ospfv3:locator/ospfv3:end-x-sids/ospfv3:end-x-sid/ospfv3:usp
Modify some containers:
/ospfv3:configuration/ospfv3:ospfv3/ospfv3:processes/ospfv3:process/ospfv3:areas/ospfv3:area/ospfv3:interfaces/ospfv3:interface/ospfv3:link-sd/ospfv3:cost
/ospfv3:configuration/ospfv3:ospfv3/ospfv3:processes/ospfv3:process/ospfv3:microloop-prevention/ospfv3:lfa
Modify some cases:
/ospfv3:configuration/ospfv3:ospfv3/ospfv3:processes/ospfv3:process/ospfv3:areas/ospfv3:area/ospfv3:interfaces/ospfv3:interface/ospfv3:link-sd/ospfv3:cost/ospfv3:cost/ospfv3:maximum
/ospfv3:configuration/ospfv3:ospfv3/ospfv3:processes/ospfv3:process/ospfv3:areas/ospfv3:area/ospfv3:interfaces/ospfv3:interface/ospfv3:link-sd/ospfv3:cost/ospfv3:cost/ospfv3:increase-value
/ospfv3:configuration/ospfv3:ospfv3/ospfv3:processes/ospfv3:process/ospfv3:areas/ospfv3:area/ospfv3:interfaces/ospfv3:interface/ospfv3:ldp-sync/ospfv3:hold-time/ospfv3:ldp-sync-hold-time/ospfv3:infinite
/ospfv3:configuration/ospfv3:ospfv3/ospfv3:processes/ospfv3:process/ospfv3:areas/ospfv3:area/ospfv3:interfaces/ospfv3:interface/ospfv3:ldp-sync/ospfv3:hold-time/ospfv3:ldp-sync-hold-time/ospfv3:hold-time-value
/ospfv3:configuration/ospfv3:ospfv3/ospfv3:processes/ospfv3:process/ospfv3:areas/ospfv3:area/ospfv3:interfaces/ospfv3:interface/ospfv3:adjust-metric/ospfv3:adjust-metric/ospfv3:increase-value
/ospfv3:configuration/ospfv3:ospfv3/ospfv3:processes/ospfv3:process/ospfv3:areas/ospfv3:area/ospfv3:interfaces/ospfv3:interface/ospfv3:adjust-metric/ospfv3:adjust-metric/ospfv3:maximum' ;
  }

  revision 2022-12-21 {
    description 'Add a leaf:
/ospfv3:configuration/ospfv3:ospfv3/ospfv3:processes/ospfv3:process/ospfv3:redistribute/ospfv3:redistribute-other/ospfv3:redistribute-other/ospfv3:asno
Add new enumeration value:
/ospfv3:configuration/ospfv3:ospfv3/ospfv3:processes/ospfv3:process/ospfv3:redistribute/ospfv3:redistribute-other/ospfv3:redistribute-other/ospfv3:protocol' ;
  }

  revision 2022-09-19 {
    description 'Modify a container to presence:
/ospfv3:configuration/ospfv3:ospfv3/ospfv3:processes/ospfv3:process/ospfv3:notify-default-route
Add a leaf:
/ospfv3:configuration/ospfv3:ospfv3/ospfv3:processes/ospfv3:process/ospfv3:notify-default-route/ospfv3:rib-match-prefix-list' ;
  }

  revision 2022-05-10 {
    description 'Modify leaf:
/ospfv3:state/ospfv3:neighbors/ospfv3:normal-neighbors/ospfv3:normal-neighbor/ospfv3:process-id
/ospfv3:state/ospfv3:neighbors/ospfv3:normal-neighbors/ospfv3:normal-neighbor/ospfv3:interface-name' ;
  }

  revision 2022-03-29 {
    description 'Add a containers and a leaf:
/ospfv3:configuration/ospfv3:ospfv3/ospfv3:processes/ospfv3:process/ospfv3:frr/ospfv3:policy
/ospfv3:configuration/ospfv3:ospfv3/ospfv3:processes/ospfv3:process/ospfv3:frr/ospfv3:policy/ospfv3:host-only
/ospfv3:configuration/ospfv3:ospfv3/ospfv3:processes/ospfv3:process/ospfv3:microloop-prevention/ospfv3:policy
/ospfv3:configuration/ospfv3:ospfv3/ospfv3:processes/ospfv3:process/ospfv3:microloop-prevention/ospfv3:policy/ospfv3:host-only' ;
  }

  revision 2022-03-25 {
    description 'Add four containers and four leaf:
/ospfv3:configuration/ospfv3:ospfv3/ospfv3:processes/ospfv3:process/ospfv3:stub-router
/ospfv3:configuration/ospfv3:ospfv3/ospfv3:processes/ospfv3:process/ospfv3:stub-router/ospfv3:intra-area-prefix-lsa
/ospfv3:configuration/ospfv3:ospfv3/ospfv3:processes/ospfv3:process/ospfv3:stub-router/ospfv3:external-lsa
/ospfv3:configuration/ospfv3:ospfv3/ospfv3:processes/ospfv3:process/ospfv3:stub-router/ospfv3:external-lsa/ospfv3:external-lsa-metric
/ospfv3:configuration/ospfv3:ospfv3/ospfv3:processes/ospfv3:process/ospfv3:stub-router/ospfv3:inter-area-prefix-lsa
/ospfv3:configuration/ospfv3:ospfv3/ospfv3:processes/ospfv3:process/ospfv3:stub-router/ospfv3:inter-area-prefix-lsa/ospfv3:inter-area-prefix-lsa-metric
/ospfv3:configuration/ospfv3:ospfv3/ospfv3:processes/ospfv3:process/ospfv3:stub-router/ospfv3:on-startup
/ospfv3:configuration/ospfv3:ospfv3/ospfv3:processes/ospfv3:process/ospfv3:stub-router/ospfv3:on-startup/ospfv3:interval
Add reset value:
/ospfv3:configuration/ospfv3:ospfv3/ospfv3:processes/ospfv3:process/ospfv3:stub-router/ospfv3:intra-area-prefix-lsa' ;
  }

  revision 2022-03-21 {
    description 'Modify leaf:
/ospfv3:state/ospfv3:interfaces/ospfv3:normal-interfaces/ospfv3:normal-interface/ospfv3:interface-id
/ospfv3:state/ospfv3:interfaces/ospfv3:normal-interfaces/ospfv3:normal-interface/ospfv3:instance-id' ;
  }

  revision 2022-03-09 {
    description 'Add a leaf:
/ospfv3:configuration/ospfv3:ospfv3/ospfv3:processes/ospfv3:process/ospfv3:areas/ospfv3:area/ospfv3:interfaces/ospfv3:interface/ospfv3:hello-jitter' ;
  }

  revision 2022-01-11 {
    description 'Add a notification:
/ospfv3:notification
Add a container:
/ospfv3:notification/ospfv3:neighbors
Add a container:
/ospfv3:notification/ospfv3:neighbors/ospfv3:normal-nbrs
Add a list:
/ospfv3:notification/ospfv3:neighbors/ospfv3:normal-nbrs/ospfv3:normal-nbr
Add a leaf:
/ospfv3:notification/ospfv3:neighbors/ospfv3:normal-nbrs/ospfv3:normal-nbr/ospfv3:proc-id
Add a leaf:
/ospfv3:notification/ospfv3:neighbors/ospfv3:normal-nbrs/ospfv3:normal-nbr/ospfv3:area-ip
Add a leaf:
/ospfv3:notification/ospfv3:neighbors/ospfv3:normal-nbrs/ospfv3:normal-nbr/ospfv3:if-name
Add a leaf:
/ospfv3:notification/ospfv3:neighbors/ospfv3:normal-nbrs/ospfv3:normal-nbr/ospfv3:nbr-id
Add a leaf:
/ospfv3:notification/ospfv3:neighbors/ospfv3:normal-nbrs/ospfv3:normal-nbr/ospfv3:nbr-state
Add a container:
/ospfv3:notification/ospfv3:neighbors/ospfv3:virtual-nbrs
Add a list:
/ospfv3:notification/ospfv3:neighbors/ospfv3:virtual-nbrs/ospfv3:virtual-nbr
Add a leaf:
/ospfv3:notification/ospfv3:neighbors/ospfv3:virtual-nbrs/ospfv3:virtual-nbr/ospfv3:proc-id
Add a leaf:
/ospfv3:notification/ospfv3:neighbors/ospfv3:virtual-nbrs/ospfv3:virtual-nbr/ospfv3:transit-area-ip
Add a leaf:
/ospfv3:notification/ospfv3:neighbors/ospfv3:virtual-nbrs/ospfv3:virtual-nbr/ospfv3:nbr-id
Add a leaf:
/ospfv3:notification/ospfv3:neighbors/ospfv3:virtual-nbrs/ospfv3:virtual-nbr/ospfv3:nbr-state
Add a container:
/ospfv3:notification/ospfv3:interfaces
Add a container:
/ospfv3:notification/ospfv3:interfaces/ospfv3:normal-ifs
Add a list:
/ospfv3:notification/ospfv3:interfaces/ospfv3:normal-ifs/ospfv3:normal-if
Add a leaf:
/ospfv3:notification/ospfv3:interfaces/ospfv3:normal-ifs/ospfv3:normal-if/ospfv3:proc-id
Add a leaf:
/ospfv3:notification/ospfv3:interfaces/ospfv3:normal-ifs/ospfv3:normal-if/ospfv3:area-ip
Add a leaf:
/ospfv3:notification/ospfv3:interfaces/ospfv3:normal-ifs/ospfv3:normal-if/ospfv3:if-name
Add a leaf:
/ospfv3:notification/ospfv3:interfaces/ospfv3:normal-ifs/ospfv3:normal-if/ospfv3:if-state
Add a leaf:
/ospfv3:notification/ospfv3:interfaces/ospfv3:normal-ifs/ospfv3:normal-if/ospfv3:event
Add a container:
/ospfv3:notification/ospfv3:interfaces/ospfv3:virtual-links
Add a list:
/ospfv3:notification/ospfv3:interfaces/ospfv3:virtual-links/ospfv3:virtual-link
Add a leaf:
/ospfv3:notification/ospfv3:interfaces/ospfv3:virtual-links/ospfv3:virtual-link/ospfv3:proc-id
Add a leaf:
/ospfv3:notification/ospfv3:interfaces/ospfv3:virtual-links/ospfv3:virtual-link/ospfv3:transit-area-ip
Add a leaf:
/ospfv3:notification/ospfv3:interfaces/ospfv3:virtual-links/ospfv3:virtual-link/ospfv3:nbr-id
Add a leaf:
/ospfv3:notification/ospfv3:interfaces/ospfv3:virtual-links/ospfv3:virtual-link/ospfv3:if-state
Add a leaf:
/ospfv3:notification/ospfv3:interfaces/ospfv3:virtual-links/ospfv3:virtual-link/ospfv3:event
Add a container:
/ospfv3:notification/ospfv3:nbr-flapping
Add a container:
/ospfv3:notification/ospfv3:nbr-flapping/ospfv3:nbrs
Add a list:
/ospfv3:notification/ospfv3:nbr-flapping/ospfv3:nbrs/ospfv3:nbr
Add a leaf:
/ospfv3:notification/ospfv3:nbr-flapping/ospfv3:nbrs/ospfv3:nbr/ospfv3:proc-id
Add a leaf:
/ospfv3:notification/ospfv3:nbr-flapping/ospfv3:nbrs/ospfv3:nbr/ospfv3:area-ip
Add a leaf:
/ospfv3:notification/ospfv3:nbr-flapping/ospfv3:nbrs/ospfv3:nbr/ospfv3:if-name
Add a leaf:
/ospfv3:notification/ospfv3:nbr-flapping/ospfv3:nbrs/ospfv3:nbr/ospfv3:nbr-id
Add a leaf:
/ospfv3:notification/ospfv3:nbr-flapping/ospfv3:nbrs/ospfv3:nbr/ospfv3:flapping-state' ;
  }

  revision 2021-10-11 {
    description 'Add a container:
/ospfv3:configuration/ospfv3:ospfv3/ospfv3:processes/ospfv3:process/ospfv3:areas/ospfv3:area/ospfv3:interfaces/ospfv3:interface/ospfv3:virtual-system

Add a leaf:
/ospfv3:configuration/ospfv3:ospfv3/ospfv3:processes/ospfv3:process/ospfv3:areas/ospfv3:area/ospfv3:interfaces/ospfv3:interface/ospfv3:virtual-system/ospfv3:router-id' ;
  }

  revision 2021-10-09 {
    description 'Add choice node:
/ospfv3:configuration/ospfv3:ospfv3/ospfv3:processes/ospfv3:process/ospfv3:areas/ospfv3:area/ospfv3:authentication
Add choice node:
/ospfv3:configuration/ospfv3:ospfv3/ospfv3:processes/ospfv3:process/ospfv3:areas/ospfv3:area/ospfv3:interfaces/ospfv3:interface/ospfv3:authentication' ;
  }

  revision 2021-08-09 {
    description 'Add container:
/ospfv3:configuration/ospfv3:ospfv3/ospfv3:processes/ospfv3:process/ospfv3:te-link-attribute
/ospfv3:configuration/ospfv3:ospfv3/ospfv3:processes/ospfv3:process/ospfv3:te-link-attribute/ospfv3:sr-policy
Add a leaf:
/ospfv3:configuration/ospfv3:ospfv3/ospfv3:processes/ospfv3:process/ospfv3:te-link-attribute/ospfv3:sr-policy/ospfv3:advertise-capability
Add a leaf:
/ospfv3:configuration/ospfv3:ospfv3/ospfv3:processes/ospfv3:process/ospfv3:te-link-attribute/ospfv3:sr-policy/ospfv3:receive-capability' ;
  }

  revision 2021-08-06 {
    description 'Add a leaf:
/ospfv3:configuration/ospfv3:ospfv3/ospfv3:processes/ospfv3:process/ospfv3:areas/ospfv3:area/ospfv3:interfaces/ospfv3:interface/ospfv3:fast-hello' ;
  }

  revision 2021-06-15 {
    description 'Add a leaf:
/ospfv3:configuration/ospfv3:ospfv3/ospfv3:processes/ospfv3:process/ospfv3:te-link-bandwidth

Add container and leaf:
/ospfv3:configuration/ospfv3:ospfv3/ospfv3:processes/ospfv3:process/ospfv3:areas/ospfv3:area/ospfv3:interfaces/ospfv3:interface/ospfv3:ldp-sync/
/ospfv3:configuration/ospfv3:ospfv3/ospfv3:processes/ospfv3:process/ospfv3:areas/ospfv3:area/ospfv3:interfaces/ospfv3:interface/ospfv3:ldp-sync/ospfv3:hold-time/
/ospfv3:configuration/ospfv3:ospfv3/ospfv3:processes/ospfv3:process/ospfv3:areas/ospfv3:area/ospfv3:interfaces/ospfv3:interface/ospfv3:ldp-sync/ospfv3:hold-time/ospfv3:infinite/
/ospfv3:configuration/ospfv3:ospfv3/ospfv3:processes/ospfv3:process/ospfv3:areas/ospfv3:area/ospfv3:interfaces/ospfv3:interface/ospfv3:ldp-sync/ospfv3:hold-time/ospfv3:hold-time-value/
/ospfv3:configuration/ospfv3:ospfv3/ospfv3:processes/ospfv3:process/ospfv3:areas/ospfv3:area/ospfv3:interfaces/ospfv3:interface/ospfv3:ldp-sync/ospfv3:adjust-metric/
/ospfv3:configuration/ospfv3:ospfv3/ospfv3:processes/ospfv3:process/ospfv3:areas/ospfv3:area/ospfv3:interfaces/ospfv3:interface/ospfv3:ldp-sync/ospfv3:adjust-metric/ospfv3:increase-value/
/ospfv3:configuration/ospfv3:ospfv3/ospfv3:processes/ospfv3:process/ospfv3:areas/ospfv3:area/ospfv3:interfaces/ospfv3:interface/ospfv3:ldp-sync/ospfv3:adjust-metric/ospfv3:maximum/' ;
  }

  revision 2021-05-24 {
    description 'Add a new container:
/ospfv3:configuration/ospfv3:ospfv3/ospfv3:processes/ospfv3:process/ospfv3:hostname
Add a new leaf:
/ospfv3:configuration/ospfv3:ospfv3/ospfv3:processes/ospfv3:process/ospfv3:hostname/ospfv3:dynamic-capability
Add a new leaf:
/ospfv3:configuration/ospfv3:ospfv3/ospfv3:processes/ospfv3:process/ospfv3:hostname/ospfv3:hostname' ;
  }

  revision 2021-04-01 {
    description 'Add a new container:
/ospfv3:configuration/ospfv3:ospfv3/ospfv3:processes/ospfv3:process/ospfv3:frr/ospfv3:multi-home
Add a new leaf:
/ospfv3:configuration/ospfv3:ospfv3/ospfv3:processes/ospfv3:process/ospfv3:frr/ospfv3:multi-home/ospfv3:multi-home' ;
  }

  revision 2021-03-08 {
    description 'Add a new container:
/ospfv3:configuration/ospfv3:ospfv3/ospfv3:processes/ospfv3:process/ospfv3:flex-algorithms
Add a new list:
/ospfv3:configuration/ospfv3:ospfv3/ospfv3:processes/ospfv3:process/ospfv3:flex-algorithms/ospfv3:flex-algorithm
Add a new leaf:
/ospfv3:configuration/ospfv3:ospfv3/ospfv3:processes/ospfv3:process/ospfv3:flex-algorithms/ospfv3:flex-algorithm/ospfv3:number' ;
  }

  revision 2021-02-25 {
    description 'Add leaf:
/ospfv3:configuration/ospfv3:ospfv3/ospfv3:processes/ospfv3:process/ospfv3:areas/ospfv3:area/ospfv3:traffic-eng' ;
  }

  revision 2021-02-10 {
    description 'add new leaf:
/ospfv3:configuration/ospfv3:ospfv3/ospfv3:processes/ospfv3:process/ospfv3:microloop-preventing/ospfv3:lfa/ospfv3:capability
/ospfv3:configuration/ospfv3:ospfv3/ospfv3:processes/ospfv3:process/ospfv3:microloop-preventing/ospfv3:lfa/ospfv3:delay-time' ;
  }

  revision 2021-01-08 {
    description 'Add some containers and leafs:
/ospfv3:configuration/ospfv3:ospfv3/ospfv3:processes/ospfv3:process/ospfv3:segment-routing/ospfv3:srv6/ospfv3:locators/ospfv3:locator/ospfv3:end-sid-auto
/ospfv3:configuration/ospfv3:ospfv3/ospfv3:processes/ospfv3:process/ospfv3:segment-routing/ospfv3:srv6/ospfv3:locators/ospfv3:locator/ospfv3:end-sid-auto/ospfv3:psp
/ospfv3:configuration/ospfv3:ospfv3/ospfv3:processes/ospfv3:process/ospfv3:segment-routing/ospfv3:srv6/ospfv3:locators/ospfv3:locator/ospfv3:end-sid-auto/ospfv3:usp
/ospfv3:configuration/ospfv3:ospfv3/ospfv3:processes/ospfv3:process/ospfv3:segment-routing/ospfv3:srv6/ospfv3:locators/ospfv3:locator/ospfv3:end-x-sid-auto
/ospfv3:configuration/ospfv3:ospfv3/ospfv3:processes/ospfv3:process/ospfv3:segment-routing/ospfv3:srv6/ospfv3:locators/ospfv3:locator/ospfv3:end-x-sid-auto/ospfv3:psp
/ospfv3:configuration/ospfv3:ospfv3/ospfv3:processes/ospfv3:process/ospfv3:segment-routing/ospfv3:srv6/ospfv3:locators/ospfv3:locator/ospfv3:end-x-sid-auto/ospfv3:usp' ;
  }

  revision 2020-10-20 {
    description 'modify leaf:&#xD;
/ospfv3:configuration/ospfv3:ospfv3/ospfv3:processes/ospfv3:process/ospfv3:frr-policy/ospfv3:route-policy/ospfv3:intfs/ospfv3:route-policy-name&#xD;
/ospfv3:configuration/ospfv3:ospfv3/ospfv3:processes/ospfv3:process/ospfv3:distance-policy/ospfv3:policy-name' ;
  }

  revision 2020-09-23 {
    description 'Add some containers,lists and leafs:
/ospfv3:configuration/ospfv3:ospfv3/ospfv3:processes/ospfv3:process/ospfv3:segment-routing/ospfv3:srv6/ospfv3:locators
/ospfv3:configuration/ospfv3:ospfv3/ospfv3:processes/ospfv3:process/ospfv3:segment-routing/ospfv3:srv6/ospfv3:locators/ospfv3:locator
/ospfv3:configuration/ospfv3:ospfv3/ospfv3:processes/ospfv3:process/ospfv3:segment-routing/ospfv3:srv6/ospfv3:locators/ospfv3:locator/ospfv3:locator-name
/ospfv3:configuration/ospfv3:ospfv3/ospfv3:processes/ospfv3:process/ospfv3:segment-routing/ospfv3:srv6/ospfv3:locators/ospfv3:locator/ospfv3:end-sids
/ospfv3:configuration/ospfv3:ospfv3/ospfv3:processes/ospfv3:process/ospfv3:segment-routing/ospfv3:srv6/ospfv3:locators/ospfv3:locator/ospfv3:end-sids/ospfv3:end-sid
/ospfv3:configuration/ospfv3:ospfv3/ospfv3:processes/ospfv3:process/ospfv3:segment-routing/ospfv3:srv6/ospfv3:locators/ospfv3:locator/ospfv3:end-sids/ospfv3:end-sid/ospfv3:func-code
/ospfv3:configuration/ospfv3:ospfv3/ospfv3:processes/ospfv3:process/ospfv3:segment-routing/ospfv3:srv6/ospfv3:locators/ospfv3:locator/ospfv3:end-sids/ospfv3:end-sid/ospfv3:psp
/ospfv3:configuration/ospfv3:ospfv3/ospfv3:processes/ospfv3:process/ospfv3:segment-routing/ospfv3:srv6/ospfv3:locators/ospfv3:locator/ospfv3:end-sids/ospfv3:end-sid/ospfv3:usp
/ospfv3:configuration/ospfv3:ospfv3/ospfv3:processes/ospfv3:process/ospfv3:segment-routing/ospfv3:srv6/ospfv3:locators/ospfv3:locator/ospfv3:end-x-sids
/ospfv3:configuration/ospfv3:ospfv3/ospfv3:processes/ospfv3:process/ospfv3:segment-routing/ospfv3:srv6/ospfv3:locators/ospfv3:locator/ospfv3:end-x-sids/ospfv3:end-x-sid
/ospfv3:configuration/ospfv3:ospfv3/ospfv3:processes/ospfv3:process/ospfv3:segment-routing/ospfv3:srv6/ospfv3:locators/ospfv3:locator/ospfv3:end-x-sids/ospfv3:end-x-sid/ospfv3:func-code
/ospfv3:configuration/ospfv3:ospfv3/ospfv3:processes/ospfv3:process/ospfv3:segment-routing/ospfv3:srv6/ospfv3:locators/ospfv3:locator/ospfv3:end-x-sids/ospfv3:end-x-sid/ospfv3:interface-name
/ospfv3:configuration/ospfv3:ospfv3/ospfv3:processes/ospfv3:process/ospfv3:segment-routing/ospfv3:srv6/ospfv3:locators/ospfv3:locator/ospfv3:end-x-sids/ospfv3:end-x-sid/ospfv3:neighbor-id
/ospfv3:configuration/ospfv3:ospfv3/ospfv3:processes/ospfv3:process/ospfv3:segment-routing/ospfv3:srv6/ospfv3:locators/ospfv3:locator/ospfv3:end-x-sids/ospfv3:end-x-sid/ospfv3:psp
/ospfv3:configuration/ospfv3:ospfv3/ospfv3:processes/ospfv3:process/ospfv3:segment-routing/ospfv3:srv6/ospfv3:locators/ospfv3:locator/ospfv3:end-x-sids/ospfv3:end-x-sid/ospfv3:usp' ;
  }

  revision 2020-09-12 {
    description 'Add a container and leafs:
/ospfv3:configuration/ospfv3:ospfv3/ospfv3:processes/ospfv3:process/ospfv3:areas/ospfv3:area/ospfv3:interfaces/ospfv3:interface/ospfv3:link-sd
/ospfv3:configuration/ospfv3:ospfv3/ospfv3:processes/ospfv3:process/ospfv3:areas/ospfv3:area/ospfv3:interfaces/ospfv3:interface/ospfv3:link-sd/ospfv3:cost
/ospfv3:configuration/ospfv3:ospfv3/ospfv3:processes/ospfv3:process/ospfv3:areas/ospfv3:area/ospfv3:interfaces/ospfv3:interface/ospfv3:link-sd/ospfv3:cost/ospfv3:cost
/ospfv3:configuration/ospfv3:ospfv3/ospfv3:processes/ospfv3:process/ospfv3:areas/ospfv3:area/ospfv3:interfaces/ospfv3:interface/ospfv3:link-sd/ospfv3:cost/ospfv3:cost/ospfv3:maximum
/ospfv3:configuration/ospfv3:ospfv3/ospfv3:processes/ospfv3:process/ospfv3:areas/ospfv3:area/ospfv3:interfaces/ospfv3:interface/ospfv3:link-sd/ospfv3:cost/ospfv3:cost/ospfv3:maximum/ospfv3:maximum
/ospfv3:configuration/ospfv3:ospfv3/ospfv3:processes/ospfv3:process/ospfv3:areas/ospfv3:area/ospfv3:interfaces/ospfv3:interface/ospfv3:link-sd/ospfv3:cost/ospfv3:cost/ospfv3:increase-value
/ospfv3:configuration/ospfv3:ospfv3/ospfv3:processes/ospfv3:process/ospfv3:areas/ospfv3:area/ospfv3:interfaces/ospfv3:interface/ospfv3:link-sd/ospfv3:cost/ospfv3:cost/ospfv3:increase-value/ospfv3:increase-value' ;
  }

  revision 2020-08-20 {
    description 'Add a container and leafs:
/ospfv3:configuration/ospfv3:ospfv3/ospfv3:processes/ospfv3:process/ospfv3:areas/ospfv3:area/ospfv3:multi-area-interfaces
/ospfv3:configuration/ospfv3:ospfv3/ospfv3:processes/ospfv3:process/ospfv3:areas/ospfv3:area/ospfv3:multi-area-interfaces/ospfv3:multi-area-interface/interface-name
/ospfv3:configuration/ospfv3:ospfv3/ospfv3:processes/ospfv3:process/ospfv3:areas/ospfv3:area/ospfv3:multi-area-interfaces/ospfv3:multi-area-interface/hello-interval
/ospfv3:configuration/ospfv3:ospfv3/ospfv3:processes/ospfv3:process/ospfv3:areas/ospfv3:area/ospfv3:multi-area-interfaces/ospfv3:multi-area-interface/dead-interval
/ospfv3:configuration/ospfv3:ospfv3/ospfv3:processes/ospfv3:process/ospfv3:areas/ospfv3:area/ospfv3:multi-area-interfaces/ospfv3:multi-area-interface/cost
/ospfv3:configuration/ospfv3:ospfv3/ospfv3:processes/ospfv3:process/ospfv3:areas/ospfv3:area/ospfv3:multi-area-interfaces/ospfv3:multi-area-interface/mtu-ignore
/ospfv3:configuration/ospfv3:ospfv3/ospfv3:processes/ospfv3:process/ospfv3:areas/ospfv3:area/ospfv3:multi-area-interfaces/ospfv3:multi-area-interface/retransmit-delay
/ospfv3:configuration/ospfv3:ospfv3/ospfv3:processes/ospfv3:process/ospfv3:areas/ospfv3:area/ospfv3:multi-area-interfaces/ospfv3:multi-area-interface/transmit-delay
/ospfv3:configuration/ospfv3:ospfv3/ospfv3:processes/ospfv3:process/ospfv3:areas/ospfv3:area/ospfv3:multi-area-interfaces/ospfv3:multi-area-interface/authentication
/ospfv3:configuration/ospfv3:ospfv3/ospfv3:processes/ospfv3:process/ospfv3:areas/ospfv3:area/ospfv3:multi-area-interfaces/ospfv3:multi-area-interface/authentication/keychain' ;
  }

  revision 2020-07-23 {
    description 'add leaf:/ospfv3:configuration/ospfv3:ospfv3/ospfv3:processes/ospfv3:process/ospfv3:suppress-flapping/ospfv3:adjacency/ospfv3:capability
add container:/ospfv3:configuration/ospfv3:ospfv3/ospfv3:processes/ospfv3:process/ospfv3:areas/ospfv3:area/ospfv3:interfaces/ospfv3:interface/ospfv3:suppress-flapping' ;
  }

  revision 2020-07-15 {
    description 'Add three containers and a leaf:
/ospfv3:configuration/ospfv3:ospfv3/ospfv3:processes/ospfv3:process/ospfv3:max-metric
/ospfv3:configuration/ospfv3:ospfv3/ospfv3:processes/ospfv3:process/ospfv3:max-metric/ospfv3:router-lsa
/ospfv3:configuration/ospfv3:ospfv3/ospfv3:processes/ospfv3:process/ospfv3:max-metric/ospfv3:router-lsa/ospfv3:on-startup
/ospfv3:configuration/ospfv3:ospfv3/ospfv3:processes/ospfv3:process/ospfv3:max-metric/ospfv3:router-lsa/ospfv3:on-startup/timeout' ;
  }

  revision 2020-07-14 {
    description 'Change ciphertext len from 108 to 128
/ospfv3:configuration/ospfv3:ospfv3/ospfv3:processes/ospfv3:process/ospfv3:areas/ospfv3:area/ospfv3:ipsec/ospfv3:ipsec/ospfv3:authentication/ospfv3:authentication
/ospfv3:configuration/ospfv3:ospfv3/ospfv3:processes/ospfv3:process/ospfv3:areas/ospfv3:area/ospfv3:ipsec/ospfv3:ipsec/ospfv3:encryption/ospfv3:encryption


/ospfv3:configuration/ospfv3:ospfv3/ospfv3:processes/ospfv3:process/ospfv3:areas/ospfv3:area/ospfv3:interface/ospfv3:interface/ospfv3:ipsec/ospfv3:ipsec/ospfv3:encryption/ospfv3:encryption
/ospfv3:configuration/ospfv3:ospfv3/ospfv3:processes/ospfv3:process/ospfv3:areas/ospfv3:area/ospfv3:interface/ospfv3:interface/ospfv3:ipsec/ospfv3:ipsec/ospfv3:authentication/ospfv3:authentication



/ospfv3:configuration/ospfv3:ospfv3/ospfv3:processes/ospfv3:process/ospfv3:areas/ospfv3:area/ospfv3:virtual-link/ospfv3:virtual-link/ospfv3:ipsec/ospfv3:ipsec/ospfv3:encryption/ospfv3:encryption
/ospfv3:configuration/ospfv3:ospfv3/ospfv3:processes/ospfv3:process/ospfv3:areas/ospfv3:area/ospfv3:virtual-link/ospfv3:virtual-link/ospfv3:ipsec/ospfv3:ipsec/ospfv3:authentication/ospfv3:authentication' ;
  }

  revision 2020-07-03 {
    description 'Change ciphertext or plaintext
/ospfv3:configuration/ospfv3:ospfv3/ospfv3:processes/ospfv3:process/ospfv3:areas/ospfv3:area/ospfv3:ipsec/ospfv3:ipsec/ospfv3:authentication/ospfv3:authentication
/ospfv3:configuration/ospfv3:ospfv3/ospfv3:processes/ospfv3:process/ospfv3:areas/ospfv3:area/ospfv3:ipsec/ospfv3:ipsec/ospfv3:encryption/ospfv3:encryption


/ospfv3:configuration/ospfv3:ospfv3/ospfv3:processes/ospfv3:process/ospfv3:areas/ospfv3:area/ospfv3:interface/ospfv3:interface/ospfv3:ipsec/ospfv3:ipsec/ospfv3:encryption/ospfv3:encryption
/ospfv3:configuration/ospfv3:ospfv3/ospfv3:processes/ospfv3:process/ospfv3:areas/ospfv3:area/ospfv3:interface/ospfv3:interface/ospfv3:ipsec/ospfv3:ipsec/ospfv3:authentication/ospfv3:authentication



/ospfv3:configuration/ospfv3:ospfv3/ospfv3:processes/ospfv3:process/ospfv3:areas/ospfv3:area/ospfv3:virtual-link/ospfv3:virtual-link/ospfv3:ipsec/ospfv3:ipsec/ospfv3:encryption/ospfv3:encryption
/ospfv3:configuration/ospfv3:ospfv3/ospfv3:processes/ospfv3:process/ospfv3:areas/ospfv3:area/ospfv3:virtual-link/ospfv3:virtual-link/ospfv3:ipsec/ospfv3:ipsec/ospfv3:authentication/ospfv3:authentication' ;
  }

  revision 2020-06-21 {
    description 'Modify range:
/ospfv3:configuration/ospfv3:ospfv3/ospfv3:processes/ospfv3:process/ospfv3:distribute-list/ospfv3:distribute-list-in/ospfv3:policy-name/ospfv3:route-map/ospfv3:route-map-name
/ospfv3:configuration/ospfv3:ospfv3/ospfv3:processes/ospfv3:process/ospfv3:redistribute/ospfv3:redistribute-ospf/ospfv3:redistribute-ospf/ospfv3:route-map-name
/ospfv3:configuration/ospfv3:ospfv3/ospfv3:processes/ospfv3:process/ospfv3:redistribute/ospfv3:redistribute-isis/ospfv3:redistribute-isis/ospfv3:route-map-name
/ospfv3:configuration/ospfv3:ospfv3/ospfv3:processes/ospfv3:process/ospfv3:redistribute/ospfv3:redistribute-other/ospfv3:redistribute-other/ospfv3:route-map-name
/ospfv3:configuration/ospfv3:ospfv3/ospfv3:processes/ospfv3:process/ospfv3:redistribute/ospfv3:redistribute-ps/ospfv3:redistribute-ps/ospfv3:route-map-name
/ospfv3:configuration/ospfv3:ospfv3/ospfv3:processes/ospfv3:process/ospfv3:notify-default-route/ospfv3:route-map
/ospfv3:configuration/ospfv3:ospfv3/ospfv3:processes/ospfv3:process/ospfv3:prefix-priority/ospfv3:prefix-lists/ospfv3:prefix-list/ospfv3:prefix-name' ;
  }

  revision 2020-06-02 {
    description 'Add three new leafs:
/ospfv3:configuration/ospfv3:ospfv3/ospfv3:processes/ospfv3:process/ospfv3:bfd-template
/ospfv3:configuration/ospfv3:ospfv3/ospfv3:processes/ospfv3:process/ospfv3:areas/ospfv3:area/ospfv3:bfd-template
/ospfv3:configuration/ospfv3:ospfv3/ospfv3:processes/ospfv3:process/ospfv3:areas/ospfv3:area/ospfv3:interfaces/ospfv3:interface/ospfv3:bfd-template' ;
  }

  revision 2020-05-21 {
    description 'Add new container:
/ospfv3:configuration/ospfv3:ospfv3/ospfv3:processes/ospfv3:process/ospfv3:areas/ospfv3:area/ospfv3:nssa
Add new container:
/ospfv3:configuration/ospfv3:ospfv3/ospfv3:processes/ospfv3:process/ospfv3:areas/ospfv3:area/ospfv3:nssa/ospfv3:default-information-originate
Add new leaf:
/ospfv3:configuration/ospfv3:ospfv3/ospfv3:processes/ospfv3:process/ospfv3:areas/ospfv3:area/ospfv3:nssa/ospfv3:default-information-originate/ospfv3:metric
Add new leaf:
/ospfv3:configuration/ospfv3:ospfv3/ospfv3:processes/ospfv3:process/ospfv3:areas/ospfv3:area/ospfv3:nssa/ospfv3:default-information-originate/ospfv3:metric-type
Add new leaf:
/ospfv3:configuration/ospfv3:ospfv3/ospfv3:processes/ospfv3:process/ospfv3:areas/ospfv3:area/ospfv3:nssa/ospfv3:translator-role
Add new leaf:
/ospfv3:configuration/ospfv3:ospfv3/ospfv3:processes/ospfv3:process/ospfv3:areas/ospfv3:area/ospfv3:nssa/ospfv3:trans-stab-interval
Add new leaf:
/ospfv3:configuration/ospfv3:ospfv3/ospfv3:processes/ospfv3:process/ospfv3:areas/ospfv3:area/ospfv3:nssa/ospfv3:no-summary
Add new leaf:
/ospfv3:configuration/ospfv3:ospfv3/ospfv3:processes/ospfv3:process/ospfv3:areas/ospfv3:area/ospfv3:nssa/ospfv3:no-redistribution
Add new leaf:
/ospfv3:configuration/ospfv3:ospfv3/ospfv3:processes/ospfv3:process/ospfv3:areas/ospfv3:area/ospfv3:nssa/ospfv3:suppress-fa
Add new list:
/ospfv3:configuration/ospfv3:ospfv3/ospfv3:processes/ospfv3:process/ospfv3:areas/ospfv3:area/ospfv3:ranges/ospfv3:nssa-range
Add new leaf:
/ospfv3:configuration/ospfv3:ospfv3/ospfv3:processes/ospfv3:process/ospfv3:areas/ospfv3:area/ospfv3:ranges/ospfv3:nssa-range/ospfv3:prefix
Add new leaf:
/ospfv3:configuration/ospfv3:ospfv3/ospfv3:processes/ospfv3:process/ospfv3:areas/ospfv3:area/ospfv3:ranges/ospfv3:nssa-range/ospfv3:prefix-len
Add new leaf:
/ospfv3:configuration/ospfv3:ospfv3/ospfv3:processes/ospfv3:process/ospfv3:areas/ospfv3:area/ospfv3:ranges/ospfv3:nssa-range/ospfv3:not-advertise
Add new leaf:
/ospfv3:configuration/ospfv3:ospfv3/ospfv3:processes/ospfv3:process/ospfv3:areas/ospfv3:area/ospfv3:ranges/ospfv3:nssa-range/ospfv3:metric
Add new leaf:
/ospfv3:configuration/ospfv3:ospfv3/ospfv3:processes/ospfv3:process/ospfv3:areas/ospfv3:area/ospfv3:ranges/ospfv3:nssa-range/ospfv3:tag' ;
  }

  revision 2020-04-10 {
    description 'Add new container:
/ospfv3:configuration/ospfv3:ospfv3/ospfv3:processes/ospfv3:process/ospfv3:areas/ospfv3:area/ospfv3:interfaces/ospfv3:interface/ospfv3:ti-lfa
Add new list:
/ospfv3:configuration/ospfv3:ospfv3/ospfv3:processes/ospfv3:process/ospfv3:areas/ospfv3:area/ospfv3:interfaces/ospfv3:interface/ospfv3:ti-lfa/ospfv3:srlg
Add new leaf:
/ospfv3:configuration/ospfv3:ospfv3/ospfv3:processes/ospfv3:process/ospfv3:areas/ospfv3:area/ospfv3:interfaces/ospfv3:interface/ospfv3:ti-lfa/ospfv3:srlg/ospfv3:srlg-id' ;
  }

  revision 2020-03-28 {
    description 'Add new leaf:
/ospfv3:configuration/ospfv3:ospfv3/ospfv3:processes/ospfv3:process/ospfv3:segment-routing/ospfv3:mpls/ospfv3:adj-sid/ospfv3:type' ;
  }

  revision 2020-02-19 {
    description 'add leaf:
/ospfv3:configuration/ospfv3:ospfv3/ospfv3:processes/ospfv3:process/ospfv3:te-link-delay' ;
  }

  revision 2019-12-16 {
    description 'IPSEC add encrypted key leaf node' ;
  }

  revision 2019-11-24 {
    description "Feature 'segment-routing' add new project-label-info.
    Feature 'distance-policy' add new project-label-info." ;
  }

  revision 2019-11-23 {
    description 'Add new container:
/ospfv3:configuration/ospfv3:ospfv3/ospfv3:processes/ospfv3:process/ospfv3:areas/ospfv3:area/ospfv3:interfaces/ospfv3:interface/ospfv3:cost-bfd-down
Add new leaf:
/ospfv3:configuration/ospfv3:ospfv3/ospfv3:processes/ospfv3:process/ospfv3:areas/ospfv3:area/ospfv3:interfaces/ospfv3:interface/ospfv3:cost-bfd-down/ospfv3:cost-bfd-down/ospfv3:increase-value/ospfv3:increase-value
Add new leaf:
/ospfv3:configuration/ospfv3:ospfv3/ospfv3:processes/ospfv3:process/ospfv3:areas/ospfv3:area/ospfv3:interfaces/ospfv3:interface/ospfv3:cost-bfd-down/ospfv3:cost-bfd-down/ospfv3:maximum/ospfv3:maximum' ;
  }

  revision 2019-11-13 {
    description 'Add new container:
/ospfv3:configuration/ospfv3:ospfv3/ospfv3:processes/ospfv3:process/ospfv3:segment-routing/ospfv3:mpls/ospfv3:entropy/ospfv3:capability' ;
  }

  revision 2019-10-17 {
    description 'Add new container:
/ospfv3:configuration/ospfv3:ospfv3/ospfv3:processes/ospfv3:process/ospfv3:microloop-prevention' ;
  }

  revision 2019-10-08 {
    description 'Add new container:
/ospfv3:configuration/ospfv3:ospfv3/ospfv3:processes/ospfv3:process/ospfv3:frr' ;
  }

  revision 2019-08-20 {
    description 'Add new container:
/ospfv3:configuration/ospfv3:ospfv3/ospfv3:processes/ospfv3:process/ospfv3:segment-routing/ospfv3:srv6
Add new container:
/ospfv3:configuration/ospfv3:ospfv3/ospfv3:processes/ospfv3:process/ospfv3:areas/ospfv3:area/ospfv3:interfaces/ospfv3:interface/ospfv3:segment-routing/ospfv3:srv6' ;
  }

  revision 2019-08-03 {
    description 'Add new container:
/ospfv3:configuration/ospfv3:ospfv3/ospfv3:processes/ospfv3:process/ospfv3:areas/ospfv3:area/ospfv3:interfaces/ospfv3:interface/ospfv3:cost-lag-down
Add new leaf:
/ospfv3:configuration/ospfv3:ospfv3/ospfv3:processes/ospfv3:process/ospfv3:areas/ospfv3:area/ospfv3:interfaces/ospfv3:interface/ospfv3:cost-lag-down/ospfv3:cost-lag-down/ospfv3:increase-value/ospfv3:increase-value
Add new leaf:
/ospfv3:configuration/ospfv3:ospfv3/ospfv3:processes/ospfv3:process/ospfv3:areas/ospfv3:area/ospfv3:interfaces/ospfv3:interface/ospfv3:cost-lag-down/ospfv3:cost-lag-down/ospfv3:maximum/ospfv3:maximum' ;
  }

  revision 2019-07-11 {
    description 'Add new container:
/ospfv3:configuration/ospfv3:ospfv3/ospfv3:processes/ospfv3:process/ospfv3:bgp-ls
Add new leaf:
/ospfv3:configuration/ospfv3:ospfv3/ospfv3:processes/ospfv3:process/ospfv3:bgp-ls/ospfv3:instance-id' ;
  }

  revision 2019-06-20 {
    description '1.Add a new leaf:
/ospfv3:configuration/ospfv3:ospfv3/ospfv3:processes/ospfv3:process/ospfv3:redistribute/ospfv3:redistribute/ospfv3:redistribute/ospfv3:host-only' ;
  }

  revision 2019-03-28 {
    description 'Add new container:
/ospfv3:configuration/ospfv3:ospfv3/ospfv3:processes/ospfv3:process/ospfv3:segment-routing' ;
  }

  revision 2019-03-08 {
    description '1.Add a new enum type:
/ospfv3:configuration/ospfv3:ospfv3/ospfv3:processes/ospfv3:process/ospfv3:redistribute/ospfv3:redistribute-other/ospfv3:redistribute-other/ospfv3:protocol' ;
  }

  revision 2018-11-28 {
    description 'Add new container:
/ospfv3:configuration/ospfv3:ospfv3/ospfv3:processes/ospfv3:process/ospfv3:distance-policy
Add new leaf:
/ospfv3:configuration/ospfv3:ospfv3/ospfv3:processes/ospfv3:process/ospfv3:distance-policy/ospfv3:policy-type
Add new leaf:
/ospfv3:configuration/ospfv3:ospfv3/ospfv3:processes/ospfv3:process/ospfv3:distance-policy/ospfv3:policy-name' ;
  }

  revision 2018-07-27 {
    description 'Add new enumeration value:
/ospfv3:state/ospfv3:ospfv3/ospfv3:processes/ospfv3:process/ospfv3:areas/ospfv3:area/ospfv3:ipsec/ospfv3:authentication-algorithm
/ospfv3:state/ospfv3:ospfv3/ospfv3:processes/ospfv3:process/ospfv3:areas/ospfv3:area/ospfv3:ipsec/ospfv3:encryption-algorithm' ;
  }

  revision 2018-04-12 {
    description 'Add new enumeration value:
/ospfv3:configuration/ospfv3:ospfv3/ospfv3:processes/ospfv3:process/ospfv3:redistribute/ospfv3:redistribute-other/ospfv3:redistribute-other/ospfv3:protocol' ;
  }

  revision 2017-10-27 {
    description 'Add default value:
/ospfv3:configuration/ospfv3:ospfv3/ospfv3:processes/ospfv3:process/ospfv3:reference-bandwidth' ;
  }

  revision 2017-07-05 {
    description 'Add new container:
/ospfv3:configuration/ospfv3:ospfv3/ospfv3:processes/ospfv3:process/ospfv3:frr-policy' ;
  }

  revision 2017-06-04 {
    description '1.Add new container:
/ospfv3:configuration/ospfv3:ospfv3/ospfv3:processes/ospfv3:process/ospfv3:areas/ospfv3:area/ospfv3:keychain
/ospfv3:configuration/ospfv3:ospfv3/ospfv3:processes/ospfv3:process/ospfv3:areas/ospfv3:area/ospfv3:interfaces/ospfv3:interface/ospfv3:keychain
2.Add new cases:
/ospfv3:configuration/ospfv3:ospfv3/ospfv3:processes/ospfv3:process/ospfv3:areas/ospfv3:area/ospfv3:ipsec/ospfv3:ipsec/ospfv3:authentication/ospfv3:authentication/ospfv3:authentication-key/ospfv3:authentication-key/ospfv3:keychain
/ospfv3:configuration/ospfv3:ospfv3/ospfv3:processes/ospfv3:process/ospfv3:areas/ospfv3:area/ospfv3:ipsec/ospfv3:ipsec/ospfv3:encryption/ospfv3:encryption/ospfv3:authentication-key/ospfv3:authentication-key/ospfv3:keychain
/ospfv3:configuration/ospfv3:ospfv3/ospfv3:processes/ospfv3:process/ospfv3:areas/ospfv3:area/ospfv3:ipsec/ospfv3:ipsec/ospfv3:encryption/ospfv3:encryption/ospfv3:encryption-key/ospfv3:encryption-key/ospfv3:keychain
/ospfv3:configuration/ospfv3:ospfv3/ospfv3:processes/ospfv3:process/ospfv3:areas/ospfv3:area/ospfv3:virtual-links/ospfv3:virtual-link/ospfv3:ipsec/ospfv3:ipsec/ospfv3:authentication/ospfv3:authentication/ospfv3:authentication-key/ospfv3:authentication-key/ospfv3:keychain
/ospfv3:configuration/ospfv3:ospfv3/ospfv3:processes/ospfv3:process/ospfv3:areas/ospfv3:area/ospfv3:virtual-links/ospfv3:virtual-link/ospfv3:ipsec/ospfv3:ipsec/ospfv3:encryption/ospfv3:encryption/ospfv3:encryption-key/ospfv3:encryption-key/ospfv3:keychain
/ospfv3:configuration/ospfv3:ospfv3/ospfv3:processes/ospfv3:process/ospfv3:areas/ospfv3:area/ospfv3:virtual-links/ospfv3:virtual-link/ospfv3:ipsec/ospfv3:ipsec/ospfv3:encryption/ospfv3:encryption/ospfv3:authentication-key/ospfv3:authentication-key/ospfv3:keychain
/ospfv3:configuration/ospfv3:ospfv3/ospfv3:processes/ospfv3:process/ospfv3:areas/ospfv3:area/ospfv3:interfaces/ospfv3:interface/ospfv3:ipsec/ospfv3:ipsec/ospfv3:authentication/ospfv3:authentication/ospfv3:authentication/ospfv3:authentication-ipsec/ospfv3:authentication-key/ospfv3:authentication-key/ospfv3:keychain
/ospfv3:configuration/ospfv3:ospfv3/ospfv3:processes/ospfv3:process/ospfv3:areas/ospfv3:area/ospfv3:interfaces/ospfv3:interface/ospfv3:ipsec/ospfv3:ipsec/ospfv3:encryption/ospfv3:encryption/ospfv3:encryption/ospfv3:encryption-ipsec/ospfv3:authentication-key/ospfv3:authentication-key/ospfv3:keychain
/ospfv3:configuration/ospfv3:ospfv3/ospfv3:processes/ospfv3:process/ospfv3:areas/ospfv3:area/ospfv3:interfaces/ospfv3:interface/ospfv3:ipsec/ospfv3:ipsec/ospfv3:encryption/ospfv3:encryption/ospfv3:encryption/ospfv3:encryption-ipsec/ospfv3:encryption-key/ospfv3:encryption-key/ospfv3:keychain
3.Add new enum values:
/ospfv3:state/ospfv3:ospfv3/ospfv3:interfaces/ospfv3:normal-interfaces/ospfv3:normal-interface/ospfv3:ipsec/ospfv3:authentication-algorithm
/ospfv3:state/ospfv3:ospfv3/ospfv3:interfaces/ospfv3:normal-interfaces/ospfv3:normal-interface/ospfv3:ipsec/ospfv3:encryption-algorithm' ;
  }

  revision 2017-05-18 {
    description 'Add new leaf:
/ospfv3:configuration/ospfv3:ospfv3/ospfv3:processes/ospfv3:process/ospfv3:reference-bandwidth' ;
  }

  revision 2017-03-31 {
    description 'Add new container:
/ospfv3:configuration/ospfv3:ospfv3/ospfv3:processes/ospfv3:process/ospfv3:areas/ospfv3:area/ospfv3:interfaces/ospfv3:interface/ospfv3:link-damping
Add new leaf:
/ospfv3:state/ospfv3:ospfv3/ospfv3:interfaces/ospfv3:normal-interfaces/ospfv3:normal-interface/ospfv3:damp-state
/ospfv3:state/ospfv3:ospfv3/ospfv3:interfaces/ospfv3:normal-interfaces/ospfv3:normal-interface/ospfv3:damp-remain' ;
  }

  revision 2017-01-17 {
    description 'Add new enumeration value:
1./ospfv3:configuration/ospfv3:ospfv3/ospfv3:processes/ospfv3:process/ospfv3:redistribute/ospfv3:redistribute-other/ospfv3:redistribute-other/ospfv3:protocol' ;
  }

  revision 2016-12-08 {
    description 'Add new leaf:
/ospfv3:configuration/ospfv3:ospfv3/ospfv3:processes/ospfv3:process/ospfv3:redistribute/ospfv3:redistribute-ospf/ospfv3:redistribute-ospf/ospfv3:with-origin-metric
/ospfv3:configuration/ospfv3:ospfv3/ospfv3:processes/ospfv3:process/ospfv3:redistribute/ospfv3:redistribute-isis/ospfv3:redistribute-isis/ospfv3:with-origin-metric
/ospfv3:configuration/ospfv3:ospfv3/ospfv3:processes/ospfv3:process/ospfv3:redistribute/ospfv3:redistribute-other/ospfv3:redistribute-other/ospfv3:with-origin-metric' ;
  }

  revision 2016-07-04 {
    description 'Add new container:
/ospfv3:configuration/ospfv3:ospfv3/ospfv3:processes/ospfv3:process/ospfv3:domain-ids
Add new leaf:
/ospfv3:configuration/ospfv3:ospfv3/ospfv3:processes/ospfv3:process/ospfv3:areas/ospfv3:area/ospfv3:stub/ospfv3:default-origin' ;
  }

  revision 2016-06-23 {
    description '1.Add leaf node:
/ospfv3:configuration/ospfv3:ospfv3/ospfv3:processes/ospfv3:process/ospfv3:cap-vrf-lite' ;
  }

  revision 2016-06-15 {
    description 'Add new enum item:
/configuration/ospfv3/processes/process/redistribute/redistribute-other/redistribute-other/protocol' ;
  }

  revision 2016-01-21 {
    description '1.Modify the description:
/ospfv3:state/ospfv3:ospfv3/ospfv3:interfaces/ospfv3:normal-interfaces/ospfv3:normal-interface/ospfv3:interface-state
/ospfv3:state/ospfv3:ospfv3/ospfv3:interfaces/ospfv3:normal-interfaces/ospfv3:normal-interface/ospfv3:ldp-link-state' ;
  }

  revision 2015-12-08 {
    description '1.Add leaf node:
/ospfv3:configuration/ospfv3:ospfv3/ospfv3:processes/ospfv3:process/ospfv3:ldp-igp-sync
/ospfv3:configuration/ospfv3:ospfv3/ospfv3:processes/ospfv3:process/ospfv3:areas/ospfv3:area/ospfv3:ldp-igp-sync
/ospfv3:configuration/ospfv3:ospfv3/ospfv3:processes/ospfv3:process/ospfv3:areas/ospfv3:area/ospfv3:interfaces/ospfv3:interface/ospfv3:ldp-igp-sync
/ospfv3:state/ospfv3:ospfv3/ospfv3:interfaces/ospfv3:normal-interfaces/ospfv3:normal-interface/ospfv3:ldp-sync
/ospfv3:state/ospfv3:ospfv3/ospfv3:interfaces/ospfv3:normal-interfaces/ospfv3:normal-interface/ospfv3:ldp-sync-state
/ospfv3:state/ospfv3:ospfv3/ospfv3:interfaces/ospfv3:normal-interfaces/ospfv3:normal-interface/ospfv3:ldp-link-state
/ospfv3:state/ospfv3:ospfv3/ospfv3:interfaces/ospfv3:normal-interfaces/ospfv3:normal-interface/ospfv3:no-cut-edge' ;
  }

  revision 2015-08-04 {
    description '1.Modify derivedType:
/ospfv3:configuration/ospfv3:ospfv3/ospfv3:processes/ospfv3:process/ospfv3:summary-prefixs/ospfv3:summary-prefix/ospfv3:summary-prefix
/ospfv3:configuration/ospfv3:ospfv3/ospfv3:processes/ospfv3:process/ospfv3:areas/ospfv3:area/ospfv3:ranges/ospfv3:range/ospfv3:prefix
2.Refresh the config label' ;
  }

  revision 2015-07-06 {
    description 'Delete enumeration values:
/ospfv3:state/ospfv3:ospfv3/ospfv3:neighbors/ospfv3:normal-neighbors/ospfv3:normal-neighbor/ospfv3:neighbor-state' ;
  }

  revision 2015-06-10 {
    description '1.Modify range:
/ospfv3:state/ospfv3:ospfv3/ospfv3:interfaces/ospfv3:virtual-interfaces/ospfv3:virtual-interface/ospfv3:interface-id
2.Modify the description:
/ospfv3:state/ospfv3:ospfv3/ospfv3:neighbors/ospfv3:normal-neighbors/ospfv3:normal-neighbor/ospfv3:options/ospfv3:v6-bit' ;
  }

  revision 2015-06-03 {
    description '1.Modify the units of these leaf nodes:
/ospfv3:configuration/ospfv3:ospfv3/ospfv3:processes/ospfv3:process/ospfv3:areas/ospfv3:area/ospfv3:interfaces/ospfv3:interface/ospfv3:ipsec/ospfv3:ipsec/ospfv3:authentication/ospfv3:authentication/ospfv3:authentication/ospfv3:authentication-ipsec/ospfv3:roll-interval
/ospfv3:configuration/ospfv3:ospfv3/ospfv3:processes/ospfv3:process/ospfv3:areas/ospfv3:area/ospfv3:interfaces/ospfv3:interface/ospfv3:ipsec/ospfv3:ipsec/ospfv3:encryption/ospfv3:encryption/ospfv3:encryption/ospfv3:encryption-ipsec/ospfv3:roll-interval
/ospfv3:configuration/ospfv3:ospfv3/ospfv3:processes/ospfv3:process/ospfv3:areas/ospfv3:area/ospfv3:ipsec/ospfv3:ipsec/ospfv3:authentication/ospfv3:authentication/ospfv3:roll-interval
/ospfv3:configuration/ospfv3:ospfv3/ospfv3:processes/ospfv3:process/ospfv3:areas/ospfv3:area/ospfv3:ipsec/ospfv3:ipsec/ospfv3:encryption/ospfv3:encryption/ospfv3:roll-interval
/ospfv3:configuration/ospfv3:ospfv3/ospfv3:processes/ospfv3:process/ospfv3:areas/ospfv3:area/ospfv3:virtual-links/ospfv3:virtual-link/ospfv3:ipsec/ospfv3:ipsec/ospfv3:authentication/ospfv3:authentication/ospfv3:roll-interval
/ospfv3:configuration/ospfv3:ospfv3/ospfv3:processes/ospfv3:process/ospfv3:areas/ospfv3:area/ospfv3:virtual-links/ospfv3:virtual-link/ospfv3:ipsec/ospfv3:ipsec/ospfv3:encryption/ospfv3:encryption/ospfv3:roll-interval
2.Delete an enumeration value:
/ospfv3:state/ospfv3:ospfv3/ospfv3:neighbors/ospfv3:virtual-neighbors/ospfv3:virtual-neighbor/ospfv3:neighbor-state
3.Modify the description:
/ospfv3:state/ospfv3:ospfv3/ospfv3:neighbors/ospfv3:virtual-neighbors/ospfv3:virtual-neighbor/ospfv3:options/ospfv3:v6-bit' ;
  }

  revision 2015-05-04 {
    description 'Add new container:
/configuration/ospfv3/processes/process/redistribute/redistribute-ps' ;
  }

  revision 2015-03-26 {
    description 'Add state and operation of OSPFv3.' ;
  }

  revision 2015-01-14 {
    description 'Add new container:
/configuration/ospfv3/processes/process/notify-default-route' ;
  }

  revision 2014-12-22 {
    description 'Add new enum item:
/configuration/ospfv3/processes/process/redistribute/redistribute-other/redistribute-other/protocol
Change container of leaves to container of list:
/configuration/ospfv3/processes/process/timers-throttle-spf
Rename:
/configuration/ospfv3/processes/process/summary-prefixs/summary-prefix/summary_prefix
/configuration/ospfv3/processes/process/timers-throttle-spf' ;
  }

  revision 2014-09-29 {
    description 'Rename some container and leaf node:
/configuration/ospfv3/processes/process/max-path
/configuration/ospfv3/processes/process/areas/area/bfd-cfg
/configuration/ospfv3/processes/process/areas/area/interfaces/interface/bfd-cfg
/configuration/ospfv3/processes/process/areas/area/interfaces/interface/network-type/network-type/p-to-mp-nbma
/configuration/ospfv3/processes/process/areas/area/interfaces/interface/network-type/network-type/p-to-mp-nb/p-to-mp-nbma
/configuration/ospfv3/processes/process/areas/area/interfaces/interface/interface-ipsec
/configuration/ospfv3/processes/process/areas/area/interfaces/interface/ipsec/interface-ipsec
/configuration/ospfv3/processes/process/areas/area/virtual-links/virtual-link/vlink-ipsec
/configuration/ospfv3/processes/process/areas/area/virtual-links/virtual-link/ipsec/vlink-ipsec
/configuration/ospfv3/processes/process/areas/area/area-ipsec
/configuration/ospfv3/processes/process/areas/area/ipsec/area-ipsec' ;
  }

  revision 2014-01-13 {
    description 'Initial version.' ;
  }

  feature distance-policy {
    description 'The feature is for distance-policy.' ;
  }

  feature segment-routing {
    description 'SR support labels' ;
  }

  feature srv6-adjacency-set {
    description 'The feature is for adjacency-set.' ;
    ncd:revise-date 2025-05-14 ;
  }

  container configuration {
    description 'Configuration.' ;
    container ospfv3 {
      description 'OSPFv3 configuration.' ;
      container global {
        leaf memory-overload-protection {
          type enumeration {
            enum enable {
              value 1 ;
              description 'Enable memory overload protection' ;
            }

            enum disable {
              value 0 ;
              description 'Disable memory overload protection' ;
            }

          }

          description 'Configure memory overload protection for OSPFv3.' ;
          default disable ;
        }

        description 'OSPFv3 global configuration.' ;
        ncd:revise-date 2025-06-30 ;
      }

      container processes {
        description 'OSPFv3 process configuration.' ;
        list process {
          description 'OSPFv3 process configuration.' ;
          key proc-id ;
          leaf proc-id {
            description 'OSPFv3 process ID.' ;
            type uint32 {
              range 1..65535 ;

            }

          }

          leaf vrf-name {
            description 'VPN routing/forwarding instance (VRF) name.' ;
            type string {
              length 1..32 ;

            }

          }

          leaf bfd-enable {
            description 'BFD configuration of OSPFv3 process.' ;
            type empty ;

          }

          leaf bfd-template {
            description 'Configure BFD template for OSPFv3.' ;
            type string {
              length 1..31 ;

            }

            ncd:revise-date 2020-06-21 ;
          }

          leaf default-metric {
            description 'Default metric of Type 5 LSA.' ;
            type uint32 {
              range 1..16777214 ;

            }

            default 20 ;
          }

          leaf maximum-paths {
            description 'Maximum of paths to one destination.The default value of product can be customized with performance parameters.If not, the default value is 1.' ;
            type uint32 {
              range 1..128 ;

            }

            default 1 ;
          }

          leaf fast-reroute {
            description 'Fast-reroute.' ;
            type empty ;

          }

          leaf nsf {
            description 'Non-stop forwarding.' ;
            type empty ;

          }

          leaf grace-period {
            description 'The max period of a graceful restart.' ;
            type uint32 {
              range 1..1800 ;

            }

            units second ;
            default 120 ;
          }

          leaf ispf {
            description 'Incremental SPF computation.' ;
            type empty ;

          }

          leaf ldp-igp-sync {
            description 'Configure MPLS LDP IGP sync.' ;
            type empty ;

            ncd:revise-date 2015-12-08 ;
          }

          leaf cap-vrf-lite {
            description 'Configure capability vrf lite' ;
            type empty ;

            ncd:revise-date 2016-06-23 ;
          }

          leaf reference-bandwidth {
            description 'The reference bandwidth in terms of Mbps.' ;
            type uint32 {
              range 1..4000000 ;

            }

            units Mbps ;
            default 100 ;
            ncd:revise-date 2017-05-18 ;
          }

          leaf te-link-bandwidth {
            description 'Set TE link bandwidth capability' ;
            type enumeration {
              enum disable {
                value 0 ;
                description 'Set TE link bandwidth disable' ;
              }

              enum enable {
                value 1 ;
                description 'Set TE link bandwidth enable' ;
              }

            }

            default disable ;
            ncd:revise-date 2021-06-15 ;
          }

          leaf te-link-delay {
            description 'Set OSPF TE link delay' ;
            type enumeration {
              enum enable {
                value 1 ;
                description 'Enable TE link delay' ;
              }

              enum disable {
                value 2 ;
                description 'Disable TE link delay' ;
              }

            }

            default disable ;
            ncd:revise-date 2020-02-19 ;
          }

          leaf rfc1583-value {
            type enumeration {
              enum enable {
                value 1 ;
                description 'enable' ;
              }

              enum disable {
                value 0 ;
                description 'disable' ;
              }

            }

            default disable ;
            description 'Ospf compatible with rfc1583 when calculating external route' ;
            ncd:revise-date 2023-03-27 ;
          }

          container frr-policy {
            description 'Configure OSPF backup route policy.' ;
            presence frr-policy ;
            choice policy-type {
              description 'Configure OSPF backup route policy type.' ;
              mandatory true ;
              case route-policy {
                description 'Configure OSPF backup route-policy.' ;
                leaf route-policy-name {
                  description 'Configure route-policy name.' ;
                  type string {
                    length 1..200 {
                      description 'Name of the route-policy,characters from 1 to 200.' ;
                    }

                  }

                  mandatory true ;
                }

              }

            }

            ncd:revise-date 2017-07-05 ;
          }

          container router-id {
            description 'Router-id.' ;
            presence router-id-presence ;
            leaf router-id {
              description 'Router-id.' ;
              type ncd:ipv4-address ;

              mandatory true ;
            }

          }

          container distance {
            description 'Distance of OSPF route.' ;
            leaf external {
              description 'Distance for external routes.' ;
              type uint8 {
                range 1..255 ;

              }

              default 110 ;
            }

            leaf inter-area {
              description 'Distance for inter-area routes.' ;
              type uint8 {
                range 1..255 ;

              }

              default 110 ;
            }

            leaf intra-area {
              description 'Distance for intra-area routes.' ;
              type uint8 {
                range 1..255 ;

              }

              default 110 ;
            }

          }

          container distribute-list {
            description 'Filter networks in routing updates.' ;
            container distribute-list-in {
              description 'Filter incoming routing updates.' ;
              presence dl-in-presence ;
              container policy-name {
                description 'Policy name.' ;
                choice policy-name {
                  description 'Policy name.' ;
                  mandatory true ;
                  case access-list {
                    description 'Access list.' ;
                    leaf acl-name {
                      description 'Access list name.' ;
                      type string {
                        length 1..31 ;

                      }

                      mandatory true ;
                    }

                  }

                  case route-map {
                    description 'Route-map.' ;
                    leaf route-map-name {
                      description 'Route-map name.' ;
                      type string {
                        length 1..200 ;

                      }

                      mandatory true ;
                    }

                  }

                }

              }

            }

          }

          container prefix-priority {
            description 'Priority for prefix convergence.' ;
            presence prefix-priority-presence ;
            container prefix-lists {
              description 'Prefix-list for prefix convergence.' ;
              presence prefix-list-presence ;
              list prefix-list {
                description 'Prefix-list for prefix convergence.' ;
                key priority ;
                leaf priority {
                  description 'Priority for prefix.' ;
                  type enumeration {
                    enum critical {
                      value 1 ;
                      description 'Critical priority.' ;
                    }

                    enum high {
                      value 2 ;
                      description 'High priority.' ;
                    }

                    enum medium {
                      value 3 ;
                      description 'Medium priority.' ;
                    }

                  }

                }

                leaf prefix-name {
                  description 'Prefix-list name.' ;
                  type string {
                    length 1..169 ;

                  }

                  mandatory true ;
                }

              }

            }

            container tags {
              description 'Tag value for prefix convergence.' ;
              presence tags-presence ;
              list tag {
                description 'Tag value for prefix convergence.' ;
                key 'priority tag-value' ;
                leaf priority {
                  description 'Priority for prefix.' ;
                  type enumeration {
                    enum critical {
                      value 1 ;
                      description 'Critical priority.' ;
                    }

                    enum high {
                      value 2 ;
                      description 'High priority.' ;
                    }

                    enum medium {
                      value 3 ;
                      description 'Medium priority.' ;
                    }

                  }

                }

                leaf tag-value {
                  description 'Tag value of prefix.' ;
                  type uint32 {
                    range 0..4294967295 ;

                  }

                }

              }

            }

          }

          container redistribute {
            description 'Redistribute.' ;
            container redistribute-ospf {
              description 'Redistribute information from OSPF.' ;
              presence redistribute-ospf-presence ;
              list redistribute-ospf {
                description 'Redistribute information from OSPF.' ;
                key ospf-proc-id ;
                leaf ospf-proc-id {
                  description 'OSPF process ID for redistribute.' ;
                  type uint32 {
                    range 1..65535 ;

                  }

                }

                leaf metric {
                  description 'Metric for redistributed routes.' ;
                  type uint32 {
                    range 1..16777214 ;

                  }

                }

                leaf metric-type {
                  description 'Metric type for redistributed routes.' ;
                  type enumeration {
                    enum ext-2 {
                      value 0 ;
                      description 'External metric-type 2.' ;
                    }

                    enum ext-1 {
                      value 1 ;
                      description 'External metric-type 1.' ;
                    }

                  }

                  default ext-2 ;
                }

                leaf route-map-name {
                  description 'Route map reference.' ;
                  type string {
                    length 1..200 ;

                  }

                }

                leaf tag {
                  description 'Tag for redistributed routes.' ;
                  type uint32 {
                    range 0..4294967295 ;

                  }

                  default 0 ;
                }

                leaf with-origin-metric {
                  description 'Use origin metric of the route.' ;
                  type empty ;

                  ncd:revise-date 2016-12-08 ;
                }

                leaf host-only {
                  type empty ;

                  ncd:revise-date 2019-06-20 ;
                }

              }

            }

            container redistribute-isis {
              description 'Redistribute information from ISIS.' ;
              presence redistribute-isis-presence ;
              list redistribute-isis {
                description 'Redistribute information from ISIS.' ;
                key isis-proc-id ;
                leaf isis-proc-id {
                  description 'ISIS process ID for redistribute.' ;
                  type uint32 {
                    range 0..65535 ;

                  }

                }

                leaf metric {
                  description 'Metric for redistributed routes.' ;
                  type uint32 {
                    range 1..16777214 ;

                  }

                }

                leaf metric-type {
                  description 'Metric type for redistributed routes.' ;
                  type enumeration {
                    enum ext-2 {
                      value 0 ;
                      description 'External metric-type 2.' ;
                    }

                    enum ext-1 {
                      value 1 ;
                      description 'External metric-type 1.' ;
                    }

                  }

                  default ext-2 ;
                }

                leaf route-map-name {
                  description 'Route map reference.' ;
                  type string {
                    length 1..200 ;

                  }

                }

                leaf tag {
                  description 'Tag for redistributed routes.' ;
                  type uint32 {
                    range 0..4294967295 ;

                  }

                  default 0 ;
                }

                leaf with-origin-metric {
                  description 'Use origin metric of the route.' ;
                  type empty ;

                  ncd:revise-date 2016-12-08 ;
                }

                leaf host-only {
                  type empty ;

                  ncd:revise-date 2019-06-20 ;
                }

              }

            }

            container redistribute-other {
              description 'Redistribute information from other protocol.' ;
              presence redistribute-other-presence ;
              list redistribute-other {
                description 'Redistribute information from other protocol.' ;
                key protocol ;
                leaf protocol {
                  description 'Route protocol.' ;
                  type enumeration {
                    enum static {
                      value 1 ;
                      description 'Static routes.' ;
                    }

                    enum connected {
                      value 2 ;
                      description 'Connected routes.' ;
                    }

                    enum rip {
                      value 3 ;
                      description 'Routing information protocol (RIPNG).' ;
                    }

                    enum bgp {
                      value 6 ;
                      description 'Border gateway protocol for ipv6 (BGP).' ;
                    }

                    enum subscriber-host {
                      value 7 ;
                      description "Bras subscriber's host routes." ;
                    }

                    enum aftr {
                      value 8 ;
                      description 'AFTR routes.' ;
                    }

                    enum sf-nat64 {
                      value 9 ;
                      description 'Stateful NAT64 routes.' ;
                    }

                    enum sl-nat64 {
                      value 10 ;
                      description 'Stateless NAT64 routes.' ;
                    }

                    enum dhcp-pd {
                      value 11 ;
                      description 'DHCP-PD routes.' ;
                    }

                    enum subscriber-aggregation {
                      value 14 ;
                      description "Bras subscriber's aggregation routes." ;
                    }

                    enum user-special {
                      value 15 ;
                      description 'User special routes.' ;
                    }

                    enum bras-pool {
                      value 16 ;
                      description 'Bras-pool routes.' ;
                    }

                    enum zenic-local {
                      value 17 ;
                      description 'Zenic-local routes.' ;
                    }

                    enum dyn-leasedline {
                      value 18 ;
                      description 'Dynamic-leased-line routes assigned by AAA' ;
                    }

                    enum bgp-ext {
                      value 20 ;
                      description 'BGP external routes.' ;
                    }

                    enum bgp-int {
                      value 21 ;
                      description 'BGP internal routes.' ;
                    }

                    enum nd-host {
                      value 22 ;
                      description 'ND-HOST routes.' ;
                    }

                  }

                }

                leaf metric {
                  description 'Metric for redistributed routes.' ;
                  type uint32 {
                    range 1..16777214 ;

                  }

                }

                leaf metric-type {
                  description 'Metric type for redistributed routes.' ;
                  type enumeration {
                    enum ext-2 {
                      value 0 ;
                      description 'External metric-type 2.' ;
                    }

                    enum ext-1 {
                      value 1 ;
                      description 'External metric-type 1.' ;
                    }

                  }

                  default ext-2 ;
                }

                leaf route-map-name {
                  description 'Route map reference.' ;
                  type string {
                    length 1..200 ;

                  }

                }

                leaf tag {
                  description 'Tag for redistributed routes.' ;
                  type uint32 {
                    range 0..4294967295 ;

                  }

                  default 0 ;
                }

                leaf with-origin-metric {
                  description 'Use origin metric of the route.' ;
                  type empty ;

                  ncd:revise-date 2016-12-08 ;
                }

                leaf host-only {
                  type empty ;

                  ncd:revise-date 2019-06-20 ;
                }

                leaf asno {
                  description 'Autonomous system number(valid for BGP only).' ;
                  type ncd:asn-dot {
                    length 1..11 ;

                  }

                  ncd:revise-date 2022-12-21 ;
                }

              }

            }

            container redistribute-ps {
              description 'Redistribute PS route.' ;
              list redistribute-ps {
                description 'Redistribute PS route.' ;
                key type ;
                leaf type {
                  description 'PS route type.' ;
                  type enumeration {
                    enum ps-busi-addr {
                      value 12 ;
                      description 'ps-busi-addr routes.' ;
                    }

                    enum ps-user-addr {
                      value 13 ;
                      description 'ps-user-addr routes.' ;
                    }

                  }

                }

                leaf with-origin-metric {
                  description 'Use origin metric of the route.' ;
                  type empty ;

                }

                leaf metric {
                  description 'Metric for redistributed routes.' ;
                  type uint32 {
                    range 1..16777214 ;

                  }

                }

                leaf metric-type {
                  description 'Metric type for redistributed routes.' ;
                  type enumeration {
                    enum ext-2 {
                      value 0 ;
                      description 'External metric-type 2.' ;
                    }

                    enum ext-1 {
                      value 1 ;
                      description 'External metric-type 1.' ;
                    }

                  }

                  default ext-2 ;
                }

                leaf route-map-name {
                  description 'Route map reference.' ;
                  type string {
                    length 1..200 ;

                  }

                }

                leaf tag {
                  description 'Tag for redistributed routes.' ;
                  type uint32 {
                    range 0..4294967295 ;

                  }

                  default 0 ;
                }

                leaf host-only {
                  type empty ;

                  ncd:revise-date 2019-06-20 ;
                }

              }

              ncd:revise-date 2015-05-04 ;
            }

          }

          container summary-prefixs {
            description 'Summarize external routes matching prefix/length.' ;
            list summary-prefix {
              description 'Summarize external routes matching prefix/length.' ;
              key 'summary-prefix prefix-len' ;
              leaf summary-prefix {
                description 'IPv6 address prefix.' ;
                type ncd:ipv6-address ;

              }

              leaf prefix-len {
                description 'Prefix length.' ;
                type ncd:ipv6-mask-length ;

              }

              container tag {
                description 'Tag for convergence routes.' ;
                presence tag ;
                leaf tag {
                  type uint32 {
                    range 0..4294967295 ;

                  }

                  description 'Tag for convergence routes.' ;
                  mandatory true ;
                }

                leaf tag-flag {
                  type enumeration {
                    enum tag-valid {
                      value 1 ;
                      description 'tag-valid' ;
                    }

                    enum tag-invalid {
                      value 0 ;
                      description 'tag-invalid' ;
                    }

                  }

                  description 'Tag flag.If the tag value exists,tag-flag must be set to tag-valid.' ;
                  mandatory true ;
                }

                ncd:revise-date 2024-07-15 ;
              }

            }

          }

          container timers-throttle {
            description 'Timers for throttle.' ;
            presence throttle-presence ;
            container spf {
              description 'Ospf SPF throttle timers' ;
              presence spf ;
              leaf hold-time {
                description 'Hold time for SPF calculation in milliseconds' ;
                type uint32 {
                  range 1..600000 {
                    description 'Hold time for SPF calculation in milliseconds' ;
                  }

                }

                units millisecond ;
                mandatory true ;
              }

              leaf delay-time {
                description 'Min delay for SPF calculation in milliseconds' ;
                type uint32 {
                  range 1..600000 {
                    description 'Min delay for SPF calculation in milliseconds' ;
                  }

                }

                units millisecond ;
                mandatory true ;
              }

              leaf max-delay-time {
                description 'Max delay for SPF calculation in milliseconds' ;
                type uint32 {
                  range 1..600000 {
                    description 'Max delay for SPF calculation in milliseconds' ;
                  }

                }

                units millisecond ;
                mandatory true ;
              }

            }

            container lsa-update {
              description 'Ospf LSA update throttle timers' ;
              presence lsa-update ;
              leaf hold-time {
                description 'Hold time for LSA update in milliseconds' ;
                type uint32 {
                  range 1..600000 {
                    description 'Hold time for LSA update in milliseconds' ;
                  }

                }

                units millisecond ;
                mandatory true ;
              }

              leaf delay-time {
                description 'Min delay for LSA update in milliseconds' ;
                type uint32 {
                  range 1..600000 {
                    description 'Min delay for LSA update in milliseconds' ;
                  }

                }

                units millisecond ;
                mandatory true ;
              }

              leaf max-delay-time {
                description 'Max delay for LSA update in milliseconds' ;
                type uint32 {
                  range 1..600000 {
                    description 'Max delay for LSA update in milliseconds' ;
                  }

                }

                units millisecond ;
                mandatory true ;
              }

            }

            container lsa-arrival {
              description 'Ospf LSA arrival throttle timers' ;
              presence lsa-arrival ;
              leaf hold-time {
                description 'Hold time for LSA arrival in milliseconds' ;
                type uint32 {
                  range 0..600000 {
                    description 'Hold time for LSA arrival in milliseconds' ;
                  }

                }

                units millisecond ;
                mandatory true ;
              }

              leaf delay-time {
                description 'Min delay for LSA arrival in milliseconds' ;
                type uint32 {
                  range 0..600000 {
                    description 'Min delay for LSA arrival in milliseconds' ;
                  }

                }

                units millisecond ;
                mandatory true ;
              }

              leaf max-delay-time {
                description 'Max delay for LSA arrival in milliseconds' ;
                type uint32 {
                  range 0..600000 {
                    description 'Max delay for LSA update in milliseconds' ;
                  }

                }

                units millisecond ;
                mandatory true ;
              }

            }

          }

          container notify-default-route {
            description 'Notify default route.' ;
            presence notify-default-route-presence ;
            leaf always {
              description 'Generate a type-5 LSA even if there is no default route.' ;
              type empty ;

            }

            leaf metric {
              description 'Metric of generated type-5 LSA.' ;
              type uint32 {
                range 1..16777214 ;

              }

              default 1 ;
            }

            leaf metric-type {
              description 'Metric type of generated type-5 LSA.' ;
              type enumeration {
                enum ext-2 {
                  value 0 ;
                  description 'External metric-type 2.' ;
                }

                enum ext-1 {
                  value 1 ;
                  description 'External metric-type 1.' ;
                }

              }

              default ext-2 ;
            }

            leaf route-map {
              description 'Route map reference.' ;
              type string {
                length 1..200 ;

              }

            }

            leaf rib-match-prefix-list {
              description 'Name of the prefix-list.' ;
              type string {
                length 1..169 ;

              }

              ncd:revise-date 2022-09-19 ;
            }

          }

          container areas {
            description 'OSPFv3 area configuration.' ;
            list area {
              description 'OSPFv3 area configuration.' ;
              key area-id ;
              leaf area-id {
                description 'OSPFv3 area ID in IP address format.' ;
                type ncd:ipv4-address ;

              }

              leaf bfd {
                description 'BFD configuration of OSPFv3 area.' ;
                type enumeration {
                  enum enable {
                    value 1 ;
                    description 'Enable BFD capability of the area.' ;
                  }

                  enum disable {
                    value 2 ;
                    description 'Disable BFD capability of the area.' ;
                  }

                }

              }

              leaf bfd-template {
                description 'Configure BFD template for OSPFv3 area.' ;
                type string {
                  length 1..31 ;

                }

                ncd:revise-date 2020-06-21 ;
              }

              leaf ldp-igp-sync {
                description 'Configure MPLS LDP IGP sync.' ;
                type enumeration {
                  enum enable {
                    value 1 ;
                    description 'Enable MPLS LDP IGP sync.' ;
                  }

                  enum disable {
                    value 2 ;
                    description 'Disable MPLS LDP IGP sync.' ;
                  }

                }

                ncd:revise-date 2015-12-08 ;
              }

              container ranges {
                description 'Summarize inter-area routes matching prefix/length.' ;
                list range {
                  description 'Summarize inter-area routes matching prefix/length.' ;
                  key 'prefix prefix-len' ;
                  leaf prefix {
                    description 'IPv6 address prefix.' ;
                    type ncd:ipv6-address ;

                  }

                  leaf prefix-len {
                    description 'Prefix length.' ;
                    type ncd:ipv6-mask-length ;

                  }

                  leaf not-advertise {
                    description 'DoNotAdvertise this range.' ;
                    type empty ;

                  }

                }

                list nssa-range {
                  description 'Summarize routes when nssa abr translates type-7 routes to type-5 lsa' ;
                  key 'prefix prefix-len' ;
                  leaf prefix {
                    description 'IPv6 address prefix.' ;
                    type ncd:ipv6-address ;

                  }

                  leaf prefix-len {
                    description 'Prefix length' ;
                    type ncd:ipv6-mask-length ;

                  }

                  leaf not-advertise {
                    description 'advertise this range or not' ;
                    type empty ;

                  }

                  leaf metric {
                    description 'nssa range metric' ;
                    type uint32 {
                      range 1..16777214 ;

                    }

                  }

                  leaf tag {
                    description 'nssa range tag' ;
                    type uint32 ;

                  }

                  ncd:revise-date 2020-05-21 ;
                }

              }

              container interfaces {
                description 'OSPFv3 interface configuration.' ;
                list interface {
                  description 'OSPFv3 interface configuration.' ;
                  key interface-name ;
                  leaf interface-name {
                    description 'Interface name.' ;
                    type ncd:ifname {
                      length 1..31 ;

                    }

                  }

                  leaf instance-id {
                    description 'Instance ID of OSPFv3 interface.' ;
                    type uint32 {
                      range 0..255 ;

                    }

                    default 0 ;
                  }

                  leaf bfd {
                    description 'BFD configuration of OSPFv3 interface.' ;
                    type enumeration {
                      enum enable {
                        value 1 ;
                        description 'Enable BFD capability of the interface.' ;
                      }

                      enum disable {
                        value 2 ;
                        description 'Disable BFD capability of the interface.' ;
                      }

                    }

                  }

                  leaf bfd-template {
                    description 'Configure BFD template for OSPFv3 interface.' ;
                    type string {
                      length 1..31 ;

                    }

                    ncd:revise-date 2020-06-21 ;
                  }

                  leaf cost {
                    description 'Cost value of OSPFv3 interface.' ;
                    type uint32 {
                      range 1..65535 ;

                    }

                  }

                  leaf hello-interval {
                    description 'Time between hello packets.' ;
                    type uint32 {
                      range 1..65535 ;

                    }

                    units second ;
                  }

                  leaf dead-interval {
                    description 'Interval after which a neighbor is declared dead.' ;
                    type uint32 {
                      range 1..65535 ;

                    }

                    units second ;
                  }

                  leaf retransmit-interval {
                    description 'Time between retransmitting lost link state advertisements.' ;
                    type uint32 {
                      range 1..65535 ;

                    }

                    units second ;
                    default 5 ;
                  }

                  leaf transmit-delay {
                    description 'LSA transmit delay.' ;
                    type uint32 {
                      range 1..65535 ;

                    }

                    units second ;
                    default 1 ;
                  }

                  leaf priority {
                    description 'Router priority.' ;
                    type uint32 {
                      range 0..255 ;

                    }

                    default 1 ;
                  }

                  leaf mtu-ignore {
                    description 'Ignore the mtu mismatch when exchanging DD packet.' ;
                    type empty ;

                  }

                  leaf linklsa-suppress-enable {
                    description 'DONOT originate link LSA.' ;
                    type empty ;

                  }

                  leaf fast-reroute-disable {
                    description 'Disable this interface FRR capability.' ;
                    type empty ;

                  }

                  leaf passive {
                    description 'Control routing updates on an interface.' ;
                    type empty ;

                  }

                  leaf ldp-igp-sync {
                    description 'Enable MPLS LDP IGP sync.' ;
                    type enumeration {
                      enum enable {
                        value 1 ;
                        description 'Enable MPLS LDP IGP sync.' ;
                      }

                      enum disable {
                        value 2 ;
                        description 'Disable MPLS LDP IGP sync.' ;
                      }

                    }

                    ncd:revise-date 2015-12-08 ;
                  }

                  container link-damping {
                    description 'Configure interface cost and time when link is in damping status' ;
                    presence link-damping ;
                    container cost {
                      description 'Configure interface cost when link is in damping status' ;
                      choice cost {
                        description 'Configure interface cost when link is in damping status' ;
                        mandatory true ;
                        case maximum {
                          description 'Set maximum cost when link is in damping status' ;
                          leaf maximum {
                            description 'Set maximum cost when link is in damping status' ;
                            type empty ;

                            mandatory true ;
                          }

                        }

                        case increase-value {
                          description 'Set increase cost when link is in damping status' ;
                          leaf increase-value {
                            description 'Set increase cost when link is in damping status' ;
                            type uint32 {
                              range 100..10000 {
                                description 'Set increase cost range when link is in damping status' ;
                              }

                            }

                            mandatory true ;
                          }

                        }

                      }

                    }

                    leaf damping-time {
                      description 'Configure interface damping time' ;
                      type uint32 {
                        range 1..3600000 {
                          description 'Set time range when link is in damping status' ;
                        }

                      }

                      units millisecond ;
                      mandatory true ;
                    }

                    ncd:revise-date 2017-03-31 ;
                  }

                  container network-type {
                    description 'Network type of OSPFv3 interface.' ;
                    choice network-type {
                      description 'Network type of OSPFv3 interface.' ;
                      case broadcast {
                        description 'Broadcast.' ;
                        leaf broadcast {
                          description 'Broadcast.' ;
                          type empty ;

                          mandatory true ;
                        }

                      }

                      case nbma {
                        description 'Non-broadcast multiple access.' ;
                        leaf nbma {
                          description 'Non-broadcast multiple access.' ;
                          type empty ;

                          mandatory true ;
                        }

                      }

                      case point-to-point {
                        description 'Point-to-point.' ;
                        leaf point-to-point {
                          description 'Point-to-point.' ;
                          type empty ;

                          mandatory true ;
                        }

                      }

                      case point-to-multipoint {
                        description 'Point-to-multipoint.' ;
                        leaf point-to-multipoint {
                          description 'Point-to-multipoint.' ;
                          type empty ;

                          mandatory true ;
                        }

                      }

                      case p-to-mp-nb {
                        description 'Point-to-multipoint non-broadcast.' ;
                        leaf p-to-mp-nb {
                          description 'Point-to-multipoint non-broadcast.' ;
                          type empty ;

                          mandatory true ;
                        }

                      }

                    }

                  }

                  container neighbors {
                    description 'Neighbor configuration of OSPFv3 interface.' ;
                    list neighbor {
                      description 'Neighbor configuration of OSPFv3 interface.' ;
                      key nbr-linklocal-address ;
                      leaf nbr-linklocal-address {
                        description 'Link-local address of the neighbor.' ;
                        type ncd:ipv6-address ;

                      }

                      leaf priority {
                        description 'OSPF priority of non-broadcast neighbor.' ;
                        type uint32 {
                          range 0..255 ;

                        }

                        default 1 ;
                      }

                      leaf poll-interval {
                        description 'Poll interval time of non-broadcast neighbor.' ;
                        type uint32 {
                          range 120..65535 ;

                        }

                        units second ;
                        default 120 ;
                      }

                      leaf cost {
                        description 'OSPF cost of point-to-multipoint neighbor.' ;
                        type uint32 {
                          range 1..65535 ;

                        }

                      }

                    }

                  }

                  container cost-lag-down {
                    description 'Configure interface cost when link detects lag down.' ;
                    choice cost-lag-down {
                      description 'Configure interface cost when link detects lag down.' ;
                      case increase-value {
                        description 'Set increase cost when link detects lag down.' ;
                        leaf increase-value {
                          description 'The increase cost value' ;
                          type uint16 {
                            range 100..10000 ;

                          }

                        }

                      }

                      case maximum {
                        description 'Set maximum cost when link detects lag down.' ;
                        leaf maximum {
                          description 'Set maximum cost' ;
                          type empty ;

                        }

                      }

                    }

                    ncd:revise-date 2019-08-03 ;
                  }

                  container segment-routing {
                    description 'Configure segment-routing parameters' ;
                    container srv6 {
                      description 'Set IPv6 segment routing for IPv6 dataplane.' ;
                      leaf pspFlag {
                        if-feature segment-routing ;

                        description 'PSP flavour' ;
                        type enumeration {
                          enum enable {
                            value 1 ;
                            description 'enable' ;
                          }

                          enum disable {
                            value 0 ;
                            description 'disable' ;
                          }

                        }

                        default disable ;
                      }

                    }

                    ncd:revise-date 2019-08-20 ;
                  }

                  container cost-bfd-down {
                    description 'Configure interface cost when link detects bfd down.' ;
                    choice cost-bfd-down {
                      description 'Configure interface cost when link detects bfd down.' ;
                      case increase-value {
                        description 'Set increase cost when link detects bfd down.' ;
                        leaf increase-value {
                          description 'The increase cost value' ;
                          type uint16 {
                            range 100..10000 ;

                          }

                        }

                      }

                      case maximum {
                        description 'Set maximum cost when link detects bfd down.' ;
                        leaf maximum {
                          description 'Set maximum cost' ;
                          type empty ;

                        }

                      }

                    }

                    ncd:revise-date 2019-11-23 ;
                  }

                  container ti-lfa {
                    description 'tilfa attribute of interface' ;
                    list srlg {
                      description 'shared risk link group of this interface' ;
                      key srlg-id ;
                      leaf srlg-id {
                        description 'identity of srlg' ;
                        type uint32 ;

                      }

                    }

                    ncd:revise-date 2020-04-10 ;
                  }

                  container suppress-flapping {
                    description 'Suppress flapping.' ;
                    container adjacency {
                      description 'Suppress flapping for adjacency.' ;
                      leaf capability {
                        description 'Capability of suppress flapping for adjacency.' ;
                        type enumeration {
                          enum enable {
                            value 1 ;
                            description 'Enable suppress flapping for adjacency.' ;
                          }

                          enum disable {
                            value 2 ;
                            description 'Disable suppress flapping for adjacency.' ;
                          }

                        }

                      }

                      container detect-parameter {
                        description 'Set detect parameter of suppress flapping for adjacency.' ;
                        presence detect-parameter ;
                        leaf detect-interval {
                          description 'Detect interval.' ;
                          type uint16 {
                            range 1..300 ;

                          }

                          units second ;
                          mandatory true ;
                        }

                        leaf threshold {
                          description 'Threshold of flapping.' ;
                          type uint16 {
                            range 1..1000 ;

                          }

                          units second ;
                          mandatory true ;
                        }

                        leaf resume-interval {
                          description 'Resume interval.' ;
                          type uint16 {
                            range 2..1000 ;

                          }

                          units second ;
                          mandatory true ;
                        }

                      }

                      container hold-down {
                        description 'Hold down mode.' ;
                        presence hold-down ;
                        leaf hold-interval {
                          description 'Hold down interval.' ;
                          type uint16 {
                            range 1..600 ;

                          }

                          units second ;
                          mandatory true ;
                        }

                      }

                    }

                    ncd:revise-date 2020-07-23 ;
                  }

                  container virtual-system {
                    description 'Configure virtual system.' ;
                    presence virtual-system-presence ;
                    leaf router-id {
                      description 'Virtual system router-id.' ;
                      type ncd:ipv4-address ;

                      mandatory true ;
                    }

                    ncd:revise-date 2021-10-11 ;
                  }

                  container link-sd {
                    description 'Configure interface cost  when link is detected SD signal.' ;
                    presence link-sd ;
                    container cost {
                      description 'Configure interface cost when link is detected SD signal.' ;
                      choice cost {
                        description 'Configure interface cost when link is detected SD signal.' ;
                        default increase-value ;
                        case maximum {
                          description 'Set maximum cost when link is in detected SD signal.' ;
                          leaf maximum {
                            description 'Set maximum cost when link is in detected SD signal.' ;
                            type empty ;

                          }

                        }

                        case increase-value {
                          description 'Set increase cost when link is detected SD signal.' ;
                          leaf increase-value {
                            description 'Set increase cost when link is detected SD signal.' ;
                            type uint16 {
                              range 100..10000 ;

                            }

                            default 3000 ;
                          }

                        }

                      }

                    }

                    leaf capability {
                      default enable ;
                      description 'Configure link-SD capability.' ;
                      type enumeration {
                        enum enable {
                          value 1 ;
                          description 'Enable link-SD capability.' ;
                        }

                        enum disable {
                          description 'Disable link-SD capability.' ;
                          value 0 ;
                        }

                      }

                      ncd:revise-date 2023-04-07 ;
                    }

                    ncd:revise-date 2020-09-12 ;
                  }

                  container ldp-sync {
                    description 'Configure MPLS LDP IGP sync hold time and metric.' ;
                    container hold-time {
                      description 'Configure MPLS LDP IGP sync hold time.' ;
                      choice ldp-sync-hold-time {
                        description 'Configure MPLS LDP IGP sync hold time.' ;
                        case infinite {
                          description 'Configure ldp sync hold-timer never start.' ;
                          leaf infinite {
                            description 'Configure ldp sync hold-timer never start.' ;
                            type empty ;

                          }

                          ncd:revise-date 2021-06-15 ;
                        }

                        case hold-time-value {
                          description 'Configure time of ldp sync hold-timer.' ;
                          leaf hold-time-value {
                            description 'Configure time of ldp sync hold-timer.' ;
                            type uint16 {
                              range 1..65535 ;

                            }

                          }

                        }

                      }

                    }

                    container adjust-metric {
                      description 'Configure interface metric when ldp state is unachieved.' ;
                      choice adjust-metric {
                        description 'Configure interface metric when ldp state is unachieved.' ;
                        case increase-value {
                          description 'Configure interface increase metric when ldp sync state is unachieved.' ;
                          leaf increase-value {
                            description 'Configure interface increase metric when ldp sync state is unachieved.' ;
                            type uint16 {
                              range 100..10000 ;

                            }

                          }

                        }

                        case maximum {
                          description 'Configure interface metric to maximum when ldp state is unachieved.' ;
                          leaf maximum {
                            description 'Configure interface metric to maximum when ldp state is unachieved.' ;
                            type empty ;

                          }

                        }

                      }

                    }

                    ncd:revise-date 2021-06-15 ;
                  }

                  leaf fast-hello {
                    description 'Configure fast-hello send' ;
                    type enumeration {
                      enum disable {
                        value 0 ;
                      }

                      enum enable {
                        value 1 ;
                      }

                    }

                    default disable ;
                    ncd:revise-date 2021-08-06 ;
                  }

                  leaf hello-jitter {
                    description 'Configure hello jitter' ;
                    type enumeration {
                      enum disable {
                        value 0 ;
                      }

                      enum enable {
                        value 1 ;
                      }

                    }

                    default enable ;
                    ncd:revise-date 2022-03-09 ;
                  }

                  choice authentication {
                    case ipsec {
                      container ipsec {
                        description 'IPSEC configuration of interface.' ;
                        choice ipsec {
                          description 'IPSEC configuration of interface.' ;
                          case authentication {
                            description 'IPSEC authentication configuration of interface.' ;
                            container authentication {
                              description 'IPSEC authentication configuration of interface.' ;
                              presence intf-auth-presence ;
                              choice authentication {
                                description 'IPSEC authentication configuration of interface.' ;
                                case authentication-ipsec {
                                  description 'IPSEC authentication configuration of interface.' ;
                                  leaf spi-id {
                                    description 'Security parameters index ID.' ;
                                    type uint32 {
                                      range 256..32767 ;

                                    }

                                    mandatory true ;
                                  }

                                  container authentication-key {
                                    description 'Key of authentication algorithm.' ;
                                    choice authentication-key {
                                      description 'Key of authentication algorithm.' ;
                                      mandatory true ;
                                      case md5 {
                                        description 'Message Digest Algorithm.' ;
                                        choice md5-password-type {
                                          case unencrypted {
                                            leaf md5-key {
                                              description 'MD5 key.' ;
                                              type string {
                                                length 32 ;

                                              }

                                              mandatory true ;
                                            }

                                          }

                                          case encrypted {
                                            leaf encry-md5-key {
                                              description 'Encrypted md5 key.' ;
                                              type string {
                                                length 1..128 ;

                                              }

                                              mandatory true ;
                                            }

                                          }

                                        }

                                      }

                                      case sha1 {
                                        description 'Secure Hash Algorithm.' ;
                                        choice sha1-password-type {
                                          case unencrypted {
                                            leaf sha1-key {
                                              description 'SHA1 key.' ;
                                              type string {
                                                length 40 ;

                                              }

                                              mandatory true ;
                                            }

                                          }

                                          case encrypted {
                                            leaf encry-sha1-key {
                                              description 'Encrypted sha1 key.' ;
                                              type string {
                                                length 1..128 ;

                                              }

                                              mandatory true ;
                                            }

                                          }

                                        }

                                      }

                                      case keychain {
                                        description 'Keychain.' ;
                                        leaf keychain-name {
                                          description 'Keychain name.' ;
                                          type string {
                                            length 1..31 ;

                                          }

                                          mandatory true ;
                                        }

                                      }

                                    }

                                  }

                                  leaf roll-interval {
                                    description 'Rollover interval.' ;
                                    type uint32 {
                                      range 0..100000 ;

                                    }

                                    units minute ;
                                    default 0 ;
                                  }

                                }

                                case authentication-null {
                                  description 'NO authentication.' ;
                                  leaf authentication-null {
                                    description 'NO authentication.' ;
                                    type empty ;

                                    mandatory true ;
                                  }

                                }

                              }

                            }

                          }

                          case encryption {
                            description 'IPSEC encryption configuration of interface.' ;
                            container encryption {
                              description 'IPSEC encryption configuration of interface.' ;
                              presence intf-encryption-presence ;
                              choice encryption {
                                description 'IPSEC encryption configuration of interface.' ;
                                case encryption-ipsec {
                                  description 'IPSEC encryption configuration of interface.' ;
                                  leaf spi-id {
                                    description 'Security parameters index ID.' ;
                                    type uint32 {
                                      range 256..32767 ;

                                    }

                                    mandatory true ;
                                  }

                                  container encryption-key {
                                    description 'Key of encryption algorithm.' ;
                                    choice encryption-key {
                                      description 'Key of encryption algorithm.' ;
                                      mandatory true ;
                                      case null {
                                        description 'ESP without encryption.' ;
                                        leaf null {
                                          description 'NULL encryption.' ;
                                          type empty ;

                                          mandatory true ;
                                        }

                                      }

                                      case des {
                                        description 'Data Encrypt Standard algorithm.' ;
                                        choice des-password-type {
                                          case unencrypted {
                                            leaf des-key {
                                              description 'DES key.' ;
                                              type string {
                                                length 16 ;

                                              }

                                              mandatory true ;
                                            }

                                          }

                                          case encrypted {
                                            leaf encry-des-key {
                                              description 'Encrypted des key.' ;
                                              type string {
                                                length 1..128 ;

                                              }

                                              mandatory true ;
                                            }

                                          }

                                        }

                                      }

                                      case triple-des {
                                        description 'Triple Data Encryption algorithm.' ;
                                        choice triple-des-password-type {
                                          case unencrypted {
                                            leaf triple-des-key {
                                              description '3DES key.' ;
                                              type string {
                                                length 48 ;

                                              }

                                              mandatory true ;
                                            }

                                          }

                                          case encrypted {
                                            leaf encry-triple-des-key {
                                              description 'Encrypted 3des key.' ;
                                              type string {
                                                length 1..128 ;

                                              }

                                              mandatory true ;
                                            }

                                          }

                                        }

                                      }

                                      case aes-cbc {
                                        description 'Advanced Encryption Standard algorithm.' ;
                                        choice aes-password-type {
                                          case unencrypted {
                                            leaf aes-cbc-key {
                                              description 'AES key.' ;
                                              type string {
                                                length 32 ;

                                              }

                                              mandatory true ;
                                            }

                                          }

                                          case encrypted {
                                            leaf encry-aes-cbc-key {
                                              description 'Encrypted aes key.' ;
                                              type string {
                                                length 1..128 ;

                                              }

                                              mandatory true ;
                                            }

                                          }

                                        }

                                      }

                                      case keychain {
                                        description 'Keychain.' ;
                                        leaf keychain-name {
                                          description 'Keychain name.' ;
                                          type string {
                                            length 1..31 ;

                                          }

                                          mandatory true ;
                                        }

                                      }

                                    }

                                  }

                                  container authentication-key {
                                    description 'Key of authentication algorithm.' ;
                                    choice authentication-key {
                                      description 'Key of authentication algorithm.' ;
                                      mandatory true ;
                                      case md5 {
                                        description 'Message Digest Algorithm.' ;
                                        choice md5-password-type {
                                          case unencrypted {
                                            leaf md5-key {
                                              description 'MD5 key.' ;
                                              type string {
                                                length 32 ;

                                              }

                                              mandatory true ;
                                            }

                                          }

                                          case encrypted {
                                            leaf encry-md5-key {
                                              description 'Encrypted MD5 key.' ;
                                              type string {
                                                length 1..128 ;

                                              }

                                              mandatory true ;
                                            }

                                          }

                                        }

                                      }

                                      case sha1 {
                                        description 'Secure Hash Algorithm.' ;
                                        choice sha1-password-type {
                                          case unencrypted {
                                            leaf sha1-key {
                                              description 'SHA1 key.' ;
                                              type string {
                                                length 40 ;

                                              }

                                              mandatory true ;
                                            }

                                          }

                                          case encrypted {
                                            leaf encry-sha1-key {
                                              description 'Encrypted sha1 key.' ;
                                              type string {
                                                length 1..128 ;

                                              }

                                              mandatory true ;
                                            }

                                          }

                                        }

                                      }

                                      case keychain {
                                        description 'Keychain' ;
                                        leaf keychain-name {
                                          description 'Keychain name.' ;
                                          type string {
                                            length 1..31 ;

                                          }

                                          mandatory true ;
                                        }

                                      }

                                    }

                                  }

                                  leaf roll-interval {
                                    description 'Rollover interval.' ;
                                    type uint32 {
                                      range 0..100000 ;

                                    }

                                    units minute ;
                                    default 0 ;
                                  }

                                }

                                case encryption-null {
                                  description 'NO encryption.' ;
                                  leaf encryption-null {
                                    description 'NO encryption.' ;
                                    type empty ;

                                    mandatory true ;
                                  }

                                }

                              }

                            }

                          }

                        }

                      }

                    }

                    case keychain {
                      container keychain {
                        description 'Keychain configuration of interface.' ;
                        presence intf-auth-keychain-presence ;
                        leaf keychain-name {
                          description 'The name of interface authentication keychain.' ;
                          type string {
                            length 1..31 ;

                          }

                          mandatory true ;
                        }

                      }

                    }

                    ncd:revise-date 2021-10-09 ;
                  }

                  leaf wait-interval {
                    description 'Interval for the interface to exit waiting state' ;
                    type uint32 {
                      range 0..65535 ;

                    }

                    units second ;
                    ncd:revise-date 2023-01-17 ;
                  }

                  container bfd-flap-detect {
                    description 'Bfd flap detect.' ;
                    presence bfd-flap-detect ;
                    choice cost {
                      description 'Configure interface cost when BFD-flapping detected.' ;
                      case increase-value {
                        leaf increase-value {
                          description 'The increase cost value.' ;
                          type uint16 {
                            range 100..10000 ;

                          }

                        }

                      }

                      case maximum {
                        leaf maximum {
                          description 'Set maximum cost.' ;
                          type empty ;

                        }

                      }

                    }

                    container detect-parameter {
                      description 'Set detect parameter for BFD flapping.' ;
                      presence detect-parameter ;
                      leaf detect-interval {
                        description 'Detect interval value in seconds.' ;
                        type uint16 {
                          range 1..300 ;

                        }

                        units second ;
                        mandatory true ;
                      }

                      leaf threshold {
                        description 'Flapping count threshold.' ;
                        type uint16 {
                          range 1..10 ;

                        }

                        mandatory true ;
                      }

                      leaf resume-interval {
                        description 'Resume interval value in seconds.' ;
                        type uint16 {
                          range 1..3600 ;

                        }

                        units second ;
                        mandatory true ;
                      }

                    }

                    ncd:revise-date 2023-02-03 ;
                  }

                  container lag-flap-detect {
                    description 'Lag flap detect.' ;
                    presence lag-flap-detect ;
                    choice cost {
                      description 'Configure interface cost when LAG-flapping detected.' ;
                      case increase-value {
                        leaf increase-value {
                          description 'The increase cost value.' ;
                          type uint16 {
                            range 100..10000 ;

                          }

                        }

                      }

                      case maximum {
                        leaf maximum {
                          description 'Set maximum cost.' ;
                          type empty ;

                        }

                      }

                    }

                    container detect-parameter {
                      description 'Set detect parameter for LAG flapping.' ;
                      presence detect-parameter ;
                      leaf detect-interval {
                        description 'Detect interval value in seconds.' ;
                        type uint16 {
                          range 1..300 ;

                        }

                        units second ;
                        mandatory true ;
                      }

                      leaf threshold {
                        description 'Flapping count threshold.' ;
                        type uint16 {
                          range 1..10 ;

                        }

                        mandatory true ;
                      }

                      leaf resume-interval {
                        description 'Resume interval value in seconds.' ;
                        type uint16 {
                          range 1..3600 ;

                        }

                        units second ;
                        mandatory true ;
                      }

                    }

                    ncd:revise-date 2023-02-03 ;
                  }

                }

              }

              container stub {
                description 'Specify a stub area.' ;
                leaf no-summary {
                  description 'Do not inject inter-area routes into area.' ;
                  type empty ;

                }

                leaf default-cost {
                  description "Stub's advertised default summary cost." ;
                  type uint32 {
                    range 0..16777215 ;

                  }

                  default 1 ;
                }

                leaf default-origin {
                  description 'Notify default route in stub area.' ;
                  type empty ;

                  ncd:revise-date 2016-07-04 ;
                }

              }

              container virtual-links {
                description 'Configuration of virtual link.' ;
                list virtual-link {
                  description 'Configuration of virtual link.' ;
                  key neighbor-id ;
                  leaf neighbor-id {
                    description 'Router ID of the virtual link neighbor.' ;
                    type ncd:ipv4-address ;

                  }

                  leaf hello-interval {
                    description 'Time between hello packets over virtual link.' ;
                    type uint32 {
                      range 1..8192 ;

                    }

                    units second ;
                    default 10 ;
                  }

                  leaf dead-interval {
                    description 'Interval after which a virtual link neighbor is declared dead.' ;
                    type uint32 {
                      range 1..8192 ;

                    }

                    units second ;
                  }

                  leaf retransmit-interval {
                    description 'Time between retransmitting lost link state advertisements over virtual link.' ;
                    type uint32 {
                      range 1..8192 ;

                    }

                    units second ;
                    default 5 ;
                  }

                  leaf transmit-delay {
                    description 'LSA transmit delay over virtual link.' ;
                    type uint32 {
                      range 1..8192 ;

                    }

                    units second ;
                    default 1 ;
                  }

                  container ipsec {
                    description 'IPSEC configuration of virtual link.' ;
                    choice ipsec {
                      description 'IPSEC configuration of virtual link.' ;
                      case authentication {
                        description 'IPSEC authentication configuration of virtual link.' ;
                        container authentication {
                          description 'IPSEC authentication configuration of virtual link.' ;
                          presence vlink-auth-presence ;
                          leaf spi-id {
                            description 'Security parameters index ID.' ;
                            type uint32 {
                              range 256..32767 ;

                            }

                            mandatory true ;
                          }

                          container authentication-key {
                            description 'Key of authentication algorithm.' ;
                            choice authentication-key {
                              description 'Key of authentication algorithm.' ;
                              mandatory true ;
                              case md5 {
                                description 'Message Digest Algorithm.' ;
                                choice md5-password-type {
                                  case unencrypted {
                                    leaf md5-key {
                                      description 'MD5 key.' ;
                                      type string {
                                        length 32 ;

                                      }

                                      mandatory true ;
                                    }

                                  }

                                  case encrypted {
                                    leaf encry-md5-key {
                                      description 'Encrypted MD5 key.' ;
                                      type string {
                                        length 1..128 ;

                                      }

                                      mandatory true ;
                                    }

                                    ncd:revise-date 2019-12-16 ;
                                  }

                                }

                              }

                              case sha1 {
                                description 'Secure Hash Algorithm.' ;
                                choice sha1-password-type {
                                  case unencrypted {
                                    leaf sha1-key {
                                      description 'SHA1 key.' ;
                                      type string {
                                        length 40 ;

                                      }

                                      mandatory true ;
                                    }

                                  }

                                  case encrypted {
                                    leaf encry-sha1-key {
                                      description 'Encrypted SHA1 key.' ;
                                      type string {
                                        length 1..128 ;

                                      }

                                      mandatory true ;
                                    }

                                    ncd:revise-date 2019-12-16 ;
                                  }

                                }

                              }

                              case keychain {
                                description 'Keychain.' ;
                                leaf keychain-name {
                                  description 'Keychain name.' ;
                                  type string {
                                    length 1..31 ;

                                  }

                                  mandatory true ;
                                }

                                ncd:revise-date 2017-06-04 ;
                              }

                            }

                          }

                          leaf roll-interval {
                            description 'Rollover interval.' ;
                            type uint32 {
                              range 0..100000 ;

                            }

                            units minute ;
                            default 0 ;
                          }

                        }

                      }

                      case encryption {
                        description 'IPSEC encryption configuration of virtual link.' ;
                        container encryption {
                          description 'IPSEC encryption configuration of virtual link.' ;
                          presence vlink-encryption-presence ;
                          leaf spi-id {
                            description 'Security parameters index ID.' ;
                            type uint32 {
                              range 256..32767 ;

                            }

                            mandatory true ;
                          }

                          container encryption-key {
                            description 'Key of encryption algorithm. Must be configured with authentication-key.' ;
                            choice encryption-key {
                              description 'Key of encryption algorithm.' ;
                              mandatory true ;
                              case null {
                                description 'NULL encryption.' ;
                                leaf null {
                                  description 'NULL encryption.' ;
                                  type empty ;

                                  mandatory true ;
                                }

                              }

                              case des {
                                description 'Data Encrypt Standard algorithm.' ;
                                choice des-password-type {
                                  case unencrypted {
                                    leaf des-key {
                                      description 'DES key.' ;
                                      type string {
                                        length 16 ;

                                      }

                                      mandatory true ;
                                    }

                                  }

                                  case encrypted {
                                    leaf encry-des-key {
                                      description 'Encrypted des key.' ;
                                      type string {
                                        length 1..128 ;

                                      }

                                      mandatory true ;
                                    }

                                    ncd:revise-date 2019-12-16 ;
                                  }

                                }

                              }

                              case triple-des {
                                description 'Triple Data Encryption algorithm.' ;
                                choice triple-des-password-type {
                                  case unencrypted {
                                    leaf triple-des-key {
                                      description '3DES key.' ;
                                      type string {
                                        length 48 ;

                                      }

                                      mandatory true ;
                                    }

                                  }

                                  case encrypted {
                                    leaf encry-triple-des-key {
                                      description 'Encrypted 3des key.' ;
                                      type string {
                                        length 1..128 ;

                                      }

                                      mandatory true ;
                                    }

                                    ncd:revise-date 2019-12-16 ;
                                  }

                                }

                              }

                              case aes-cbc {
                                description 'Advanced Encryption Standard algorithm.' ;
                                choice aes-password-type {
                                  case unencrypted {
                                    leaf aes-cbc-key {
                                      description 'AES key.' ;
                                      type string {
                                        length 32 ;

                                      }

                                      mandatory true ;
                                    }

                                  }

                                  case encrypted {
                                    leaf encry-aes-cbc-key {
                                      description 'Encrypted aes key.' ;
                                      type string {
                                        length 1..128 ;

                                      }

                                      mandatory true ;
                                    }

                                    ncd:revise-date 2019-12-16 ;
                                  }

                                }

                              }

                              case keychain {
                                description 'Keychain.' ;
                                leaf keychain-name {
                                  description 'Keychain name.' ;
                                  type string {
                                    length 1..31 ;

                                  }

                                  mandatory true ;
                                }

                                ncd:revise-date 2017-06-04 ;
                              }

                            }

                          }

                          container authentication-key {
                            description 'Key of authentication algorithm. Must be configured with encryption-key.' ;
                            choice authentication-key {
                              description 'Key of authentication algorithm.' ;
                              mandatory true ;
                              case md5 {
                                description 'Message Digest Algorithm.' ;
                                choice md5-password-type {
                                  case unencrypted {
                                    leaf md5-key {
                                      description 'MD5 key.' ;
                                      type string {
                                        length 32 ;

                                      }

                                      mandatory true ;
                                    }

                                  }

                                  case encrypted {
                                    leaf encry-md5-key {
                                      description 'Encrypted MD5 key.' ;
                                      type string {
                                        length 1..128 ;

                                      }

                                      mandatory true ;
                                    }

                                    ncd:revise-date 2019-12-16 ;
                                  }

                                }

                              }

                              case sha1 {
                                description 'Secure Hash Algorithm.' ;
                                choice sha1-password-type {
                                  case unencrypted {
                                    leaf sha1-key {
                                      description 'SHA1 key.' ;
                                      type string {
                                        length 40 ;

                                      }

                                      mandatory true ;
                                    }

                                  }

                                  case encrypted {
                                    leaf encry-sha1-key {
                                      description 'Encrypted sha1 key.' ;
                                      type string {
                                        length 1..128 ;

                                      }

                                      mandatory true ;
                                    }

                                    ncd:revise-date 2019-12-16 ;
                                  }

                                }

                              }

                              case keychain {
                                description 'Keychain' ;
                                leaf keychain-name {
                                  description 'Keychain name.' ;
                                  type string {
                                    length 1..31 ;

                                  }

                                  mandatory true ;
                                }

                                ncd:revise-date 2017-06-04 ;
                              }

                            }

                          }

                          leaf roll-interval {
                            description 'Rollover interval.' ;
                            type uint32 {
                              range 0..100000 ;

                            }

                            units minute ;
                            default 0 ;
                          }

                        }

                      }

                    }

                  }

                }

              }

              container nssa {
                description 'Specify a NSSA area' ;
                leaf translator-role {
                  description "Config the router's translator role when translating type-7 route to type-5 route" ;
                  type enumeration {
                    enum candidate {
                      value 0 ;
                      description 'The router is a member of candidate list' ;
                    }

                    enum always {
                      value 1 ;
                      description 'The router is always a translator' ;
                    }

                  }

                  default candidate ;
                }

                leaf trans-stab-interval {
                  description 'The interval of keep translating when translating state becomes disable' ;
                  type uint32 {
                    range 0..65535 {
                      description 'The interval of keep translating when translating state becomes disable' ;
                    }

                  }

                  default 40 ;
                }

                leaf no-summary {
                  description 'Do not send summary LSA into area' ;
                  type empty ;

                }

                leaf no-redistribution {
                  description 'Do not redistribute external LSA into NSSA area' ;
                  type empty ;

                }

                leaf suppress-fa {
                  description 'Suppress FA when translating Type-7 to Type-5' ;
                  type empty ;

                }

                container default-information-originate {
                  description 'nssa area default information config' ;
                  presence default-information-originate-presence ;
                  leaf metric {
                    description 'The metric of default type-7 route' ;
                    type uint32 {
                      range 1..16777214 {
                        description 'The metric of default type-7 route' ;
                      }

                    }

                    default 1 ;
                  }

                  leaf metric-type {
                    description 'The metric type of default type-7 route' ;
                    type enumeration {
                      enum ext-2 {
                        value 0 ;
                        description 'The metric of default type-7 route is ext-2' ;
                      }

                      enum ext-1 {
                        value 1 ;
                        description 'The metric of default type-7 route is ext-1' ;
                      }

                    }

                    default ext-2 ;
                  }

                }

                ncd:revise-date 2020-05-21 ;
              }

              container multi-area-interfaces {
                description 'Configure multi-area adjacency' ;
                list multi-area-interface {
                  description 'Configure multi-area adjacency on this interface' ;
                  key interface-name ;
                  leaf interface-name {
                    description 'Interface name' ;
                    type ncd:ifname {
                      length 1..31 ;

                    }

                  }

                  leaf hello-interval {
                    description 'The time between hello packets, Seconds' ;
                    type uint32 {
                      range 1..65535 ;

                    }

                    units second ;
                  }

                  leaf dead-interval {
                    description 'The interval after which a neighbor is declared dead, Seconds' ;
                    type uint32 {
                      range 1..65535 ;

                    }

                    units second ;
                  }

                  leaf cost {
                    description 'The cost of sending a data packet on the interface, expressed in the link state metric.' ;
                    type uint32 {
                      range 1..65535 ;

                    }

                  }

                  leaf mtu-ignore {
                    description 'Ignore the mtu mismatch when exchanging DD packet' ;
                    type empty ;

                  }

                  leaf retransmit-interval {
                    description 'Time between retransmitting lost link state advertisements, Seconds' ;
                    type uint32 {
                      range 1..65535 ;

                    }

                    units second ;
                    default 5 ;
                  }

                  leaf transmit-delay {
                    description 'The estimated number of seconds it takes to transmit a LSU packet over this interface.' ;
                    type uint32 {
                      range 1..65535 ;

                    }

                    units second ;
                    default 1 ;
                  }

                  container authentication {
                    description 'Authentication' ;
                    choice authentication {
                      description 'Authentication' ;
                      case keychain {
                        description 'Authentication keychain name' ;
                        leaf keychain {
                          description 'Authentication keychain name' ;
                          type string {
                            length 1..31 ;

                          }

                        }

                      }

                    }

                  }

                }

                ncd:revise-date 2020-08-20 ;
              }

              container mpls {
                description 'MPLS configuration of area.' ;
                leaf traffic-eng {
                  description 'Configure traffic-eng capability for OSPFv3 area.' ;
                  type enumeration {
                    enum enable {
                      value 1 ;
                      description 'Enable traffic-eng capability of the area.' ;
                    }

                    enum disable {
                      value 0 ;
                      description 'Disable traffic-eng capability of the area.' ;
                    }

                  }

                  default disable ;
                }

                ncd:revise-date 2021-02-25 ;
              }

              choice authentication {
                case ipsec {
                  container ipsec {
                    description 'IPSEC configuration of area.' ;
                    choice ipsec {
                      description 'IPSEC configuration of area.' ;
                      case authentication {
                        description 'IPSEC authentication configuration of area.' ;
                        container authentication {
                          description 'IPSEC authentication configuration of area.' ;
                          presence area-auth-presence ;
                          leaf spi-id {
                            description 'Security parameters index ID.' ;
                            type uint32 {
                              range 256..32767 ;

                            }

                            mandatory true ;
                          }

                          container authentication-key {
                            description 'Key of authentication algorithm.' ;
                            choice authentication-key {
                              description 'Key of authentication algorithm.' ;
                              mandatory true ;
                              case md5 {
                                description 'Message Digest Algorithm.' ;
                                choice md5-password-type {
                                  case unencrypted {
                                    leaf md5-key {
                                      description 'MD5 key.' ;
                                      type string {
                                        length 32 ;

                                      }

                                      mandatory true ;
                                    }

                                  }

                                  case encrypted {
                                    leaf encry-md5-key {
                                      description 'Encrypted MD5 key.' ;
                                      type string {
                                        length 1..128 ;

                                      }

                                      mandatory true ;
                                    }

                                  }

                                }

                              }

                              case sha1 {
                                description 'Secure Hash Algorithm.' ;
                                choice sha1-password-type {
                                  case unencrypted {
                                    leaf sha1-key {
                                      description 'SHA1 key.' ;
                                      type string {
                                        length 40 ;

                                      }

                                      mandatory true ;
                                    }

                                  }

                                  case encrypted {
                                    leaf encry-sha1-key {
                                      description 'SHA1 key.' ;
                                      type string {
                                        length 1..128 ;

                                      }

                                      mandatory true ;
                                    }

                                  }

                                }

                              }

                              case keychain {
                                description 'Keychain.' ;
                                leaf keychain-name {
                                  description 'Keychain name.' ;
                                  type string {
                                    length 1..31 ;

                                  }

                                  mandatory true ;
                                }

                              }

                            }

                          }

                          leaf roll-interval {
                            description 'Rollover interval.' ;
                            type uint32 {
                              range 0..100000 ;

                            }

                            units minute ;
                            default 0 ;
                          }

                        }

                      }

                      case encryption {
                        description 'IPSEC encryption configuration of area.' ;
                        container encryption {
                          description 'IPSEC encryption configuration of area.' ;
                          presence area-encryption-presence ;
                          leaf spi-id {
                            description 'Security parameters index ID.' ;
                            type uint32 {
                              range 256..32767 ;

                            }

                            mandatory true ;
                          }

                          container encryption-key {
                            description 'Key of encryption algorithm.' ;
                            choice encryption-key {
                              description 'Key of encryption algorithm.' ;
                              mandatory true ;
                              case null {
                                description 'NULL encryption.' ;
                                leaf null {
                                  description 'NULL encryption.' ;
                                  type empty ;

                                  mandatory true ;
                                }

                              }

                              case des {
                                description 'Data Encrypt Standard algorithm.' ;
                                choice des-password-type {
                                  case unencrypted {
                                    leaf des-key {
                                      description 'DES key.' ;
                                      type string {
                                        length 16 ;

                                      }

                                      mandatory true ;
                                    }

                                  }

                                  case encrypted {
                                    leaf encry-des-key {
                                      description 'Encrypted des key.' ;
                                      type string {
                                        length 1..128 ;

                                      }

                                      mandatory true ;
                                    }

                                  }

                                }

                              }

                              case triple-des {
                                description 'Triple Data Encryption algorithm.' ;
                                choice triple-des-password-type {
                                  case unencrypted {
                                    leaf triple-des-key {
                                      description '3DES key.' ;
                                      type string {
                                        length 48 ;

                                      }

                                      mandatory true ;
                                    }

                                  }

                                  case encrypted {
                                    leaf encry-triple-des-key {
                                      description 'Encrypted 3DES key.' ;
                                      type string {
                                        length 1..128 ;

                                      }

                                      mandatory true ;
                                    }

                                  }

                                }

                              }

                              case aes-cbc {
                                description 'Advanced Encryption Standard algorithm.' ;
                                choice aes-password-type {
                                  case unencrypted {
                                    leaf aes-cbc-key {
                                      description 'AES key.' ;
                                      type string {
                                        length 32 ;

                                      }

                                      mandatory true ;
                                    }

                                  }

                                  case encrypted {
                                    leaf encry-aes-cbc-key {
                                      description 'AES key.' ;
                                      type string {
                                        length 1..128 ;

                                      }

                                      mandatory true ;
                                    }

                                  }

                                }

                              }

                              case keychain {
                                description 'Keychain.' ;
                                leaf keychain-name {
                                  description 'Keychain name.' ;
                                  type string {
                                    length 1..31 ;

                                  }

                                  mandatory true ;
                                }

                              }

                            }

                          }

                          container authentication-key {
                            description 'Key of authentication algorithm.' ;
                            choice authentication-key {
                              description 'Key of authentication algorithm.' ;
                              mandatory true ;
                              case md5 {
                                description 'Message Digest Algorithm.' ;
                                choice md5-password-type {
                                  case unencrypted {
                                    leaf md5-key {
                                      description 'MD5 key.' ;
                                      type string {
                                        length 32 ;

                                      }

                                      mandatory true ;
                                    }

                                  }

                                  case encrypted {
                                    leaf encry-md5-key {
                                      description 'Encrypted MD5 key.' ;
                                      type string {
                                        length 1..128 ;

                                      }

                                      mandatory true ;
                                    }

                                  }

                                }

                              }

                              case sha1 {
                                description 'Secure Hash Algorithm.' ;
                                choice sha1-password-type {
                                  case unencryted {
                                    leaf sha1-key {
                                      description 'SHA1 key.' ;
                                      type string {
                                        length 40 ;

                                      }

                                      mandatory true ;
                                    }

                                  }

                                  case encrypted {
                                    leaf encry-sha1-key {
                                      description 'Encrypted SHA1 key.' ;
                                      type string {
                                        length 1..128 ;

                                      }

                                      mandatory true ;
                                    }

                                  }

                                }

                              }

                              case keychain {
                                description 'Keychain' ;
                                leaf keychain-name {
                                  description 'Keychain name.' ;
                                  type string {
                                    length 1..31 ;

                                  }

                                  mandatory true ;
                                }

                              }

                            }

                          }

                          leaf roll-interval {
                            description 'Rollover interval.' ;
                            type uint32 {
                              range 0..100000 ;

                            }

                            units minute ;
                            default 0 ;
                          }

                        }

                      }

                    }

                  }

                }

                case keychain {
                  container keychain {
                    description 'Keychain configuration of area.' ;
                    presence area-auth-keychain-presence ;
                    leaf keychain-name {
                      description 'The name of area authentication keychain.' ;
                      type string {
                        length 1..31 ;

                      }

                      mandatory true ;
                    }

                  }

                }

                ncd:revise-date 2021-10-09 ;
              }

            }

          }

          container domain-ids {
            description 'OSPFv3 domain ID configuration.' ;
            list domain-id {
              description 'OSPFv3 domain ID configuration.' ;
              key 'type value' ;
              leaf type {
                description 'domain ID type.' ;
                type enumeration {
                  enum 0005 {
                    value 1 ;
                    description 'Type 0x0005.' ;
                  }

                  enum 0105 {
                    value 2 ;
                    description 'Type 0x0105.' ;
                  }

                  enum 0205 {
                    value 3 ;
                    description 'Type 0x0205.' ;
                  }

                  enum 8005 {
                    description 'Type 0x8005.' ;
                    value 4 ;
                  }

                }

              }

              leaf value {
                description 'domain ID value.' ;
                type string {
                  length 12 ;

                }

              }

              leaf flag {
                description 'Specify the domain ID is primary domain ID or secondary domain ID.' ;
                type enumeration {
                  enum primary {
                    value 0 ;
                    description 'Primary domain ID.' ;
                  }

                  enum secondary {
                    value 1 ;
                    description 'Secondary domain ID.' ;
                  }

                }

              }

            }

            ncd:revise-date 2016-07-04 ;
          }

          container distance-policy {
            if-feature distance-policy ;

            description 'Distance of policy.' ;
            leaf policy-type {
              description 'The type of policy.' ;
              type enumeration {
                enum route-policy {
                  value 1 ;
                  description 'Route-type is route-policy.' ;
                }

                enum route-map {
                  value 2 ;
                  description 'Route-type is route-map.' ;
                }

              }

            }

            leaf policy-name {
              description 'The name of policy.' ;
              type string {
                length 1..200 {
                  description 'Name of policy,characters from 1 to 200.' ;
                }

              }

            }

            ncd:revise-date 2018-11-28 ;
          }

          container segment-routing {
            description 'Configure segment-routing parameters' ;
            container mpls {
              description 'Configure segment-routing mpls parameters' ;
              leaf capability {
                if-feature segment-routing ;

                description 'Configure segment-routing mpls capability' ;
                type enumeration {
                  enum enable {
                    value 1 ;
                    description 'enable' ;
                  }

                  enum disable {
                    value 2 ;
                    description 'disable' ;
                  }

                }

                default disable ;
              }

              container adj-sid {
                description 'Set segment routing MPLS adj-sid type.' ;
                leaf type {
                  description 'Configure segment routing MPLS adj-sid type.' ;
                  type enumeration {
                    enum hybrid {
                      value 1 ;
                      description 'hybrid' ;
                    }

                    enum static {
                      value 2 ;
                      description 'static' ;
                    }

                  }

                  default hybrid ;
                }

                ncd:revise-date 2020-03-28 ;
              }

              container entropy-label {
                description 'Configure segment routing mpls entropy label.' ;
                leaf capability {
                  description 'Configure segment routing mpls entropy label.' ;
                  type enumeration {
                    enum enable {
                      value 1 ;
                      description 'Enable' ;
                    }

                    enum disable {
                      value 2 ;
                      description 'Disable' ;
                    }

                  }

                  default disable ;
                }

                ncd:revise-date 2019-11-13 ;
              }

            }

            container srv6 {
              description 'Set IPv6 segment routing for IPv6 dataplane.' ;
              leaf capability {
                if-feature segment-routing ;

                description 'Configure  capability' ;
                type enumeration {
                  enum enable {
                    value 1 ;
                    description 'enable' ;
                  }

                  enum disable {
                    value 2 ;
                    description 'disable' ;
                  }

                }

                default disable ;
              }

              leaf compress {
                type enumeration {
                  enum uet-32 {
                    value 1 ;
                    description 'Specify the compress algorithm is uet-32.' ;
                  }

                  enum uet-128 {
                    value 0 ;
                    description 'Specify the compress algorithm is uet-128.' ;
                  }

                }

                description 'Set IPv6 segment routing with compressibility.' ;
                default uet-128 ;
                ncd:revise-date 2024-01-10 ;
              }

              leaf pspFlag {
                if-feature segment-routing ;

                description 'PSP flavour' ;
                type enumeration {
                  enum enable {
                    value 1 ;
                    description 'enable' ;
                  }

                  enum disable {
                    value 0 ;
                    description 'disable' ;
                  }

                }

                default disable ;
              }

              container locators {
                description 'SRv6 locator configuration.' ;
                list locator {
                  description 'SRv6 locator configuration.' ;
                  key locator-name ;
                  leaf locator-name {
                    description 'The name of locator.' ;
                    type string {
                      length 1..31 ;

                    }

                  }

                  leaf adjacency-set {
                    type enumeration {
                      enum disable {
                        value 0 ;
                        description 'Disable the SID refers to a set of adjacencies.' ;
                      }

                      enum enable {
                        value 1 ;
                        description 'Enable the SID refers to a set of adjacencies.' ;
                      }

                    }

                    description 'Configure a set of OSPFv3 neighbor adjacencies.' ;
                    default disable ;
                    if-feature srv6-adjacency-set {
                      ncd:revise-date 2025-05-14 ;
                    }

                    ncd:revise-date 2025-03-05 ;
                  }

                  container end-sids {
                    description 'End-SID configuration.' ;
                    list end-sid {
                      description 'End-SID configuration.' ;
                      key func-code ;
                      leaf func-code {
                        description 'The function code of End-SID.' ;
                        type ncd:ipv6-address ;

                      }

                      leaf psp {
                        description 'The PSP attribute of End-SID. The valid value range is 0 - 1.' ;
                        type int8 {
                          range 0..1 ;

                        }

                        default 0 ;
                      }

                      leaf usp {
                        description 'The USP attribute of End-SID. The valid value range is 0 - 1.' ;
                        type int8 {
                          range 0..1 ;

                        }

                        default 0 ;
                      }

                      leaf usd {
                        type int8 {
                          range 0..1 ;

                        }

                        default 0 ;
                        description 'The USD attribute of End-SID. The valid value range is 0 - 1.' ;
                        ncd:revise-date 2023-03-24 ;
                      }

                    }

                    list end-sid-compress {
                      description 'Compressed End-SID configuration.' ;
                      key func-code ;
                      leaf func-code {
                        description 'The function code of End-SID.' ;
                        type ncd:ipv6-address ;

                      }

                      leaf psp {
                        type uint8 {
                          range 0..1 ;

                        }

                        description 'The PSP attribute of End-SID. The valid value range is 0 - 1.' ;
                        default 0 ;
                      }

                      leaf usp {
                        type uint8 {
                          range 0..1 ;

                        }

                        description 'The USP attribute of End-SID. The valid value range is 0 - 1.' ;
                        default 0 ;
                      }

                      leaf usd {
                        description 'The USD attribute of End-SID. The valid value range is 0 - 1.' ;
                        default 0 ;
                        type uint8 {
                          range 0..1 ;

                        }

                      }

                      leaf encap-type {
                        description 'The encapsulation type attribute of End SID.' ;
                        default uet-128 ;
                        type enumeration {
                          enum uet-128 {
                            value 0 ;
                          }

                          enum uet-32 {
                            value 1 ;
                          }

                        }

                      }

                      ncd:revise-date 2024-01-10 ;
                    }

                  }

                  container end-x-sids {
                    description 'End-X-SID configuration.' ;
                    list end-x-sid {
                      description 'End-X-SID configuration.' ;
                      key func-code ;
                      leaf func-code {
                        description 'The function code of End-X-SID.' ;
                        type ncd:ipv6-address ;

                      }

                      leaf interface-name {
                        description 'The name of interface associated with End-X-SID.' ;
                        type ncd:ifname {
                          length 1..31 ;

                        }

                        mandatory true ;
                      }

                      leaf neighbor-id {
                        description 'The router-id of neighbor associated with End-X-SID.' ;
                        type ncd:ipv4-address ;

                      }

                      leaf psp {
                        description 'The PSP attribute of End.X SID. The valid value range is 0 - 1.' ;
                        type uint8 {
                          range 0..1 ;

                        }

                        default 0 ;
                      }

                      leaf usp {
                        description 'The USP attribute of End.X SID. The valid value range is 0 - 1.' ;
                        type uint8 {
                          range 0..1 ;

                        }

                        default 0 ;
                      }

                      leaf usd {
                        type uint8 {
                          range 0..1 ;

                        }

                        default 0 ;
                        description 'The USD attribute of End.X SID. The valid value range is 0 - 1.' ;
                        ncd:revise-date 2023-03-24 ;
                      }

                    }

                    list end-x-sid-compress {
                      leaf func-code {
                        type ncd:ipv6-address ;

                        description 'The function code of End-X-SID.' ;
                      }

                      leaf interface-name {
                        type ncd:ifname {
                          length 1..31 ;

                        }

                        description 'The name of interface associated with End-X-SID.' ;
                        mandatory true ;
                      }

                      leaf neighbor-id {
                        type ncd:ipv4-address ;

                        description 'The router-id of neighbor associated with End-X-SID.' ;
                      }

                      leaf psp {
                        type uint8 {
                          range 0..1 ;

                        }

                        description 'The PSP attribute of End.X SID. The valid value range is 0 - 1.' ;
                        default 0 ;
                      }

                      leaf usp {
                        type uint8 {
                          range 0..1 ;

                        }

                        description 'The USP attribute of End.X SID. The valid value range is 0 - 1.' ;
                        default 0 ;
                      }

                      leaf usd {
                        type uint8 {
                          range 0..1 ;

                        }

                        description 'The USD attribute of End.X SID. The valid value range is 0 - 1.' ;
                        default 0 ;
                      }

                      description 'Compress End-X-SID configuration.' ;
                      leaf encap-type {
                        description 'Specify the compress algorithm.' ;
                        default uet-128 ;
                        type enumeration {
                          enum uet-32 {
                            description 'Specify the compress algorithm is uet-32.' ;
                            value 1 ;
                          }

                          enum uet-128 {
                            description 'Specify the compress algorithm is uet-128.' ;
                            value 0 ;
                          }

                        }

                      }

                      key func-code ;
                      ncd:revise-date 2024-01-10 ;
                    }

                  }

                  container end-sid-auto {
                    description 'Configure the SRv6 End SID automatically.' ;
                    presence end-sid-auto ;
                    leaf psp {
                      description 'The PSP attribute of End-SID-AUTO.' ;
                      type empty ;

                    }

                    leaf usp {
                      description 'The USP attribute of End-SID-AUTO.' ;
                      type empty ;

                    }

                    leaf usd {
                      type empty ;

                      description 'The USD attribute of End-SID-AUTO.' ;
                      ncd:revise-date 2023-03-24 ;
                    }

                    ncd:revise-date 2021-01-08 ;
                  }

                  container end-x-sid-auto {
                    description 'Configure the SRv6 End X SID automatically.' ;
                    presence end-x-sid-auto ;
                    leaf psp {
                      description 'The PSP attribute of End-X-SID-AUTO.' ;
                      type empty ;

                    }

                    leaf usp {
                      description 'The USP attribute of End-X-SID-AUTO.' ;
                      type empty ;

                    }

                    leaf usd {
                      type empty ;

                      description 'The USD attribute of End-X-SID-AUTO.' ;
                      ncd:revise-date 2023-03-24 ;
                    }

                    ncd:revise-date 2021-01-08 ;
                  }

                  container end-x-multi-sid-autos {
                    list end-x-multi-sid-auto {
                      leaf psp {
                        description 'The PSP attribute of End.X SID.' ;
                        type uint8 {
                          range 0..1 ;

                        }

                        default 0 ;
                      }

                      leaf usp {
                        description 'The USP attribute of End.X SID.' ;
                        type uint8 {
                          range 0..1 ;

                        }

                        default 0 ;
                      }

                      leaf usd {
                        description 'The USD attribute of End.X SID.' ;
                        type uint8 {
                          range 0..1 ;

                        }

                        default 0 ;
                      }

                      key 'psp usp usd' ;
                      description 'Configure the SRv6 multiple End.X SID automatically.' ;
                    }

                    description 'Configure the SRv6 multiple End.X SID automatically.' ;
                    list end-x-multi-sid-auto-compress {
                      leaf encap-type {
                        description 'The  encapsulation type of End.X SID.' ;
                        type enumeration {
                          enum uet-32 {
                            value 1 ;
                          }

                          enum uet-128 {
                            value 0 ;
                          }

                        }

                      }

                      leaf psp {
                        description 'The PSP attribute of End.X SID.' ;
                        type uint8 {
                          range 0..1 ;

                        }

                      }

                      leaf usp {
                        description 'The USP attribute of End.X SID.' ;
                        type uint8 {
                          range 0..1 ;

                        }

                      }

                      leaf usd {
                        type uint8 {
                          range 0..1 ;

                        }

                        description 'The USD attribute of End.X SID.' ;
                      }

                      description 'Configure the SRv6 multiple compression End.X SID automatically.' ;
                      key 'encap-type psp usp usd' ;
                      ncd:revise-date 2024-01-10 ;
                    }

                    ncd:revise-date 2023-03-24 ;
                  }

                  container end-multi-sid-autos {
                    list end-multi-sid-auto {
                      leaf psp {
                        type uint8 {
                          range 0..1 ;

                        }

                        default 0 ;
                        description 'The PSP attribute of End SID.' ;
                      }

                      leaf usp {
                        type uint8 {
                          range 0..1 ;

                        }

                        default 0 ;
                        description 'The USP attribute of End SID.' ;
                      }

                      leaf usd {
                        type uint8 {
                          range 0..1 ;

                        }

                        default 0 ;
                        description 'The USD attribute of End SID.' ;
                      }

                      key 'psp usp usd' ;
                      description 'Configure the SRv6 multiple End SID automatically.' ;
                    }

                    description 'Configure the SRv6 multiple End SID automatically.' ;
                    list end-multi-sid-auto-compress {
                      description 'Configure the SRv6 multiple compressed End SID automatically.' ;
                      key 'psp usp usd encap-type' ;
                      leaf psp {
                        description 'The PSP attribute of End SID.' ;
                        type uint8 {
                          range 0..1 ;

                        }

                      }

                      leaf usp {
                        type uint8 {
                          range 0..1 ;

                        }

                        description 'The USP attribute of End SID.' ;
                      }

                      leaf usd {
                        type uint8 {
                          range 0..1 ;

                        }

                        description 'The USD attribute of End SID.' ;
                      }

                      leaf encap-type {
                        description 'The encapsulation type attribute of End SID.' ;
                        type enumeration {
                          enum uet-128 {
                            value 0 ;
                          }

                          enum uet-32 {
                            value 1 ;
                          }

                        }

                      }

                      ncd:revise-date 2024-01-10 ;
                    }

                    ncd:revise-date 2023-03-24 ;
                  }

                }

                ncd:revise-date 2020-09-23 ;
              }

              leaf locator-fixed-length {
                description 'Configure compatibility mode for locator-fixed-length.' ;
                default disable ;
                type enumeration {
                  enum enable {
                    value 1 ;
                    description 'Enable' ;
                  }

                  enum disable {
                    value 2 ;
                    description 'Disable' ;
                  }

                }

                ncd:revise-date 2024-05-22 ;
              }

              ncd:revise-date 2019-08-20 ;
            }

            ncd:revise-date 2019-03-28 ;
          }

          container bgp-ls {
            description 'Distribute link-state data using BGP.' ;
            presence bgp-ls ;
            leaf instance-id {
              description 'Link-state data instance identifier.' ;
              type uint32 {
                range 0..65535 ;

              }

              default 0 ;
            }

            ncd:revise-date 2019-07-11 ;
          }

          container frr {
            description 'OSPF fast reroute parameters' ;
            presence fast-route ;
            container ti-lfa {
              description 'Set OSPF TI-LFA' ;
              presence ti-lfa ;
              container protection-type {
                description 'Specify protection type' ;
                presence protection-type ;
                leaf node-protecting {
                  description 'Specify node protecting' ;
                  type empty ;

                }

              }

              leaf srv6 {
                if-feature segment-routing ;

                description 'Configure srv6 fast-reroute TI-LFA' ;
                type enumeration {
                  enum enable {
                    value 1 ;
                    description 'enable' ;
                  }

                  enum disable {
                    value 2 ;
                    description 'disable' ;
                  }

                }

                default disable ;
              }

              leaf sr-mpls {
                if-feature segment-routing ;

                description 'Configure sr-mpls fast-reroute TI-LFA' ;
                type enumeration {
                  enum enable {
                    value 1 ;
                    description 'enable' ;
                  }

                  enum disable {
                    value 2 ;
                    description 'disable' ;
                  }

                }

                default disable ;
              }

            }

            container tilfa-priority {
              description 'OSPF fast-reroute TI-LFA priority' ;
              presence priority ;
              leaf tilfa-priority {
                description 'OSPF fast-reroute TI-LFA priority' ;
                type uint8 {
                  range 1..255 ;

                }

                default 110 ;
              }

            }

            container ipfrr-priority {
              description 'OSPF fast-reroute IP-FRR priority' ;
              presence priority ;
              leaf ipfrr-priority {
                description 'OSPF fast-reroute IP-FRR priority' ;
                type uint8 {
                  range 1..255 ;

                }

                default 110 ;
              }

            }

            container multi-home {
              description 'OSPF fast-reroute multi-home' ;
              leaf multi-home {
                description 'Config OSPF fast-reroute multi-home' ;
                type enumeration {
                  enum enable {
                    value 1 ;
                    description 'Enable fast-reroute multi-home' ;
                  }

                  enum disable {
                    value 2 ;
                    description 'Disable fast-reroute multi-home' ;
                  }

                }

                default disable ;
              }

              ncd:revise-date 2021-04-01 ;
            }

            container policy {
              description 'Configure OSPF backup route policy.' ;
              leaf host-only {
                description 'Filter OSPF backup route based on host.' ;
                type empty ;

              }

              ncd:revise-date 2022-03-29 ;
            }

            ncd:revise-date 2019-10-08 ;
          }

          container microloop-prevention {
            description 'Configure microloop prevention for OSPFv3.' ;
            container segment-routing {
              if-feature segment-routing ;

              description 'Configure microloop prevention for segment routing.' ;
              container mpls {
                description 'Configure microloop prevention for IPv6 SR-MPLS.' ;
                leaf capability {
                  description 'Microloop prevention capability for SR-MPLS.' ;
                  type enumeration {
                    enum enable {
                      value 1 ;
                      description 'Enable microloop-prevention for SR MPLS.' ;
                    }

                    enum disable {
                      value 2 ;
                      description 'Disable microloop-prevention for SR MPLS.' ;
                    }

                  }

                  default disable ;
                }

              }

              container srv6 {
                description 'Configure microloop prevention for SRv6.' ;
                leaf capability {
                  description 'Microloop prevention capability for SRv6.' ;
                  type enumeration {
                    enum enable {
                      value 1 ;
                      description 'Enable microloop-prevention for SRv6.' ;
                    }

                    enum disable {
                      value 2 ;
                      description 'Disable microloop-prevention for SRv6.' ;
                    }

                  }

                  default disable ;
                }

              }

              leaf delay-time {
                description 'Delay time of microloop prevention for SR.' ;
                type uint32 {
                  range 1..300000 {
                    description 'delay time' ;
                  }

                }

                units milliseconds ;
                default 3000 ;
              }

            }

            container lfa {
              description 'Configure microloop prevention for lfa.' ;
              leaf capability {
                description 'Microloop prevention capability for lfa.' ;
                type enumeration {
                  enum enable {
                    value 1 ;
                  }

                  enum disable {
                    value 2 ;
                  }

                }

                default enable ;
              }

              leaf delay-time {
                description 'Delay time of microloop prevention for lfa.' ;
                type uint32 {
                  range 1..300000 ;

                }

                units milliseconds ;
                default 3000 ;
              }

              ncd:revise-date 2021-02-10 ;
            }

            container policy {
              description 'Configure microloop prevention route policy.' ;
              leaf host-only {
                description 'Configure microloop prevention filter route based on host.' ;
                type empty ;

              }

              ncd:revise-date 2022-03-29 ;
            }

            ncd:revise-date 2019-10-17 ;
          }

          container max-metric {
            description 'Origin max-metric router-LSAs' ;
            container router-lsa {
              description 'Origin max-metric router-LSAs' ;
              presence router-lsa ;
              container on-startup {
                description 'Origin max-metric router-LSAs after reboot' ;
                leaf timeout {
                  description 'Configure timeout of originating max-metric router-LSAs' ;
                  type uint32 {
                    range 5..86400 {
                      description 'Configure timeout of originating max-metric router-LSAs' ;
                    }

                  }

                }

              }

            }

            ncd:revise-date 2020-07-15 ;
          }

          container suppress-flapping {
            description 'Suppress flapping.' ;
            container adjacency {
              description 'Suppress flapping for adjacency.' ;
              leaf capability {
                description 'Capability of suppress flapping for adjacency.' ;
                type enumeration {
                  enum enable {
                    value 1 ;
                    description 'Enable suppress flapping.' ;
                  }

                  enum disable {
                    value 2 ;
                    description 'Disable suppress flapping.' ;
                  }

                }

                default enable ;
              }

            }

            ncd:revise-date 2020-07-23 ;
          }

          container flex-algorithms {
            description 'The collection of flexible algorithms that the ospf instance supports.' ;
            list flex-algorithm {
              description 'The flexible algorithm that the ospf instance supports.' ;
              key number ;
              leaf number {
                description 'Number of the flexible algorithm.' ;
                type uint8 {
                  range 128..255 ;

                }

              }

            }

            ncd:revise-date 2021-03-08 ;
          }

          container hostname {
            description 'Configure hostname for OSPF' ;
            leaf dynamic-capability {
              description 'Configure OSPF dynamic hostname capability' ;
              type enumeration {
                enum disable {
                  value 0 ;
                  description 'Disable dynamic hostname' ;
                }

                enum enable {
                  value 1 ;
                  description 'Enable dynamic hostname' ;
                }

              }

              default disable ;
            }

            leaf hostname {
              description 'Configure hostname for OSPF' ;
              type string {
                length 1..64 ;

              }

            }

            ncd:revise-date 2021-05-24 ;
          }

          container te-link-attribute {
            description 'Set OSPF TE link attribute capability' ;
            container sr-policy {
              description 'Set OSPF TE link attribute capability for sr policy' ;
              leaf advertise-capability {
                description 'Set OSPF TE link attribute advertise capability' ;
                type enumeration {
                  enum app-specific-and-legacy {
                    value 0 ;
                    description 'Advertise OSPF TE link attribute by app-specific-and-legacy' ;
                  }

                  enum app-specific-only {
                    value 1 ;
                    description 'Advertise OSPF TE link attribute by app-specific-only' ;
                  }

                }

                default app-specific-and-legacy ;
              }

              leaf receive-capability {
                description 'Set OSPF TE link attribute receive capability' ;
                type enumeration {
                  enum app-specific-and-legacy {
                    value 0 ;
                    description 'Receive OSPF TE link attribute by app-specific-and-legacy' ;
                  }

                  enum app-specific-only {
                    value 1 ;
                    description 'Receive OSPF TE link attribute by app-specific-only' ;
                  }

                }

                default app-specific-and-legacy ;
              }

            }

            ncd:revise-date 2021-08-09 ;
          }

          container stub-router {
            description 'Set stub-router.' ;
            presence stub-router-presence ;
            leaf intra-area-prefix-lsa {
              description 'Set intra-area prefix LSA metric.' ;
              type empty ;

            }

            container external-lsa {
              description 'Set external LSA metric.' ;
              presence external-lsa-presence ;
              leaf external-lsa-metric {
                description 'Metric of external LSA.' ;
                type uint32 {
                  range 1..16777215 {
                    description 'Metric of external LSA.' ;
                  }

                }

                default 16711680 ;
              }

            }

            container inter-area-prefix-lsa {
              description 'Set inter-area prefix LSA metric.' ;
              presence inter-area-prefix-lsa-presence ;
              leaf inter-area-prefix-lsa-metric {
                description 'Metric of inter-area prefix LSA.' ;
                type uint32 {
                  range 1..16777215 {
                    description 'Metric of inter-area prefix LSA.' ;
                  }

                }

                default 16711680 ;
              }

            }

            container on-startup {
              description 'Set on-startup.' ;
              presence on-startup-presence ;
              leaf interval {
                description 'Seconds,interval of on-startup.' ;
                type uint32 {
                  range 5..65535 {
                    description 'interval of on-startup.' ;
                  }

                }

                default 500 ;
              }

            }

            ncd:revise-date 2022-03-25 ;
          }

          container slice-source-prefixs {
            description 'Advertise slice source prefix' ;
            list slice-source-prefix {
              description 'Advertise slice source prefix' ;
              key prefix-name ;
              leaf prefix-name {
                description 'Name of slice source prefix (1-63 characters)' ;
                type string {
                  length 1..63 ;

                }

              }

            }

            ncd:revise-date 2023-03-17 ;
          }

          container vpn-instance-capability {
            leaf abr-capability {
              description 'Configure the capability of area-border-router for VPN OSPF.' ;
              type enumeration {
                enum enable {
                  value 1 ;
                  description 'Enable the capability of area border router.' ;
                }

                enum disable {
                  value 2 ;
                  description 'Disable the capability of area border router.' ;
                }

                enum no-cfg {
                  value 0 ;
                  description 'Reset the capability of area border router.' ;
                }

              }

              default no-cfg ;
            }

            description 'Configure capability for VPN OSPF.' ;
            ncd:revise-date 2024-01-24 ;
          }

        }

      }

    }

  }

  container state {
    config false ;
    description 'State.' ;
    container ospfv3 {
      description 'State of OSPFv3.' ;
      container processes {
        description 'OSPFv3 process.' ;
        list process {
          description 'OSPFv3 process.' ;
          key process-id ;
          leaf process-id {
            description 'OSPFv3 process ID.' ;
            type uint32 {
              range 1..65535 ;

            }

          }

          leaf router-id {
            description 'Router-id.' ;
            type ncd:ipv4-address ;

          }

          leaf vrf-name {
            description 'VPN routing/forwarding instance (VRF) name.' ;
            type string {
              length 1..32 ;

            }

          }

          leaf socket-state {
            description 'State of socket.' ;
            type enumeration {
              enum enable {
                value 1 ;
                description 'Enable socket.' ;
              }

              enum disable {
                value 2 ;
                description 'Disable socket.' ;
              }

            }

          }

          container distance {
            description 'Distance of OSPF route.' ;
            leaf external {
              description 'Distance for external routes.' ;
              type uint8 ;

            }

            leaf inter-area {
              description 'Distance for inter-area routes.' ;
              type uint8 ;

            }

            leaf intra-area {
              description 'Distance for intra-area routes.' ;
              type uint8 ;

            }

          }

          leaf external-lsa-count {
            description 'Count of external LSA.' ;
            type uint32 ;

          }

          leaf route-count {
            description 'Count of route.' ;
            type uint32 ;

          }

          leaf default-metric {
            description 'Default metric of Type 5 LSA.' ;
            type uint32 {
              range 1..16777214 ;

            }

          }

          container area-count {
            description 'Count of area.' ;
            leaf total-count {
              description 'Count of area.' ;
              type uint32 ;

            }

            leaf normal-count {
              description 'Count of normal area.' ;
              type uint32 ;

            }

            leaf stub-count {
              description 'Count of stub area.' ;
              type uint32 ;

            }

          }

          container areas {
            description 'OSPFv3 area.' ;
            list area {
              description 'OSPFv3 area.' ;
              key area-id ;
              leaf area-id {
                description 'OSPFv3 area ID in IP address format.' ;
                type ncd:ipv4-address ;

              }

              leaf interface-count {
                description 'Count of interface.' ;
                type uint32 ;

              }

              container ipsec {
                description 'IPSEC configuration of area.' ;
                leaf spi-id {
                  description 'Security parameters index ID.' ;
                  type uint32 {
                    range 256..32767 ;

                  }

                }

                leaf type {
                  description 'Type of authentication or encryption.' ;
                  type enumeration {
                    enum authentication {
                      value 1 ;
                    }

                    enum encryption {
                      value 2 ;
                    }

                  }

                }

                leaf authentication-algorithm {
                  description 'Type of authentication algorithm.' ;
                  type enumeration {
                    enum md5 {
                      value 1 ;
                      description 'Message Digest Algorithm.' ;
                    }

                    enum sha1 {
                      value 2 ;
                      description 'Secure Hash Algorithm.' ;
                    }

                    enum keychain {
                      value 4 ;
                      description 'Use keychain for authentication.' ;
                    }

                  }

                }

                leaf encryption-algorithm {
                  description 'Type of encryption algorithm.' ;
                  type enumeration {
                    enum null {
                      value 1 ;
                      description 'NULL encryption.' ;
                    }

                    enum des {
                      value 2 ;
                      description 'Data Encrypt Standard algorithm.' ;
                    }

                    enum triple-des {
                      value 3 ;
                      description 'Triple Data Encryption algorithm.' ;
                    }

                    enum aes-cbc {
                      value 4 ;
                      description 'Advanced Encryption Standard algorithm.' ;
                    }

                    enum keychain-encryption {
                      value 6 ;
                      description 'Use keychain for encryption.' ;
                    }

                  }

                }

              }

              leaf area-type {
                description 'Type of area.' ;
                type enumeration {
                  enum stub {
                    value 1 ;
                  }

                  enum normal {
                    value 2 ;
                  }

                  enum nssa {
                    value 3 ;
                  }

                }

              }

              leaf default-cost {
                description "Stub's advertised default summary cost." ;
                type uint32 {
                  range 0..16777215 ;

                }

              }

              leaf spf-calculate-times {
                description 'SPF calculate times.' ;
                type uint32 ;

              }

              leaf ispf-calculate-times {
                description 'Incremental SPF calculate times' ;
                type uint32 ;

              }

              leaf lsa-count {
                description 'Count of LSA.' ;
                type uint32 ;

              }

              leaf unknown-lsa-count {
                description 'Count of unknown LSA.' ;
                type uint32 ;

              }

            }

          }

          ncd:select process-id ;
        }

      }

      container interfaces {
        description 'OSPFv3 interface.' ;
        container normal-interfaces {
          description 'OSPFv3 normal interface.' ;
          list normal-interface {
            description 'OSPFv3 normal interface.' ;
            key 'process-id area-id interface-name' ;
            leaf process-id {
              description 'OSPFv3 process ID.' ;
              type uint32 {
                range 1..65535 ;

              }

            }

            leaf area-id {
              description 'OSPFv3 area ID in IP address format.' ;
              type ncd:ipv4-address ;

            }

            leaf interface-name {
              description 'Interface name.' ;
              type ncd:ifname {
                length 1..31 ;

              }

            }

            leaf admin-state {
              description 'Interface admin state.' ;
              type enumeration {
                enum up {
                  value 1 ;
                }

                enum down {
                  value 2 ;
                }

              }

            }

            leaf protocol-state {
              description 'Interface protocol state.' ;
              type enumeration {
                enum up {
                  value 1 ;
                }

                enum down {
                  value 2 ;
                }

              }

            }

            leaf linklocal-address {
              description 'Link-local address.' ;
              type ncd:ipv6-address ;

            }

            leaf interface-id {
              description 'Interface ID.' ;
              type uint32 {
                range 0..4294967295 ;

              }

            }

            leaf instance-id {
              description 'Interface ID.' ;
              type uint8 ;

            }

            leaf network-type {
              description 'Network type.' ;
              type enumeration {
                enum Nbma {
                  value 3 ;
                }

                enum Point-to-point {
                  value 1 ;
                }

                enum Point-to-multipoint {
                  value 4 ;
                }

                enum P-to-mp-nb {
                  value 5 ;
                }

                enum Broadcast {
                  value 2 ;
                }

                enum Loopback {
                  value 6 ;
                }

              }

            }

            leaf cost {
              description 'Cost value of OSPFv3 interface.' ;
              type uint32 {
                range 1..65535 ;

              }

            }

            leaf transmit-delay {
              description 'LSA transmit delay over link.' ;
              type uint32 {
                range 1..65535 ;

              }

              units second ;
            }

            leaf interface-state {
              description 'State of OSPF interface machine.' ;
              type enumeration {
                enum Down {
                  value 1 ;
                  description 'This is the initial interface state.' ;
                }

                enum Standby {
                  value 2 ;
                  description 'In this state, the interface is one of multiple interfaces to a link and this interface is designated Standby and is not sending or receiving control packets.' ;
                }

                enum Loopback {
                  value 3 ;
                  description "In this state, the router's interface to the network is looped back." ;
                }

                enum Waiting {
                  value 4 ;
                  description 'In this state, the router is trying to determine the identity of the (Backup) Designated Router for the network.' ;
                }

                enum Point-to-point {
                  value 5 ;
                  description 'In this state, the interface is operational, and connects either to a physical point-to-point network or to a virtual link.' ;
                }

                enum DROther {
                  value 6 ;
                  description 'The interface is to a broadcast or NBMA network on which another router has been selected to be the Designated Router.' ;
                }

                enum Backup {
                  value 7 ;
                  description 'In this state, the router itself is the Backup Designated Router on the attached network.' ;
                }

                enum DR {
                  value 8 ;
                  description 'In this state, this router itself is the Designated Router on the attached network.' ;
                }

              }

            }

            leaf priority {
              description 'Router priority.' ;
              type uint32 {
                range 0..255 ;

              }

            }

            leaf ldp-sync-config {
              description 'MPLS LDP IGP sync.' ;
              type enumeration {
                enum disable {
                  value 0 ;
                  description 'MPLS LDP IGP sync is disabled.' ;
                }

                enum enable {
                  value 1 ;
                  description 'MPLS LDP IGP sync is enabled.' ;
                }

              }

              ncd:revise-date 2015-12-08 ;
            }

            leaf ldp-sync-state {
              description 'MPLS LDP IGP sync of the interface.' ;
              type enumeration {
                enum unachieve {
                  value 0 ;
                  description 'MPLS LDP IGP sync state is unachieved.' ;
                }

                enum achieve {
                  value 1 ;
                  description 'MPLS LDP IGP sync state is achieved.' ;
                }

                enum unknown {
                  value 2 ;
                  description 'MPLS LDP IGP sync state is unknown.' ;
                }

              }

              ncd:revise-date 2015-12-08 ;
            }

            leaf ldp-link-state {
              description 'Router lsa link state caused by MPLS LDP IGP state.' ;
              type enumeration {
                enum send-max-metric {
                  value 0 ;
                  description 'MPLS LDP IGP link state is sending max metric.' ;
                }

                enum unreachable {
                  value 1 ;
                  description 'MPLS LDP IGP link state is unreachable.' ;
                }

                enum send-normal-metric {
                  value 2 ;
                  description 'MPLS LDP IGP link state is sending normal metric.' ;
                }

                enum send-increase-metric {
                  value 3 ;
                  description 'MPLS LDP IGP link state is sending increase metric.' ;
                }

              }

              ncd:revise-date 2015-12-08 ;
            }

            leaf no-cut-edge {
              description 'There is alternate path for the directly connected network.' ;
              type empty ;

              ncd:revise-date 2015-12-08 ;
            }

            leaf dr {
              description 'Designated Router ID.' ;
              type ncd:ipv4-address ;

            }

            leaf dr-linklocal-address {
              description 'Link-local address of the DR.' ;
              type ncd:ipv6-address ;

            }

            leaf bdr {
              description 'Backup designated Router ID.' ;
              type ncd:ipv4-address ;

            }

            leaf bdr-linklocal-address {
              description 'Link-local address of the BDR.' ;
              type ncd:ipv6-address ;

            }

            leaf hello-interval {
              description 'Time between hello packets.' ;
              type uint32 {
                range 1..65535 ;

              }

              units second ;
            }

            leaf dead-interval {
              description 'Interval after which a neighbor is declared dead.' ;
              type uint32 {
                range 1..65535 ;

              }

              units second ;
            }

            leaf wait-interval {
              description 'The Interval that interface exit waiting state.' ;
              type uint32 {
                range 0..65535 ;

              }

              units second ;
            }

            leaf retransmit-interval {
              description 'Time between retransmitting lost link state advertisements.' ;
              type uint32 {
                range 1..65535 ;

              }

              units second ;
              default 5 ;
            }

            leaf neighbor-count {
              description 'Count of neighbor.' ;
              type uint32 ;

            }

            leaf full-neighbor-count {
              description 'Full neighbor count.' ;
              type uint32 ;

            }

            leaf linklsa-suppress {
              description 'Link lsa suppress.' ;
              type empty ;

            }

            leaf damp-state {
              description 'Link damp state of the interface.' ;
              type enumeration {
                enum inactive {
                  value 0 ;
                  description 'Link Damp state of this interface is inactive.' ;
                }

                enum active {
                  value 1 ;
                  description 'Link Damp state of this interface is active.' ;
                }

              }

              ncd:revise-date 2017-03-31 ;
            }

            leaf damp-remain {
              description 'Link damp remaining time.' ;
              type uint32 {
                range 0..3600000 {
                  description 'Link damp remaining time.' ;
                }

              }

              ncd:revise-date 2017-03-31 ;
            }

            container ipsec {
              description 'IPSEC states of interface.' ;
              leaf spi-id {
                description 'Security parameters index ID.' ;
                type uint32 ;

              }

              leaf type {
                description 'Type of authentication or encryption.' ;
                type enumeration {
                  enum authentication-null {
                    value 1 ;
                  }

                  enum encryption-null {
                    value 2 ;
                  }

                  enum authentication {
                    value 3 ;
                  }

                  enum encryption {
                    value 4 ;
                  }

                }

              }

              leaf authentication-algorithm {
                description 'Type of authentication algorithm.' ;
                type enumeration {
                  enum md5 {
                    value 1 ;
                    description 'Message Digest Algorithm.' ;
                  }

                  enum sha1 {
                    value 2 ;
                    description 'Secure Hash Algorithm.' ;
                  }

                  enum keychain {
                    value 4 ;
                    description 'Use keychain for authentication.' ;
                  }

                }

              }

              leaf encryption-algorithm {
                description 'Type of encryption algorithm.' ;
                type enumeration {
                  enum null {
                    value 1 ;
                    description 'NULL encryption.' ;
                  }

                  enum des {
                    value 2 ;
                    description 'Data Encrypt Standard algorithm.' ;
                  }

                  enum triple-des {
                    value 3 ;
                    description 'Triple Data Encryption algorithm.' ;
                  }

                  enum aes-cbc {
                    value 4 ;
                    description 'Advanced Encryption Standard algorithm.' ;
                  }

                  enum keychain-encryption {
                    value 6 ;
                    description 'Use keychain for encryption.' ;
                  }

                }

              }

              leaf state {
                description 'State of IPSEC.' ;
                type enumeration {
                  enum down {
                    value 0 ;
                  }

                  enum start {
                    value 1 ;
                  }

                  enum rekeying-add-new-in {
                    value 2 ;
                  }

                  enum rekeying-add-new-out {
                    value 3 ;
                  }

                  enum rekeying-del-old-in {
                    value 4 ;
                  }

                  enum up {
                    value 5 ;
                  }

                }

              }

            }

            ncd:select interface-name ;
            ncd:select process-id ;
            ncd:select "process-id interface-name" ;
          }

        }

        container virtual-interfaces {
          description 'OSPFv3 virtual interface.' ;
          list virtual-interface {
            description 'OSPFv3 virtual interface.' ;
            key 'process-id area-id neighbor-id' ;
            leaf process-id {
              description 'OSPFv3 process ID.' ;
              type uint32 {
                range 1..65535 ;

              }

            }

            leaf area-id {
              description 'OSPFv3 area ID in IP address format.' ;
              type ncd:ipv4-address ;

            }

            leaf neighbor-id {
              description 'Router ID of the virtual link neighbor.' ;
              type ncd:ipv4-address ;

            }

            leaf interface-id {
              description 'Virtual interface ID.' ;
              type uint32 {
                range 2147483648..4294967294 ;

              }

            }

            leaf state {
              description 'State of the virtual link.' ;
              type enumeration {
                enum down {
                  value 0 ;
                  description 'The virtual-link is down.' ;
                }

                enum up {
                  value 1 ;
                  description 'The virtual-link is up.' ;
                }

              }

            }

            leaf neighbor-ipv6-address {
              description 'IPv6 address of the virtual neighbor.' ;
              type ncd:ipv6-address ;

            }

            leaf out-interface-name {
              description 'The outgoing interface name of virtual interface.' ;
              type ncd:ifname {
                length 1..31 ;

              }

            }

            leaf cost {
              description 'Cost value of OSPFv3 virtual link interface.' ;
              type uint32 {
                range 1..65535 ;

              }

            }

            leaf hello-interval {
              description 'Time between hello packets over virtual link.' ;
              type uint32 {
                range 1..8192 ;

              }

              units second ;
              default 10 ;
            }

            leaf dead-interval {
              description 'Interval after which a virtual neighbor is declared dead.' ;
              type uint32 {
                range 1..8192 ;

              }

              units second ;
            }

            leaf wait-interval {
              description 'Interval after which a virtual interface to exit the waiting state.' ;
              type uint32 {
                range 1..8192 ;

              }

              units second ;
            }

            leaf retransmit-interval {
              description 'Time between retransmitting lost link state advertisements over virtual link.' ;
              type uint32 {
                range 1..8192 ;

              }

              units second ;
              default 5 ;
            }

            leaf transmit-delay {
              description 'LSA transmit delay over virtual link.' ;
              type uint32 {
                range 1..8192 ;

              }

              units second ;
              default 1 ;
            }

            leaf interface-state {
              description 'State of the virtual interface.' ;
              type enumeration {
                enum Down {
                  value 1 ;
                  description 'This is the initial interface state.' ;
                }

                enum Point-to-point {
                  value 5 ;
                  description 'In this state, the interface is operational, and connects either to a physical point-to-point network or to a virtual link.' ;
                }

              }

            }

            leaf neighbor-state {
              description 'State of the virtual neighbor.' ;
              type enumeration {
                enum Down {
                  value 1 ;
                  description 'This is the initial state of a neighbor conversation.' ;
                }

                enum Init {
                  value 3 ;
                  description 'In this state, an Hello packet has recently been seen from the neighbor.' ;
                }

                enum 2-Way {
                  value 4 ;
                  description 'In this state, communication between the two routers is bidirectional.' ;
                }

                enum ExStart {
                  value 5 ;
                  description 'This is the first step in creating an adjacency between the two neighboring routers.' ;
                }

                enum Exchange {
                  value 6 ;
                  description 'In this state the router is describing its entire link state database by sending Database Description packets to the neighbor.' ;
                }

                enum Loading {
                  value 7 ;
                  description 'In this state, Link State Request packets are sent to the neighbor asking for the more recent LSAs that have been discovered (but not yet received) in the Exchange state.' ;
                }

                enum Full {
                  value 8 ;
                  description 'In this state, the neighboring routers are fully adjacent.' ;
                }

              }

            }

            container ipsec {
              description 'IPSEC states of virtual link.' ;
              leaf spi-id {
                description 'Security parameters index ID.' ;
                type uint32 {
                  range 256..32767 ;

                }

              }

              leaf type {
                description 'Type of authentication or encryption.' ;
                type enumeration {
                  enum authentication {
                    value 3 ;
                    description 'Authentication type.' ;
                  }

                  enum encryption {
                    value 4 ;
                    description 'Encryption type.' ;
                  }

                }

              }

              leaf authentication-algorithm {
                description 'Type of authentication algorithm.' ;
                type enumeration {
                  enum md5 {
                    value 1 ;
                    description 'Message Digest Algorithm.' ;
                  }

                  enum sha1 {
                    value 2 ;
                    description 'Secure Hash Algorithm.' ;
                  }

                  enum keychain {
                    value 4 ;
                    description 'Use keychain for authentication.' ;
                  }

                }

              }

              leaf encryption-algorithm {
                description 'Type of encryption algorithm.' ;
                type enumeration {
                  enum null {
                    value 1 ;
                    description 'NULL encryption.' ;
                  }

                  enum des {
                    value 2 ;
                    description 'Data Encrypt Standard algorithm.' ;
                  }

                  enum triple-des {
                    value 3 ;
                    description 'Triple Data Encryption algorithm.' ;
                  }

                  enum aes-cbc {
                    value 4 ;
                    description 'Advanced Encryption Standard algorithm.' ;
                  }

                  enum keychain-encryption {
                    value 6 ;
                    description 'Use keychain for encryption.' ;
                  }

                }

              }

              leaf state {
                description 'State of IPSEC.' ;
                type enumeration {
                  enum down {
                    value 0 ;
                    description 'Down state.' ;
                  }

                  enum start {
                    value 1 ;
                    description 'Start state.' ;
                  }

                  enum rekeying-add-new-in {
                    value 2 ;
                    description 'Rekeying(add-new-in) state.' ;
                  }

                  enum rekeying-add-new-out {
                    value 3 ;
                    description 'Rekeying(add-new-out) state.' ;
                  }

                  enum rekeying-del-old-in {
                    value 4 ;
                    description 'Rekeying(del-old-in) state.' ;
                  }

                  enum up {
                    value 5 ;
                    description 'Up state.' ;
                  }

                }

              }

            }

            ncd:select process-id ;
          }

        }

      }

      container neighbors {
        description 'OSPFv3 neighbor.' ;
        container normal-neighbors {
          description 'OSPFv3 normal neighbor.' ;
          list normal-neighbor {
            description 'OSPFv3 normal neighbor.' ;
            key 'process-id area-id interface-name neighbor-id' ;
            leaf process-id {
              description 'OSPFv3 process ID.' ;
              type uint32 {
                range 1..4294967295 ;

              }

            }

            leaf area-id {
              description 'OSPFv3 area ID in IP address format.' ;
              type ncd:ipv4-address ;

            }

            leaf interface-name {
              description 'The outgoing interface name of  interface.' ;
              type ncd:ifname {
                length 1..31 ;

              }

            }

            leaf neighbor-id {
              description 'Router ID of the neighbor.' ;
              type ncd:ipv4-address ;

            }

            leaf interface-id {
              description 'Interface ID.' ;
              type uint32 ;

            }

            leaf neighbor-linklocal-address {
              description 'Link-local address of neighbor.' ;
              type ncd:ipv6-address ;

            }

            leaf priority {
              description 'Neighbor router priority.' ;
              type uint32 {
                range 0..255 ;

              }

            }

            leaf neighbor-state {
              description 'Neighbor router state.' ;
              type enumeration {
                enum Init {
                  value 3 ;
                }

                enum 2-Way {
                  value 4 ;
                }

                enum Exstart {
                  value 5 ;
                }

                enum Exchange {
                  value 6 ;
                }

                enum Loading {
                  value 7 ;
                }

                enum Full {
                  value 8 ;
                }

              }

            }

            leaf neighbor-role {
              description 'State of the interface.' ;
              type enumeration {
                enum DR {
                  value 1 ;
                }

                enum Backup {
                  value 2 ;
                }

                enum DROther {
                  value 3 ;
                }

              }

            }

            leaf state-change-times {
              description 'Neighbor router state change times.' ;
              type uint32 ;

            }

            leaf dr {
              description 'Designated Router ID.' ;
              type ncd:ipv4-address ;

            }

            leaf bdr {
              description 'Backup designated Router ID.' ;
              type ncd:ipv4-address ;

            }

            leaf retransmit-list-count {
              description 'Database retransmit packet count.' ;
              type uint32 ;

            }

            leaf dd-list-count {
              description 'DD packet count in list.' ;
              type uint32 ;

            }

            leaf request-list-count {
              description 'Request packet count in list.' ;
              type uint32 ;

            }

            leaf dead-time {
              description 'Dead Time.' ;
              type string {
                length 1..15 ;

              }

            }

            leaf full-time {
              description 'Neighbor full time.' ;
              type string {
                length 1..15 ;

              }

            }

            leaf options-field {
              description 'Options field of neighbor.' ;
              type uint32 ;

            }

            container options {
              description 'Options of neighbor.' ;
              leaf v6-bit {
                description 'If this bit is clear, the router/link should be excluded from IPv6 routing calculations.' ;
                type empty ;

              }

              leaf e-bit {
                description 'This bit describes the way AS-external-LSAs are flooded.' ;
                type empty ;

              }

              leaf n-bit {
                description 'This bit indicates whether or not the router is attached to an NSSA.' ;
                type empty ;

              }

              leaf r-bit {
                description "This bit (the `Router' bit) indicates whether the originator is an active router." ;
                type empty ;

              }

              leaf dc-bit {
                description "This bit describes the router's handling of demand circuits." ;
                type empty ;

              }

            }

            ncd:select neighbor-id ;
            ncd:select "process-id neighbor-id" ;
            ncd:select process-id ;
            ncd:select interface-name ;
            ncd:select "interface-name neighbor-id" ;
            ncd:select "process-id interface-name" ;
            ncd:select "process-id interface-name neighbor-id" ;
          }

        }

        container virtual-neighbors {
          description 'OSPFv3 virtual neighbor.' ;
          list virtual-neighbor {
            description 'OSPFv3 virtual neighbor.' ;
            key 'process-id transit-area-id neighbor-id' ;
            leaf process-id {
              description 'OSPFv3 process ID.' ;
              type uint32 {
                range 1..65535 ;

              }

            }

            leaf transit-area-id {
              description 'OSPFv3 virtual link transit area ID in IP address format.' ;
              type ncd:ipv4-address ;

            }

            leaf neighbor-id {
              description 'Router ID of the neighbor.' ;
              type ncd:ipv4-address ;

            }

            leaf area-id {
              description 'OSPFv3 area ID in IP address format.' ;
              type ncd:ipv4-address ;

            }

            leaf out-interface-name {
              description 'The outgoing interface name of virtual interface.' ;
              type ncd:ifname {
                length 1..31 ;

              }

            }

            leaf interface-id {
              description 'Interface ID.' ;
              type uint32 ;

            }

            leaf neighbor-ipv6-address {
              description 'IPv6 address of the virtual neighbor.' ;
              type ncd:ipv6-address ;

            }

            leaf priority {
              description 'Neighbor router priority.' ;
              type uint32 {
                range 0..255 ;

              }

            }

            leaf neighbor-state {
              description 'Neighbor router state.' ;
              type enumeration {
                enum Down {
                  value 1 ;
                }

                enum Init {
                  value 3 ;
                }

                enum 2-Way {
                  value 4 ;
                }

                enum Exstart {
                  value 5 ;
                }

                enum Exchange {
                  value 6 ;
                }

                enum Loading {
                  value 7 ;
                }

                enum Full {
                  value 8 ;
                }

              }

            }

            leaf state-change-times {
              description 'Neighbor router state change times.' ;
              type uint32 ;

            }

            leaf retransmit-list-count {
              description 'Database retransmit packet count.' ;
              type uint32 ;

            }

            leaf dd-list-count {
              description 'DD packet count in list.' ;
              type uint32 ;

            }

            leaf request-list-count {
              description 'Request packet count in list.' ;
              type uint32 ;

            }

            leaf dead-time {
              description 'Dead Time.' ;
              type string {
                length 1..15 ;

              }

            }

            leaf full-time {
              description 'Neighbor full time.' ;
              type string {
                length 1..15 ;

              }

            }

            leaf options-field {
              description 'Options field of neighbor.' ;
              type uint32 ;

            }

            container options {
              description 'Options of neighbor.' ;
              leaf v6-bit {
                description 'If this bit is clear, the router/link should be excluded from IPv6 routing calculations.' ;
                type empty ;

              }

              leaf e-bit {
                description 'This bit describes the way AS-external-LSAs are flooded.' ;
                type empty ;

              }

              leaf n-bit {
                description 'This bit indicates whether or not the router is attached to an NSSA.' ;
                type empty ;

              }

              leaf r-bit {
                description "This bit (the `Router' bit) indicates whether the originator is an active router." ;
                type empty ;

              }

              leaf dc-bit {
                description "This bit describes the router's handling of demand circuits." ;
                type empty ;

              }

            }

          }

        }

      }

    }

    ncd:revise-date 2015-03-26 ;
  }

  container operation {
    config false ;
    description 'Operation model.' ;
    container ospfv3 {
      description 'Operation of OSPFv3.' ;
      container clear {
        description 'Clear Operation.' ;
        container process {
          description 'Clear an OSPFv3 process based on the process-id.' ;
          leaf process-id {
            description 'OSPFv3 process ID.' ;
            type uint32 {
              range 1..65535 ;

            }

          }

        }

      }

    }

    ncd:revise-date 2015-03-26 ;
  }

  notification notification {
    description 'notification of OSPFv3,only telemetry upload is supported.' ;
    container neighbors {
      config false ;
      description 'OSPFv3 normal neighbors.' ;
      container normal-nbrs {
        description 'OSPFv3 normal neighbor.' ;
        list normal-nbr {
          description 'OSPFv3 normal neighbor.' ;
          key 'proc-id area-ip if-name nbr-id' ;
          leaf proc-id {
            description 'OSPFv3 process ID.' ;
            type uint32 {
              range 1..65535 ;

            }

          }

          leaf area-ip {
            description 'OSPFv3 area ID in IP address format.' ;
            type ncd:ipv4-address ;

          }

          leaf if-name {
            description 'The outgoing interface name of  interface.' ;
            type ncd:ifname {
              length 1..31 ;

            }

          }

          leaf nbr-id {
            description 'Router ID of the neighbor.' ;
            type ncd:ipv4-address ;

          }

          leaf nbr-state {
            description 'The state of OSPF neighbor.' ;
            type enumeration {
              enum Down {
                value 0 ;
                description 'The state of OSPF neighbor is Down.' ;
              }

              enum Attempt {
                value 1 ;
                description 'The state of OSPF neighbor is Attempt.' ;
              }

              enum Init {
                value 2 ;
                description 'The state of OSPF neighbor is Init.' ;
              }

              enum 2-Way {
                value 3 ;
                description 'The state of OSPF neighbor is 2-Way.' ;
              }

              enum ExStart {
                value 4 ;
                description 'The state of OSPF neighbor is Exstart.' ;
              }

              enum Exchange {
                value 5 ;
                description 'The state of OSPF neighbor is Exchange.' ;
              }

              enum Loading {
                value 6 ;
                description 'The state of OSPF neighbor is Loading.' ;
              }

              enum Full {
                value 7 ;
                description 'The state of OSPF neighbor is Full.' ;
              }

              enum DependUpon {
                value 8 ;
              }

            }

          }

        }

      }

      container virtual-nbrs {
        description 'OSPFv3 virtual neighbor.' ;
        list virtual-nbr {
          description 'OSPFv3 virtual neighbor.' ;
          key 'proc-id transit-area-ip neighbor-id' ;
          leaf proc-id {
            description 'OSPFv3 process ID.' ;
            type uint32 {
              range 1..65535 ;

            }

          }

          leaf transit-area-ip {
            description 'OSPFv3 virtual link transit area ID in IP address format.' ;
            type ncd:ipv4-address ;

          }

          leaf neighbor-id {
            description 'Router ID of the neighbor.' ;
            type ncd:ipv4-address ;

          }

          leaf nbr-state {
            description 'The state of OSPF neighbor.' ;
            type enumeration {
              enum Down {
                value 0 ;
                description 'The state of OSPF neighbor is Down.' ;
              }

              enum Attempt {
                value 1 ;
                description 'The state of OSPF neighbor is Attempt.' ;
              }

              enum Init {
                value 2 ;
                description 'The state of OSPF neighbor is Init.' ;
              }

              enum 2-Way {
                value 3 ;
                description 'The state of OSPF neighbor is 2-Way.' ;
              }

              enum ExStart {
                value 4 ;
                description 'The state of OSPF neighbor is Exstart.' ;
              }

              enum Exchange {
                value 5 ;
                description 'The state of OSPF neighbor is Exchange.' ;
              }

              enum Loading {
                value 6 ;
                description 'The state of OSPF neighbor is Loading.' ;
              }

              enum Full {
                value 7 ;
                description 'The state of OSPF neighbor is Full.' ;
              }

              enum DependUpon {
                value 8 ;
              }

            }

          }

        }

      }

    }

    container interfaces {
      config false ;
      description 'OSPFv3 interfaces.' ;
      container normal-ifs {
        description 'OSPFv3 normal interfaces.' ;
        list normal-if {
          description 'OSPFv3 normal interface.' ;
          key 'proc-id area-ip if-name' ;
          leaf proc-id {
            description 'OSPFv3 process ID.' ;
            type uint32 {
              range 1..65535 ;

            }

          }

          leaf area-ip {
            description 'OSPFv3 area ID in IP address format.' ;
            type ncd:ipv4-address ;

          }

          leaf if-name {
            description 'Interface name.' ;
            type ncd:ifname {
              length 1..31 ;

            }

          }

          leaf if-state {
            description 'State of OSPF interface machine.' ;
            type enumeration {
              enum Down {
                value 1 ;
                description 'This is the initial interface state.' ;
              }

              enum Standby {
                value 2 ;
                description 'In this state, the interface is one of multiple interfaces to a link and this interface is designated Standby and is not sending or receiving control packets.' ;
              }

              enum Loopback {
                value 3 ;
                description "In this state, the router's interface to the network is looped back." ;
              }

              enum Waiting {
                value 4 ;
                description 'In this state, the router is trying to determine the identity of the (Backup) Designated Router for the network.' ;
              }

              enum Point-to-point {
                value 5 ;
                description 'In this state, the interface is operational, and connects either to a physical point-to-point network or to a virtual link.' ;
              }

              enum DROther {
                value 6 ;
                description 'The interface is to a broadcast or NBMA network on which another router has been selected to be the Designated Router.' ;
              }

              enum Backup {
                value 7 ;
                description 'In this state, the router itself is the Backup Designated Router on the attached network.' ;
              }

              enum DR {
                value 8 ;
                description 'In this state, this router itself is the Designated Router on the attached network.' ;
              }

              enum DependUpon {
                value 0 ;
                description 'The depend upon state of interface.' ;
              }

            }

          }

          leaf event {
            description 'Change event of OSPFv3 interface machine.' ;
            type string {
              length 1..31 ;

            }

          }

        }

      }

      container virtual-links {
        description 'OSPFv3 virtual interface.' ;
        list virtual-link {
          description 'OSPFv3 virtual interface.' ;
          key 'proc-id transit-area-ip nbr-id' ;
          leaf proc-id {
            description 'OSPFv3 process ID.' ;
            type uint32 {
              range 1..65535 ;

            }

          }

          leaf transit-area-ip {
            description 'OSPFv3 transit area ip in IP address format.' ;
            type ncd:ipv4-address ;

          }

          leaf nbr-id {
            description 'Router ID of the virtual link neighbor.' ;
            type ncd:ipv4-address ;

          }

          leaf if-state {
            description 'State of OSPF interface machine.' ;
            type enumeration {
              enum Down {
                value 1 ;
                description 'This is the initial interface state.' ;
              }

              enum Standby {
                value 2 ;
                description 'In this state, the interface is one of multiple interfaces to a link and this interface is designated Standby and is not sending or receiving control packets.' ;
              }

              enum Loopback {
                value 3 ;
                description "In this state, the router's interface to the network is looped back." ;
              }

              enum Waiting {
                value 4 ;
                description 'In this state, the router is trying to determine the identity of the (Backup) Designated Router for the network.' ;
              }

              enum Point-to-point {
                value 5 ;
                description 'In this state, the interface is operational, and connects either to a physical point-to-point network or to a virtual link.' ;
              }

              enum DROther {
                value 6 ;
                description 'The interface is to a broadcast or NBMA network on which another router has been selected to be the Designated Router.' ;
              }

              enum Backup {
                value 7 ;
                description 'In this state, the router itself is the Backup Designated Router on the attached network.' ;
              }

              enum DR {
                value 8 ;
                description 'In this state, this router itself is the Designated Router on the attached network.' ;
              }

              enum DependUpon {
                value 0 ;
                description 'The depend upon state of interface.' ;
              }

            }

          }

          leaf event {
            description 'Change event of OSPFv3 interface machine.' ;
            type string {
              length 1..31 ;

            }

          }

        }

      }

    }

    container nbr-flapping {
      config false ;
      description 'OSPFv3 neighbor flapping information.' ;
      container nbrs {
        description 'OSPFv3 neighbor information.' ;
        list nbr {
          description 'OSPFv3 neighbor.' ;
          key 'proc-id area-ip if-name nbr-id' ;
          leaf proc-id {
            description 'OSPFv3 process ID.' ;
            type uint32 {
              range 1..65535 ;

            }

          }

          leaf area-ip {
            description 'OSPFv3 area ID in IP address format.' ;
            type ncd:ipv4-address ;

          }

          leaf if-name {
            description 'The outgoing interface name of  interface.' ;
            type ncd:ifname {
              length 1..31 ;

            }

          }

          leaf nbr-id {
            description 'Router ID of the neighbor.' ;
            type ncd:ipv4-address ;

          }

          leaf flapping-state {
            description 'The flapping state of OSPF neighbor.' ;
            type enumeration {
              enum normal {
                value 0 ;
                description 'The flapping state of OSPF neighbor is normal.' ;
              }

              enum holdDown {
                value 1 ;
                description 'The flapping state of OSPF neighbor is holdDown.' ;
              }

              enum maxCost {
                value 2 ;
                description 'The flapping state of OSPF neighbor is maxCost.' ;
              }

            }

          }

        }

      }

    }

    container nbr-cnts {
      description 'OSPFv3 neighbor count information.' ;
      list nbr-cnt {
        leaf proc-id {
          type uint32 {
            range 1..65535 ;

          }

          description 'OSPFv3 process ID.' ;
        }

        leaf total-nbr-cnt {
          type uint32 ;

          description 'The total count of OSPF neighbors.' ;
        }

        leaf full-nbr-cnt {
          type uint32 ;

          description 'The count of OSPF adjacent neighbors.' ;
        }

        key proc-id ;
        description 'OSPFv3 neighbor count.' ;
      }

      ncd:revise-date 2023-05-17 ;
    }

    container sample {
      container neighbors {
        container normal-nbrs {
          list normal-nbr {
            leaf proc-id {
              type uint32 {
                range 1..65535 ;

              }

              description 'OSPFv3 process ID.' ;
            }

            leaf area-ip {
              type ncd:ipv4-address ;

              description 'OSPFv3 area ID in IP address format.' ;
            }

            leaf if-name {
              type ncd:ifname {
                length 1..31 ;

              }

              description 'The outgoing interface name of  interface.' ;
            }

            leaf nbr-id {
              type ncd:ipv4-address ;

              description 'Router ID of the neighbor.' ;
            }

            leaf nbr-state {
              type enumeration {
                enum Down {
                  value 0 ;
                  description 'The state of OSPF neighbor is Down.' ;
                }

                enum Attempt {
                  value 1 ;
                  description 'The state of OSPF neighbor is Attempt.' ;
                }

                enum Init {
                  value 2 ;
                  description 'The state of OSPF neighbor is Init.' ;
                }

                enum 2-Way {
                  value 3 ;
                  description 'The state of OSPF neighbor is 2-Way.' ;
                }

                enum ExStart {
                  value 4 ;
                  description 'The state of OSPF neighbor is Exstart.' ;
                }

                enum Exchange {
                  value 5 ;
                  description 'The state of OSPF neighbor is Exchange.' ;
                }

                enum Loading {
                  value 6 ;
                  description 'The state of OSPF neighbor is Loading.' ;
                }

                enum Full {
                  value 7 ;
                  description 'The state of OSPF neighbor is Full.' ;
                }

                enum DependUpon {
                  value 8 ;
                }

              }

              description 'The state of OSPF neighbor.' ;
            }

            key 'proc-id area-ip if-name nbr-id' ;
            description 'OSPFv3 normal neighbor.' ;
          }

          description 'OSPFv3 normal neighbor.' ;
        }

        description 'OSPFv3 normal neighbors.' ;
      }

      container nbr-cnts {
        list nbr-cnt {
          leaf proc-id {
            type uint32 {
              range 1..65535 ;

            }

            description 'OSPFv3 process ID.' ;
          }

          leaf total-nbr-cnt {
            type uint32 ;

            description 'The total count of OSPF neighbors.' ;
          }

          leaf full-nbr-cnt {
            type uint32 ;

            description 'The count of OSPF adjacent neighbors.' ;
          }

          key proc-id ;
          description 'OSPFv3 neighbor count.' ;
        }

        description 'OSPFv3 neighbor count information.' ;
      }

      description 'Periodic sampling of OSPFv3,only telemetry upload is supported.' ;
      ncd:revise-date 2025-02-05 ;
    }

    ncd:revise-date 2022-01-11 ;
  }

}
