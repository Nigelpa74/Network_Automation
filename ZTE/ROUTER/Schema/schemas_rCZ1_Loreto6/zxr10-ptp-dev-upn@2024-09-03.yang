module zxr10-ptp-dev-upn {
  namespace 'http://www.zte.com.cn/zxr10/netconf/schema/rosng/ptp-dev-upn'
            ;
  prefix ptp-dev-upn ;
  yang-version 1 ;
  import zxr10-ptp {
    prefix ptp ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  revision 2024-09-03 {
    description 'add:/ptp:configuration/ptp:ptp/ptp:ptp-1588/ptp:port/ptp:port-lists/ptp:free-ports/ptp:free-port/ptp:trans-mode' ;
  }

  revision 2022-04-01 {
    description 'modify:/ptp:configuration/ptp:ptp/ptp:ptp-1588/ptp:clock-node/'
              + 'ptp:clock-type'
                ;
  }
  revision 2021-08-17 {
    description 'Delete'+"\n"
              + '/ptp:configuration/ptp:ptp/ptp:ptp-1588/ptp:port/ptp:port-list'
              + 's/ptp:free-ports/ptp:free-port/ptp:sync-interval,'+"\n"
              + '/ptp:configuration/ptp:ptp/ptp:ptp-1588/ptp:port/ptp:port-list'
              + 's/ptp:free-ports/ptp:free-port/ptp:delay-interval,'+"\n"
              + '/ptp:configuration/ptp:ptp/ptp:ptp-1588/ptp:port/ptp:combined-'
              + 'oc-lists/ptp:free-combined-oc-lists/ptp:free-combined-oc/ptp:s'
              + 'ync-interval,'+"\n"
              + '/ptp:configuration/ptp:ptp/ptp:ptp-1588/ptp:port/ptp:combined-'
              + 'oc-lists/ptp:free-combined-oc-lists/ptp:free-combined-oc/ptp:d'
              + 'elay-interval'+"\n"
              + 'ADD:/ptp:configuration/ptp:ptp/ptp:ptp-1588/ptp:oam-node/ptp:f'
              + 'req-detection-switch'
                ;
  }
  revision 2021-06-20 {
    description 'delete /ptp:configuration/ptp:ptp/ptp:ptp-1588/ptp:clock-assoc'
              + 'iation/ptp:pll-associate-switch'
                ;
  }
  revision 2019-01-07 ;
  deviation '/ptp:configuration/ptp:ptp/ptp:ptp-1588/ptp:port/ptp:port-lists/pt'
          + 'p:free-ports/ptp:free-port/ptp:domain-delay-mechanism'
            {
    deviate not-supported ;
  }
  deviation '/ptp:configuration/ptp:ptp/ptp:ptp-1588/ptp:port/ptp:port-lists/pt'
          + 'p:free-ports/ptp:free-port/ptp:multi-domain'
            {
    deviate not-supported ;
  }
  deviation '/ptp:configuration/ptp:ptp/ptp:ptp-1588/ptp:port-phys/ptp:phy-port'
          + '/ptp:pdelay-interval'
            {
    deviate not-supported ;
  }
  deviation '/ptp:configuration/ptp:ptp/ptp:ptp-1588/ptp:port-phys/ptp:phy-port'
          + '/ptp:status'
            {
    deviate replace {
      default disable ;
      type enumeration {
        enum disable {
          value 0 ;
        }
        enum enable {
          value 1 ;
        }
      }
    }
  }
  deviation '/ptp:configuration/ptp:ptp/ptp:ptp-1588/ptp:port-phys/ptp:phy-port'
          + '/ptp:accuracy-mode'
            {
    deviate not-supported ;
  }
  deviation '/ptp:configuration/ptp:ptp/ptp:ptp-1588/ptp:oam-node/ptp:freq-dete'
          + 'ction-switch'
            {
    deviate replace {
      default off ;
      type enumeration {
        enum off {
          value 0 ;
        }
      }
    }
  }
  deviation '/ptp:configuration/ptp:ptp/ptp:ptp-1588/ptp:clock-node/ptp:clock-t'
          + 'ype'
            {
    description clock-type. ;
    deviate replace {
      type enumeration {
        enum oc {
          value 1 ;
          description 'Ordinary clock.'
                      ;
        }
        enum bc {
          value 2 ;
          description 'Boundary clock.'
                      ;
        }
        enum e2etc {
          value 8 ;
          description 'E2E transparent clock.'
                      ;
        }
        enum e2etcbc {
          value 10 ;
          description 'E2E transparent clock and boundary clock.'
                      ;
        }
        enum p2ptc {
          value 4 ;
          description 'P2P transparent clock.'
                      ;
        }
        enum p2ptcoc {
          value 5 ;
          description 'P2P transparent and ordinary clock.'
                      ;
        }
        enum e2etcoc {
          value 9 ;
          description 'E2E transparent and ordinary clock.'
                      ;
        }
      }
    }
  }

  deviation "/ptp:configuration/ptp:ptp/ptp:ptp-1588/ptp:port/ptp:port-lists/ptp:free-ports/ptp:free-port/ptp:trans-mode" {
    deviate replace {
      type enumeration {
        enum multicast {
          value 0 ;
        }

        enum unicast {
          value 1 ;
        }

      }

    }

  }

}
