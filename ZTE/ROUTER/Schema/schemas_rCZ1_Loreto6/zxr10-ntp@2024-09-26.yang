module zxr10-ntp {
  namespace "http://www.zte.com.cn/zxr10/netconf/schema/rosng/ntp" ;
  prefix ntp ;
  yang-version 1 ;
  import zxr10-netconf-defs {
    prefix ncd ;
    revision-date 2013-11-22 ;
  }

  organization "ZTE Corporation" ;
  contact "ZTE Corporation
  Nanjing Institute of ZTE Corporation
  No.68 Zijinghua Rd. Yuhuatai District, Nanjing, China
  Tel: +86-25-52870000" ;
  description 'The netconf module to describe NTP.' ;
  revision 2024-09-26 {
    description 'Add:
/ntp:configuration/ntp:ntp/ntp:ntp-server/ntp:ntp-server-ipv4/ntp:ntp-ipv4-list/ntp:source-if,
/ntp:configuration/ntp:ntp/ntp:ntp-server/ntp:ntp-server-ipv4/ntp:ntp-ipv4-mng-list/ntp:source-if,
/ntp:configuration/ntp:ntp/ntp:ntp-server/ntp:ntp-server-ipv4/ntp:ntp-ipv4-vrf-list/ntp:source-if,
/ntp:configuration/ntp:ntp/ntp:ntp-server/ntp:ntp-server-ipv6/ntp:ntp-ipv6-list/ntp:source-if,
/ntp:configuration/ntp:ntp/ntp:ntp-server/ntp:ntp-server-ipv6/ntp:ntp-ipv6-mng-list/ntp:source-if,
/ntp:configuration/ntp:ntp/ntp:ntp-server/ntp:ntp-server-ipv6/ntp:ntp-ipv6-vrf-list/ntp:source-if,
/ntp:configuration/ntp:ntp/ntp:ntp-server/ntp:ntp-dns-server/ntp:ntp-dns-list/ntp:source-if,
/ntp:configuration/ntp:ntp/ntp:ntp-server/ntp:ntp-dns-server/ntp:ntp-dns-mng-list/ntp:source-if,
/ntp:configuration/ntp:ntp/ntp:ntp-server/ntp:ntp-dns-server/ntp:ntp-dns-vrf-list/ntp:source-if,
/ntp:configuration/ntp:ntp/ntp:ntp-peer/ntp:ntp-peer-ipv4/ntp:ntp-ipv4-list/ntp:source-if,
/ntp:configuration/ntp:ntp/ntp:ntp-peer/ntp:ntp-peer-ipv4/ntp:ntp-ipv4-mng-list/ntp:source-if,
/ntp:configuration/ntp:ntp/ntp:ntp-peer/ntp:ntp-peer-ipv4/ntp:ntp-ipv4-vrf-list/ntp:source-if,
/ntp:configuration/ntp:ntp/ntp:ntp-peer/ntp:ntp-peer-ipv6/ntp:ntp-ipv6-list/ntp:source-if,
/ntp:configuration/ntp:ntp/ntp:ntp-peer/ntp:ntp-peer-ipv6/ntp:ntp-ipv6-mng-list/ntp:source-if,
/ntp:configuration/ntp:ntp/ntp:ntp-peer/ntp:ntp-peer-ipv6/ntp:ntp-ipv6-vrf-list/ntp:source-if,
/ntp:configuration/ntp:ntp/ntp:ntp-peer/ntp:ntp-dns-peer/ntp:ntp-dns-list/ntp:source-if,
/ntp:configuration/ntp:ntp/ntp:ntp-peer/ntp:ntp-dns-peer/ntp:ntp-dns-mng-list/ntp:source-if,
/ntp:configuration/ntp:ntp/ntp:ntp-peer/ntp:ntp-dns-peer/ntp:ntp-dns-vrf-list/ntp:source-if,
/ntp:configuration/ntp:ntp/ntp:ntp-server-with-name/ntp:server/ntp:source-if.' ;
  }

  revision 2020-12-21 {
    description 'Add:/ntp:configuration/ntp:ntp/ntp:ntp-global/ntp:md5-strong-password-check' ;
  }

  revision 2020-07-23 {
    description 'Add:/ntp:configuration/ntp:ntp/ntp:ntp-service' ;
  }

  revision 2020-06-30 {
    description "Modify the description of
    /ntp:configuration/ntp:ntp/ntp:ntp-authentication/ntp:ntp-authentication-key/ntp:ntp-authentication-key/ntp:md5-encrypted-key/ntp:encrypted-key;
    Add length for
    /ntp:configuration/ntp:ntp/ntp:ntp-authentication/ntp:ntp-authentication-key/ntp:ntp-authentication-key/ntp:md5-encrypted-key/ntp:encrypted-key,length is 24~84'" ;
  }

  revision 2020-04-16 {
    description 'Add:/ntp:configuration/ntp:ntp/ntp:ntp-global/ntp:master-mode
Add:/ntp:configuration/ntp:ntp/ntp:ntp-monitor-clients
Add:/ntp:state/ntp:ntp/ntp:ntp-monitor-clients
Add:ntp/state/ntp/ntp-current-status/current-server-name' ;
  }

  revision 2019-07-19 {
    description 'Add:/ntp:configuration/ntp:ntp/ntp:ntp-server-with-name
Add:/ntp:state/ntp:ntp/ntp:ntp-association/ntp:ntp-association-list/ntp:name
Modify the range of
/ntp:state/ntp:ntp/ntp:ntp-association/ntp:ntp-association-list/ntp:priority' ;
  }

  revision 2019-04-19 {
    description 'Modify the range of
/ntp:configuration/ntp:ntp/ntp:ntp-server/ntp:ntp-server-ipv4/ntp:ntp-ipv4-list/ntp:priority,
/ntp:configuration/ntp:ntp/ntp:ntp-server/ntp:ntp-server-ipv4/ntp:ntp-ipv4-mng-list/ntp:priority,
/ntp:configuration/ntp:ntp/ntp:ntp-server/ntp:ntp-server-ipv4/ntp:ntp-ipv4-vrf-list/ntp:priority,
/ntp:configuration/ntp:ntp/ntp:ntp-server/ntp:ntp-server-ipv6/ntp:ntp-ipv6-list/ntp:priority,
/ntp:configuration/ntp:ntp/ntp:ntp-server/ntp:ntp-server-ipv6/ntp:ntp-ipv6-mng-list/ntp:priority,
/ntp:configuration/ntp:ntp/ntp:ntp-server/ntp:ntp-server-ipv6/ntp:ntp-ipv6-vrf-list/ntp:priority,
/ntp:configuration/ntp:ntp/ntp:ntp-server/ntp:ntp-dns-server/ntp:ntp-dns-list/ntp:priority,
/ntp:configuration/ntp:ntp/ntp:ntp-server/ntp:ntp-dns-server/ntp:ntp-dns-mng-list/ntp:priority,
/ntp:configuration/ntp:ntp/ntp:ntp-server/ntp:ntp-dns-server/ntp:ntp-dns-vrf-list/ntp:priority,
/ntp:configuration/ntp:ntp/ntp:ntp-peer/ntp:ntp-peer-ipv4/ntp:ntp-ipv4-list/ntp:priority,
/ntp:configuration/ntp:ntp/ntp:ntp-peer/ntp:ntp-peer-ipv4/ntp:ntp-ipv4-mng-list/ntp:priority,
/ntp:configuration/ntp:ntp/ntp:ntp-peer/ntp:ntp-peer-ipv4/ntp:ntp-ipv4-vrf-list/ntp:priority,
/ntp:configuration/ntp:ntp/ntp:ntp-peer/ntp:ntp-peer-ipv6/ntp:ntp-ipv6-list/ntp:priority,
/ntp:configuration/ntp:ntp/ntp:ntp-peer/ntp:ntp-peer-ipv6/ntp:ntp-ipv6-mng-list/ntp:priority,
/ntp:configuration/ntp:ntp/ntp:ntp-peer/ntp:ntp-peer-ipv6/ntp:ntp-ipv6-vrf-list/ntp:priority,
/ntp:configuration/ntp:ntp/ntp:ntp-peer/ntp:ntp-dns-peer/ntp:ntp-dns-list/ntp:priority,
/ntp:configuration/ntp:ntp/ntp:ntp-peer/ntp:ntp-dns-peer/ntp:ntp-dns-mng-list/ntp:priority,
/ntp:configuration/ntp:ntp/ntp:ntp-peer/ntp:ntp-dns-peer/ntp:ntp-dns-vrf-list/ntp:priority.
Add /ntp:state/ntp:ntp/ntp:ntp-association/ntp:ntp-association-list/ntp:host-name,
/ntp:state/ntp:ntp/ntp:ntp-association/ntp:ntp-association-list/ntp:port,
/ntp:state/ntp:ntp/ntp:ntp-association/ntp:ntp-association-list/ntp:iburst,
/ntp:state/ntp:ntp/ntp:ntp-association/ntp:ntp-association-list/ntp:root-dispersion.' ;
  }

  revision 2018-08-16 {
    description 'Add:
/ntp:configuration/ntp:ntp/ntp:ntp-global/ntp:port,
/ntp:configuration/ntp:ntp/ntp:ntp-server/ntp:ntp-server-ipv4/ntp:ntp-ipv4-list/ntp:port,
/ntp:configuration/ntp:ntp/ntp:ntp-server/ntp:ntp-server-ipv4/ntp:ntp-ipv4-mng-list/ntp:port,
/ntp:configuration/ntp:ntp/ntp:ntp-server/ntp:ntp-server-ipv4/ntp:ntp-ipv4-vrf-list/ntp:port,
/ntp:configuration/ntp:ntp/ntp:ntp-server/ntp:ntp-server-ipv6/ntp:ntp-ipv6-list/ntp:port,
/ntp:configuration/ntp:ntp/ntp:ntp-server/ntp:ntp-server-ipv6/ntp:ntp-ipv6-mng-list/ntp:port,
/ntp:configuration/ntp:ntp/ntp:ntp-server/ntp:ntp-server-ipv6/ntp:ntp-ipv6-vrf-list/ntp:port,
/ntp:configuration/ntp:ntp/ntp:ntp-server/ntp:ntp-dns-server/ntp:ntp-dns-list/ntp:port,
/ntp:configuration/ntp:ntp/ntp:ntp-server/ntp:ntp-dns-server/ntp:ntp-dns-mng-list/ntp:port,
/ntp:configuration/ntp:ntp/ntp:ntp-server/ntp:ntp-dns-server/ntp:ntp-dns-vrf-list/ntp:port,
/ntp:configuration/ntp:ntp/ntp:ntp-server/ntp:ntp-server-ipv4/ntp:ntp-ipv4-list/ntp:minpoll,
/ntp:configuration/ntp:ntp/ntp:ntp-server/ntp:ntp-server-ipv4/ntp:ntp-ipv4-mng-list/ntp:minpoll,
/ntp:configuration/ntp:ntp/ntp:ntp-server/ntp:ntp-server-ipv4/ntp:ntp-ipv4-vrf-list/ntp:minpoll,
/ntp:configuration/ntp:ntp/ntp:ntp-server/ntp:ntp-server-ipv6/ntp:ntp-ipv6-list/ntp:minpoll,
/ntp:configuration/ntp:ntp/ntp:ntp-server/ntp:ntp-server-ipv6/ntp:ntp-ipv6-mng-list/ntp:minpoll,
/ntp:configuration/ntp:ntp/ntp:ntp-server/ntp:ntp-server-ipv6/ntp:ntp-ipv6-vrf-list/ntp:minpoll,
/ntp:configuration/ntp:ntp/ntp:ntp-server/ntp:ntp-dns-server/ntp:ntp-dns-list/ntp:minpoll,
/ntp:configuration/ntp:ntp/ntp:ntp-server/ntp:ntp-dns-server/ntp:ntp-dns-mng-list/ntp:minpoll,
/ntp:configuration/ntp:ntp/ntp:ntp-server/ntp:ntp-dns-server/ntp:ntp-dns-vrf-list/ntp:minpoll,
/ntp:configuration/ntp:ntp/ntp:ntp-server/ntp:ntp-server-ipv4/ntp:ntp-ipv4-list/ntp:maxpoll,
/ntp:configuration/ntp:ntp/ntp:ntp-server/ntp:ntp-server-ipv4/ntp:ntp-ipv4-mng-list/ntp:maxpoll,
/ntp:configuration/ntp:ntp/ntp:ntp-server/ntp:ntp-server-ipv4/ntp:ntp-ipv4-vrf-list/ntp:maxpoll,
/ntp:configuration/ntp:ntp/ntp:ntp-server/ntp:ntp-server-ipv6/ntp:ntp-ipv6-list/ntp:maxpoll,
/ntp:configuration/ntp:ntp/ntp:ntp-server/ntp:ntp-server-ipv6/ntp:ntp-ipv6-mng-list/ntp:maxpoll,
/ntp:configuration/ntp:ntp/ntp:ntp-server/ntp:ntp-server-ipv6/ntp:ntp-ipv6-vrf-list/ntp:maxpoll,
/ntp:configuration/ntp:ntp/ntp:ntp-server/ntp:ntp-dns-server/ntp:ntp-dns-list/ntp:maxpoll,
/ntp:configuration/ntp:ntp/ntp:ntp-server/ntp:ntp-dns-server/ntp:ntp-dns-mng-list/ntp:maxpoll,
/ntp:configuration/ntp:ntp/ntp:ntp-server/ntp:ntp-dns-server/ntp:ntp-dns-vrf-list/ntp:maxpoll,
/ntp:configuration/ntp:ntp/ntp:ntp-server/ntp:ntp-server-ipv4/ntp:ntp-ipv4-list/ntp:iburst,
/ntp:configuration/ntp:ntp/ntp:ntp-server/ntp:ntp-server-ipv4/ntp:ntp-ipv4-mng-list/ntp:iburst,
/ntp:configuration/ntp:ntp/ntp:ntp-server/ntp:ntp-server-ipv4/ntp:ntp-ipv4-vrf-list/ntp:iburst,
/ntp:configuration/ntp:ntp/ntp:ntp-server/ntp:ntp-server-ipv6/ntp:ntp-ipv6-list/ntp:iburst,
/ntp:configuration/ntp:ntp/ntp:ntp-server/ntp:ntp-server-ipv6/ntp:ntp-ipv6-mng-list/ntp:iburst,
/ntp:configuration/ntp:ntp/ntp:ntp-server/ntp:ntp-server-ipv6/ntp:ntp-ipv6-vrf-list/ntp:iburst,
/ntp:configuration/ntp:ntp/ntp:ntp-server/ntp:ntp-dns-server/ntp:ntp-dns-list/ntp:iburst,
/ntp:configuration/ntp:ntp/ntp:ntp-server/ntp:ntp-dns-server/ntp:ntp-dns-mng-list/ntp:iburst,
/ntp:configuration/ntp:ntp/ntp:ntp-server/ntp:ntp-dns-server/ntp:ntp-dns-vrf-list/ntp:iburst,
/ntp:configuration/ntp:ntp/ntp:ntp-peer/ntp:ntp-peer-ipv4/ntp:ntp-ipv4-list/ntp:port,
/ntp:configuration/ntp:ntp/ntp:ntp-peer/ntp:ntp-peer-ipv4/ntp:ntp-ipv4-mng-list/ntp:port,
/ntp:configuration/ntp:ntp/ntp:ntp-peer/ntp:ntp-peer-ipv4/ntp:ntp-ipv4-vrf-list/ntp:port,
/ntp:configuration/ntp:ntp/ntp:ntp-peer/ntp:ntp-peer-ipv6/ntp:ntp-ipv6-list/ntp:port,
/ntp:configuration/ntp:ntp/ntp:ntp-peer/ntp:ntp-peer-ipv6/ntp:ntp-ipv6-mng-list/ntp:port,
/ntp:configuration/ntp:ntp/ntp:ntp-peer/ntp:ntp-peer-ipv6/ntp:ntp-ipv6-vrf-list/ntp:port,
/ntp:configuration/ntp:ntp/ntp:ntp-peer/ntp:ntp-dns-peer/ntp:ntp-dns-list/ntp:port,
/ntp:configuration/ntp:ntp/ntp:ntp-peer/ntp:ntp-dns-peer/ntp:ntp-dns-mng-list/ntp:port,
/ntp:configuration/ntp:ntp/ntp:ntp-peer/ntp:ntp-dns-peer/ntp:ntp-dns-vrf-list/ntp:port,
/ntp:configuration/ntp:ntp/ntp:ntp-peer/ntp:ntp-peer-ipv4/ntp:ntp-ipv4-list/ntp:minpoll,
/ntp:configuration/ntp:ntp/ntp:ntp-peer/ntp:ntp-peer-ipv4/ntp:ntp-ipv4-mng-list/ntp:minpoll,
/ntp:configuration/ntp:ntp/ntp:ntp-peer/ntp:ntp-peer-ipv4/ntp:ntp-ipv4-vrf-list/ntp:minpoll,
/ntp:configuration/ntp:ntp/ntp:ntp-peer/ntp:ntp-peer-ipv6/ntp:ntp-ipv6-list/ntp:minpoll,
/ntp:configuration/ntp:ntp/ntp:ntp-peer/ntp:ntp-peer-ipv6/ntp:ntp-ipv6-mng-list/ntp:minpoll,
/ntp:configuration/ntp:ntp/ntp:ntp-peer/ntp:ntp-peer-ipv6/ntp:ntp-ipv6-vrf-list/ntp:minpoll,
/ntp:configuration/ntp:ntp/ntp:ntp-peer/ntp:ntp-dns-peer/ntp:ntp-dns-list/ntp:minpoll,
/ntp:configuration/ntp:ntp/ntp:ntp-peer/ntp:ntp-dns-peer/ntp:ntp-dns-mng-list/ntp:minpoll,
/ntp:configuration/ntp:ntp/ntp:ntp-peer/ntp:ntp-dns-peer/ntp:ntp-dns-vrf-list/ntp:minpoll,
/ntp:configuration/ntp:ntp/ntp:ntp-peer/ntp:ntp-peer-ipv4/ntp:ntp-ipv4-list/ntp:maxpoll,
/ntp:configuration/ntp:ntp/ntp:ntp-peer/ntp:ntp-peer-ipv4/ntp:ntp-ipv4-mng-list/ntp:maxpoll,
/ntp:configuration/ntp:ntp/ntp:ntp-peer/ntp:ntp-peer-ipv4/ntp:ntp-ipv4-vrf-list/ntp:maxpoll,
/ntp:configuration/ntp:ntp/ntp:ntp-peer/ntp:ntp-peer-ipv6/ntp:ntp-ipv6-list/ntp:maxpoll,
/ntp:configuration/ntp:ntp/ntp:ntp-peer/ntp:ntp-peer-ipv6/ntp:ntp-ipv6-mng-list/ntp:maxpoll,
/ntp:configuration/ntp:ntp/ntp:ntp-peer/ntp:ntp-peer-ipv6/ntp:ntp-ipv6-vrf-list/ntp:maxpoll,
/ntp:configuration/ntp:ntp/ntp:ntp-peer/ntp:ntp-dns-peer/ntp:ntp-dns-list/ntp:maxpoll,
/ntp:configuration/ntp:ntp/ntp:ntp-peer/ntp:ntp-dns-peer/ntp:ntp-dns-mng-list/ntp:maxpoll,
/ntp:configuration/ntp:ntp/ntp:ntp-peer/ntp:ntp-dns-peer/ntp:ntp-dns-vrf-list/ntp:maxpoll,
/ntp:configuration/ntp:ntp/ntp:ntp-multi-broad/ntp:ntp-multicast/ntp:ntp-server/ntp:ntp-ipv4-server-list/ntp:port,
/ntp:configuration/ntp:ntp/ntp:ntp-multi-broad/ntp:ntp-multicast/ntp:ntp-server/ntp:ntp-ipv6-server-list/ntp:port,
/ntp:configuration/ntp:ntp/ntp:ntp-multi-broad/ntp:ntp-broadcast/ntp:ntp-server-list/ntp:port' ;
  }

  revision 2018-02-02 {
    description 'Add:/ntp:configuration/ntp:ntp/ntp:ntp-server/ntp:ntp-dns-server
Add:/ntp:configuration/ntp:ntp/ntp:ntp-peer/ntp:ntp-dns-peer' ;
  }

  revision 2017-07-03 {
    description 'Add:/ntp:configuration/ntp:ntp/ntp:ntp-authentication/ntp:ntp-authentication-key' ;
  }

  revision 2015-06-24 {
    description 'Modify the description of 
/ntp:configuration/ntp:ntp/ntp:ntp-global/ntp:enable,
/ntp:configuration/ntp:ntp/ntp:ntp-server/ntp:ntp-server-ipv4/ntp:ntp-ipv4-list/ntp:priority,
/ntp:configuration/ntp:ntp/ntp:ntp-server/ntp:ntp-server-ipv4/ntp:ntp-ipv4-mng-list/ntp:priority
/ntp:configuration/ntp:ntp/ntp:ntp-server/ntp:ntp-server-ipv4/ntp:ntp-ipv4-vrf-list/ntp:priority
/ntp:configuration/ntp:ntp/ntp:ntp-server/ntp:ntp-server-ipv6/ntp:ntp-ipv6-list/ntp:priority,
/ntp:configuration/ntp:ntp/ntp:ntp-server/ntp:ntp-server-ipv6/ntp:ntp-ipv6-mng-list/ntp:priority
/ntp:configuration/ntp:ntp/ntp:ntp-server/ntp:ntp-server-ipv6/ntp:ntp-ipv6-vrf-list/ntp:priority
/ntp:configuration/ntp:ntp/ntp:ntp-peer/ntp:ntp-peer-ipv4/ntp:ntp-ipv4-list/ntp:priority,
/ntp:configuration/ntp:ntp/ntp:ntp-peer/ntp:ntp-peer-ipv4/ntp:ntp-ipv4-mng-list/ntp:priority,
/ntp:configuration/ntp:ntp/ntp:ntp-peer/ntp:ntp-peer-ipv4/ntp:ntp-ipv4-vrf-list/ntp:priority,
/ntp:configuration/ntp:ntp/ntp:ntp-peer/ntp:ntp-peer-ipv6/ntp:ntp-ipv6-list/ntp:priority,
/ntp:configuration/ntp:ntp/ntp:ntp-peer/ntp:ntp-peer-ipv6/ntp:ntp-ipv6-mng-list/ntp:priority,
/ntp:configuration/ntp:ntp/ntp:ntp-peer/ntp:ntp-peer-ipv6/ntp:ntp-ipv6-vrf-list/ntp:priority,
/ntp:configuration/ntp:ntp/ntp:ntp-peer/ntp:ntp-peer-ipv6/ntp:ntp-ipv6-list/ntp:version,
/ntp:configuration/ntp:ntp/ntp:ntp-peer/ntp:ntp-peer-ipv6/ntp:ntp-ipv6-mng-list/ntp:version,
/ntp:configuration/ntp:ntp/ntp:ntp-peer/ntp:ntp-peer-ipv6/ntp:ntp-ipv6-vrf-list/ntp:version,
/ntp:configuration/ntp:ntp/ntp:ntp-peer/ntp:ntp-peer-ipv4/ntp:ntp-ipv4-vrf-list,
/ntp:configuration/ntp:ntp/ntp:ntp-peer/ntp:ntp-peer-ipv6/ntp:ntp-ipv6-vrf-list,
/ntp:state/ntp:ntp/ntp:ntp-association/ntp:ntp-association-list/ntp:id' ;
  }

  revision 2014-07-01 {
    description 'Add length for
ntp\state\ntp\ntp-current-status\current-time,length is 0~31;
ntp\state\ntp\ntp-current-status\current-server,length is 0~85;
ntp\state\ntp\ntp-association\ntp-association-list\delay,length is 0~15.' ;
  }

  revision 2014-05-21 {
    description 'Modify the description of
/ntp:configuration/ntp:ntp/ntp:ntp-global/ntp:enable;
/ntp:configuration/ntp:ntp/ntp:ntp-global/ntp:master;
/ntp:configuration/ntp:ntp/ntp:ntp-global/ntp:poll-interval;
/ntp:configuration/ntp:ntp/ntp:ntp-acl/ntp:acl-name-ipv4;
/ntp:configuration/ntp:ntp/ntp:ntp-acl/ntp:acl-name-ipv6;
/ntp:configuration/ntp:ntp/ntp:ntp-multi-broad/ntp:ntp-multicast/ntp:ntp-server/ntp:ntp-ipv6-server-list/ntp:version;
/ntp:configuration/ntp:ntp/ntp:ntp-authentication/ntp:authenticate;
/ntp:state/ntp:ntp/ntp:ntp-current-status/ntp:current-server;
change the range of
/ntp:configuration/ntp:ntp/ntp:ntp-multi-broad/ntp:ntp-multicast/ntp:ntp-server/ntp:ntp-ipv6-server-list/ntp:version.' ;
  }

  revision 2014-05-08 {
    description 'Modify the length of VRF name,add length for ifname.
/ntp:configuration/ntp:ntp/ntp:ntp-server/ntp:ntp-server-ipv4/ntp:ntp-ipv4-vrf-list/ntp:vrf-name;
/ntp:configuration/ntp:ntp/ntp:ntp-server/ntp:ntp-server-ipv6/ntp:ntp-ipv6-vrf-list/ntp:vrf-name;
/ntp:configuration/ntp:ntp/ntp:ntp-peer/ntp:ntp-peer-ipv4/ntp:ntp-ipv4-vrf-list/ntp:vrf-name;
/ntp:configuration/ntp:ntp/ntp:ntp-peer/ntp:ntp-peer-ipv6/ntp:ntp-ipv6-vrf-list/ntp:vrf-name;
/ntp:configuration/ntp:ntp/ntp:ntp-source/ntp:source-if;
/ntp:configuration/ntp:ntp/ntp:ntp-multi-broad/ntp:ntp-multicast/ntp:ntp-server/ntp:ntp-ipv4-server-list/ntp:ifname;
/ntp:configuration/ntp:ntp/ntp:ntp-multi-broad/ntp:ntp-multicast/ntp:ntp-server/ntp:ntp-ipv6-server-list/ntp:ifname;
/ntp:configuration/ntp:ntp/ntp:ntp-multi-broad/ntp:ntp-multicast/ntp:ntp-client/ntp:ntp-ipv4-client-list/ntp:ifname;
/ntp:configuration/ntp:ntp/ntp:ntp-multi-broad/ntp:ntp-multicast/ntp:ntp-client/ntp:ntp-ipv6-client-list/ntp:ifname;
/ntp:configuration/ntp:ntp/ntp:ntp-multi-broad/ntp:ntp-broadcast/ntp:ntp-server-list/ntp:ifname;
/ntp:configuration/ntp:ntp/ntp:ntp-multi-broad/ntp:ntp-broadcast/ntp:ntp-client-list/ntp:ifname.' ;
  }

  revision 2014-01-20 {
    description 'Modify the range of the trusted-key from 0~4294967295 to 1~4294967295;Add action type for trusted-key.' ;
  }

  revision 2013-11-06 {
    description 'Initial version.' ;
  }

  feature master-mode {
    description 'This flag identifies the master-mode is or not supported.' ;
  }

  feature monitor-clients {
    description 'This flag identifies the monitor-clients is or not supported.' ;
  }

  container configuration {
    description 'The configuration of NTP.' ;
    container ntp {
      description 'The node of NTP.' ;
      container ntp-global {
        description 'The node of NTP global configuration.' ;
        leaf enable {
          description 'The NTP global enable switch,0 means off,1 means on.' ;
          type enumeration {
            enum disable {
              value 0 ;
              description 'The NTP is disabled.' ;
            }

            enum enable {
              value 1 ;
              description 'The NTP is enabled.' ;
            }

          }

          default disable ;
        }

        leaf master {
          description 'The NTP server stratum value:the valid range is 1-15,0 means disable master.' ;
          type uint8 {
            range 0..15 {
              description 'The NTP server stratum value:the valid range is 1-15,0 means disable master.' ;
            }

          }

          default 0 ;
        }

        leaf poll-interval {
          description 'The NTP poll interval,the range is 4 to 17.' ;
          type uint8 {
            range 4..17 {
              description 'The NTP poll interval,the range is 4 to 17.' ;
            }

          }

          units log2 ;
          default 6 ;
        }

        leaf port {
          description 'NTP source UDP port' ;
          type uint16 {
            range "123 | 1025..65535" ;

          }

          default 123 ;
          ncd:revise-date 2018-08-16 ;
        }

        leaf master-mode {
          if-feature master-mode ;

          description 'Configure the working mode of the server, fast means fast mode, slow means slow mode, and the default is slow mode.' ;
          type enumeration {
            enum fast {
              value 1 ;
              description 'Master-mode is fast.' ;
            }

            enum slow {
              value 0 ;
              description 'Master-mode is slow.' ;
            }

          }

          default slow ;
          ncd:revise-date 2020-04-16 ;
        }

        leaf md5-strong-password-check {
          description 'The NTP MD5 strong password check status,0 means off,1 means on.' ;
          type enumeration {
            enum disable {
              value 0 ;
              description 'Disable MD5 strong password check.' ;
            }

            enum enable {
              value 1 ;
              description 'Enable MD5 strong password check.' ;
            }

          }

          default disable ;
          ncd:revise-date 2020-12-21 ;
        }

      }

      container ntp-acl {
        description 'The ACL configuration of NTP.' ;
        leaf acl-name-ipv4 {
          description 'The NTP IPv4 access-group,ACL name.' ;
          type string {
            length 0..31 {
              description 'The NTP IPv4 access-group,ACL name.' ;
            }

          }

        }

        leaf acl-name-ipv6 {
          description 'The NTP IPv6 access-group,ACL name.' ;
          type string {
            length 0..31 {
              description 'The NTP IPv6 access-group,ACL name.' ;
            }

          }

        }

      }

      container ntp-source {
        description 'The source configuration of NTP.' ;
        leaf source-ipv4 {
          description 'The NTP IPv4 source address.' ;
          type ncd:ipv4-address ;

        }

        leaf source-ipv6 {
          description 'The NTP IPv6 source address.' ;
          type ncd:ipv6-address ;

        }

        leaf source-if {
          description 'The NTP source interface name.' ;
          type ncd:ifname {
            length 0..31 ;

          }

          default '' ;
        }

      }

      container ntp-server {
        description 'The node of NTP server configuration.' ;
        container ntp-server-ipv4 {
          description 'The NTP IPv4 server configuration.' ;
          list ntp-ipv4-list {
            description 'The NTP IPv4 server list.' ;
            key ip-address ;
            leaf ip-address {
              description 'The NTP server IPv4 address.' ;
              type ncd:ipv4-address ;

            }

            leaf version {
              description 'The NTP version number, it can be in the range from 1 to 4. 
The default value is 3.' ;
              type uint8 {
                range 1..4 {
                  description 'The NTP version number.' ;
                }

              }

              default 3 ;
            }

            leaf lock {
              description 'The NTP server lock status.0 means unlock,and 1 means the server is locked.' ;
              type enumeration {
                enum unlock {
                  value 0 ;
                  description 'The server is unlocked.' ;
                }

                enum lock {
                  value 1 ;
                  description 'The server is locked.' ;
                }

              }

              default unlock ;
            }

            leaf priority {
              description 'The NTP server priority,the lower value the higher priority.' ;
              type uint8 {
                range 1..6 {
                  description 'The NTP server priority.' ;
                }

              }

              mandatory true ;
            }

            leaf key-id {
              description 'The NTP authentication key.' ;
              type uint32 {
                range 0..4294967295 {
                  description 'The NTP authentication key id.' ;
                }

              }

              default 0 ;
            }

            leaf port {
              description 'NTP server UDP port.' ;
              type uint16 {
                range "123 | 1025..65535" ;

              }

              default 123 ;
              ncd:revise-date 2018-08-16 ;
            }

            leaf minpoll {
              description 'Min poll,the range is 3 to 6.' ;
              type uint8 {
                range 3..6 ;

              }

              default 3 ;
              ncd:revise-date 2018-08-16 ;
            }

            leaf maxpoll {
              description 'Max poll,the range is 7 to 17.' ;
              type uint8 {
                range 7..17 ;

              }

              default 10 ;
              ncd:revise-date 2018-08-16 ;
            }

            leaf iburst {
              description 'NTP burst packet flag.' ;
              type enumeration {
                enum true {
                  value 1 ;
                }

                enum false {
                  value 0 ;
                }

              }

              default false ;
              ncd:revise-date 2018-08-16 ;
            }

            leaf source-if {
              type ncd:ifname ;

              description 'The NTP source interface name.' ;
              ncd:revise-date 2024-09-26 ;
            }

          }

          list ntp-ipv4-mng-list {
            description 'The NTP IPv4 MNG server list.' ;
            key ip-address ;
            leaf ip-address {
              description 'The NTP server IPv4 address.' ;
              type ncd:ipv4-address ;

            }

            leaf version {
              description 'The NTP version number, it can be in the range from 1 to 4. 
The default value is 3.' ;
              type uint8 {
                range 1..4 {
                  description 'The NTP version number.' ;
                }

              }

              default 3 ;
            }

            leaf lock {
              description 'The NTP server lock status.0 means unlock,and 1 means the server is locked.' ;
              type enumeration {
                enum unlock {
                  value 0 ;
                  description 'The server is unlocked.' ;
                }

                enum lock {
                  value 1 ;
                  description 'The server is locked.' ;
                }

              }

              default unlock ;
            }

            leaf priority {
              description 'The NTP server priority,the lower value the higher priority.' ;
              type uint8 {
                range 1..6 {
                  description 'The NTP server priority.' ;
                }

              }

              mandatory true ;
            }

            leaf key-id {
              description 'The NTP authentication key.' ;
              type uint32 {
                range 0..4294967295 {
                  description 'The NTP authentication key.' ;
                }

              }

              default 0 ;
            }

            leaf port {
              description 'NTP server UDP port.' ;
              type uint16 {
                range "123 | 1025..65535" ;

              }

              default 123 ;
              ncd:revise-date 2018-08-16 ;
            }

            leaf minpoll {
              description 'Min poll,the range is 3 to 6.' ;
              type uint8 {
                range 3..6 ;

              }

              default 3 ;
              ncd:revise-date 2018-08-16 ;
            }

            leaf maxpoll {
              description 'Max poll,the range is 7 to 17.' ;
              type uint8 {
                range 7..17 ;

              }

              default 10 ;
              ncd:revise-date 2018-08-16 ;
            }

            leaf iburst {
              description 'NTP burst packet flag.' ;
              type enumeration {
                enum true {
                  value 1 ;
                }

                enum false {
                  value 0 ;
                }

              }

              default false ;
              ncd:revise-date 2018-08-16 ;
            }

            leaf source-if {
              type ncd:ifname ;

              description 'The NTP source interface name.' ;
              ncd:revise-date 2024-09-26 ;
            }

          }

          list ntp-ipv4-vrf-list {
            description 'The NTP IPv4 VRF server list.' ;
            key 'vrf-name ip-address' ;
            leaf vrf-name {
              description 'VRF name.' ;
              type string {
                length 1..32 {
                  description 'VRF name.' ;
                }

              }

            }

            leaf ip-address {
              description 'The NTP server IPv4 address.' ;
              type ncd:ipv4-address ;

            }

            leaf version {
              description 'The NTP version number, it can be in the range from 1 to 4. 
The default value is 3.' ;
              type uint8 {
                range 1..4 {
                  description 'The NTP version number.' ;
                }

              }

              default 3 ;
            }

            leaf lock {
              description 'The NTP server lock status.0 means unlock,and 1 means the server is locked.' ;
              type enumeration {
                enum unlock {
                  value 0 ;
                  description 'The server is unlocked.' ;
                }

                enum lock {
                  value 1 ;
                  description 'The server is locked.' ;
                }

              }

              default unlock ;
            }

            leaf priority {
              description 'The NTP server priority,the lower value the higher priority.' ;
              type uint8 {
                range 1..6 {
                  description 'The NTP server priority.' ;
                }

              }

              mandatory true ;
            }

            leaf key-id {
              description 'The NTP authentication key.' ;
              type uint32 {
                range 0..4294967295 {
                  description 'The NTP authentication key.' ;
                }

              }

              default 0 ;
            }

            leaf port {
              description 'NTP server UDP port.' ;
              type uint16 {
                range "123 | 1025..65535" ;

              }

              default 123 ;
              ncd:revise-date 2018-08-16 ;
            }

            leaf minpoll {
              description 'Min poll,the range is 3 to 6.' ;
              type uint8 {
                range 3..6 ;

              }

              default 3 ;
              ncd:revise-date 2018-08-16 ;
            }

            leaf maxpoll {
              description 'Max poll,the range is 7 to 17.' ;
              type uint8 {
                range 7..17 ;

              }

              default 10 ;
              ncd:revise-date 2018-08-16 ;
            }

            leaf iburst {
              description 'NTP burst packet flag.' ;
              type enumeration {
                enum true {
                  value 1 ;
                }

                enum false {
                  value 0 ;
                }

              }

              default false ;
              ncd:revise-date 2018-08-16 ;
            }

            leaf source-if {
              type ncd:ifname ;

              description 'The NTP source interface name.' ;
              ncd:revise-date 2024-09-26 ;
            }

          }

        }

        container ntp-server-ipv6 {
          description 'The NTP IPv6 server configuration.' ;
          list ntp-ipv6-list {
            description 'The NTP IPv6 server list.' ;
            key ipv6-address ;
            leaf ipv6-address {
              description 'The NTP server IPv6 address.' ;
              type ncd:ipv6-address ;

            }

            leaf version {
              description 'The NTP version number, it only can be 4.' ;
              type uint8 {
                range 4 {
                  description 'The NTP version number.' ;
                }

              }

              default 4 ;
            }

            leaf lock {
              description 'The NTP server lock status.0 means unlock,and 1 means the server is locked.' ;
              type enumeration {
                enum unlock {
                  value 0 ;
                  description 'The server is unlocked.' ;
                }

                enum lock {
                  value 1 ;
                  description 'The server is locked.' ;
                }

              }

              default unlock ;
            }

            leaf priority {
              description 'The NTP server priority,the lower value the higher priority.' ;
              type uint8 {
                range 1..6 {
                  description 'The NTP server priority.' ;
                }

              }

              mandatory true ;
            }

            leaf key-id {
              description 'The NTP authentication key.' ;
              type uint32 {
                range 0..4294967295 {
                  description 'The NTP authentication key.' ;
                }

              }

              default 0 ;
            }

            leaf port {
              description 'NTP server UDP port.' ;
              type uint16 {
                range "123 | 1025..65535" ;

              }

              default 123 ;
              ncd:revise-date 2018-08-16 ;
            }

            leaf minpoll {
              description 'Min poll,the range is 3 to 6.' ;
              type uint8 {
                range 3..6 ;

              }

              default 3 ;
              ncd:revise-date 2018-08-16 ;
            }

            leaf maxpoll {
              description 'Max poll,the range is 7 to 17.' ;
              type uint8 {
                range 7..17 ;

              }

              default 10 ;
              ncd:revise-date 2018-08-16 ;
            }

            leaf iburst {
              description 'NTP burst packet flag.' ;
              type enumeration {
                enum true {
                  value 1 ;
                }

                enum false {
                  value 0 ;
                }

              }

              default false ;
              ncd:revise-date 2018-08-16 ;
            }

            leaf source-if {
              type ncd:ifname ;

              description 'The NTP source interface name.' ;
              ncd:revise-date 2024-09-26 ;
            }

          }

          list ntp-ipv6-mng-list {
            description 'The NTP IPv6 MNG server list.' ;
            key ipv6-address ;
            leaf ipv6-address {
              description 'The NTP server IPv6 address.' ;
              type ncd:ipv6-address ;

            }

            leaf version {
              description 'The NTP version number, it only can be 4.' ;
              type uint8 {
                range 4 {
                  description 'The NTP version number.' ;
                }

              }

              default 4 ;
            }

            leaf lock {
              description 'The NTP server lock status.0 means unlock,and 1 means the server is locked.' ;
              type enumeration {
                enum unlock {
                  value 0 ;
                  description 'The server is unlocked.' ;
                }

                enum lock {
                  value 1 ;
                  description 'The server is locked.' ;
                }

              }

              default unlock ;
            }

            leaf priority {
              description 'The NTP server priority,the lower value the higher priority.' ;
              type uint8 {
                range 1..6 {
                  description 'The NTP server priority.' ;
                }

              }

              mandatory true ;
            }

            leaf key-id {
              description 'The NTP authentication key.' ;
              type uint32 {
                range 0..4294967295 {
                  description 'The NTP authentication key.' ;
                }

              }

              default 0 ;
            }

            leaf port {
              description 'NTP server UDP port.' ;
              type uint16 {
                range "123 | 1025..65535" ;

              }

              default 123 ;
              ncd:revise-date 2018-08-16 ;
            }

            leaf minpoll {
              description 'Min poll,the range is 3 to 6.' ;
              type uint8 {
                range 3..6 ;

              }

              default 3 ;
              ncd:revise-date 2018-08-16 ;
            }

            leaf maxpoll {
              description 'Max poll,the range is 7 to 17.' ;
              type uint8 {
                range 7..17 ;

              }

              default 10 ;
              ncd:revise-date 2018-08-16 ;
            }

            leaf iburst {
              description 'NTP burst packet flag.' ;
              type enumeration {
                enum true {
                  value 1 ;
                }

                enum false {
                  value 0 ;
                }

              }

              default false ;
              ncd:revise-date 2018-08-16 ;
            }

            leaf source-if {
              type ncd:ifname ;

              description 'The NTP source interface name.' ;
              ncd:revise-date 2024-09-26 ;
            }

          }

          list ntp-ipv6-vrf-list {
            description 'The NTP IPv6 VRF server list.' ;
            key 'vrf-name ipv6-address' ;
            leaf vrf-name {
              description 'VRF name.' ;
              type string {
                length 1..32 {
                  description 'VRF name.' ;
                }

              }

            }

            leaf ipv6-address {
              description 'The NTP server IPv6 address.' ;
              type ncd:ipv6-address ;

            }

            leaf version {
              description 'The NTP version number, it only can be 4.' ;
              type uint8 {
                range 4 {
                  description 'The NTP version number.' ;
                }

              }

              default 4 ;
            }

            leaf lock {
              description 'The NTP server lock status.0 means unlock,and 1 means the server is locked.' ;
              type uint16 {
                range 0..1 {
                  description 'The NTP server lock status.' ;
                }

              }

              default 0 ;
            }

            leaf priority {
              description 'The NTP server priority,the lower value the higher priority.' ;
              type uint8 {
                range 1..6 {
                  description 'The NTP server priority.' ;
                }

              }

              mandatory true ;
            }

            leaf key-id {
              description 'The NTP authentication key.' ;
              type uint32 {
                range 0..4294967295 {
                  description 'The NTP authentication key.' ;
                }

              }

              default 0 ;
            }

            leaf port {
              description 'NTP server UDP port.' ;
              type uint16 {
                range "123 | 1025..65535" ;

              }

              default 123 ;
              ncd:revise-date 2018-08-16 ;
            }

            leaf minpoll {
              description 'Min poll,the range is 3 to 6.' ;
              type uint8 {
                range 3..6 ;

              }

              default 3 ;
              ncd:revise-date 2018-08-16 ;
            }

            leaf maxpoll {
              description 'Max poll,the range is 7 to 17.' ;
              type uint8 {
                range 7..17 ;

              }

              default 10 ;
              ncd:revise-date 2018-08-16 ;
            }

            leaf iburst {
              description 'NTP burst packet flag.' ;
              type enumeration {
                enum true {
                  value 1 ;
                }

                enum false {
                  value 0 ;
                }

              }

              default false ;
              ncd:revise-date 2018-08-16 ;
            }

            leaf source-if {
              type ncd:ifname ;

              description 'The NTP source interface name.' ;
              ncd:revise-date 2024-09-26 ;
            }

          }

        }

        container ntp-dns-server {
          description 'The NTP DNS server configuration.' ;
          list ntp-dns-list {
            description 'The NTP DNS server list.' ;
            key host-name ;
            leaf host-name {
              description 'The NTP server Host Name.' ;
              type string {
                length 1..128 ;

              }

            }

            leaf version {
              description 'The NTP version number, it can be in the range from 1 to 4. 
The default value is 3.' ;
              type uint8 {
                range 1..4 {
                  description 'The NTP version number.' ;
                }

              }

              default 3 ;
            }

            leaf lock {
              description 'The NTP server lock status.0 means unlock,and 1 means the server is locked.' ;
              type enumeration {
                enum unlock {
                  value 0 ;
                  description 'The server is unlocked.' ;
                }

                enum lock {
                  value 1 ;
                  description 'The server is locked.' ;
                }

              }

              default unlock ;
            }

            leaf priority {
              description 'The NTP server priority,the lower value the higher priority.' ;
              type uint8 {
                range 1..6 {
                  description 'The NTP server priority.' ;
                }

              }

              mandatory true ;
            }

            leaf key-id {
              description 'The NTP authentication key.' ;
              type uint32 {
                range 0..4294967295 {
                  description 'The NTP authentication key id.' ;
                }

              }

              default 0 ;
            }

            leaf port {
              description 'NTP server UDP port.' ;
              type uint16 {
                range "123 | 1025..65535" ;

              }

              default 123 ;
              ncd:revise-date 2018-08-16 ;
            }

            leaf minpoll {
              description 'Min poll,the range is 3 to 6.' ;
              type uint8 {
                range 3..6 ;

              }

              default 3 ;
              ncd:revise-date 2018-08-16 ;
            }

            leaf maxpoll {
              description 'Max poll,the range is 7 to 17.' ;
              type uint8 {
                range 7..17 ;

              }

              default 10 ;
              ncd:revise-date 2018-08-16 ;
            }

            leaf iburst {
              description 'NTP burst packet flag.' ;
              type enumeration {
                enum true {
                  value 1 ;
                }

                enum false {
                  value 0 ;
                }

              }

              default false ;
              ncd:revise-date 2018-08-16 ;
            }

            leaf source-if {
              type ncd:ifname ;

              description 'The NTP source interface name.' ;
              ncd:revise-date 2024-09-26 ;
            }

          }

          list ntp-dns-mng-list {
            description 'The NTP DNS MNG server list.' ;
            key host-name ;
            leaf host-name {
              description 'The NTP server Host Name.' ;
              type string {
                length 1..128 ;

              }

            }

            leaf version {
              description 'The NTP version number, it can be in the range from 1 to 4. 
The default value is 3.' ;
              type uint8 {
                range 1..4 {
                  description 'The NTP version number.' ;
                }

              }

              default 3 ;
            }

            leaf lock {
              description 'The NTP server lock status.0 means unlock,and 1 means the server is locked.' ;
              type enumeration {
                enum unlock {
                  value 0 ;
                  description 'The server is unlocked.' ;
                }

                enum lock {
                  value 1 ;
                  description 'The server is locked.' ;
                }

              }

              default unlock ;
            }

            leaf priority {
              description 'The NTP server priority,the lower value the higher priority.' ;
              type uint8 {
                range 1..6 {
                  description 'The NTP server priority.' ;
                }

              }

              mandatory true ;
            }

            leaf key-id {
              description 'The NTP authentication key.' ;
              type uint32 {
                range 0..4294967295 {
                  description 'The NTP authentication key id.' ;
                }

              }

              default 0 ;
            }

            leaf port {
              description 'NTP server UDP port.' ;
              type uint16 {
                range "123 | 1025..65535" ;

              }

              default 123 ;
              ncd:revise-date 2018-08-16 ;
            }

            leaf minpoll {
              description 'Min poll,the range is 3 to 6.' ;
              type uint8 {
                range 3..6 ;

              }

              default 3 ;
              ncd:revise-date 2018-08-16 ;
            }

            leaf maxpoll {
              description 'Max poll,the range is 7 to 17.' ;
              type uint8 {
                range 7..17 ;

              }

              default 10 ;
              ncd:revise-date 2018-08-16 ;
            }

            leaf iburst {
              description 'NTP burst packet flag.' ;
              type enumeration {
                enum true {
                  value 1 ;
                }

                enum false {
                  value 0 ;
                }

              }

              default false ;
              ncd:revise-date 2018-08-16 ;
            }

            leaf source-if {
              type ncd:ifname ;

              description 'The NTP source interface name.' ;
              ncd:revise-date 2024-09-26 ;
            }

          }

          list ntp-dns-vrf-list {
            description 'The NTP DNS VRF server list.' ;
            key 'vrf-name host-name' ;
            leaf vrf-name {
              description 'VRF name.' ;
              type string {
                length 1..32 {
                  description 'VRF name.' ;
                }

              }

            }

            leaf host-name {
              description 'The NTP server Host Name.' ;
              type string {
                length 1..128 ;

              }

            }

            leaf version {
              description 'The NTP version number, it can be in the range from 1 to 4. 
The default value is 3.' ;
              type uint8 {
                range 1..4 {
                  description 'The NTP version number.' ;
                }

              }

              default 3 ;
            }

            leaf lock {
              description 'The NTP server lock status.0 means unlock,and 1 means the server is locked.' ;
              type enumeration {
                enum unlock {
                  value 0 ;
                  description 'The server is unlocked.' ;
                }

                enum lock {
                  value 1 ;
                  description 'The server is locked.' ;
                }

              }

              default unlock ;
            }

            leaf priority {
              description 'The NTP server priority,the lower value the higher priority.' ;
              type uint8 {
                range 1..6 {
                  description 'The NTP server priority.' ;
                }

              }

              mandatory true ;
            }

            leaf key-id {
              description 'The NTP authentication key.' ;
              type uint32 {
                range 0..4294967295 {
                  description 'The NTP authentication key id.' ;
                }

              }

              default 0 ;
            }

            leaf port {
              description 'NTP server UDP port.' ;
              type uint16 {
                range "123 | 1025..65535" ;

              }

              default 123 ;
              ncd:revise-date 2018-08-16 ;
            }

            leaf minpoll {
              description 'Min poll,the range is 3 to 6.' ;
              type uint8 {
                range 3..6 ;

              }

              default 3 ;
              ncd:revise-date 2018-08-16 ;
            }

            leaf maxpoll {
              description 'Max poll,the range is 7 to 17.' ;
              type uint8 {
                range 7..17 ;

              }

              default 10 ;
              ncd:revise-date 2018-08-16 ;
            }

            leaf iburst {
              description 'NTP burst packet flag.' ;
              type enumeration {
                enum true {
                  value 1 ;
                }

                enum false {
                  value 0 ;
                }

              }

              default false ;
              ncd:revise-date 2018-08-16 ;
            }

            leaf source-if {
              type ncd:ifname ;

              description 'The NTP source interface name.' ;
              ncd:revise-date 2024-09-26 ;
            }

          }

          ncd:revise-date 2018-02-02 ;
        }

      }

      container ntp-peer {
        description 'The node of NTP peer configuration.' ;
        container ntp-peer-ipv4 {
          description 'The NTP IPv4 peer configuration.' ;
          list ntp-ipv4-list {
            description 'The NTP IPv4 peer list.' ;
            key ip-address ;
            leaf ip-address {
              description 'The NTP peer IPv4 address.' ;
              type ncd:ipv4-address ;

            }

            leaf version {
              description 'The NTP version number, it can be in the range from 1 to 4. 
The default value is 3.' ;
              type uint8 {
                range 1..4 {
                  description 'The NTP version number.' ;
                }

              }

              default 3 ;
            }

            leaf priority {
              description 'The NTP peer priority,the lower value the higher priority.' ;
              type uint8 {
                range 1..6 {
                  description 'The NTP peer priority.' ;
                }

              }

              mandatory true ;
            }

            leaf key-id {
              description 'The NTP authentication key.' ;
              type uint32 {
                range 0..4294967295 {
                  description 'The NTP authentication key.' ;
                }

              }

              default 0 ;
            }

            leaf port {
              description 'NTP peer UDP port.' ;
              type uint16 {
                range "123 | 1025..65535" ;

              }

              default 123 ;
              ncd:revise-date 2018-08-16 ;
            }

            leaf minpoll {
              description 'Min poll,the range is 3 to 6.' ;
              type uint8 {
                range 3..6 ;

              }

              default 3 ;
              ncd:revise-date 2018-08-16 ;
            }

            leaf maxpoll {
              description 'Max poll,the range is 7 to 17.' ;
              type uint8 {
                range 7..17 ;

              }

              default 10 ;
              ncd:revise-date 2018-08-16 ;
            }

            leaf source-if {
              type ncd:ifname ;

              description 'The NTP source interface name.' ;
              ncd:revise-date 2024-09-26 ;
            }

          }

          list ntp-ipv4-mng-list {
            description 'The NTP IPv4 MNG peer list.' ;
            key ip-address ;
            leaf ip-address {
              description 'The NTP peer IPv4 address.' ;
              type ncd:ipv4-address ;

            }

            leaf version {
              description 'The NTP version number, it can be in the range from 1 to 4. 
The default value is 3.' ;
              type uint8 {
                range 1..4 {
                  description 'The NTP version number.' ;
                }

              }

              default 3 ;
            }

            leaf priority {
              description 'The NTP peer priority,the lower value the higher priority.' ;
              type uint8 {
                range 1..6 {
                  description 'The NTP peer priority.' ;
                }

              }

              mandatory true ;
            }

            leaf key-id {
              description 'The NTP authentication key.' ;
              type uint32 {
                range 0..4294967295 {
                  description 'The NTP authentication key.' ;
                }

              }

              default 0 ;
            }

            leaf port {
              description 'NTP peer UDP port.' ;
              type uint16 {
                range "123 | 1025..65535" ;

              }

              default 123 ;
              ncd:revise-date 2018-08-16 ;
            }

            leaf minpoll {
              description 'Min poll,the range is 3 to 6.' ;
              type uint8 {
                range 3..6 ;

              }

              default 3 ;
              ncd:revise-date 2018-08-16 ;
            }

            leaf maxpoll {
              description 'Max poll,the range is 7 to 17.' ;
              type uint8 {
                range 7..17 ;

              }

              default 10 ;
              ncd:revise-date 2018-08-16 ;
            }

            leaf source-if {
              type ncd:ifname ;

              description 'The NTP source interface name.' ;
              ncd:revise-date 2024-09-26 ;
            }

          }

          list ntp-ipv4-vrf-list {
            description 'The NTP IPv4 VRF peer list.' ;
            key 'vrf-name ip-address' ;
            leaf vrf-name {
              description 'VRF name.' ;
              type string {
                length 1..32 {
                  description 'VRF name.' ;
                }

              }

            }

            leaf ip-address {
              description 'The NTP peer IPv4 address.' ;
              type ncd:ipv4-address ;

            }

            leaf version {
              description 'The NTP version number, it can be in the range from 1 to 4. 
The default value is 3.' ;
              type uint8 {
                range 1..4 {
                  description 'The NTP version number.' ;
                }

              }

              default 3 ;
            }

            leaf priority {
              description 'The NTP peer priority,the lower value the higher priority.' ;
              type uint8 {
                range 1..6 {
                  description 'The NTP peer priority.' ;
                }

              }

              mandatory true ;
            }

            leaf key-id {
              description 'The NTP authentication key.' ;
              type uint32 {
                range 0..4294967295 {
                  description 'The NTP authentication key.' ;
                }

              }

              default 0 ;
            }

            leaf port {
              description 'NTP peer UDP port.' ;
              type uint16 {
                range "123 | 1025..65535" ;

              }

              default 123 ;
              ncd:revise-date 2018-08-16 ;
            }

            leaf minpoll {
              description 'Min poll,the range is 3 to 6.' ;
              type uint8 {
                range 3..6 ;

              }

              default 3 ;
              ncd:revise-date 2018-08-16 ;
            }

            leaf maxpoll {
              description 'Max poll,the range is 7 to 17.' ;
              type uint8 {
                range 7..17 ;

              }

              default 10 ;
              ncd:revise-date 2018-08-16 ;
            }

            leaf source-if {
              type ncd:ifname ;

              description 'The NTP source interface name.' ;
              ncd:revise-date 2024-09-26 ;
            }

          }

        }

        container ntp-peer-ipv6 {
          description 'The NTP IPv6 peer configuration.' ;
          list ntp-ipv6-list {
            description 'The NTP IPv6 peer list.' ;
            key ipv6-address ;
            leaf ipv6-address {
              description 'The NTP peer IPv6 address.' ;
              type ncd:ipv6-address ;

            }

            leaf version {
              description 'The NTP version number, it only can be 4.' ;
              type uint8 {
                range 1..4 {
                  description 'The NTP version number.' ;
                }

              }

              default 4 ;
            }

            leaf priority {
              description 'The NTP peer priority,the lower value the higher priority.' ;
              type uint8 {
                range 1..6 {
                  description 'The NTP peer priority.' ;
                }

              }

              mandatory true ;
            }

            leaf key-id {
              description 'The NTP authentication key.' ;
              type uint32 {
                range 0..4294967295 {
                  description 'The NTP authentication key.' ;
                }

              }

              default 0 ;
            }

            leaf port {
              description 'NTP peer UDP port.' ;
              type uint16 {
                range "123 | 1025..65535" ;

              }

              default 123 ;
              ncd:revise-date 2018-08-16 ;
            }

            leaf minpoll {
              description 'Min poll,the range is 3 to 6.' ;
              type uint8 {
                range 3..6 ;

              }

              default 3 ;
              ncd:revise-date 2018-08-16 ;
            }

            leaf maxpoll {
              description 'Max poll,the range is 7 to 17.' ;
              type uint8 {
                range 7..17 ;

              }

              default 10 ;
              ncd:revise-date 2018-08-16 ;
            }

            leaf source-if {
              type ncd:ifname ;

              description 'The NTP source interface name.' ;
              ncd:revise-date 2024-09-26 ;
            }

          }

          list ntp-ipv6-mng-list {
            description 'The NTP IPv6 MNG peer list.' ;
            key ipv6-address ;
            leaf ipv6-address {
              description 'The NTP peer IPv6 address.' ;
              type ncd:ipv6-address ;

            }

            leaf version {
              description 'The NTP version number, it only can be 4.' ;
              type uint8 {
                range 1..4 {
                  description 'The NTP version number.' ;
                }

              }

              default 4 ;
            }

            leaf priority {
              description 'The NTP peer priority,the lower value the higher priority.' ;
              type uint8 {
                range 1..6 {
                  description 'The NTP peer priority.' ;
                }

              }

              mandatory true ;
            }

            leaf key-id {
              description 'The NTP authentication key.' ;
              type uint32 {
                range 0..4294967295 {
                  description 'The NTP authentication key.' ;
                }

              }

              default 0 ;
            }

            leaf port {
              description 'NTP peer UDP port.' ;
              type uint16 {
                range "123 | 1025..65535" ;

              }

              default 123 ;
              ncd:revise-date 2018-08-16 ;
            }

            leaf minpoll {
              description 'Min poll,the range is 3 to 6.' ;
              type uint8 {
                range 3..6 ;

              }

              default 3 ;
              ncd:revise-date 2018-08-16 ;
            }

            leaf maxpoll {
              description 'Max poll,the range is 7 to 17.' ;
              type uint8 {
                range 7..17 ;

              }

              default 10 ;
              ncd:revise-date 2018-08-16 ;
            }

            leaf source-if {
              type ncd:ifname ;

              description 'The NTP source interface name.' ;
              ncd:revise-date 2024-09-26 ;
            }

          }

          list ntp-ipv6-vrf-list {
            description 'The NTP IPv6 VRF peer list.' ;
            key 'vrf-name ipv6-address' ;
            leaf vrf-name {
              description 'VRF name.' ;
              type string {
                length 1..32 {
                  description 'VRF name.' ;
                }

              }

            }

            leaf ipv6-address {
              description 'The NTP peer IPv6 address.' ;
              type ncd:ipv6-address ;

            }

            leaf version {
              description 'The NTP version number, it only can be 4.' ;
              type uint8 {
                range 1..4 {
                  description 'The NTP version number.' ;
                }

              }

              default 4 ;
            }

            leaf priority {
              description 'The NTP peer priority,the lower value the higher priority.' ;
              type uint8 {
                range 1..6 {
                  description 'The NTP peer priority.' ;
                }

              }

              mandatory true ;
            }

            leaf key-id {
              description 'The NTP authentication key.' ;
              type uint32 {
                range 0..4294967295 {
                  description 'The NTP authentication key.' ;
                }

              }

              default 0 ;
            }

            leaf port {
              description 'NTP peer UDP port.' ;
              type uint16 {
                range "123 | 1025..65535" ;

              }

              default 123 ;
              ncd:revise-date 2018-08-16 ;
            }

            leaf minpoll {
              description 'Min poll,the range is 3 to 6.' ;
              type uint8 {
                range 3..6 ;

              }

              default 3 ;
              ncd:revise-date 2018-08-16 ;
            }

            leaf maxpoll {
              description 'Max poll,the range is 7 to 17.' ;
              type uint8 {
                range 7..17 ;

              }

              default 10 ;
              ncd:revise-date 2018-08-16 ;
            }

            leaf source-if {
              type ncd:ifname ;

              description 'The NTP source interface name.' ;
              ncd:revise-date 2024-09-26 ;
            }

          }

        }

        container ntp-dns-peer {
          description 'The NTP DNS peer configuration.' ;
          list ntp-dns-list {
            description 'The NTP DNS server list.' ;
            key host-name ;
            leaf host-name {
              description 'The NTP peer Host Name.' ;
              type string {
                length 1..128 ;

              }

            }

            leaf version {
              description 'The NTP version number, it can be in the range from 1 to 4. 
The default value is 3.' ;
              type uint8 {
                range 1..4 {
                  description 'The NTP version number.' ;
                }

              }

              default 3 ;
            }

            leaf priority {
              description 'The NTP peer priority,the lower value the higher priority.' ;
              type uint8 {
                range 1..6 {
                  description 'The NTP server priority.' ;
                }

              }

              mandatory true ;
            }

            leaf key-id {
              description 'The NTP authentication key.' ;
              type uint32 {
                range 0..4294967295 {
                  description 'The NTP authentication key id.' ;
                }

              }

              default 0 ;
            }

            leaf port {
              description 'NTP peer UDP port.' ;
              type uint16 {
                range "123 | 1025..65535" ;

              }

              default 123 ;
              ncd:revise-date 2018-08-16 ;
            }

            leaf minpoll {
              description 'Min poll,the range is 3 to 6.' ;
              type uint8 {
                range 3..6 ;

              }

              default 3 ;
              ncd:revise-date 2018-08-16 ;
            }

            leaf maxpoll {
              description 'Max poll,the range is 7 to 17.' ;
              type uint8 {
                range 7..17 ;

              }

              default 10 ;
              ncd:revise-date 2018-08-16 ;
            }

            leaf source-if {
              type ncd:ifname ;

              description 'The NTP source interface name.' ;
              ncd:revise-date 2024-09-26 ;
            }

          }

          list ntp-dns-mng-list {
            description 'The NTP DNS MNG peer list.' ;
            key host-name ;
            leaf host-name {
              description 'The NTP server Host Name.' ;
              type string {
                length 1..128 ;

              }

            }

            leaf version {
              description 'The NTP version number, it can be in the range from 1 to 4. 
The default value is 3.' ;
              type uint8 {
                range 1..4 {
                  description 'The NTP version number.' ;
                }

              }

              default 3 ;
            }

            leaf priority {
              description 'The NTP server priority,the lower value the higher priority.' ;
              type uint8 {
                range 1..6 {
                  description 'The NTP server priority.' ;
                }

              }

              mandatory true ;
            }

            leaf key-id {
              description 'The NTP authentication key.' ;
              type uint32 {
                range 0..4294967295 {
                  description 'The NTP authentication key id.' ;
                }

              }

              default 0 ;
            }

            leaf port {
              description 'NTP peer UDP port.' ;
              type uint16 {
                range "123 | 1025..65535" ;

              }

              default 123 ;
              ncd:revise-date 2018-08-16 ;
            }

            leaf minpoll {
              description 'Min poll,the range is 3 to 6.' ;
              type uint8 {
                range 3..6 ;

              }

              default 3 ;
              ncd:revise-date 2018-08-16 ;
            }

            leaf maxpoll {
              description 'Max poll,the range is 7 to 17.' ;
              type uint8 {
                range 7..17 ;

              }

              default 10 ;
              ncd:revise-date 2018-08-16 ;
            }

            leaf source-if {
              type ncd:ifname ;

              description 'The NTP source interface name.' ;
              ncd:revise-date 2024-09-26 ;
            }

          }

          list ntp-dns-vrf-list {
            description 'The NTP DNS VRF server list.' ;
            key 'vrf-name host-name' ;
            leaf vrf-name {
              description 'VRF name.' ;
              type string {
                length 1..32 {
                  description 'VRF name.' ;
                }

              }

            }

            leaf host-name {
              description 'The NTP server Host Name.' ;
              type string {
                length 1..128 ;

              }

            }

            leaf version {
              description 'The NTP version number, it can be in the range from 1 to 4. 
The default value is 3.' ;
              type uint8 {
                range 1..4 {
                  description 'The NTP version number.' ;
                }

              }

              default 3 ;
            }

            leaf priority {
              description 'The NTP peer priority,the lower value the higher priority.' ;
              type uint8 {
                range 1..6 {
                  description 'The NTP server priority.' ;
                }

              }

              mandatory true ;
            }

            leaf key-id {
              description 'The NTP authentication key.' ;
              type uint32 {
                range 0..4294967295 {
                  description 'The NTP authentication key id.' ;
                }

              }

              default 0 ;
            }

            leaf port {
              description 'NTP peer UDP port.' ;
              type uint16 {
                range "123 | 1025..65535" ;

              }

              default 123 ;
              ncd:revise-date 2018-08-16 ;
            }

            leaf minpoll {
              description 'Min poll,the range is 3 to 6.' ;
              type uint8 {
                range 3..6 ;

              }

              default 3 ;
              ncd:revise-date 2018-08-16 ;
            }

            leaf maxpoll {
              description 'Max poll,the range is 7 to 17.' ;
              type uint8 {
                range 7..17 ;

              }

              default 10 ;
              ncd:revise-date 2018-08-16 ;
            }

            leaf source-if {
              type ncd:ifname ;

              description 'The NTP source interface name.' ;
              ncd:revise-date 2024-09-26 ;
            }

          }

          ncd:revise-date 2018-02-02 ;
        }

      }

      container ntp-multi-broad {
        description 'The NTP multicast and broadcast configuration.' ;
        leaf broadcast-delay {
          description 'The NTP estimated round-trip delay in microseconds.' ;
          type uint32 {
            range 0..999999 {
              description 'The NTP estimated round-trip delay in microseconds.' ;
            }

          }

          units microsecond ;
          default 0 ;
        }

        container ntp-multicast {
          description 'The node of NTP multicast configuration.' ;
          container ntp-sever {
            description 'The NTP Multicast server configuration.' ;
            list ntp-ipv4-server-list {
              description 'The NTP multicast IPv4 server list.' ;
              key 'ifname ip-address' ;
              leaf ifname {
                description 'The source interface binded by NTP multicast server.' ;
                type ncd:ifname {
                  length 1..31 ;

                }

              }

              leaf ip-address {
                description 'The NTP multicast server IPv4 address.' ;
                type ncd:ipv4-address ;

              }

              leaf version {
                description 'The NTP version number, it can be in the range from 1 to 4. 
The default value is 3.' ;
                type uint8 {
                  range 1..4 {
                    description 'The NTP version number.' ;
                  }

                }

                default 3 ;
              }

              leaf key-id {
                description 'The NTP authentication key.' ;
                type uint32 {
                  range 0..4294967295 {
                    description 'The NTP authentication key.' ;
                  }

                }

                default 0 ;
              }

              leaf ttl {
                description 'TTL of the multicast packet.' ;
                type uint8 {
                  range 1..255 {
                    description 'TTL of the multicast packet.' ;
                  }

                }

                default 255 ;
              }

              leaf port {
                description 'NTP multicast UDP port.' ;
                type uint16 {
                  range "123 | 1025..65535" ;

                }

                default 123 ;
                ncd:revise-date 2018-08-16 ;
              }

            }

            list ntp-ipv6-server-list {
              description 'The NTP multicast IPv6 server list.' ;
              key 'ifname ipv6-address' ;
              leaf ifname {
                description 'The source interface binded by NTP multicast server.' ;
                type ncd:ifname {
                  length 1..31 ;

                }

              }

              leaf ipv6-address {
                description 'The NTP multicast server IPv6 address.' ;
                type ncd:ipv6-address ;

              }

              leaf version {
                description 'The NTP version number, it only can be 4.' ;
                type uint8 {
                  range 4 {
                    description 'The NTP version number.' ;
                  }

                }

                default 4 ;
              }

              leaf key-id {
                description 'The NTP authentication key.' ;
                type uint32 {
                  range 0..4294967295 {
                    description 'The NTP authentication key.' ;
                  }

                }

                default 0 ;
              }

              leaf ttl {
                description 'TTL of the multicast packet.' ;
                type uint8 {
                  range 1..255 {
                    description 'TTL of the multicast packet.' ;
                  }

                }

                default 255 ;
              }

              leaf port {
                description 'NTP multicast UDP port.' ;
                type uint16 {
                  range "123 | 1025..65535" ;

                }

                default 123 ;
                ncd:revise-date 2018-08-16 ;
              }

            }

          }

          container ntp-client {
            description 'The NTP Multicast client configuration.' ;
            list ntp-ipv4-client-list {
              description 'The NTP multicast IPv4 client list.' ;
              key 'ifname ip-address' ;
              leaf ifname {
                description 'The source interface binded by NTP multicast client.' ;
                type ncd:ifname {
                  length 1..31 ;

                }

              }

              leaf ip-address {
                description 'The NTP multicast client IPv4 address.' ;
                type ncd:ipv4-address ;

              }

            }

            list ntp-ipv6-client-list {
              description 'The NTP multicast IPv6 client list.' ;
              key 'ifname ipv6-address' ;
              leaf ifname {
                description 'The source interface binded by NTP multicast client.' ;
                type ncd:ifname {
                  length 1..31 ;

                }

              }

              leaf ipv6-address {
                description 'The NTP multicast client IPv6 address.' ;
                type ncd:ipv6-address ;

              }

            }

          }

        }

        container ntp-broadcast {
          description 'The node of NTP broadcast configuration.' ;
          list ntp-server-list {
            description 'The NTP broadcast server list.' ;
            key ifname ;
            leaf ifname {
              description 'The source interface binded by NTP broadcast server.' ;
              type ncd:ifname {
                length 1..31 ;

              }

            }

            leaf version {
              description 'The NTP version number, it can be in the range from 1 to 4. 
The default value is 3.' ;
              type uint8 {
                range 1..4 {
                  description 'The NTP version number.' ;
                }

              }

              default 3 ;
            }

            leaf key-id {
              description 'The NTP authentication key.' ;
              type uint32 {
                range 0..4294967295 {
                  description 'The NTP authentication key.' ;
                }

              }

              default 0 ;
            }

            leaf port {
              description 'NTP broadcast UDP port.' ;
              type uint16 {
                range "123 | 1025..65535" ;

              }

              default 123 ;
              ncd:revise-date 2018-08-16 ;
            }

          }

          list ntp-client-list {
            description 'The NTP broadcast client list.' ;
            key ifname ;
            leaf ifname {
              description 'The source interface binded by NTP broadcast client.' ;
              type ncd:ifname {
                length 1..31 ;

              }

            }

          }

        }

      }

      container ntp-authentication {
        description 'The node of NTP authentication configuration.' ;
        leaf authenticate {
          description 'The NTP authentication switch,0 means off,1 means on.' ;
          type enumeration {
            enum disable {
              value 0 ;
              description 'The authentication is disabled.' ;
            }

            enum enable {
              value 1 ;
              description 'The authentication is enabled.' ;
            }

          }

          default disable ;
        }

        list ntp-trusted-key {
          description 'The NTP trusted-key list.' ;
          key key-id ;
          leaf key-id {
            description 'The NTP authentication key.' ;
            type uint32 {
              range 1..4294967295 {
                description 'The NTP authentication key.' ;
              }

            }

          }

        }

        container ntp-authentication-key {
          description 'The node of NTP authentication key configuration.' ;
          presence ture ;
          list ntp-authentication-key {
            description 'The NTP authentication-key list.' ;
            key key-id ;
            leaf key-id {
              description 'The NTP authentication key.' ;
              type uint32 {
                range 1..4294967295 {
                  description 'The NTP authentication key.' ;
                }

              }

            }

            choice encryption-mode {
              description 'The NTP encryption mode.' ;
              mandatory true ;
              case md5-clear-key {
                description 'MD5 clear key.' ;
                leaf clear-key {
                  description 'Clear key,the length is 1-16 characters.' ;
                  type string ;

                }

              }

              case md5-encrypted-key {
                description 'MD5 encrypted key.' ;
                leaf encrypted-key {
                  description 'Encrypted key.' ;
                  type string {
                    length 24..84 ;

                  }

                }

              }

              case keychain {
                description 'Refer to the keychain model.' ;
                leaf keychain-name {
                  description 'Keychain name,the length is 1-16 characters.' ;
                  type string ;

                }

              }

            }

          }

          ncd:revise-date 2017-07-03 ;
        }

      }

      container ntp-server-with-name {
        description 'The node of NTP server with name configuration.' ;
        list server {
          description 'The server list.' ;
          key name ;
          leaf name {
            description 'The NTP server Name.' ;
            type string {
              length 1..128 ;

            }

          }

          leaf vrf-name {
            description 'VRF name.' ;
            type string {
              length 1..32 {
                description 'VRF name.' ;
              }

            }

          }

          leaf address {
            description 'The NTP server address(IP address or DNS domain name).' ;
            type string {
              length 1..128 ;

            }

            mandatory true ;
          }

          leaf association-type {
            description 'The association type for this NTP server.Default:SERVER.' ;
            type enumeration {
              enum SERVER {
                value 0 ;
                description 'Client association mode.' ;
              }

              enum PEER {
                value 1 ;
                description 'Symmetric active association mode.' ;
              }

            }

            default SERVER ;
          }

          leaf version {
            description 'The NTP version number, it can be in the range from 1 to 4. 
The default value is 4.' ;
            type uint8 {
              range 1..4 {
                description 'The NTP version number.' ;
              }

            }

            default 4 ;
          }

          leaf prefer {
            description 'The NTP server prefer flag.' ;
            type enumeration {
              enum false {
                value 0 ;
                description 'The server is unlocked.' ;
              }

              enum true {
                value 1 ;
                description 'The server is locked.' ;
              }

            }

            default false ;
          }

          leaf priority {
            description 'The NTP server priority,the lower value the higher priority.' ;
            type uint8 {
              range 1..10 {
                description 'The NTP server priority.' ;
              }

            }

            default 10 ;
          }

          leaf key-id {
            description 'The NTP authentication key.' ;
            type uint32 {
              range 0..4294967295 {
                description 'The NTP authentication key id.' ;
              }

            }

            default 0 ;
          }

          leaf port {
            description 'NTP server UDP port.' ;
            type uint16 {
              range "123 | 1025..65535" ;

            }

            default 123 ;
          }

          leaf minpoll {
            description 'Min poll,the range is 3 to 6.' ;
            type uint8 {
              range 3..6 ;

            }

            default 3 ;
          }

          leaf maxpoll {
            description 'Max poll,the range is 7 to 17.' ;
            type uint8 {
              range 7..17 ;

            }

            default 10 ;
          }

          leaf iburst {
            description 'NTP burst packet flag.' ;
            type enumeration {
              enum true {
                value 1 ;
              }

              enum false {
                value 0 ;
              }

            }

            default false ;
          }

          leaf source-if {
            type ncd:ifname ;

            description 'The NTP source interface name.' ;
            ncd:revise-date 2024-09-26 ;
          }

        }

        ncd:revise-date 2019-07-19 ;
      }

      container ntp-monitor-clients {
        if-feature monitor-clients ;

        description 'The node of monitor clients configured by NTP server.' ;
        container ipv4-clients {
          description 'The NTP IPv4 monitor clients configuration.' ;
          list ipv4-client {
            description 'The NTP IPv4 monitor client.' ;
            key ip-address ;
            leaf ip-address {
              description 'The NTP monitor client IPv4 address.' ;
              type ncd:ipv4-address ;

            }

            leaf offset-threshold {
              description 'The threshold of offset between client and server,the range is 1 to 4294967295 milliseconds.' ;
              type uint32 {
                range 1..4294967295 ;

              }

              default 500 ;
            }

            leaf timeout {
              description 'Timeout interval of monitor client,the range is 1 to 48 hours.' ;
              type uint8 {
                range 1..48 {
                  description 'Timeout interval of monitor client,the range is 1 to 48 hours.' ;
                }

              }

              default 24 ;
            }

          }

        }

        container ipv6-clients {
          description 'The NTP IPv6 monitor clients configuration.' ;
          list ipv6-client {
            description 'The NTP IPv6 monitor client.' ;
            key ipv6-address ;
            leaf ipv6-address {
              description 'The NTP monitor client IPv6 address.' ;
              type ncd:ipv6-address ;

            }

            leaf offset-threshold {
              description 'The threshold of offset between client and server,the range is 1 to 4294967295 milliseconds.' ;
              type uint32 {
                range 1..4294967295 ;

              }

              default 500 ;
            }

            leaf timeout {
              description 'Timeout interval of monitor client,the range is 1 to 48 hours.' ;
              type uint8 {
                range 1..48 {
                  description 'Timeout interval of monitor client,the range is 1 to 48 hours.' ;
                }

              }

              default 24 ;
            }

          }

        }

        container ipv4-vrf-clients {
          description 'The NTP IPv4 VRF monitor clients configuration.' ;
          list ipv4-vrf-client {
            description 'The NTP IPv4 VRF monitor client.' ;
            key 'ip-address vrf-name' ;
            leaf ip-address {
              description 'The NTP monitor client IPv4 address.' ;
              type ncd:ipv4-address ;

            }

            leaf vrf-name {
              description 'VRF name.' ;
              type string {
                length 1..35 ;

              }

            }

            leaf offset-threshold {
              description 'The threshold of offset between client and server,the range is 1 to 4294967295 milliseconds.' ;
              type uint32 {
                range 1..4294967295 ;

              }

              default 500 ;
            }

            leaf timeout {
              description 'Timeout interval of monitor client,the range is 1 to 48 hours.' ;
              type uint8 {
                range 1..48 {
                  description 'Timeout interval of monitor client,the range is 1 to 48 hours.' ;
                }

              }

              default 24 ;
            }

          }

        }

        container ipv6-vrf-clients {
          description 'The NTP IPv6 VRF monitor clients configuration.' ;
          list ipv6-vrf-client {
            description 'The NTP IPv6 VRF monitor client.' ;
            key 'ipv6-address vrf-name' ;
            leaf ipv6-address {
              description 'The NTP monitor client IPv6 address.' ;
              type ncd:ipv6-address ;

            }

            leaf vrf-name {
              description 'VRF name.' ;
              type string {
                length 1..35 ;

              }

            }

            leaf offset-threshold {
              description 'The threshold of offset between client and server,the range is 1 to 4294967295 milliseconds.' ;
              type uint32 {
                range 1..4294967295 ;

              }

              default 500 ;
            }

            leaf timeout {
              description 'Timeout interval of monitor client,the range is 1 to 48 hours.' ;
              type uint8 {
                range 1..48 {
                  description 'Timeout interval of monitor client,the range is 1 to 48 hours.' ;
                }

              }

              default 24 ;
            }

          }

        }

        ncd:revise-date 2020-04-16 ;
      }

      container ntp-service {
        description 'The node of NTP service switch configuration.' ;
        leaf ipv4-service {
          description 'NTP IPv4 service switch,0 means disable,1 means enable.' ;
          type enumeration {
            enum disable {
              value 0 ;
              description 'Disable NTP service.' ;
            }

            enum enable {
              value 1 ;
              description 'Enable NTP service.' ;
            }

          }

          default enable ;
        }

        leaf ipv6-service {
          description 'NTP IPv6 service switch,0 means disable,1 means enable.' ;
          type enumeration {
            enum disable {
              value 0 ;
              description 'Disable NTP service.' ;
            }

            enum enable {
              value 1 ;
              description 'Enable NTP service.' ;
            }

          }

          default enable ;
        }

        ncd:revise-date 2020-07-23 ;
      }

    }

  }

  container state {
    config false ;
    description 'The state of NTP.' ;
    container ntp {
      description 'The node of NTP.' ;
      container ntp-current-status {
        description 'The current status of NTP.' ;
        leaf current-time {
          description 'The current system time.' ;
          type string {
            length 0..31 ;

          }

          default '' ;
        }

        leaf ntp-type {
          description 'The NTP type of local.' ;
          type enumeration {
            enum not-running {
              value 1 ;
              description 'NTP is not running.' ;
            }

            enum not-synchronized {
              value 2 ;
              description 'NTP is not synchronized.' ;
            }

            enum none-configured {
              value 3 ;
              description 'NTP is not configured.' ;
            }

            enum synctolocal {
              value 4 ;
              description 'NTP is synchronized to local.' ;
            }

            enum synctoremoteserver {
              value 5 ;
              description 'NTP is synchronized to remote server.' ;
            }

          }

        }

        leaf sync-status {
          description 'The current synchronization status.' ;
          type enumeration {
            enum unsynchronization {
              value 0 ;
              description 'The NTP state is unsynchronization.' ;
            }

            enum synchronization {
              value 1 ;
              description 'The NTP state is synchronization.' ;
            }

          }

          default unsynchronization ;
        }

        leaf current-stratum {
          description 'The current local stratum.' ;
          type uint8 {
            range 0..16 {
              description 'The current local stratum.' ;
            }

          }

        }

        leaf current-server {
          description 'The current server IP and VRF name.' ;
          type ncd:string-with-blank {
            length 0..85 ;

          }

        }

        leaf current-server-name {
          description 'The current server name.' ;
          type string {
            length 0..128 ;

          }

          ncd:revise-date 2020-04-16 ;
        }

      }

      container ntp-association {
        description 'The NTP association information.' ;
        list ntp-association-list {
          description 'The NTP association list.' ;
          key id ;
          leaf id {
            description 'The NTP association index.' ;
            type uint8 {
              range 1..35 {
                description 'The NTP association index.' ;
              }

            }

          }

          leaf source-address {
            description 'The NTP association source IP address.' ;
            type string {
              length 0..51 {
                description 'The NTP association source IP address.' ;
              }

            }

            default '' ;
          }

          leaf dest-address {
            description 'The NTP association destination IP address.' ;
            type string {
              length 0..51 {
                description 'The NTP association destination IP address.' ;
              }

            }

            default '' ;
          }

          leaf if-name {
            description 'The source interface binded by NTP association.' ;
            type string {
              length 0..31 {
                description 'The source interface binded by NTP association.' ;
              }

            }

            default '' ;
          }

          leaf vrf-name {
            description 'The NTP association VRF name.' ;
            type string {
              length 0..35 {
                description 'The NTP association VRF name.' ;
              }

            }

            default '' ;
          }

          leaf mode {
            description 'The NTP association local mode.' ;
            type enumeration {
              enum undefined {
                value 0 ;
                description 'The NTP association local mode is undefined.' ;
              }

              enum active {
                value 1 ;
                description 'The NTP association local mode is active.' ;
              }

              enum passive {
                value 2 ;
                description 'The NTP association local mode is passive.' ;
              }

              enum client {
                value 3 ;
                description 'The NTP association local mode is client.' ;
              }

              enum server {
                value 4 ;
                description 'The NTP association local mode is server.' ;
              }

              enum broadcast {
                value 5 ;
                description 'The NTP association local mode is broadcast/multicast server.' ;
              }

              enum broadcast-client {
                value 6 ;
                description 'The NTP association local mode is broadcast/multicast client.' ;
              }

            }

          }

          leaf flag {
            description 'The NTP association type flag.' ;
            type enumeration {
              enum persistent {
                value 0 ;
                description 'The NTP association is persistent.' ;
              }

              enum ephemeral {
                value 1 ;
                description 'The NTP association is ephemeral.' ;
              }

            }

          }

          leaf key-id {
            description 'The NTP association authentication key.' ;
            type uint32 {
              range 0..4294967295 {
                description 'The NTP association authentication key id.' ;
              }

            }

          }

          leaf version {
            description 'The NTP version number.' ;
            type uint8 {
              range 1..4 {
                description 'The NTP version number.' ;
              }

            }

          }

          leaf lock {
            description 'The NTP association lock status(prefer flag).' ;
            type enumeration {
              enum unlock {
                value 0 ;
                description 'The association is unlocked.' ;
              }

              enum lock {
                value 1 ;
                description 'The association is locked(prefer).' ;
              }

            }

          }

          leaf poll {
            description 'The NTP poll interval.' ;
            type uint8 {
              range 4..17 {
                description 'The NTP poll interval.' ;
              }

            }

            units log2 ;
          }

          leaf stratum {
            description 'The NTP association stratum value.' ;
            type uint8 {
              range 0..16 {
                description 'The NTP association stratum value.' ;
              }

            }

          }

          leaf priority {
            description 'The NTP association priority.' ;
            type uint8 {
              range 0..10 {
                description 'The NTP association priority.' ;
              }

            }

          }

          leaf reach {
            description 'The NTP association reach flag,0 means unreach.' ;
            type uint8 ;

          }

          leaf delay {
            description 'The value of NTP association delay.' ;
            type string {
              length 0..15 ;

            }

            units second ;
          }

          leaf offset {
            description 'The value of NTP association offset.' ;
            type string {
              length 0..15 ;

            }

            units second ;
          }

          leaf inuse {
            description 'The NTP association use flag,1 means use,0 means unuse.' ;
            type enumeration {
              enum not-use {
                value 0 ;
                description 'The association is not in used.' ;
              }

              enum in-use {
                value 1 ;
                description 'The association is in used.' ;
              }

            }

          }

          leaf host-name {
            description 'The NTP association host name.' ;
            type string ;

            ncd:revise-date 2019-04-19 ;
          }

          leaf port {
            description 'The NTP association port.' ;
            type uint16 ;

            ncd:revise-date 2019-04-19 ;
          }

          leaf iburst {
            description 'The NTP association iburst.' ;
            type uint8 ;

            ncd:revise-date 2019-04-19 ;
          }

          leaf root-dispersion {
            description 'The NTP association root dispersion.' ;
            type uint64 ;

            ncd:revise-date 2019-04-19 ;
          }

          leaf name {
            description 'The NTP server name.' ;
            type string ;

            ncd:revise-date 2019-07-19 ;
          }

        }

      }

      container ntp-monitor-clients {
        if-feature monitor-clients ;

        description 'The Information of NTP monitor clients.' ;
        container clients {
          description 'The IPv4/v6 monitor clients.' ;
          list ipv4-client {
            description 'The NTP IPv4 monitor client.' ;
            key ip-address ;
            leaf ip-address {
              description 'The NTP monitor client IPv4 address.' ;
              type ncd:ipv4-address ;

            }

            leaf active {
              description 'Whether the monitor client  active,0 means inactive,1 means active.' ;
              type uint8 {
                range 0..1 ;

              }

            }

            leaf client-time {
              description 'The time of NTP monitor client.' ;
              type ncd:string-with-blank {
                length 0..50 {
                  description 'The time of NTP monitor client.' ;
                }

              }

            }

            leaf server-time {
              description 'The time of NTP Server.' ;
              type ncd:string-with-blank {
                length 0..50 {
                  description 'The time of NTP Server.' ;
                }

              }

            }

            leaf offset {
              description 'The offset between monitor client and server,the unit is seconds.' ;
              type decimal64 {
                fraction-digits 3 ;
              }

            }

          }

          list ipv6-client {
            description 'The NTP IPv6 monitor client.' ;
            key ipv6-address ;
            leaf ipv6-address {
              description 'The NTP monitor client IPv6 address.' ;
              type ncd:ipv6-address ;

            }

            leaf active {
              description 'Whether the monitor client  active,0 means inactive,1 means active.' ;
              type uint8 {
                range 0..1 ;

              }

            }

            leaf client-time {
              description 'The time of NTP monitor client.' ;
              type ncd:string-with-blank {
                length 0..50 ;

              }

            }

            leaf server-time {
              description 'The time of NTP Server.' ;
              type ncd:string-with-blank {
                length 0..50 ;

              }

            }

            leaf offset {
              description 'The offset between monitor client and server,the unit is seconds.' ;
              type decimal64 {
                fraction-digits 3 ;
              }

            }

          }

        }

        container vrf-clients {
          description 'The IPv4/v6 VRF monitor clients.' ;
          list ipv4-vrf-client {
            description 'The NTP IPv4 VRF monitor client.' ;
            key 'ip-address vrf-name' ;
            leaf ip-address {
              description 'The NTP monitor client IPv4 address.' ;
              type ncd:ipv4-address ;

            }

            leaf vrf-name {
              description 'VRF name.' ;
              type string {
                length 1..35 ;

              }

            }

            leaf active {
              description 'Whether the monitor client  active,0 means inactive,1 means active.' ;
              type uint8 {
                range 0..1 ;

              }

            }

            leaf client-time {
              description 'The time of NTP monitor client.' ;
              type ncd:string-with-blank {
                length 0..50 ;

              }

            }

            leaf server-time {
              description 'The time of NTP Server.' ;
              type ncd:string-with-blank {
                length 0..50 ;

              }

            }

            leaf offset {
              description 'The offset between monitor client and server,the unit is seconds.' ;
              type decimal64 {
                fraction-digits 3 ;
              }

            }

            ncd:select "ip-address vrf-name" ;
          }

          list ipv6-vrf-client {
            description 'The NTP IPv6 VRF monitor client.' ;
            key 'ipv6-address vrf-name' ;
            leaf ipv6-address {
              description 'The NTP monitor client IPv6 address.' ;
              type ncd:ipv6-address ;

            }

            leaf vrf-name {
              description 'VRF name.' ;
              type string {
                length 1..35 ;

              }

            }

            leaf active {
              description 'Whether the monitor client  active,0 means inactive,1 means active.' ;
              type uint8 {
                range 0..1 ;

              }

            }

            leaf client-time {
              description 'The time of NTP monitor client.' ;
              type ncd:string-with-blank {
                length 0..50 ;

              }

            }

            leaf server-time {
              description 'The time of NTP Server.' ;
              type ncd:string-with-blank {
                length 0..50 ;

              }

            }

            leaf offset {
              description 'The offset between monitor client and server,the unit is seconds.' ;
              type decimal64 {
                fraction-digits 3 ;
              }

            }

            ncd:select "ipv6-address vrf-name" ;
          }

        }

        ncd:revise-date 2020-04-16 ;
      }

    }

  }

}
