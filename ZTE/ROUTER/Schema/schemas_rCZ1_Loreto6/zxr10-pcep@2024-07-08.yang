module zxr10-pcep {
  namespace "http://www.zte.com.cn/zxr10/netconf/schema/rosng/pcep" ;
  prefix pcep ;
  yang-version 1 ;
  import zxr10-netconf-defs {
    prefix ncd ;
    revision-date 2013-11-22 ;
  }

  organization "ZTE Corporation" ;
  contact "ZTE Corporation
  Nanjing Institute of ZTE Corporation
  No.68 Zijinghua Rd. Yuhuatai District, Nanjing, China
  Tel: +86-25-52870000" ;
  revision 2024-07-08 {
    description 'Modify the description of some leaf or container.' ;
  }

  revision 2022-12-09 {
    description "Add one leaf node: 'configuration/pcep/pcc/peers/peer/bind-ssl-context'." ;
  }

  revision 2022-08-10 {
    description "Modidy one leaf node's desciption:
    '/configuration/pcep/pcc/pce-auto-initiate'." ;
  }

  revision 2021-07-12 {
    description "Modidy four leaf nodes' default:
    '/configuration/pcep/pcc/capacity/delta-sync',
    '/configuration/pcep/pcc/capacity/initial-sync'
    '/configuration/pcep/pcc/capacity/lsp-db-version',
    '/configuration/pcep/pcc/capacity/resync'." ;
  }

  revision 2021-06-03 {
    description "modify a leaf node: 'configuration/pcep/pcc/capacity/vendor-info'." ;
  }

  revision 2021-05-10 {
    description "Add one leaf node: 'configuration/pcep/pcc/enterprise-number'." ;
  }

  revision 2021-04-13 {
    description "Add one leaf node: 'configuration/pcep/pcc/report-local-association'" ;
  }

  revision 2021-03-16 {
    description "Add one leaf node: 'configuration/pcep/pcc/peers/peer/dscp'." ;
  }

  revision 2021-01-19 {
    description "Add one leaf node: 'configuration/pcep/pcc/capacity/srp'." ;
  }

  revision 2020-10-22 {
    description "Add one container node:
    '/configuration/pcep/pcc/slave-lsp-names'." ;
  }

  revision 2020-10-21 {
    description "Add one leaf node: 'configuration/pcep/pcc/capacity/vendor-info'." ;
  }

  revision 2020-07-03 {
    description "Add two case nodes:
    '/configuration/pcep/pcc/peers/peer/peer-router-id-type/peer-router-id-type-choice-clear',
    '/configuration/pcep/pcc/peers/peer/slave-peer-router-id-type/slave-peer-router-id-type-choice-clear'." ;
  }

  revision 2020-06-16 {
    description "Add one leaf node: 'configuration/pcep/pcc/capacity/srv6'." ;
  }

  revision 2020-06-09 {
    description "1.Add a container node: 'configuration/pcep/pcc/backoff'." ;
  }

  revision 2020-03-06 {
    description "Modify the leaf node's default: 'configuration/pcep/pcc/state-time-enable'." ;
  }

  revision 2020-02-25 {
    description "1.Add a container node: 'state/pcep/neighborV6-pce-info'.
    2.Modidy Obsolete state to current state of the leaf node: 'state/pcep/neighbor-pce-info/neighbor-pce-entry/slave-peer-v6'." ;
  }

  revision 2020-02-12 {
    description "Modify one node: 'configuration/pcep/pcc/report-pcc-create-lsp'." ;
  }

  revision 2019-11-13 {
    description "Obsolete some nodes:
    'configuration/pcep/pcc/graceful-restart',
    'configuration/pcep/pcc/graceful-restart/gr-enable',
    'configuration/pcep/pcc/graceful-restart/max-recovery'." ;
  }

  revision 2019-10-15 {
    description "Add container nodes 'configuration/pcep/pcc/graceful-restart', and Add some leafs 'configuration/pcep/pcc/graceful-restart/gr-enable',
    'configuration/pcep/pcc/graceful-restart/max-recovery'." ;
  }

  revision 2019-07-08 {
    description "Add one leaf node: 'configuration/pcep/pcc/capacity/path-segment'." ;
  }

  revision 2019-05-17 {
    description "Add one leaf node: 'configuration/pcep/pcc/peers/peer/description'." ;
  }

  revision 2019-04-26 {
    description "Obsolete some leaf nodes:
    'configuration/pcep/lsp-info/lsps/lsp-entry/lsp-insts/lsp-inst-entry/is-splice-tunnel',
    'configuration/pcep/lsp-info/lsps/lsp-entry/lsp-insts/lsp-inst-entry/splice-label'." ;
  }

  revision 2019-03-12 {
    description "1.Add some nodes:
    'state/pcep/neighbor-pce-info/neighbor-pce-entry/peer-router-id-v6',
    'state/pcep/neighbor-pce-info/neighbor-pce-entry/slave-peer-v6',
    'state/pcep/neighbor-pce-info/neighbor-pce-entry/received-unknown-msg-num',
    'state/pcep/lsp-info/general/selected-pce-v6',
    'state/pcep/lsp-info/general/selected-pce-slave-v6',
    'state/pcep/lsp-info/lsps/lsp-entry/destination-v6',
    'state/pcep/lsp-info/lsps/lsp-entry/ext-tunnel-id-v6',
    'state/pcep/lsp-info/lsps/lsp-entry/delegate-pce-v6',
    'state/pcep/lsp-info/lsps/lsp-entry/lsp-insts/lsp-inst-entry/source-addr-v6',
    'state/pcep/lsp-info/lsps/lsp-entry/lsp-insts/lsp-inst-entry/eros/ero-entry/ero-sr-node-ip-v6',
    'state/pcep/lsp-info/lsps/lsp-entry/lsp-insts/lsp-inst-entry/eros/ero-entry/ero-sr-v4-adj-local',
    'state/pcep/lsp-info/lsps/lsp-entry/lsp-insts/lsp-inst-entry/eros/ero-entry/ero-sr-v4-adj-remote',
    'state/pcep/lsp-info/lsps/lsp-entry/lsp-insts/lsp-inst-entry/eros/ero-entry/ero-sr-v6-adj-local',
    'state/pcep/lsp-info/lsps/lsp-entry/lsp-insts/lsp-inst-entry/eros/ero-entry/ero-sr-v6-adj-remote',
    'state/pcep/lsp-info/lsps/lsp-entry/lsp-insts/lsp-inst-entry/iros/iro-entry/iro-type'.

    2.Modify some nodes:
    'state/pcep/lsp-info/lsps/lsp-entry/tunnel-id',
    'state/pcep/lsp-info/lsps/lsp-entry/lsp-insts/lsp-inst-entry/eros/ero-entry/ero-sr-sid-type'." ;
  }

  revision 2019-03-07 {
    description "1.Add one node:'configuration/pcep/vrf-name'." ;
  }

  revision 2018-11-23 {
    description "1.Add some nodes:
    'configuration/pcep/router-id-v6',
    'configuration/pcep/pcc/peers/peer/peer-router-id-v6',
    'configuration/pcep/pcc/peers/peer/slave-peer-router-id-v6',
    'operation/pcep/redelegate-pce/type/peer-addr-v6'.
    2.Modify some nodes:
    'configuration/pcep/router-id',
    'configuration/pcep/pcc/peers/peer/peer-router-id',
    'configuration/pcep/pcc/peers/peer/slave-peer-router-id',
    'operation/pcep/redelegate-pce/type/peer-addr'." ;
  }

  revision 2018-10-08 {
    description "1.Modidy range of some leaf nodes: 'pcep/pcc/peers/peer/request-response-wait', 'pcep/pcc/message-rate-limit'.
    2.Add default value of some leaf nodes: 'pcep/pcc/peers/peer/request-response-wait', 'pcep/pcc/peers/peer/precedence', 'pcep/pcc/message-rate-limit'." ;
  }

  revision 2018-08-16 {
    description "Obsolete the enum item 'pce' in leaf node: 'configuration/pcep/role'." ;
  }

  revision 2018-07-30 {
    description "Add 1 leaf nodes: 'configuration/pcep/pcc/report-pcc-create-lsp'." ;
  }

  revision 2018-07-17 {
    description "Add a leaf node message-rate-limit'
    'configuration/pcep/pcc/message-rate-limit'," ;
  }

  revision 2018-04-10 {
    description "Add 8 leaf nodes:
    'configuration/pcep/pcc/capacity/delta-sync',
    'configuration/pcep/pcc/capacity/initial-sync',
    'configuration/pcep/pcc/capacity/lsp-db-version',
    'configuration/pcep/pcc/capacity/resync',
    'configuration/pcep/pcc/report-none-instance-lsp',
    'configuration/pcep/pcc/unknown-msg-rate-limit',
    'configuration/pcep/pcc/pce-auto-initiate',
    'configuration/pcep/pcc/peers/peer/keychain'." ;
  }

  revision 2017-07-13 {
    description "Add a container node: 'state'." ;
  }

  revision 2017-05-09 {
    description "Add a leaf node: 'pcep/pcc/load-balancing'." ;
  }

  revision 2016-07-19 {
    description "Add a leaf node: 'pcep/pcc/gmpls-enable'." ;
  }

  revision 2016-07-06 {
    description "Add one leaf node: 'pcep/pcc/sr-capability'." ;
  }

  revision 2016-04-26 {
    description "1.Add some leaf nodes: 'pcep/pcc/peers/peer/keepalive-min', 'pcep/pcc/peers/peer/precedence', 'pcep/pcc/redelegation-time', 'pcep/pcc/state-time', 'pcep/pcc/state-time-enable'.
    2.Add some container nodes 'configuration/pcep/pcc/capacity', 'operation', and some nodes under these container nodes.
    3.Modidy range of some leaf nodes: 'pcep/pcc/peers/peer/keepalive-time', 'pcep/pcc/peers/peer/dead-time'." ;
  }

  revision 2016-04-12 {
    description "Delete the 'both' value of enumeration for  '/configuration/pcep/role/'." ;
  }

  revision 2015-12-22 {
    description "Add pattern description of '/pcep/router-id' ,'/pcc/peers/peer/peer-router-id','/pcc/peers/peer/slave-peer-router-id' to filter the invalide address." ;
  }

  revision 2015-09-08 {
    description 'Initial version.' ;
  }

  container configuration {
    description 'The branch of configuration model.' ;
    container pcep {
      description 'The configuration of PCEP(Path Compute Element Protocol).' ;
      leaf pcep-enable {
        description 'Enable the PCEP.' ;
        type enumeration {
          enum enable {
            value 1 ;
            description 'The PCEP is enable.' ;
          }

          enum disable {
            value 0 ;
            description 'The PCEP is disable.' ;
          }

        }

        default disable ;
      }

      leaf router-id {
        description 'The PCEP IPv4 router ID configuration.' ;
        type ncd:ipv4-address {
          pattern "([1-9]|[1-9][0-9]|1[0-9][0-9]|2[0-4][0-9]|25[0-5])(.([0-9]|[1-9][0-9]|1[0-9][0-9]|2[0-4][0-9]|25[0-5])){3}" {
            description 'To filter the invalid address.' ;
          }

        }

      }

      leaf router-id-v6 {
        description 'The PCEP IPv6 route ID configuration.' ;
        type ncd:ipv6-address {
          pattern "([0-9a-fA-F]{1,4}:){7}([0-9a-fA-F]{0,4})$|^([0-9a-fA-F]{1,4}:){1,6}(:[0-9a-fA-F]{0,4}){1,6}$|^([:]{2})(([0-9a-fA-F]{1,4}:){0,6})([0-9a-fA-F]{1,4})$|^([0-9a-fA-F]{1,4}:){6}([0-9]{1,3}.){3}([0-9]{1,3})$|^([0-9a-fA-F]{1,4}:){1,5}(:[0-9a-fA-F]{0,4}){1,5}([0-9]{1,3}.){3}([0-9]{1,3})$|^([:]{2})(([0-9a-fA-F]{1,4}:){0,5})([0-9]{1,3}.){3}([0-9]{1,3})" ;

        }

        ncd:revise-date 2018-11-23 ;
      }

      leaf role {
        description 'Configure the role of PCEP.' ;
        type enumeration {
          enum pcc {
            value 1 ;
            description 'The role is PCC.' ;
          }

          enum pce {
            value 2 ;
            description 'The role is PCE.' ;
            status obsolete ;

          }

          enum invalid {
            value 4 ;
            description 'The role is invalid.' ;
          }

        }

        default invalid ;
      }

      leaf vrf-name {
        description 'Configure VRF name.' ;
        type string {
          length 1..32 ;

        }

        ncd:revise-date 2019-03-07 ;
      }

      container pcc {
        description 'The configuration of PCC(Path Computation Client).' ;
        leaf pcc-enable {
          description 'Enable the PCC.' ;
          type enumeration {
            enum disable {
              value 0 ;
              description 'The PCC is disable.' ;
            }

            enum enable {
              value 1 ;
              description 'The PCC is enable.' ;
            }

          }

          default disable ;
        }

        container peers {
          description 'PCC Peer Configuration.' ;
          list peer {
            description 'The peer configuration list of PCC.' ;
            max-elements 65535 ;
            key peer-id ;
            leaf peer-id {
              description 'The instance id of peer.' ;
              type uint16 {
                range 1..65535 ;

              }

            }

            choice peer-router-id-type {
              case ipv4 {
                description 'IPv4 type.' ;
                leaf peer-router-id {
                  description 'The IPv4 router id of peer.' ;
                  type ncd:ipv4-address {
                    pattern "([1-9]|[1-9][0-9]|1[0-9][0-9]|2[0-4][0-9]|25[0-5])(.([0-9]|[1-9][0-9]|1[0-9][0-9]|2[0-4][0-9]|25[0-5])){3}" {
                      description 'To filter the invalid address.' ;
                    }

                  }

                }

              }

              case ipv6 {
                description 'IPv6 type.' ;
                leaf peer-router-id-v6 {
                  description 'The IPv6 router id of peer.' ;
                  type ncd:ipv6-address {
                    pattern "([0-9a-fA-F]{1,4}:){7}([0-9a-fA-F]{0,4})$|^([0-9a-fA-F]{1,4}:){1,6}(:[0-9a-fA-F]{0,4}){1,6}$|^([:]{2})(([0-9a-fA-F]{1,4}:){0,6})([0-9a-fA-F]{1,4})$|^([0-9a-fA-F]{1,4}:){6}([0-9]{1,3}.){3}([0-9]{1,3})$|^([0-9a-fA-F]{1,4}:){1,5}(:[0-9a-fA-F]{0,4}){1,5}([0-9]{1,3}.){3}([0-9]{1,3})$|^([:]{2})(([0-9a-fA-F]{1,4}:){0,5})([0-9]{1,3}.){3}([0-9]{1,3})" ;

                  }

                }

                ncd:revise-date 2018-11-23 ;
              }

              case peer-router-id-type-choice-clear {
                description 'Remove value of any entities which belong to any case within this choice.' ;
                container peer-router-id-type-all-clear {
                  description 'Remove this entitiy means to remove value of any entities which belong to any case within this choice.' ;
                  presence peer-router-id-type-all-clear ;
                }

                ncd:revise-date 2020-07-03 ;
              }

            }

            leaf master-ship {
              description 'The master ship of peer.' ;
              type enumeration {
                enum master {
                  value 1 ;
                  description 'The peer is master.' ;
                }

                enum slave {
                  value 2 ;
                  description 'The peer is slave.' ;
                }

              }

              default master ;
            }

            choice slave-peer-router-id-type {
              case ipv4 {
                description 'IPv4 type.' ;
                leaf slave-peer-router-id {
                  description 'The IPv4 router id of slave peer.' ;
                  type ncd:ipv4-address {
                    pattern "([1-9]|[1-9][0-9]|1[0-9][0-9]|2[0-4][0-9]|25[0-5])(.([0-9]|[1-9][0-9]|1[0-9][0-9]|2[0-4][0-9]|25[0-5])){3}" {
                      description 'To filter the invalid address.' ;
                    }

                  }

                }

              }

              case ipv6 {
                description 'IPv6 type.' ;
                leaf slave-peer-router-id-v6 {
                  description 'The IPv6 router id of slave peer.' ;
                  type ncd:ipv6-address {
                    pattern "([0-9a-fA-F]{1,4}:){7}([0-9a-fA-F]{0,4})$|^([0-9a-fA-F]{1,4}:){1,6}(:[0-9a-fA-F]{0,4}){1,6}$|^([:]{2})(([0-9a-fA-F]{1,4}:){0,6})([0-9a-fA-F]{1,4})$|^([0-9a-fA-F]{1,4}:){6}([0-9]{1,3}.){3}([0-9]{1,3})$|^([0-9a-fA-F]{1,4}:){1,5}(:[0-9a-fA-F]{0,4}){1,5}([0-9]{1,3}.){3}([0-9]{1,3})$|^([:]{2})(([0-9a-fA-F]{1,4}:){0,5})([0-9]{1,3}.){3}([0-9]{1,3})" ;

                  }

                }

                ncd:revise-date 2018-11-23 ;
              }

              case slave-peer-router-id-type-choice-clear {
                description 'Remove value of any entities which belong to any case within this choice.' ;
                container slave-peer-router-id-type-all-clear {
                  description 'Remove this entitiy means to remove value of any entities which belong to any case within this choice.' ;
                  presence slave-peer-router-id-type-all-clear ;
                }

                ncd:revise-date 2020-07-03 ;
              }

            }

            leaf keepalive-time {
              description 'The interval of keepalive message.' ;
              type uint8 {
                range 0..255 ;

              }

              default 30 ;
            }

            leaf dead-time {
              description 'The timeout time for the peer.' ;
              type uint8 {
                range 0..255 ;

              }

              default 120 ;
            }

            leaf request-response-wait {
              description 'The time waiting for the response of request.' ;
              type uint32 {
                range 0..300 ;

              }

              default 0 ;
            }

            leaf keepalive-min {
              description 'The minimal interval of keepalive message whitch accepted from peer node.' ;
              type uint8 {
                range 0..255 ;

              }

              default 0 ;
              ncd:revise-date 2016-04-26 ;
            }

            leaf precedence {
              description 'The precedence of PCE.' ;
              type uint8 {
                range 0..63 ;

              }

              default 63 ;
              ncd:revise-date 2016-04-26 ;
            }

            leaf keychain {
              description 'Configure keychain name.' ;
              type string {
                length 1..31 ;

              }

              ncd:revise-date 2018-04-10 ;
            }

            leaf description {
              description 'Configure description.' ;
              type string {
                length 1..80 ;

              }

              ncd:revise-date 2019-05-17 ;
            }

            leaf dscp {
              description 'The priority of PCEP session messages sending.' ;
              type uint8 {
                range 0..63 ;

              }

              ncd:revise-date 2021-03-16 ;
            }

            leaf bind-ssl-context {
              description 'Configure SSL context name.' ;
              type string {
                length 1..31 ;

              }

              ncd:revise-date 2022-12-09 ;
            }

          }

        }

        container lsp-names {
          description 'Lsp name configuration for te tunnel.' ;
          list lsp-name {
            description 'The lsp-name configuration list.' ;
            max-elements 131070 ;
            key te-tunnel-interface ;
            leaf te-tunnel-interface {
              description 'The name of te tunnel interface.' ;
              type ncd:ifname ;

            }

            leaf te-lsp-name {
              description 'The redefined lsp name of tunnel.' ;
              type string {
                length 1..63 ;

              }

              mandatory true ;
            }

          }

        }

        leaf redelegation-time {
          description 'LSP redelegation timeout interval.' ;
          type uint16 {
            range 0..3600 ;

          }

          default 30 ;
          ncd:revise-date 2016-04-26 ;
        }

        leaf state-time {
          description 'LSP state timeout interval.' ;
          type uint16 {
            range 0..3600 ;

          }

          default 60 ;
          ncd:revise-date 2016-04-26 ;
        }

        leaf state-time-enable {
          description 'Enable LSP state timeout interval configuration.' ;
          type enumeration {
            enum disable {
              value 0 ;
              description 'LSP state timeout interval is infinite.' ;
            }

            enum enable {
              value 1 ;
              description 'LSP state timeout interval can be configured.' ;
            }

          }

          default disable ;
          ncd:revise-date 2016-04-26 ;
        }

        container capacity {
          description 'The configuration of PCC capacity.' ;
          leaf stateful {
            description 'The configuration of stateful capacity.' ;
            type enumeration {
              enum enable {
                value 1 ;
                description 'The stateful capacity is enabled.' ;
              }

              enum disable {
                value 0 ;
              }

            }

            default disable ;
          }

          leaf update {
            description 'The configuration of state update capacity.' ;
            type enumeration {
              enum enable {
                value 1 ;
                description 'The state update capacity is enabled.' ;
              }

              enum disable {
                value 0 ;
              }

            }

            default disable ;
          }

          leaf initiate {
            description 'The configuration of initiate capacity.' ;
            type enumeration {
              enum enable {
                value 1 ;
                description 'The initiate capacity is enabled.' ;
              }

              enum disable {
                value 0 ;
              }

            }

            default disable ;
          }

          leaf delta-sync {
            description 'Configure delta synchronization capability.' ;
            type enumeration {
              enum disable {
                value 0 ;
                description 'The capability is Disable.' ;
              }

              enum enable {
                value 1 ;
                description 'The capability is enable.' ;
              }

            }

            default disable ;
            ncd:revise-date 2018-04-10 ;
          }

          leaf initial-sync {
            description 'Configure PCE-Triggered initial synchronization capability.' ;
            type enumeration {
              enum disable {
                value 0 ;
                description 'The capability is Disable.' ;
              }

              enum enable {
                value 1 ;
                description 'The capability is enable.' ;
              }

            }

            default disable ;
            ncd:revise-date 2018-04-10 ;
          }

          leaf lsp-db-version {
            description 'Configure include LSP-DB version capability.' ;
            type enumeration {
              enum disable {
                value 0 ;
                description 'The capability is Disable.' ;
              }

              enum enable {
                value 1 ;
                description 'The capability is enable.' ;
              }

            }

            default disable ;
            ncd:revise-date 2018-04-10 ;
          }

          leaf resync {
            description 'Configure PCE-Triggered resynchronization capability.' ;
            type enumeration {
              enum disable {
                value 0 ;
                description 'The capability is Disable.' ;
              }

              enum enable {
                value 1 ;
                description 'The capability is enable.' ;
              }

            }

            default disable ;
            ncd:revise-date 2018-04-10 ;
          }

          leaf path-segment {
            description 'Configure path segment capability.' ;
            type enumeration {
              enum disable {
                value 0 ;
                description 'The capability is Disable.' ;
              }

              enum enable {
                value 1 ;
                description 'The capability is enable.' ;
              }

            }

            default disable ;
            ncd:revise-date 2019-07-08 ;
          }

          leaf srv6 {
            description 'Enable the SRv6 capability.' ;
            type enumeration {
              enum disable {
                value 0 ;
                description 'The capability is Disable.' ;
              }

              enum enable {
                value 1 ;
                description 'The capability is enable.' ;
              }

            }

            default disable ;
            ncd:revise-date 2020-06-16 ;
          }

          leaf vendor-info {
            description 'Configure include vendor information capability.' ;
            type enumeration {
              enum disable {
                value 0 ;
                description 'The capability is Disable.' ;
              }

              enum enable {
                value 1 ;
                description 'The capability is enable.' ;
              }

            }

            default enable ;
            ncd:revise-date 2020-10-21 ;
          }

          leaf srp {
            description 'Enable the segment routing policy capability.' ;
            type enumeration {
              enum disable {
                value 0 ;
                description 'The capability is Disable.' ;
              }

              enum enable {
                value 1 ;
                description 'The capability is enable.' ;
              }

            }

            default disable ;
            ncd:revise-date 2021-01-19 ;
          }

          ncd:revise-date 2016-04-26 ;
        }

        leaf gmpls-enable {
          description 'Enable the GMPLS capability.' ;
          type enumeration {
            enum disable {
              value 0 ;
              description 'The GMPLS capability is disable.' ;
            }

            enum enable {
              value 1 ;
              description 'The GMPLS capability is enable.' ;
            }

          }

          default disable ;
          ncd:revise-date 2016-07-19 ;
        }

        leaf sr-capability {
          description 'Enable the SR capability.' ;
          type enumeration {
            enum disable {
              value 0 ;
              description 'SR capability is Disable.' ;
            }

            enum enable {
              value 1 ;
              description 'SR capability is enable.' ;
            }

          }

          default disable ;
          ncd:revise-date 2016-07-06 ;
        }

        leaf load-balancing {
          description 'Enable load-balancing.' ;
          type enumeration {
            enum disable {
              value 0 ;
              description 'The load-balancing is disable.' ;
            }

            enum enable {
              value 1 ;
              description 'The load-balancing is enable.' ;
            }

          }

          default disable ;
          ncd:revise-date 2017-05-09 ;
        }

        leaf report-local-association {
          description 'Configure local association report capability.' ;
          type enumeration {
            enum enable {
              value 1 ;
              description 'The capability is enable.' ;
            }

            enum disable {
              value 0 ;
              description 'The capability is disable.' ;
            }

          }

          default enable ;
          ncd:revise-date 2021-04-13 ;
        }

        leaf report-pcc-create-lsp {
          description 'Configure LSP created by PCC report capability.' ;
          type enumeration {
            enum disable {
              value 0 ;
              description 'The capability is Disable.' ;
            }

            enum enable {
              value 1 ;
              description 'The capability is enable.' ;
            }

          }

          default disable ;
          ncd:revise-date 2018-07-30 ;
        }

        leaf report-none-instance-lsp {
          description 'Configure LSP with none instance report capability.' ;
          type enumeration {
            enum disable {
              value 0 ;
              description 'The capability is Disable.' ;
            }

            enum enable {
              value 1 ;
              description 'The capability is enable.' ;
            }

          }

          default disable ;
          ncd:revise-date 2018-04-10 ;
        }

        leaf unknown-msg-rate-limit {
          description 'Configure the max unknown messages per minute.' ;
          type uint8 {
            range 1..255 ;

          }

          default 5 ;
          ncd:revise-date 2018-04-10 ;
        }

        leaf pce-auto-initiate {
          description 'Configure PCE automatically trigger LSP instantiation.' ;
          type enumeration {
            enum disable {
              value 0 ;
              description 'The capability is Disable.' ;
            }

            enum enable {
              value 1 ;
              description 'The capability is enable.' ;
            }

          }

          default disable ;
          ncd:revise-date 2018-04-10 ;
        }

        leaf message-rate-limit {
          description 'Configure max pcinit and pcupd message pcc can process per minute.' ;
          type uint16 {
            range 0..15000 ;

          }

          default 0 ;
          ncd:revise-date 2018-07-17 ;
        }

        container graceful-restart {
          status obsolete {
            ncd:revise-date 2019-11-13 ;
          }

          description 'PCEP GR config' ;
          leaf gr-enable {
            status obsolete {
              ncd:revise-date 2019-11-13 ;
            }

            description 'Enable GR' ;
            type enumeration {
              enum disable {
                value 0 ;
                description 'GR is disable' ;
              }

              enum enable {
                value 1 ;
                description 'GR is enable' ;
              }

            }

            default disable ;
          }

          leaf max-recovery {
            status obsolete {
              ncd:revise-date 2019-11-13 ;
            }

            description 'PCEP graceful restart Max-Recovery time' ;
            type int16 {
              range 15..3600 ;

            }

            default 120 ;
          }

          ncd:revise-date 2019-10-15 ;
        }

        container backoff {
          description 'backoff time of PCEP Session.' ;
          leaf initial-time {
            description 'Initial backoff time of PCEP Session.' ;
            type uint16 {
              range 1..65535 ;

            }

          }

          leaf max-time {
            description 'Maximum backoff time of PCEP Session.' ;
            type uint16 {
              range 1..65535 ;

            }

          }

          ncd:revise-date 2020-06-09 ;
        }

        container slave-lsp-names {
          description 'Slave LSP name configuration for TE tunnel.' ;
          list slave-lsp-name {
            description 'The slave LSP-name configuration list.' ;
            max-elements 131070 ;
            key te-tunnel-interface ;
            leaf te-tunnel-interface {
              description 'The name of te tunnel interface.' ;
              type ncd:ifname ;

            }

            leaf te-lsp-name {
              description 'The redefined slave lsp name of tunnel.' ;
              type string {
                length 1..63 ;

              }

              mandatory true ;
            }

          }

          ncd:revise-date 2020-10-22 ;
        }

        leaf enterprise-number {
          description 'The enterprise identified by the number.' ;
          type uint32 {
            range 0..4294967295 ;

          }

          default 2012 ;
          ncd:revise-date 2021-05-10 ;
        }

      }

    }

  }

  container operation {
    config false ;
    description 'The branch of operation model.' ;
    container pcep {
      description 'The operation of PCEP(Path Compute Element Protocol).' ;
      container redelegate-pce {
        description 'PCE Redelegation.' ;
        choice type {
          case peer-addr {
            description 'PCC select PCE to redelegate by IPv4 router id of peer.' ;
            leaf peer-addr {
              description 'The IPv4 router id of redelegated peer.' ;
              type ncd:ipv4-address ;

            }

          }

          case no-peer {
            description 'PCC select PCE to redelegate by precedence.' ;
            leaf no-peer {
              description 'PCE redelegation without peer.' ;
              type enumeration {
                enum NO-PEER {
                  value 0 ;
                  description 'PCE redelegation without peer.' ;
                }

              }

            }

          }

          case peer-addr-v6 {
            description 'PCC select PCE to redelegate by IPv6 router id of peer.' ;
            leaf peer-addr-v6 {
              description 'The IPv6 router id of redelegated peer.' ;
              type ncd:ipv6-address {
                pattern "([0-9a-fA-F]{1,4}:){7}([0-9a-fA-F]{0,4})$|^([0-9a-fA-F]{1,4}:){1,6}(:[0-9a-fA-F]{0,4}){1,6}$|^([:]{2})(([0-9a-fA-F]{1,4}:){0,6})([0-9a-fA-F]{1,4})$|^([0-9a-fA-F]{1,4}:){6}([0-9]{1,3}.){3}([0-9]{1,3})$|^([0-9a-fA-F]{1,4}:){1,5}(:[0-9a-fA-F]{0,4}){1,5}([0-9]{1,3}.){3}([0-9]{1,3})$|^([:]{2})(([0-9a-fA-F]{1,4}:){0,5})([0-9]{1,3}.){3}([0-9]{1,3})" ;

              }

            }

            ncd:revise-date 2018-11-23 ;
          }

        }

      }

    }

    ncd:revise-date 2016-04-26 ;
  }

  container state {
    config false ;
    description 'State information.' ;
    container pcep {
      description 'The state information of PCEP.' ;
      container neighbor-pce-info {
        description 'The state infomation of PCE neighbors.' ;
        list neighbor-pce-entry {
          description 'The PCE neighbor list.' ;
          key peer-router-id ;
          leaf peer-id {
            description 'The instance ID of peer.' ;
            type uint16 {
              range 1..65535 ;

            }

          }

          leaf peer-router-id {
            description 'The IPv4 router ID of peer.' ;
            type ncd:ipv4-address ;

          }

          leaf peer-router-id-v6 {
            status obsolete {
              ncd:revise-date 2019-07-08 ;
            }

            description 'The IPv6 router ID of peer.' ;
            type ncd:ipv6-address ;

            ncd:revise-date 2019-03-12 ;
          }

          leaf priority {
            description 'The precedence of PCE.' ;
            type uint8 {
              range 0..63 ;

            }

          }

          leaf status {
            description 'The status of session.' ;
            type enumeration {
              enum IDLE {
                value 0 ;
                description 'TCP session have been disconnected.' ;
              }

              enum TCP-PENDING {
                value 1 ;
                description 'Waiting for TCP building connection.' ;
              }

              enum OPEN-WAIT {
                value 2 ;
                description 'Waiting for open message.' ;
              }

              enum KEEP-WAIT {
                value 3 ;
                description 'Waiting for keepalive message.' ;
              }

              enum SESSION-UP {
                value 4 ;
                description 'PCEP established successfully.' ;
              }

              enum ABNORMAL {
                value 5 ;
                description 'Abnormal status.' ;
              }

            }

          }

          leaf status-time {
            description 'The time of UP or Down status.' ;
            type string ;

          }

          leaf stateful-type {
            description 'The stateful type of session.' ;
            type enumeration {
              enum STATELESS {
                value 0 ;
                description 'Stateless type.' ;
              }

              enum PASSIVE {
                value 1 ;
                description 'Passive state type.' ;
              }

              enum ACTIVE {
                value 2 ;
                description 'Active state type.' ;
              }

              enum INVALID {
                value 3 ;
                description 'Invalid state type.' ;
              }

            }

          }

          leaf master-ship {
            description 'The master ship of peer.' ;
            type enumeration {
              enum master {
                value 1 ;
                description 'The peer is master.' ;
              }

              enum slave {
                value 2 ;
                description 'The peer is slave.' ;
              }

            }

          }

          leaf slave-peer {
            description 'The IPv4 router id of slave peer.' ;
            type ncd:ipv4-address ;

          }

          leaf slave-peer-v6 {
            description 'The IPv6 router id of slave peer.' ;
            type ncd:ipv6-address ;

            ncd:revise-date 2020-02-25 ;
          }

          leaf sent-cap-stateful {
            description 'It describes whether PCC have sent stateful capability or not.' ;
            type enumeration {
              enum not-sent {
                value 0 ;
                description "PCC haven't sent the capability." ;
              }

              enum sent {
                value 1 ;
                description 'PCC have sent the capability.' ;
              }

            }

          }

          leaf sent-cap-update {
            description 'It describes whether PCC have sent update capability or not.' ;
            type enumeration {
              enum not-sent {
                value 0 ;
                description "PCC haven't sent the capability." ;
              }

              enum sent {
                value 1 ;
                description 'PCC have sent the capability.' ;
              }

            }

          }

          leaf sent-cap-initiate {
            description 'It describes whether PCC have sent initiate capability or not.' ;
            type enumeration {
              enum not-sent {
                value 0 ;
                description "PCC haven't sent the capability." ;
              }

              enum sent {
                value 1 ;
                description 'PCC have sent the capability.' ;
              }

            }

          }

          leaf sent-cap-sr {
            description 'It describes whether PCC have sent SR capability or not.' ;
            type enumeration {
              enum not-sent {
                value 0 ;
                description "PCC haven't sent the capability." ;
              }

              enum sent {
                value 1 ;
                description 'PCC have sent the capability.' ;
              }

            }

          }

          leaf sent-cap-gmpls {
            description 'It describes whether PCC have sent GMPLS capability or not.' ;
            type enumeration {
              enum not-sent {
                value 0 ;
                description "PCC haven't sent the capability." ;
              }

              enum sent {
                value 1 ;
                description 'PCC have sent the capability.' ;
              }

            }

          }

          leaf negotiated-cap-stateful {
            description 'The negotiation result of stateful capability.' ;
            type enumeration {
              enum no-received {
                value 0 ;
                description "PCC haven't received the capability." ;
              }

              enum failed {
                value 1 ;
                description 'PCC have received the capability, but have not sent.' ;
              }

              enum success {
                value 2 ;
                description 'The capability negotiation has been successful.' ;
              }

            }

          }

          leaf negotiated-cap-update {
            description 'The negotiation result of update capability.' ;
            type enumeration {
              enum no-received {
                value 0 ;
                description "PCC haven't received the capability." ;
              }

              enum failed {
                value 1 ;
                description 'PCC have received the capability, but have not sent.' ;
              }

              enum success {
                value 2 ;
                description 'The capability negotiation has been successful.' ;
              }

            }

          }

          leaf negotiated-cap-initiate {
            description 'The negotiation result of initiate capability.' ;
            type enumeration {
              enum no-received {
                value 0 ;
                description "PCC haven't received the capability." ;
              }

              enum failed {
                value 1 ;
                description 'PCC have received the capability, but have not sent.' ;
              }

              enum success {
                value 2 ;
                description 'The capability negotiation has been successful.' ;
              }

            }

          }

          leaf negotiated-cap-sr {
            description 'The negotiation result of SR capability.' ;
            type enumeration {
              enum no-received {
                value 0 ;
                description "PCC haven't received the capability." ;
              }

              enum failed {
                value 1 ;
                description 'PCC have received the capability, but have not sent.' ;
              }

              enum success {
                value 2 ;
                description 'The capability negotiation has been successful.' ;
              }

            }

          }

          leaf negotiated-cap-gmpls {
            description 'The negotiation result of GMPLS capability.' ;
            type enumeration {
              enum no-received {
                value 0 ;
                description "PCC haven't received the capability." ;
              }

              enum failed {
                value 1 ;
                description 'PCC have received the capability, but have not sent.' ;
              }

              enum success {
                value 2 ;
                description 'The capability negotiation has been successful.' ;
              }

            }

          }

          leaf peer-keepalive-min {
            description 'The minimal interval of keepalive message which accepted from peer node.' ;
            type uint8 {
              range 0..255 ;

            }

          }

          leaf local-keepalive-time {
            description 'Local interval of keepalive message.' ;
            type uint8 {
              range 0..255 ;

            }

            units seconds ;
          }

          leaf local-dead-time {
            description 'Local timeout time for the peer.' ;
            type uint8 {
              range 0..255 ;

            }

            units seconds ;
          }

          leaf peer-keepalive-time {
            description 'Peer interval of keepalive message.' ;
            type uint8 {
              range 0..255 ;

            }

            units seconds ;
          }

          leaf peer-dead-time {
            description 'Peer timeout time for the peer.' ;
            type uint8 {
              range 0..255 ;

            }

            units seconds ;
          }

          leaf unknown-msg-max-num {
            description 'The maximum tolerable number of unknown messages per minute.' ;
            type uint8 {
              range 0..255 ;

            }

          }

          leaf unknown-msg-rate {
            description 'The number of unknown messages per minute.' ;
            type uint8 {
              range 0..255 ;

            }

          }

          leaf reply-wait-time {
            description 'The time waiting for the reply of request.' ;
            type uint32 ;

            units seconds ;
          }

          leaf delegated-lsp-num {
            description 'Delegated LSP number.' ;
            type uint32 {
              range 0..4294967295 ;

            }

          }

          leaf sent-keepalive-msg-num {
            description 'The number of keepalive messages sent.' ;
            type uint32 {
              range 0..4294967295 ;

            }

          }

          leaf received-keepalive-msg-num {
            description 'The number of keepalive messages received.' ;
            type uint32 {
              range 0..4294967295 ;

            }

          }

          leaf sent-request-msg-num {
            description 'The number of request messages sent by.' ;
            type uint32 {
              range 0..4294967295 ;

            }

          }

          leaf received-request-msg-num {
            description 'The number of request messages received.' ;
            type uint32 {
              range 0..4294967295 ;

            }

          }

          leaf sent-reply-msg-num {
            description 'The number of reply messages sent.' ;
            type uint32 {
              range 0..4294967295 ;

            }

          }

          leaf received-reply-msg-num {
            description 'The number of reply messages received.' ;
            type uint32 {
              range 0..4294967295 ;

            }

          }

          leaf sent-report-msg-num {
            description 'The number of report messages sent.' ;
            type uint32 {
              range 0..4294967295 ;

            }

          }

          leaf received-report-msg-num {
            description 'The number of report messages received.' ;
            type uint32 {
              range 0..4294967295 ;

            }

          }

          leaf sent-update-msg-num {
            description 'The number of update messages sent.' ;
            type uint32 {
              range 0..4294967295 ;

            }

          }

          leaf received-update-msg-num {
            description 'The number of update messages received.' ;
            type uint32 {
              range 0..4294967295 ;

            }

          }

          leaf sent-init-msg-num {
            description 'The number of initiate messages sent.' ;
            type uint32 {
              range 0..4294967295 ;

            }

          }

          leaf received-init-msg-num {
            description 'The number of initiate messages received.' ;
            type uint32 {
              range 0..4294967295 ;

            }

          }

          leaf sent-error-msg-num {
            description 'The number of error messages sent.' ;
            type uint32 {
              range 0..4294967295 ;

            }

          }

          leaf received-error-msg-num {
            description 'The number of error messages received.' ;
            type uint32 {
              range 0..4294967295 ;

            }

          }

          leaf sent-notify-msg-num {
            description 'The number of notify messages sent.' ;
            type uint32 {
              range 0..4294967295 ;

            }

          }

          leaf received-notify-msg-num {
            description 'The number of notify messages received.' ;
            type uint32 {
              range 0..4294967295 ;

            }

          }

          leaf received-unknown-msg-num {
            description 'The number of unknown messages received.' ;
            type uint32 {
              range 0..4294967295 ;

            }

            ncd:revise-date 2019-03-12 ;
          }

          ncd:select peer-router-id ;
          ncd:select peer-router-id-v6 ;
        }

      }

      container lsp-info {
        description 'The state infomation of LSPs.' ;
        container general {
          description 'The general infomation of LSPs.' ;
          leaf lspdb-version-high {
            description 'The high 32 bits of LSP DB version.' ;
            type uint32 {
              range 0..4294967295 ;

            }

          }

          leaf lspdb-version-low {
            description 'The low 32 bits of LSP DB version.' ;
            type uint32 {
              range 0..4294967295 ;

            }

            default 0 ;
          }

          leaf redelegation-timeout {
            description 'LSP redelegation timeout interval.' ;
            type uint16 {
              range 0..3600 ;

            }

            units seconds ;
            default 0 ;
          }

          leaf state-timeout {
            description 'LSP state timeout interval.' ;
            type uint16 {
              range 0..3600 ;

            }

            units seconds ;
            default 0 ;
          }

          leaf selected-pce {
            description 'The IPv4 router ID of currently selected default delegation PCE.' ;
            type ncd:ipv4-address ;

          }

          leaf selected-pce-v6 {
            description 'The IPv6 router ID of currently selected default delegation PCE.' ;
            type ncd:ipv6-address ;

            ncd:revise-date 2019-03-12 ;
          }

          leaf selected-pce-slave {
            description 'The IPv4 router ID of currently selected default delegation slave PCE.' ;
            type ncd:ipv4-address ;

          }

          leaf selected-pce-slave-v6 {
            description 'The IPv6 router ID of currently selected default delegation slave PCE.' ;
            type ncd:ipv6-address ;

            ncd:revise-date 2019-03-12 ;
          }

        }

        container lsps {
          description 'The specific infomation of LSPs.' ;
          list lsp-entry {
            description 'The LSPs list.' ;
            key tunnel-id ;
            leaf plsp-id {
              description 'A PCEP-specific identifier for the LSP.  A PCC creates a unique PLSP-ID for each LSP that is constant for the lifetime of a PCEP session.' ;
              type uint32 {
                range 1..4294967295 ;

              }

            }

            leaf name {
              description 'The name of LSP.' ;
              type string {
                length 1..63 ;

              }

            }

            leaf tunnel-id {
              description 'Tunnel ID.' ;
              type uint32 {
                range 1..1048575 ;

              }

            }

            leaf destination {
              description 'The destination IPv4 address.' ;
              type ncd:ipv4-address ;

            }

            leaf destination-v6 {
              description 'The destination IPv6 address.' ;
              type ncd:ipv6-address ;

              ncd:revise-date 2019-03-12 ;
            }

            leaf ext-tunnel-id {
              description 'IPv4 extended tunnel ID.' ;
              type ncd:ipv4-address ;

            }

            leaf ext-tunnel-id-v6 {
              description 'IPv6 extended tunnel ID.' ;
              type ncd:ipv6-address ;

              ncd:revise-date 2019-03-12 ;
            }

            leaf delegate-cap {
              description 'The LSP can be delegated or not.' ;
              type enumeration {
                enum can-not-delegate {
                  value 0 ;
                  description 'The LSP can not be delegated.' ;
                }

                enum can-delegate {
                  value 1 ;
                  description 'The LSP can be delegated.' ;
                }

              }

            }

            leaf delegate-pce {
              description 'The IPv4 router ID of delegated PCE.' ;
              type ncd:ipv4-address ;

            }

            leaf delegate-pce-v6 {
              description 'The IPv6 router ID of delegated PCE.' ;
              type ncd:ipv6-address ;

              ncd:revise-date 2019-03-12 ;
            }

            leaf tunnel-type {
              description 'Tunnel type.' ;
              type enumeration {
                enum RSVP {
                  value 0 ;
                  description 'RSVP tunnel.' ;
                }

                enum SR {
                  value 1 ;
                  description 'SR tunnel.' ;
                }

                enum GMPLS {
                  value 2 ;
                  description 'GMPLS tunnel.' ;
                }

              }

            }

            container lsp-insts {
              description 'The specific information of LSP instances.' ;
              list lsp-inst-entry {
                description 'The LSP instances list.' ;
                key lsp-id ;
                leaf lsp-id {
                  description 'Local ID of LSP instance.' ;
                  type uint16 {
                    range 1..65535 ;

                  }

                }

                leaf source-addr {
                  description 'The IPv4 source address of LSP instance.' ;
                  type ncd:ipv4-address ;

                }

                leaf source-addr-v6 {
                  description 'The IPv6 source address of LSP instance.' ;
                  type ncd:ipv6-address ;

                  ncd:revise-date 2019-03-12 ;
                }

                leaf status {
                  description 'The status of LSP instance.' ;
                  type enumeration {
                    enum INVALID {
                      value 0 ;
                      description 'The invalid status.' ;
                    }

                    enum DOWN {
                      value 1 ;
                      description 'The down status.' ;
                    }

                    enum GOING-DOWN {
                      value 2 ;
                      description 'The going down status.' ;
                    }

                    enum GOING-UP {
                      value 3 ;
                      description 'The going up status.' ;
                    }

                    enum UP {
                      value 4 ;
                      description 'The up status.' ;
                    }

                    enum ACTIVE {
                      value 5 ;
                      description 'The active status.' ;
                    }

                  }

                }

                leaf role {
                  description 'The master ship of LSP instance.' ;
                  type enumeration {
                    enum primary {
                      value 1 ;
                      description 'The instance is primary.' ;
                    }

                    enum secondary {
                      value 2 ;
                      description 'The instance is secondary.' ;
                    }

                  }

                }

                leaf priority-setup {
                  description 'The priority of setup.' ;
                  type uint8 {
                    range 0..255 ;

                  }

                }

                leaf priority-hold {
                  description 'The priority of hold.' ;
                  type uint8 {
                    range 0..255 ;

                  }

                }

                leaf affinity-exclude-any {
                  description 'The affinity property of excluding anyone, and it have 32 bits.' ;
                  type ncd:hex ;

                }

                leaf affinity-include-any {
                  description 'The affinity property of including anyone, and it have 32 bits.' ;
                  type ncd:hex ;

                }

                leaf affinity-include-all {
                  description 'The affinity property of including all, and it have 32 bits.' ;
                  type ncd:hex ;

                }

                leaf is-splice-tunnel {
                  status obsolete {
                    ncd:revise-date 2019-04-26 ;
                  }

                  description 'It describes whether the instance is a splice tunnel or not.' ;
                  type enumeration {
                    enum not-splice-tunnel {
                      value 0 ;
                      description "It isn't splice tunnel." ;
                    }

                    enum splice-tunnel {
                      value 1 ;
                      description 'It is splice tunnel.' ;
                    }

                  }

                }

                leaf splice-label {
                  status obsolete {
                    ncd:revise-date 2019-04-26 ;
                  }

                  description 'Splice label.' ;
                  type uint32 {
                    range "0 | 16..1048575" ;

                  }

                }

                leaf tspec-type {
                  description 'TSpec type.' ;
                  type enumeration {
                    enum int {
                      value 2 ;
                      description 'TSpec type is 2.' ;
                    }

                    enum eth {
                      value 6 ;
                      description 'TSpec type is 6.' ;
                    }

                  }

                }

                leaf tspec-int-bw {
                  description 'bandwidth.' ;
                  type string ;

                  units Bps ;
                }

                leaf tspec-eth-cir {
                  description 'Committed information rate.' ;
                  type string ;

                  units Bps ;
                }

                leaf tspec-eth-cbs {
                  description 'Committed Burst Size.' ;
                  type string ;

                  units Bytes ;
                }

                leaf tspec-eth-eir {
                  description 'Excess Information Rate.' ;
                  type string ;

                  units Bps ;
                }

                leaf tspec-eth-ebs {
                  description 'Excess Burst Size.' ;
                  type string ;

                  units Bytes ;
                }

                container eros {
                  description 'The specific information of ERO.' ;
                  list ero-entry {
                    description 'The ERO list.' ;
                    key ero-id ;
                    leaf ero-id {
                      description 'ERO ID.' ;
                      type uint16 {
                        range 0..65535 ;

                      }

                    }

                    leaf ero-type {
                      description 'ERO type.' ;
                      type enumeration {
                        enum ipv4 {
                          value 1 ;
                          description 'IPv4 type.' ;
                        }

                        enum unif {
                          value 4 ;
                          description 'Unnumbered interface Type.' ;
                        }

                        enum pathkey-32bit-pceid {
                          value 64 ;
                          description 'PathKey 32bit PCE-ID type.' ;
                        }

                        enum sr {
                          value 36 ;
                          description 'SR type.' ;
                        }

                      }

                    }

                    leaf ero-ipv4-addr {
                      description 'ERO of IPv4 type: IPv4 address.' ;
                      type ncd:ipv4-address ;

                    }

                    leaf ero-unif-routerid {
                      description 'ERO of unnumbered interface type: the router ID of unnumbered interface.' ;
                      type ncd:ipv4-address ;

                    }

                    leaf ero-unif-id {
                      description 'ERO of unnumbered interface type: the unnumbered interface ID.' ;
                      type uint32 {
                        range 0..4294967295 ;

                      }

                    }

                    leaf ero-pk-pathkey {
                      description 'ERO of Path-Key type: the Path-Key is an identifier to represent the confidential path segment within the context of the PCE identified by the PCE-ID.' ;
                      type uint16 {
                        range 0..65535 ;

                      }

                    }

                    leaf ero-pk-pceid {
                      description 'ERO of Path-Key type: The PCE-ID has to be mapped to a reachable IPv4 or IPv6 address of the PCE by the first node of the confidential path segment.' ;
                      type ncd:ipv4-address ;

                    }

                    leaf ero-sr-sid-type {
                      description 'ERO of SR type: SID type.' ;
                      type enumeration {
                        enum DEFAULT {
                          value 0 ;
                          description 'Default type.' ;
                        }

                        enum NODEID_V4 {
                          value 1 ;
                          description 'The IPv4 address of node ID.' ;
                        }

                        enum NODEID_V6 {
                          value 2 ;
                          description 'The IPv6 address of node ID.' ;
                        }

                        enum ADJID_V4 {
                          value 3 ;
                          description 'The IPv4 address of adjacent link ID.' ;
                        }

                        enum ADJID_V6 {
                          value 4 ;
                          description 'The IPv6 address of adjacent link ID.' ;
                        }

                        enum UNNUMB_ADJID_V4 {
                          value 5 ;
                          description 'The IPv4 address of unnumbered adjacent link ID.' ;
                        }

                        enum SPLICE {
                          value 15 ;
                          description 'Splice type.' ;
                        }

                      }

                    }

                    leaf ero-sr-sid-contain {
                      description 'ERO of SR type: contained information type.' ;
                      type enumeration {
                        enum NULL {
                          value 0 ;
                          description 'Contain null.' ;
                        }

                        enum SID_ONLY {
                          value 1 ;
                          description 'Only contain SID.' ;
                        }

                        enum NAI_ONLY {
                          value 2 ;
                          description 'Only contain NAI.' ;
                        }

                        enum SID_NAI {
                          value 3 ;
                          description 'Contain NAI and SID.' ;
                        }

                      }

                    }

                    leaf ero-sr-sid-value {
                      description 'ERO of SR type: SID value.' ;
                      type uint32 {
                        range 0..4294967295 ;

                      }

                    }

                    leaf ero-sr-node-ip {
                      description 'ERO of SR type: The IPv4 address of node.' ;
                      type ncd:ipv4-address ;

                    }

                    leaf ero-sr-node-ip-v6 {
                      description 'ERO of SR type: The IPv6 address of node.' ;
                      type ncd:ipv6-address ;

                      ncd:revise-date 2019-03-12 ;
                    }

                    leaf ero-sr-adj-local-rid {
                      description 'ERO of SR type: the local router IP address of unnumbered adjacent link.' ;
                      type ncd:ipv4-address ;

                    }

                    leaf ero-sr-adj-local-ip {
                      description 'ERO of SR type: the local interface IP address of unnumbered adjacent link.' ;
                      type ncd:ipv4-address ;

                    }

                    leaf ero-sr-adj-peer-rid {
                      description 'ERO of SR type: the peer router IP address of unnumbered adjacent link.' ;
                      type ncd:ipv4-address ;

                    }

                    leaf ero-sr-adj-peer-ip {
                      description 'ERO of SR type: the peer interface IP address of unnumbered adjacent link.' ;
                      type ncd:ipv4-address ;

                    }

                    leaf ero-sr-v4-adj-local {
                      description 'ERO of SR type: the local IPv4 address of adjacent link.' ;
                      type ncd:ipv4-address ;

                      ncd:revise-date 2019-03-12 ;
                    }

                    leaf ero-sr-v4-adj-remote {
                      description 'ERO of SR type: the remote IPv4 address of adjacent link.' ;
                      type ncd:ipv4-address ;

                      ncd:revise-date 2019-03-12 ;
                    }

                    leaf ero-sr-v6-adj-local {
                      description 'ERO of SR type: the local IPv6 address of adjacent link.' ;
                      type ncd:ipv6-address ;

                      ncd:revise-date 2019-03-12 ;
                    }

                    leaf ero-sr-v6-adj-remote {
                      description 'ERO of SR type: the remote IPv6 address of adjacent link.' ;
                      type ncd:ipv6-address ;

                      ncd:revise-date 2019-03-12 ;
                    }

                  }

                }

                container iros {
                  description 'The specific information of IRO.' ;
                  list iro-entry {
                    description 'The IRO list.' ;
                    key iro-id ;
                    leaf iro-id {
                      description 'IRO ID.' ;
                      type uint16 {
                        range 0..65535 ;

                      }

                    }

                    leaf iro-type {
                      description 'IRO type.' ;
                      type enumeration {
                        enum ipv4 {
                          value 1 ;
                          description 'IPv4 type.' ;
                        }

                      }

                      ncd:revise-date 2019-03-12 ;
                    }

                    leaf iro-ipv4-addr {
                      description 'IRO of IPv4 type: IPv4 address.' ;
                      type ncd:ipv4-address ;

                    }

                  }

                }

                container rros {
                  description 'The specific information of RRO.' ;
                  list rro-entry {
                    description 'The RRO list.' ;
                    key rro-id ;
                    leaf rro-id {
                      description 'RRO ID.' ;
                      type uint16 {
                        range 0..65535 ;

                      }

                    }

                    leaf rro-type {
                      description 'RRO type.' ;
                      type enumeration {
                        enum ipv4 {
                          value 1 ;
                          description 'IPv4 type.' ;
                        }

                        enum label {
                          value 3 ;
                          description 'Label type.' ;
                        }

                        enum unif {
                          value 4 ;
                          description 'Unnumbered interface Type.' ;
                        }

                      }

                    }

                    leaf rro-ipv4-addr {
                      description 'RRO of IPv4 type: IPv4 address.' ;
                      type ncd:ipv4-address ;

                    }

                    leaf rro-label-value {
                      description 'RRO of label type: label value.' ;
                      type uint32 {
                        range 0..1048575 ;

                      }

                    }

                    leaf rro-unif-router-id {
                      description 'IRO of unnumbered interface type: router id.' ;
                      type ncd:ipv4-address ;

                    }

                    leaf rro-unif-id {
                      description 'RRO of unnumbered interface type: unnumbered interface ID.' ;
                      type uint32 ;

                    }

                  }

                }

                container metrics {
                  description 'The specific information of metric.' ;
                  list metric-entry {
                    description 'It contains the metric list.' ;
                    key metric-id ;
                    leaf metric-id {
                      description 'Metric ID.' ;
                      type uint16 {
                        range 0..65535 ;

                      }

                    }

                    leaf metric-type {
                      description 'Metric type.' ;
                      type enumeration {
                        enum NULL {
                          value 0 ;
                          description 'No metric type.' ;
                        }

                        enum IGP {
                          value 1 ;
                          description 'IGP.' ;
                        }

                        enum TE {
                          value 2 ;
                          description 'TE.' ;
                        }

                        enum HOP-CNT {
                          value 3 ;
                          description 'HOP-CNT.' ;
                        }

                        enum SR-MSD {
                          value 11 ;
                          description 'SR-MSD.' ;
                        }

                      }

                    }

                    leaf metric-value {
                      description 'Metric value.' ;
                      type string ;

                    }

                  }

                }

              }

            }

          }

        }

      }

      container neighborV6-pce-info {
        description 'The state information of IPV6 PCE neighbors.' ;
        list neighborV6-pce-entry {
          description 'The IPV6 PCE neighbor list.' ;
          key peer-router-id-v6 ;
          leaf peer-id {
            description 'The instance ID of peer.' ;
            type uint16 {
              range 1..65535 ;

            }

          }

          leaf peer-router-id-v6 {
            description 'The IPv6 router ID of peer.' ;
            type ncd:ipv6-address ;

          }

          leaf priority {
            description 'The precedence of PCE.' ;
            type uint8 {
              range 0..63 ;

            }

          }

          leaf status {
            description 'The status of session.' ;
            type enumeration {
              enum IDLE {
                value 0 ;
                description 'TCP session have been disconnected.' ;
              }

              enum TCP-PENDING {
                value 1 ;
                description 'Waiting for TCP building connection.' ;
              }

              enum OPEN-WAIT {
                value 2 ;
                description 'Waiting for open message.' ;
              }

              enum KEEP-WAIT {
                value 3 ;
                description 'Waiting for keepalive message.' ;
              }

              enum SESSION-UP {
                value 4 ;
                description 'PCEP established successfully.' ;
              }

              enum ABNORMAL {
                value 5 ;
                description 'Abnormal status.' ;
              }

            }

          }

          leaf status-time {
            description 'The time of UP or Down status.' ;
            type string ;

          }

          leaf stateful-type {
            description 'The stateful type of session.' ;
            type enumeration {
              enum STATELESS {
                value 0 ;
                description 'Stateless type.' ;
              }

              enum PASSIVE {
                value 1 ;
                description 'Passive state type.' ;
              }

              enum ACTIVE {
                value 2 ;
                description 'Active state type.' ;
              }

              enum INVALID {
                value 3 ;
                description 'Invalid state type.' ;
              }

            }

          }

          leaf master-ship {
            description 'The master ship of peer.' ;
            type enumeration {
              enum master {
                value 1 ;
                description 'The peer is master.' ;
              }

              enum slave {
                value 2 ;
                description 'The peer is slave.' ;
              }

            }

          }

          leaf slave-peer {
            description 'The IPv4 router id of slave peer.' ;
            type ncd:ipv4-address ;

          }

          leaf slave-peer-v6 {
            description 'The IPv6 router id of slave peer.' ;
            type ncd:ipv6-address ;

          }

          leaf sent-cap-stateful {
            description 'It describes whether PCC have sent stateful capability or not.' ;
            type enumeration {
              enum not-sent {
                value 0 ;
                description "PCC haven't sent the capability." ;
              }

              enum sent {
                value 1 ;
                description 'PCC have sent the capability.' ;
              }

            }

          }

          leaf sent-cap-update {
            description 'It describes whether PCC have sent update capability or not.' ;
            type enumeration {
              enum not-sent {
                value 0 ;
                description "PCC haven't sent the capability." ;
              }

              enum sent {
                value 1 ;
                description 'PCC have sent the capability.' ;
              }

            }

          }

          leaf sent-cap-initiate {
            description 'It describes whether PCC have sent initiate capability or not.' ;
            type enumeration {
              enum not-sent {
                value 0 ;
                description "PCC haven't sent the capability." ;
              }

              enum sent {
                value 1 ;
                description 'PCC have sent the capability.' ;
              }

            }

          }

          leaf sent-cap-sr {
            description 'It describes whether PCC have sent SR capability or not.' ;
            type enumeration {
              enum not-sent {
                value 0 ;
                description "PCC haven't sent the capability." ;
              }

              enum sent {
                value 1 ;
                description 'PCC have sent the capability.' ;
              }

            }

          }

          leaf sent-cap-gmpls {
            description 'It describes whether PCC have sent GMPLS capability or not.' ;
            type enumeration {
              enum not-sent {
                value 0 ;
                description "PCC haven't sent the capability." ;
              }

              enum sent {
                value 1 ;
                description 'PCC have sent the capability.' ;
              }

            }

          }

          leaf negotiated-cap-stateful {
            description 'The negotiation result of stateful capability.' ;
            type enumeration {
              enum no-received {
                value 0 ;
                description "PCC haven't received the capability." ;
              }

              enum failed {
                value 1 ;
                description 'PCC have received the capability, but have not sent.' ;
              }

              enum success {
                value 2 ;
                description 'The capability negotiation has been successful.' ;
              }

            }

          }

          leaf negotiated-cap-update {
            description 'The negotiation result of update capability.' ;
            type enumeration {
              enum no-received {
                value 0 ;
                description "PCC haven't received the capability." ;
              }

              enum failed {
                value 1 ;
                description 'PCC have received the capability, but have not sent.' ;
              }

              enum success {
                value 2 ;
                description 'The capability negotiation has been successful.' ;
              }

            }

          }

          leaf negotiated-cap-initiate {
            description 'The negotiation result of initiate capability.' ;
            type enumeration {
              enum no-received {
                value 0 ;
                description "PCC haven't received the capability." ;
              }

              enum failed {
                value 1 ;
                description 'PCC have received the capability, but have not sent.' ;
              }

              enum success {
                value 2 ;
                description 'The capability negotiation has been successful.' ;
              }

            }

          }

          leaf negotiated-cap-sr {
            description 'The negotiation result of SR capability.' ;
            type enumeration {
              enum no-received {
                value 0 ;
                description "PCC haven't received the capability." ;
              }

              enum failed {
                value 1 ;
                description 'PCC have received the capability, but have not sent.' ;
              }

              enum success {
                value 2 ;
                description 'The capability negotiation has been successful.' ;
              }

            }

          }

          leaf negotiated-cap-gmpls {
            description 'The negotiation result of GMPLS capability.' ;
            type enumeration {
              enum no-received {
                value 0 ;
                description "PCC haven't received the capability." ;
              }

              enum failed {
                value 1 ;
                description 'PCC have received the capability, but have not sent.' ;
              }

              enum success {
                value 2 ;
                description 'The capability negotiation has been successful.' ;
              }

            }

          }

          leaf peer-keepalive-min {
            description 'The minimal interval of keepalive message which accepted from peer node.' ;
            type uint8 {
              range 0..255 ;

            }

          }

          leaf local-keepalive-time {
            description 'Local interval of keepalive message.' ;
            type uint8 {
              range 0..255 ;

            }

            units seconds ;
          }

          leaf local-dead-time {
            description 'Local timeout time for the peer.' ;
            type uint8 {
              range 0..255 ;

            }

            units seconds ;
          }

          leaf peer-keepalive-time {
            description 'Peer interval of keepalive message.' ;
            type uint8 {
              range 0..255 ;

            }

            units seconds ;
          }

          leaf peer-dead-time {
            description 'Peer timeout time for the peer.' ;
            type uint8 {
              range 0..255 ;

            }

            units seconds ;
          }

          leaf unknown-msg-max-num {
            description 'The maximum tolerable number of unknown messages per minute.' ;
            type uint8 {
              range 0..255 ;

            }

          }

          leaf unknown-msg-rate {
            description 'The number of unknown messages per minute.' ;
            type uint8 {
              range 0..255 ;

            }

          }

          leaf reply-wait-time {
            description 'The time waiting for the reply of request.' ;
            type uint32 ;

            units seconds ;
          }

          leaf delegated-lsp-num {
            description 'Delegated LSP number.' ;
            type uint32 {
              range 0..4294967295 ;

            }

          }

          leaf sent-keepalive-msg-num {
            description 'The number of keepalive messages sent.' ;
            type uint32 {
              range 0..4294967295 ;

            }

          }

          leaf received-keepalive-msg-num {
            description 'The number of keepalive messages received.' ;
            type uint32 {
              range 0..4294967295 ;

            }

          }

          leaf sent-request-msg-num {
            description 'The number of request messages sent.' ;
            type uint32 {
              range 0..4294967295 ;

            }

          }

          leaf received-request-msg-num {
            description 'The number of request messages received.' ;
            type uint32 {
              range 0..4294967295 ;

            }

          }

          leaf sent-reply-msg-num {
            description 'The number of reply messages sent.' ;
            type uint32 {
              range 0..4294967295 ;

            }

          }

          leaf received-reply-msg-num {
            description 'The number of reply messages received.' ;
            type uint32 {
              range 0..4294967295 ;

            }

          }

          leaf sent-report-msg-num {
            description 'The number of report messages sent.' ;
            type uint32 {
              range 0..4294967295 ;

            }

          }

          leaf received-report-msg-num {
            description 'The number of report messages received.' ;
            type uint32 {
              range 0..4294967295 ;

            }

          }

          leaf sent-update-msg-num {
            description 'The number of update messages sent.' ;
            type uint32 {
              range 0..4294967295 ;

            }

          }

          leaf received-update-msg-num {
            description 'The number of update messages received.' ;
            type uint32 {
              range 0..4294967295 ;

            }

          }

          leaf sent-init-msg-num {
            description 'The number of initiate messages sent.' ;
            type uint32 {
              range 0..4294967295 ;

            }

          }

          leaf received-init-msg-num {
            description 'The number of initiate messages received.' ;
            type uint32 {
              range 0..4294967295 ;

            }

          }

          leaf sent-error-msg-num {
            description 'The number of error messages sent.' ;
            type uint32 {
              range 0..4294967295 ;

            }

          }

          leaf received-error-msg-num {
            description 'The number of error messages received.' ;
            type uint32 {
              range 0..4294967295 ;

            }

          }

          leaf sent-notify-msg-num {
            description 'The number of notify messages sent.' ;
            type uint32 {
              range 0..4294967295 ;

            }

          }

          leaf received-notify-msg-num {
            description 'The number of notify messages received.' ;
            type uint32 {
              range 0..4294967295 ;

            }

          }

          leaf received-unknown-msg-num {
            description 'The number of unknown messages received.' ;
            type uint32 {
              range 0..4294967295 ;

            }

          }

          ncd:select peer-router-id-v6 ;
        }

        ncd:revise-date 2020-02-25 ;
      }

    }

    ncd:revise-date 2017-07-13 ;
  }

}
