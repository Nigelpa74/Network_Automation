module zxr10-switchvlan-dev-15k {
  namespace 'http://www.zte.com.cn/zxr10/netconf/schema/rosng/switchvlan-dev-15k'
            ;
  prefix switchvlan-dev-15k ;
  yang-version 1 ;
  import zxr10-switchvlan {
    prefix switchvlan ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  revision 2021-09-15 {
    description '1.Delete the PC.MSE label.'
                ;
  }
  revision 2014-12-17 {
    description 'Add deviation vlan translate type.'
                ;
  }
  deviation '/switchvlan:configuration/switchvlan:switchvlan/switchvlan:vlan-tr'
          + 'anslation/switchvlan:trans-tbl/switchvlan:trans-type'
            {
    description 'The translation type.'
                ;
    deviate replace {
      type enumeration {
        enum ingress {
          value 1 ;
          description 'Ingress VLAN translation.'
                      ;
        }
      }
    }
  }
}
