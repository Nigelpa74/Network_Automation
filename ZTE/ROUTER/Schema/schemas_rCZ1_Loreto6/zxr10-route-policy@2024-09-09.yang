module zxr10-route-policy {
  namespace "http://www.zte.com.cn/zxr10/netconf/schema/rosng/route-policy" ;
  prefix rpl ;
  import zxr10-netconf-defs {
    prefix ncd ;
  }

  organization "ZTE Corporation" ;
  contact "ZTE Corporation
  Nanjing Institute of ZTE Corporation
  No.68 Zijinghua Rd. Yuhuatai District, Nanjing, China
  Tel: +86-25-52870000" ;
  description 'The netconf module to describe route-policy.' ;
  revision 2024-09-09 {
    description 'Modify leafs:
/rpl:configuration/rpl:rpl/rpl:route-policies/rpl:route-policy/rpl:route-policy-text
/rpl:configuration/rpl:rpl/rpl:sets/rpl:prefix-sets/rpl:prefix-set/rpl:prefix-set-text
/rpl:configuration/rpl:rpl/rpl:sets/rpl:as-path-sets/rpl:as-path-set/rpl:as-path-set-text
/rpl:configuration/rpl:rpl/rpl:sets/rpl:community-sets/rpl:community-set/rpl:community-set-text
/rpl:configuration/rpl:rpl/rpl:sets/rpl:excommunity-rt-sets/rpl:excommunity-rt-set/rpl:excommunity-rt-set-text
/rpl:configuration/rpl:rpl/rpl:sets/rpl:excommunity-soo-sets/rpl:excommunity-soo-set/rpl:excommunity-soo-set-text' ;
  }

  revision 2023-05-24 {
    description 'Initial version.' ;
  }

  container configuration {
    container rpl {
      container route-policies {
        list route-policy {
          leaf route-policy-name {
            type string {
              length 1..200 ;

            }

            description 'Route policy name' ;
          }

          leaf route-policy-text {
            type ncd:string-variable-text {
              length 1..1048575 ;

            }

            description 'policy statements' ;
            mandatory true ;
          }

          key route-policy-name ;
          description 'Information about an individual policy' ;
        }

        description 'All configured policies' ;
      }

      container sets {
        container prefix-sets {
          list prefix-set {
            leaf set-name {
              type string {
                length 1..200 ;

              }

              description 'Set name' ;
            }

            leaf prefix-set-text {
              type ncd:string-variable-text {
                length 1..1048575 ;

              }

              description 'prefix statements' ;
              mandatory true ;
            }

            key set-name ;
            description 'Information about an individual set' ;
          }

          description 'Information about Prefix sets' ;
        }

        container as-path-sets {
          list as-path-set {
            leaf set-name {
              type string {
                length 1..200 ;

              }

              description 'Set name' ;
            }

            leaf as-path-set-text {
              type ncd:string-variable-text {
                length 1..1048575 ;

              }

              description 'ASPath Set' ;
              mandatory true ;
            }

            key set-name ;
            description 'Information about an individual set' ;
          }

          description 'Information about AS Path sets' ;
        }

        container community-sets {
          list community-set {
            leaf set-name {
              type string {
                length 1..200 ;

              }

              description 'Set name' ;
            }

            leaf community-set-text {
              type ncd:string-variable-text {
                length 1..1048575 ;

              }

              description 'Community Set' ;
              mandatory true ;
            }

            key set-name ;
            description 'Information about an individual set' ;
          }

          description 'Information about Community sets' ;
        }

        container excommunity-rt-sets {
          list excommunity-rt-set {
            leaf set-name {
              type string {
                length 1..200 ;

              }

              description 'Set name' ;
            }

            leaf excommunity-rt-set-text {
              type ncd:string-variable-text {
                length 1..1048575 ;

              }

              description 'Extended Community RT Set' ;
              mandatory true ;
            }

            key set-name ;
            description 'Information about an individual set' ;
          }

          description 'Information about RT sets' ;
        }

        container excommunity-soo-sets {
          list excommunity-soo-set {
            leaf set-name {
              type string {
                length 1..200 ;

              }

              description 'Set name' ;
            }

            leaf excommunity-soo-set-text {
              type ncd:string-variable-text {
                length 1..1048575 ;

              }

              description 'Extended Community SOO Set' ;
              mandatory true ;
            }

            key set-name ;
            description 'Information about an individual set' ;
          }

          description 'Information about SOO sets' ;
        }

        description 'All configured sets' ;
      }

    }

  }

}
