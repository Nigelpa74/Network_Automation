module zxr10-lacp {
  namespace "http://www.zte.com.cn/zxr10/netconf/schema/rosng/lacp" ;
  prefix lacp ;
  import zxr10-netconf-defs {
    prefix ncd ;
  }

  organization "ZTE Corporation" ;
  contact "ZTE Corporation
  Nanjing Institute of ZTE Corporation
  No.68 Zijinghua Rd. Yuhuatai District, Nanjing, China
  Tel: +86-25-52870000" ;
  description 'The netconf module to describe the Link Aggregation Control Protocol' ;
  revision 2025-04-08 {
    description 'Add leaf node /lacp:configuration/lacp:lacp/lacp:local/lacp:smartgroups/lacp:smartgroup/lacp:lag-bfd-state-linkage.' ;
  }
  revision 2025-03-27 {
    description 'Add leaf node /lacp:configuration/lacp:lacp/lacp:global/lacp:mclag/lacp:mclag-global/lacp:applyArpProxy.
Add leaf node 
/lacp:configuration/lacp:lacp/lacp:global/lacp:mclag/lacp:mclag-global/lacp:applyNdProxy.' ;
  }
  revision 2025-03-04 {
    description 'Add 5960X label for feature lacp-load-balance-factor.' ;
  }

  revision 2025-01-04 {
    description 'Add container node /lacp:configuration/lacp:lacp/lacp:global/lacp:mclag/lacp:mclag-global.' ;
  }

  revision 2024-12-09 {
    description 'Add leaf node configuration/lacp/local/smartgroups/smartgroup/smartgroup-preferred-up.
Add feature smartgroup-preferred-up.' ;
  }

  revision 2024-11-25 {
    description 'Add leaf node /lacp:configuration/lacp:lacp/lacp:local/lacp:smartgroups/lacp:smartgroup/lacp:state-dampening.' ;
  }

  revision 2024-08-09 {
    description 'Add container node
/lacp:configuration/lacp:lacp/lacp:local/lacp:smartgroups/lacp:smartgroup/lacp:load-balance-factor.
Add leaf node /lacp:configuration/lacp:lacp/lacp:local/lacp:smartgroups/lacp:smartgroup/lacp:load-balance-factor/lacp:src-ip.
Add leaf node /lacp:configuration/lacp:lacp/lacp:local/lacp:smartgroups/lacp:smartgroup/lacp:load-balance-factor/lacp:dst-ip.
Add leaf node /lacp:configuration/lacp:lacp/lacp:local/lacp:smartgroups/lacp:smartgroup/lacp:load-balance-factor/lacp:l3-protocol.
Add leaf node /lacp:configuration/lacp:lacp/lacp:local/lacp:smartgroups/lacp:smartgroup/lacp:load-balance-factor/lacp:src-port.
Add leaf node /lacp:configuration/lacp:lacp/lacp:local/lacp:smartgroups/lacp:smartgroup/lacp:load-balance-factor/lacp:dst-port.
Add leaf node /lacp:configuration/lacp:lacp/lacp:local/lacp:smartgroups/lacp:smartgroup/lacp:load-balance-factor/lacp:src-mac.
Add leaf node /lacp:configuration/lacp:lacp/lacp:local/lacp:smartgroups/lacp:smartgroup/lacp:load-balance-factor/lacp:dst-mac.
Add leaf node /lacp:configuration/lacp:lacp/lacp:local/lacp:smartgroups/lacp:smartgroup/lacp:load-balance-factor/lacp:outer-vlan.
Add feature lacp-load-balance-factor.' ;
  }

  revision 2024-08-08 {
    description 'Obsolete feature node global-lag-bfd.
Obsolete container node configuration/lacp/global/lag-bfd.' ;
  }

  revision 2024-08-05 {
    description 'Add product label 61V5_1 for the feature port-selection.' ;
  }

  revision 2024-06-21 {
    description 'Obsolete the enum item mc-lag-up-num of the leaf mclag-role-selection-rule/ruleType, and add the enum item icbg-port-up-num.' ;
  }

  revision 2024-05-27 {
    description 'Add the following restriction: The satellite port cannot be assigned to the smartgroup with the PEB function enabled.' ;
  }

  revision 2024-05-24 {
    description 'Add the presence of container node /lacp:configuration/lacp:lacp/lacp:local/lacp:ports/lacp:port/lacp:lag-bfd-to-satellite.' ;
  }

  revision 2024-05-13 {
    description 'Add container node /lacp:configuration/lacp:lacp/lacp:global/lacp:mclag/lacp:mclag-standalone.
Add feature mclag-standalone.' ;
  }

  revision 2024-04-08 {
    description 'Add container node
/lacp:configuration/lacp:lacp/lacp:local/lacp:ports/lacp:port/lacp:lag-bfd-to-satellite.
Add feature /lacp:lag-bfd-to-satellite.' ;
  }

  revision 2024-04-03 {
    description 'Add leaf node configuration/lacp/local/smartgroups/smartgroup/monitor-esi-df-election.' ;
  }

  revision 2024-03-29 {
    description 'Add product lables 59X-ES and 99X for the feature negotiation-flag.' ;
  }

  revision 2024-01-11 {
    description 'Add container node configuration/lacp/global/mclag/mclag-role-selection-rules.' ;
  }

  revision 2023-12-01 {
    description 'Add leaf node configuration/lacp/local/smartgroups/smartgroup/port-selection.' ;
  }

  revision 2023-10-17 {
    description 'Change the range of leaf node smartgroup-id from 1-1024 | 1025-048 to 1-99999999.
Change the range of leaf node group-id from 1-1024 | 1025-048 to 1-99999999.' ;
  }

  revision 2023-09-08 {
    description 'Add feature negotiation-flag and its product lables do not include 59X-ES and 99X.
Add the feature negotiation-flag to the leaf node configuration/lacp/local/smartgroups/smartgroup/negotiation-flag.' ;
  }

  revision 2023-08-03 {
    description 'Add leaf node configuration/lacp/peer-link/auto-mapping-vxlan.' ;
  }

  revision 2023-05-12 {
    description 'Add units to leaf node /lacp:configuration/lacp:lacp/lacp:local/lacp:ports/lacp:port/lacp:short-timeout-time.
Change the max value of leaf node /lacp:configuration/lacp:lacp/lacp:local/lacp:ports/lacp:port/lacp:smartgroup-id from 1024 to 2048.
Add range to leaf node /lacp:configuration/lacp:lacp/lacp:local/lacp:smartgroups/lacp:smartgroup/lacp:lag-bfd/lacp:time-type/lacp:time/lacp:min-rx.
Add range to leaf node /lacp:configuration/lacp:lacp/lacp:local/lacp:smartgroups/lacp:smartgroup/lacp:lag-bfd/lacp:time-type/lacp:time/lacp:min-tx.
Change the max value of leaf node /lacp:operation/lacp:lacp/lacp:clear/lacp:group-id from 1024 to 2048.' ;
  }

  revision 2022-06-30 {
    description 'Add container node configuration/lacp/local/ports/port/lag-bfd/discriminator.
Add container node configuration/lacp/local/ports/port/lag-bfd-ipv6/discriminator.' ;
  }

  revision 2021-10-19 {
    description 'Delete the default value of the leaf node configuration/lacp/local/smartgroups/smartgroup/delay-down-time, and modify its description.' ;
  }

  revision 2021-10-08 {
    description 'Add leaf node configuration/lacp/local/ports/port/short-timeout-time.' ;
  }

  revision 2021-09-16 {
    description 'Add container node configuration/lacp/global/mclag/mclag-suspends.' ;
  }

  revision 2021-07-16 {
    description 'Add containter node configuration/lacp/global/mclag/mclag-system.
Change the mandatory sentence from true to false of the leaf node configuration/lacp/local/smartgroups/mclag/mclag-roid/node-id.
Add the default value of the leaf node configuration/lacp/local/smartgroups/mclag/mclag-roid/node-id.
Add feature mclag-ip-use-global.
Add the feature mclag-ip-use-global to the containter node configuration/lacp/local/smartgroups/mclag/mclag-ip-use-global.
Add leaf node state/lacp/member/ports/port/port-mode.
Add leaf node state/lacp/member/ports/port/ptx-state.
Add leaf node state/lacp/member/ports/port/agg-state.
Add leaf node state/lacp/member/ports/port/periodic-time.
Add leaf node state/lacp/member/ports/port/port-priority.
Add leaf node state/lacp/member/ports/port/oper-key.
Add leaf node state/lacp/member/ports/port/oper-state.
Add leaf node state/lacp/member/ports/port/rx-state.
Add leaf node state/lacp/member/ports/port/mux-state.' ;
  }

  revision 2021-07-15 {
    description 'Add feature lacp-fast-respond and its product lables do not include 5960X and 99X.
Add the feature lacp-fast-respond to the leaf node configuration/lacp/local/smartgroups/smartgroup/fast-respond.
Delete the default value of the leaf node configuration/lacp/local/smartgroups/smartgroup/fsm-mode, and modify its description.' ;
  }

  revision 2021-07-12 {
    description 'Add leaf node configuration/lacp/global/mclag/mclag-backoff/mode.
Add leaf node configuration/lacp/local/smartgroups/smartgroup/port-key.' ;
  }

  revision 2021-06-23 {
    description 'Add container node configuration/lacp/global/lag-bfd.' ;
  }

  revision 2021-05-25 {
    description 'Add the load-balance node enumeration type src-dst-ip-src-dst-port-protocol.' ;
  }

  revision 2021-05-10 {
    description 'Add leaf node configuration/lacp/local/ports/port/multi-backup.' ;
  }

  revision 2021-04-20 {
    description 'Add leaf node configuration/lacp/local/smartgroups/smartgroup/system-mac.
Add leaf node configuration/lacp/local/smartgroups/smartgroup/node-id.' ;
  }

  revision 2021-03-31 {
    description 'Add the configuration/lacp/global/mclag/mclag-track-groups/mclag-track-group/track-group-type node enumeration type nni-type.' ;
  }

  revision 2021-01-25 {
    description 'Change the presence of container node configuration/lacp/global/mclag/mclag-ccheck-critical to critical-type should be mandatory.
Add the presence of container node configuration/lacp/global/mclag/mclag-ccheck-normal.
Change leaf node configuration/lacp/global/mclag/mclag-ccheck-normal/normal-type to mandatory.
Delete revision-date 2014-06-24.
Change derived type ncd:ipv6-address to derived type ncd:ipv6-address-none-zero.
Add length to leaf node configuration/lacp/global/mclag/mclag-ipv4-address/vrf/vrf-choice/vrf-name-case/vrf-name.
Add length to leaf node configuration/lacp/global/mclag/mclag-ipv6-address/vrf/vrf-choice/vrf-name-case/vrf-name.
Add length to leaf node configuration/lacp/local/smartgroups/smartgroup/mclag/mclag-ipv4-address/vrf/vrf-choice/vrf-name-case/vrf-name.
Add length to leaf node configuration/lacp/local/smartgroups/smartgroup/mclag/mclag-ipv6-address/vrf/vrf-choice/vrf-name-case/vrf-name.' ;
  }

  revision 2021-01-08 {
    description 'Add the load-balance node enumeration type gtp.' ;
  }

  revision 2020-12-28 {
    description 'Add leaf node configuration/lacp/local/smartgroups/smartgroup/delay-down-time.' ;
  }

  revision 2020-10-22 {
    description 'Add container node configuration/lacp/global/mclag/mclag-track-groups.
Add list node configuration/lacp/global/mclag/mclag-track-groups/mclag-track-group.
Add leaf node configuration/lacp/global/mclag/mclag-track-groups/mclag-track-group/track-group-name.
Add leaf node configuration/lacp/global/mclag/mclag-track-groups/mclag-track-group/track-group-type.' ;
  }

  revision 2020-10-12 {
    description 'Add container node configuration/lacp/local/smartgroups/smartgroup/preempt.
Add leaf node configuration/lacp/local/smartgroups/smartgroup/preempt/switch.
Add leaf node configuration/lacp/local/smartgroups/smartgroup/preempt/delay-time.' ;
  }

  revision 2020-09-15 {
    description 'Add leaf node configuration/lacp/local/smartgroups/smartgroup/smartgroup-constant-up.' ;
  }

  revision 2020-09-09 {
    description 'Add leaf node configuration/lacp/local/smartgroups/smartgroup/admin-status-linkage.' ;
  }

  revision 2020-08-31 {
    description 'Add container node configuration/lacp/local/smartgroups/smartgroup/lag-bfd.
Add container node configuration/lacp/local/smartgroups/smartgroup/lag-bfd-ipv6.
Change the container node configuration/lacp/local/ports/port/lag-bfd/time to container node configuration/lacp/local/ports/port/lag-bfd/time-type-choice/time-case/time.
Add leaf node configuration/lacp/local/ports/port/lag-bfd/time-type-choice/template-case/template.
Add container node configuration/lacp/local/ports/port/lag-bfd-ipv6.' ;
  }

  revision 2020-06-30 {
    description 'Add container node configuration/lacp/global/mclag.
Add container node configuration/lacp/global/mclag/mclag-backoff.
Add container node configuration/lacp/global/mclag/mclag-consistency-check.
Add container node configuration/lacp/global/mclag/mclag-delay-time.
Add container node configuration/lacp/global/mclag/mclag-dual-malfunction-protect.
Add container node configuration/lacp/global/mclag/mclag-exempts.
Add container node configuration/lacp/global/mclag/mclag-ipv4-address.
Add container node configuration/lacp/global/mclag/mclag-ipv6-address.
Add container node configuration/lacp/global/mclag/mclag-priority.
Add container node configuration/lacp/global/mclag/mclag-tracks.
Add container node configuration/lacp/global/mclag/mclag-udp.

Add container node configuration/lacp/local/smartgroups/smartgroup/mclag/mclag-ipv4-address.
Add container node configuration/lacp/local/smartgroups/smartgroup/mclag/mclag-ipv6-address.
Add leaf node configuration/lacp/local/smartgroups/smartgroup/fsm-mode.
Add leaf node configuration/lacp/local/smartgroups/smartgroup/speed-reassign.
Add enumeration type peer-type of the leaf node configuration/lacp/local/smartgroups/smartgroup/mclag/tracks/track/track-type.
Add leaf node state/lacp/mclag/actor-roid.
Add leaf node state/lacp/mclag/actor-node-id.' ;
  }

  revision 2020-06-19 {
    description 'Add leaf node configuration\lacp\local\ports\port\description' ;
  }

  revision 2020-04-24 {
    description 'Add container mclag-ip-use-global.' ;
  }

  revision 2020-01-02 {
    description 'Add container protocol-packet.' ;
  }

  revision 2019-04-23 {
    description 'Obsolete the enum item peer-link-type of the leaf mclag-tracks/track-type.' ;
  }

  revision 2019-04-16 {
    description 'Add the range of leaf node smartgroup-id from 1025 to 2048 and change the corresponding description.
Add the range of leaf node group-id from 1025 to 2048 and change the corresponding description.' ;
  }

  revision 2018-12-21 {
    description 'Obsolete leaf node system-active-number.' ;
  }

  revision 2018-11-20 {
    description 'Add leaf node state/mclag/work-mode.
Add leaf node state/mclag/state.
Add leaf node state/mclag/actor-smartgroup-state.
Add leaf node state/mclag/partner-smartgroup-state.' ;
  }

  revision 2018-10-30 {
    description 'Add the load-balance node enumeration type dlb-flow-fixed.
Add the load-balance node enumeration type dlb-flow-timeout.
Add the load-balance node enumeration type dlb-packet.' ;
  }

  revision 2018-10-25 {
    description 'Change the range of leaf node system-active-number from 1-16 to 1-1024.
Change the range of leaf node active-number from 1-16 to 1-1024.
Change the range of leaf node active-limit from 1-16 to 1-1024.
Change the range of leaf node smartgroup-id from 1-64 to 1-1024.
Change the range of leaf node group-id from 1-64 to 1-1024.
Change the range of leaf node min-tx from 10-990 to 1-65535.
Change the range of leaf node min-rx from 10-990 to 1-65535.' ;
  }

  revision 2018-09-13 {
    description 'Add data selector leaf node.
Obsolete the container of mclag-receive-flag.' ;
  }

  revision 2018-07-18 {
    description 'Add LACP service-switch leaf node.' ;
  }

  revision 2018-06-12 {
    description 'Add alarm-to-notification leaf node.' ;
  }

  revision 2018-01-08 {
    description 'Add mclag-multi-link-role container node.
Add mclag-receive-flag container node.
Add protect-state leaf node.' ;
  }

  revision 2017-07-20 {
    description 'Add sd-detection leaf node.' ;
  }

  revision 2017-07-12 {
    description 'Add container peer-link.
Add mc-lag track peer-link-type.' ;
  }

  revision 2017-03-01 {
    description '1. Obsolete the container of old mclag-track and add the new mclag-tracks.' ;
  }

  revision 2016-11-16 {
    description 'Add list member.' ;
  }

  revision 2016-10-10 {
    description 'Add unconditional-active leaf node.
Modify description of the negotiation-flag leaf node.
Modify description of the negotiation-mac leaf node.' ;
  }

  revision 2016-09-19 {
    description 'Add negotiation-mac leaf node.' ;
  }

  revision 2016-08-25 {
    description 'Add negotiation-flag leaf node.' ;
  }

  revision 2016-03-28 {
    description 'Add port-dispersion leaf node.' ;
  }

  revision 2015-12-30 {
    description 'Add the load-balance node enumeration type dst-ip-dst-port.
Add the load-balance node enumeration type src-ip-src-port.
Add the load-balance node enumeration type src-dst-ip-src-dst-port.' ;
  }

  revision 2015-03-03 {
    description 'Add mclag-track.
Add track and lag-bfd.' ;
  }

  revision 2015-01-08 {
    description 'Modify descriptions of the nodes.' ;
  }

  revision 2014-03-17 {
    description 'Modify range of hold-off;
Modify if-filter-id of state smartgroup interface-name;
Modify if-filter-id of state port interface-name;
Modify if-filter-id of state mclag interface-name;
Add choice node clear-choice and move it to clear;
Add case node group-id-case and move it to clear-choice;
Move group-id to group-id-case;
Add case node all-case and move it to clear;
Add leaf node all and move it to all-case;
Add Perf-code of clear group-id;
Modify description of clear;
Modify description of clear group-id;
Add if-filter-id of forceswitch interface-name.' ;
  }

  revision 2014-02-28 {
    description 'Change choice name restore to restore-choice;
Change case name revertive to revertive-case;
Change case name immediately to immediately-case;
Change case name non-revertive to non-revertive-case;
Change leaf name hold-time to restore-time;
Add container restore and move restore-choice to restore;
Add reset-value of fast-respond;
Add reset-value of revertive;
Add reset-value of immediately;
Add reset-value of non-revertive;
Add reset-value of back-up.' ;
  }

  revision 2014-01-20 {
    description 'Add container local;
Add container smartgroups;
Add container ports;
Move smartgroup to smartgroups;
Move port to ports;
Move smartgroups and ports to local;
Modify revertive keyref path;
Modify immediately keyref path;
Modify non-revertive keyref path;
Modify mclag-system keyref path;
Modify mclag-roid keyref path;
Modify mclag-iccp keyref path;
Modify mclag-attr keyref path;
Modify range of active-limit;
Add leaf smartgroup-id and move it to state node port.' ;
  }

  revision 2014-01-09 {
    description 'Modify range of system-active-number;
Modify Perf-code of system-active-number;
Modify enum order and description of load-balance;
Modify Perf-code of load-balance;
Modify range and default value of active-number;
Modify Perf-code of active-number;
Modify range of active-limit;
Modify Perf-code of active-limit;
Modify range of hold-off;
Modify range of smartgroup-id;
Modify Perf-code of smartgroup-id;
Modify if-filter-id of smartgroup interface-name;
Modify if-filter-id of port interface-name;
Modify enum order of lacp-state.' ;
  }

  revision 2013-10-22 {
    description 'Modify system-active-number and active-number node range from 1 .. 32 to 1 .. 65535;
Add the load-balance node enumeration type per-subinterface;
Add the default value of active-number and load-balance node;

Modify the data type of the mac node and partner-system-mac node from string to mac-address.
Change mclag-system node from choice to container.
Change mclag-roid node from choice to container.
Change mclag-iccp node from choice to container.
Change mclag-attr node from choice to container.' ;
  }

  revision 2013-06-19 {
    description 'The initial version' ;
  }

  feature lacp-protocol-packet {
    description 'Set the rule of the control plane sending protocol packet for smartgroup.' ;
  }

  feature lacp-fast-respond {
    description 'The fast respond of smartgroup.' ;
  }

  feature mclag-ip-use-global {
    description 'The IP address of MC-LAG uses the IP address configured globally.' ;
  }

  feature auto-mapping-vxlan {
    description 'Auto mapping VXLAN.' ;
    ncd:revise-date 2023-08-03 ;
  }

  feature negotiation-flag {
    ncd:revise-date 2023-09-08 ;
  }

  feature port-selection {
    description 'The port selection of smartgroup.' ;
    ncd:revise-date 2023-12-01 ;
  }

  feature mclag-role-selection-rule {
    description 'The rule of global MC-LAG role selection.' ;
    ncd:revise-date 2024-01-11 ;
  }

  feature monitor-esi-df-election {
    description 'The monitor ESI DF election of smartgroup.' ;
    ncd:revise-date 2024-04-03 ;
  }

  feature lag-bfd-to-satellite {
    description 'Lag Bfd to-satellite' ;
    ncd:revise-date 2024-04-08 ;
  }

  feature mclag-standalone {
    description 'The parameter of MC-LAG standalone to be configured.' ;
    ncd:revise-date 2024-05-13 ;
  }

  feature lacp-load-balance-factor {
    description 'The parameter of LACP load balance factor to be configured.' ;
    ncd:revise-date 2024-08-09 ;
  }

  feature smartgroup-preferred-up {
    description 'The protocol preferred up flag of smartgroup.' ;
    ncd:revise-date 2024-12-09 ;
  }
  
  feature mclag-apply-arp-proxy {
    description 'The parameter of MC-LAG apply ARP proxy to be configured.' ;
    ncd:revise-date 2025-03-27 ;
  }

  feature mclag-apply-nd-proxy {
    description 'The parameter of MC-LAG apply ND proxy to be configured.' ;
    ncd:revise-date 2025-03-27 ;
  }
  
  container configuration {
    description 'Describe the configuration of Link Aggregation Control Protocol.' ;
    container lacp {
      description 'Describe the parameters of LACP to be configured.' ;
      container global {
        description 'Describe the global parameters to be configured.' ;
        leaf system-priority {
          description 'The global system priority. In the case of the smartgroup-priority leaf of smartgroup list is not configured, this value will be used.' ;
          type uint16 {
            range 1..65535 ;

          }

          default 32768 ;
        }

        leaf system-active-number {
          status obsolete {
            ncd:revise-date 2018-12-21 ;
          }

          description 'The global system active number, its maximum value depends on the performance parameters. In the case of the active-number leaf of smartgroup list is not configured, this value will be used.' ;
          type uint32 {
            range 1..1024 {
              description 'The maximum value depends on the performance parameters.' ;
            }

          }

          default 1 ;
        }

        leaf alarm-to-notification {
          description 'The flag that turns alarm to notification, its default value depends on the performance parameters.' ;
          type enumeration {
            enum disable {
              value 0 ;
              description 'Disable the alarm to notification function.' ;
            }

            enum enable {
              value 1 ;
              description 'Enable the alarm to notification function.' ;
            }

          }

          ncd:revise-date 2018-06-12 ;
        }

        leaf service-switch {
          description 'LACP service switch, its default value depends on the performance parameters.' ;
          type enumeration {
            enum disable {
              value 0 ;
              description 'Disable LACP service.' ;
            }

            enum enable {
              value 1 ;
              description 'Enable LACP service.' ;
            }

          }

          ncd:revise-date 2018-07-18 ;
        }

        container mclag {
          description 'Describe the parameters of global MC-LAG to be configured.' ;
          container mclag-backoff {
            description 'Describe the parameters of global MC-LAG backoff to be configured.' ;
            leaf backoff {
              description 'The backoff of global MC-LAG.' ;
              type enumeration {
                enum disable {
                  value 1 ;
                  description 'Disable global MC-LAG backoff .' ;
                }

                enum enable {
                  value 0 ;
                  description 'Enable global MC-LAG backoff.' ;
                }

              }

              default enable ;
            }

            leaf mode {
              description 'The backoff mode of global MC-LAG. Its default value which is between [aggressive,hold] and generally aggressive, depends on product specification.' ;
              type enumeration {
                enum aggressive {
                  value 0 ;
                  description 'The backoff mode of global MC-LAG is aggressive.' ;
                }

                enum hold {
                  value 1 ;
                  description 'The backoff mode of global MC-LAG is hold.' ;
                }

              }

              ncd:revise-date 2021-07-12 ;
            }

          }

          container mclag-ccheck-critical {
            description 'Describe the parameters of global MC-LAG consistency check to be configured.' ;
            presence "critical-type should be mandatory" ;
            leaf critical-type {
              description 'The consistency check type of global MC-LAG is critical.' ;
              type empty ;

              mandatory true ;
            }

            leaf mode {
              description 'The consistency check mode of global MC-LAG.' ;
              type enumeration {
                enum loose {
                  value 0 ;
                  description 'The consistency check mode of global MC-LAG is loose.' ;
                }

                enum strict {
                  value 1 ;
                  description 'The consistency check mode of global MC-LAG is strict.' ;
                }

              }

              default loose ;
            }

          }

          container mclag-ccheck-normal {
            description 'Describe the parameters of global MC-LAG consistency check to be configured.' ;
            presence "normal-type should be mandatory" ;
            leaf normal-type {
              description 'The consistency check type of global MC-LAG is normal.' ;
              type empty ;

              mandatory true ;
            }

          }

          container mclag-delay-time {
            description 'Describe the parameters of global MC-LAG delay time to be configured.' ;
            leaf delay-down-time {
              description 'The delay down time to global MC-LAG, its default value depends on the performance parameters.' ;
              type uint16 {
                range 0..180 ;

              }

              units second ;
              default 3 ;
            }

            leaf delay-up-time {
              description 'The delay up time to global MC-LAG, its default value depends on the performance parameters.' ;
              type uint16 {
                range 0..3600 ;

              }

              units second ;
              default 480 ;
            }

            leaf reload-delay-up-time {
              description 'The reload delay up time to global MC-LAG, its default value depends on the performance parameters.' ;
              type uint16 {
                range 0..3600 ;

              }

              units second ;
              default 480 ;
            }

          }

          container mclag-dual-malfunction-protect {
            description 'Describe the parameters of global MC-LAG dual malfunction protect to be configured.' ;
            leaf dual-malfunction-protect {
              description 'The dual malfunction protect of global MC-LAG,its default value depends on the performance parameters.' ;
              type enumeration {
                enum disable {
                  value 0 ;
                  description 'The dual malfunction protect of global MC-LAG is disable.' ;
                }

                enum enable {
                  value 1 ;
                  description 'The dual malfunction protect of global MC-LAG is enable.' ;
                }

              }

              default enable ;
            }

          }

          container mclag-exempts {
            description 'Describe the parameters of global MC-LAG exempt interface to be configured.' ;
            list mclag-exempt {
              description 'Describe the parameters of global MC-LAG exempt interface to be configured.' ;
              key interface-name ;
              leaf interface-name {
                description 'The exempt interface of global MC-LAG.' ;
                type ncd:ifname ;

              }

            }

          }

          container mclag-ipv4-address {
            description 'Describe the parameters of global MC-LAG IPv4 source and destination address to be configured.' ;
            presence "source-address and destination-address should be mandatory" ;
            leaf source-address {
              description 'The IPv4 source address of global MC-LAG.' ;
              type ncd:ipv4-address ;

              mandatory true ;
            }

            leaf destination-address {
              description 'The IPv4 destination address of global MC-LAG.' ;
              type ncd:ipv4-address ;

              mandatory true ;
            }

            container vrf {
              description 'Describe the parameters of global MC-LAG VRF name to be configured.' ;
              choice vrf-choice {
                description 'The VRF name of global MC-LAG.' ;
                case vrf-name-case {
                  description 'The VRF name of global MC-LAG, whose name cannot be mng.' ;
                  leaf vrf-name {
                    description 'The VRF name of global MC-LAG, whose name cannot be mng.' ;
                    type string {
                      length 1..32 ;

                    }

                  }

                }

                case vrf-mng-case {
                  description 'The VRF mng instance of global MC-LAG.' ;
                  leaf vrf-mng {
                    description 'The VRF mng instance of global MC-LAG.' ;
                    type empty ;

                  }

                }

              }

            }

          }

          container mclag-ipv6-address {
            description 'Describe the parameters of global MC-LAG IPv6 source and destination address to be configured.' ;
            presence "source-address and destination-address should be mandatory" ;
            leaf source-address {
              description 'The IPv6 source address of global MC-LAG.' ;
              type ncd:ipv6-address-none-zero ;

              mandatory true ;
            }

            leaf destination-address {
              description 'The IPv6 destination address of global MC-LAG.' ;
              type ncd:ipv6-address-none-zero ;

              mandatory true ;
            }

            container vrf {
              description 'Describe the parameters of global MC-LAG VRF name to be configured.' ;
              choice vrf-choice {
                description 'The VRF name of global MC-LAG.' ;
                case vrf-name-case {
                  description 'The VRF name of global MC-LAG, whose name cannot be mng.' ;
                  leaf vrf-name {
                    description 'The VRF name of global MC-LAG, whose name cannot be mng.' ;
                    type string {
                      length 1..32 ;

                    }

                  }

                }

                case vrf-mng-case {
                  description 'The VRF mng instance of global MC-LAG.' ;
                  leaf vrf-mng {
                    description 'The VRF mng instance of global MC-LAG.' ;
                    type empty ;

                  }

                }

              }

            }

          }

          container mclag-priority {
            description 'Describe the parameters of global MC-LAG priority to be configured.' ;
            leaf priority {
              description 'The priority of global MC-LAG.' ;
              type uint32 {
                range 1..65535 ;

              }

              default 32768 ;
            }

          }

          container mclag-tracks {
            description 'Describe the parameters of global MC-LAG track to be configured.' ;
            presence "track-name and track-type should be mandatory" ;
            list mclag-track {
              description 'Describe the parameters of global MC-LAG track to be configured.' ;
              key track-name ;
              leaf track-name {
                description 'The track name of global MC-LAG.' ;
                type string {
                  length 1..31 ;

                }

              }

              leaf track-type {
                description 'The track type of global MC-LAG.' ;
                type enumeration {
                  enum peer-type {
                    value 3 ;
                    description 'The track type of global MC-LAG is peer-type.' ;
                  }

                }

                mandatory true ;
              }

            }

          }

          container mclag-udp {
            description 'Describe the parameters of global MC-LAG udp port switch to be configured.' ;
            leaf udp {
              description 'The udp port switch to global MC-LAG, its default value depends on the performance parameters.' ;
              type enumeration {
                enum disable {
                  value 0 ;
                  description 'The udp port switch of global MC-LAG is disable.' ;
                }

                enum enable {
                  value 1 ;
                  description 'The udp port switch of global MC-LAG is enable.' ;
                }

              }

              default enable ;
            }

          }

          container mclag-track-groups {
            description 'Describe the parameters of global MC-LAG track-group to be configured.' ;
            presence "track-group-name and track-group-type should be mandatory" ;
            list mclag-track-group {
              description 'Describe the parameters of global MC-LAG track-group to be configured.' ;
              key track-group-name ;
              leaf track-group-name {
                description 'The track-group name of global MC-LAG.' ;
                type string {
                  length 1..31 ;

                }

              }

              leaf track-group-type {
                description 'The track-group type of global MC-LAG.' ;
                type enumeration {
                  enum controller-type {
                    value 1 ;
                    description 'The track-group type of global MC-LAG is controller-type.' ;
                  }

                  enum nni-type {
                    value 2 ;
                    description 'The track-group type of global MC-LAG is nni-type.' ;
                  }

                }

                mandatory true ;
              }

            }

            ncd:revise-date 2020-10-22 ;
          }

          container mclag-system {
            description 'Describe the parameters of global MC-LAG system to be configured.' ;
            presence "system-id and system-priority should be mandatory" ;
            leaf system-id {
              description 'The system MAC of global MC-LAG.' ;
              type ncd:mac-address ;

              mandatory true ;
            }

            leaf system-priority {
              description 'The system priority of global MC-LAG.' ;
              type uint16 {
                range 1..65535 ;

              }

              mandatory true ;
            }

            ncd:revise-date 2021-07-16 ;
          }

          container mclag-suspends {
            description 'Describe the parameters of global MC-LAG suspend interface to be configured.' ;
            list mclag-suspend {
              description 'Describe the parameters of global MC-LAG suspend interface to be configured.' ;
              key interface-name ;
              leaf interface-name {
                description 'The suspend interface of global MC-LAG.' ;
                type ncd:ifname ;

              }

            }

            ncd:revise-date 2021-09-16 ;
          }

          container mclag-role-selection-rules {
            description 'Describe the parameters of global MC-LAG role selection rule to be configured.' ;
            list mclag-role-selection-rule {
              description 'Describe the parameters of global MC-LAG role selection rule to be configured.' ;
              key ruleType ;
              leaf ruleType {
                description 'The rule of global MC-LAG role selection.' ;
                type enumeration {
                  enum mc-lag-up-num {
                    value 1 ;
                    description 'MC-LAG up num.' ;
                    status obsolete {
                      ncd:revise-date 2024-06-21 ;
                    }

                  }

                  enum icbg-port-up-num {
                    value 2 ;
                    description 'ICBG port up num.' ;
                  }

                }

              }

              if-feature mclag-role-selection-rule ;

            }

            ncd:revise-date 2024-01-11 ;
          }

          container mclag-standalone {
            leaf switch {
              type enumeration {
                enum disable {
                  description 'The MC-LAG standalone switch of smartgroup is disable.' ;
                  value 0 ;
                }

                enum enable {
                  description 'The MC-LAG standalone switch of smartgroup is enable.' ;
                  value 1 ;
                }

              }

              description 'The MC-LAG standalone switch of smartgroup.' ;
              default disable ;
            }

            leaf delay-time {
              description 'The MC-LAG standalone delay time of smartgroup.' ;
              default 0 ;
              units second ;
              type uint16 {
                range 0..3600 ;

              }

            }

            description 'The parameter of MC-LAG standalone to be configured.' ;
            if-feature mclag-standalone {
              ncd:revise-date 2024-05-13 ;
            }

          }

          container mclag-global {
            container authentication {
              choice mode-choice {
                case hmac-sha256-case {
                  container hmac-sha256 {
                    choice password-choice {
                      case clear-case {
                        leaf clear-password {
                          type string {
                            length 8..16 ;

                          }

                          description 'The clear password.' ;
                          mandatory true ;
                        }

                        description 'Set the clear password.' ;
                      }

                      case encrypted-case {
                        leaf encrypted-password {
                          type string {
                            length 84 ;

                          }

                          description 'The encrypted password.' ;
                          mandatory true ;
                        }

                        description 'Encrypted the password.' ;
                      }

                      description 'Set MC-LAG authentication password.' ;
                      mandatory true ;
                    }

                    description 'MC-LAG authentication mode is HMAC-SHA256.' ;
                    presence "password should be mandatory" ;
                  }

                  description 'MC-LAG authentication mode is HMAC-SHA256.' ;
                }

                case sm4-case {
                  container sm4 {
                    choice password-choice {
                      case clear-case {
                        leaf clear-password {
                          type string {
                            length 8..16 ;

                          }

                          description 'The clear password.' ;
                          mandatory true ;
                        }

                        description 'Set the clear password.' ;
                      }

                      case encrypted-case {
                        leaf encrypted-password {
                          type string {
                            length 84 ;

                          }

                          description 'The encrypted password.' ;
                          mandatory true ;
                        }

                        description 'Encrypted the password.' ;
                      }

                      description 'Set MC-LAG authentication password.' ;
                      mandatory true ;
                    }

                    description 'MC-LAG authentication mode is SM4.' ;
                    presence "password should be mandatory" ;
                  }

                  description 'MC-LAG authentication mode is SM4.' ;
                }

                description 'The authentication mode.' ;
              }

              description 'Describe the parameters of authentication to be configured.' ;
            }

            leaf applyArpProxy {
              type enumeration {
                enum enable {
                  value 1 ;
                  description 'Enable MC-LAG apply ARP proxy table.' ;
                }

                enum disable {
                  value 0 ;
                  description 'Disable MC-LAG apply ARP proxy table.' ;
                }

              }

              description 'MC-LAG apply ARP proxy table.' ;
              default disable ;
              if-feature mclag-apply-arp-proxy ;

              ncd:revise-date 2025-03-27 ;
            }

            leaf applyNdProxy {
              type enumeration {
                enum enable {
                  value 1 ;
                  description 'Enable MC-LAG apply ND proxy table.' ;
                }

                enum disable {
                  value 0 ;
                  description 'Disable MC-LAG apply ND proxy table.' ;
                }

              }

              description 'MC-LAG apply ND proxy table.' ;
              default disable ;
              if-feature mclag-apply-nd-proxy ;

              ncd:revise-date 2025-03-27 ;
            }
            description 'Describe the parameters of global MC-LAG to be configured.' ;
            ncd:revise-date 2025-01-04 ;
          }

          ncd:revise-date 2020-06-30 ;
        }

        container lag-bfd {
          description 'The lag-bfd of global.' ;
          status obsolete {
            ncd:revise-date 2024-08-08 ;
          }

          presence "destination should be mandatory" ;
          leaf source {
            description 'The source IP of lag-bfd.' ;
            type ncd:ipv4-address-none-zero ;

            status obsolete ;

          }

          leaf destination {
            description 'The destination IP of lag-bfd.' ;
            type ncd:ipv4-address-none-zero ;

            mandatory true ;
            status obsolete ;

          }

          container time {
            description 'The time parameters of lag-bfd.' ;
            presence "min-tx and min-rx and multiplier should be mandatory" ;
            leaf min-tx {
              description 'The minimum send interval of lag-bfd, its minimum value and maximum value depend on the performance parameters.' ;
              type uint32 {
                range 1..65535 {
                  description 'The minimum value and maximum value depend on the performance parameters.' ;
                }

              }

              units millisecond ;
              mandatory true ;
              status obsolete ;

            }

            leaf min-rx {
              description 'The minimum receive interval of lag-bfd, its minimum value and maximum value depend on the performance parameters.' ;
              type uint32 {
                range 1..65535 {
                  description 'The minimum value and maximum value depend on the performance parameters.' ;
                }

              }

              units millisecond ;
              mandatory true ;
              status obsolete ;

            }

            leaf multiplier {
              description 'The detect multiplier of lag-bfd.' ;
              type uint8 {
                range 3..50 ;

              }

              mandatory true ;
              status obsolete ;

            }

            status obsolete ;

          }

          ncd:revise-date 2021-06-23 ;
        }

      }

      container local {
        description 'Describe the parameters of smartgroup and member port to be configured.' ;
        container smartgroups {
          description 'Describe the parameters of smartgroup to be configured.' ;
          list smartgroup {
            description 'Describe the parameters of smartgroup to be configured. The smartgroup interface is created and deleted by Interface Management.' ;
            key interface-name ;
            leaf interface-name {
              description 'The interface name of smartgroup.' ;
              type ncd:ifname ;

            }

            leaf bond-mode {
              description 'The bond mode of smartgroup. Smartgroup has two modes, on and 802.3ad.' ;
              type enumeration {
                enum on {
                  value 0 ;
                  description 'The aggregated mode is on.' ;
                }

                enum 802.3ad {
                  value 1 ;
                  description 'The aggregated mode is 802.3ad.' ;
                }

              }

              default on ;
            }

            leaf load-balance {
              description 'The load sharing strategy of smartgroup, its default value depends on the performance parameters.' ;
              type enumeration {
                enum dst-ip {
                  value 1 ;
                  description 'The load-balance mode is dst-ip.' ;
                }

                enum dst-mac {
                  value 2 ;
                  description 'The load-balance mode is dst-mac.' ;
                }

                enum src-dst-ip {
                  value 3 ;
                  description 'The load-balance mode is src-dst-ip.' ;
                }

                enum src-dst-mac {
                  value 4 ;
                  description 'The load-balance mode is src-dst-mac.' ;
                }

                enum src-ip {
                  value 5 ;
                  description 'The load-balance mode is src-ip.' ;
                }

                enum src-mac {
                  value 6 ;
                  description 'The load-balance mode is src-mac.' ;
                }

                enum src-port {
                  value 7 ;
                  description 'The load-balance mode is src-port.' ;
                }

                enum dst-port {
                  value 8 ;
                  description 'The load-balance mode is dst-port.' ;
                }

                enum src-dst-port {
                  value 9 ;
                  description 'The load-balance mode is src-dst-port.' ;
                }

                enum per-destination {
                  value 10 ;
                  description 'The load-balance mode is per-destination.' ;
                }

                enum per-packet {
                  value 11 ;
                  description 'The load-balance mode is per-packet.' ;
                }

                enum pri-label {
                  value 12 ;
                  description 'The load-balance mode is pri-label.' ;
                }

                enum pub-label {
                  value 13 ;
                  description 'The load-balance mode is pub-label.' ;
                }

                enum pub-pri-label {
                  value 14 ;
                  description 'The load-balance mode is pub-pri-label.' ;
                }

                enum vlan {
                  value 15 ;
                  description 'The load-balance mode is vlan.' ;
                }

                enum mac-vlan {
                  value 16 ;
                  description 'The load-balance mode is mac-vlan.' ;
                }

                enum intelligent-hash {
                  value 17 ;
                  description 'The load-balance mode is intelligent-hash.' ;
                }

                enum per-subinterface {
                  value 18 ;
                  description 'The load-balance mode is per-subinterface.' ;
                }

                enum dst-ip-dst-port {
                  value 19 ;
                  description 'The load-balance mode is dst-ip-dst-port.' ;
                }

                enum src-ip-src-port {
                  value 20 ;
                  description 'The load-balance mode is src-ip-src-port.' ;
                }

                enum src-dst-ip-src-dst-port {
                  value 21 ;
                  description 'The load-balance mode is src-dst-ip-src-dst-port.' ;
                }

                enum enhance {
                  value 24 ;
                  description 'The load-balance mode is enhance.' ;
                }

                enum dlb-flow-fixed {
                  value 25 ;
                  description 'The load-balance mode is dlb-flow-fixed.' ;
                }

                enum dlb-flow-timeout {
                  value 26 ;
                  description 'The load-balance mode is dlb-flow-timeout.' ;
                }

                enum dlb-packet {
                  value 27 ;
                  description 'The load-balance mode is dlb-packet.' ;
                }

                enum gtp {
                  value 28 ;
                  description 'The load-balance mode is gtp.' ;
                }

                enum src-dst-ip-src-dst-port-protocol {
                  value 29 ;
                  description 'The load-balance mode is src-dst-ip-src-dst-port-protocol.' ;
                }

              }

              default per-destination ;
            }

            leaf active-number {
              description 'The active number of smartgroup, its maximum value depends on the performance parameters.' ;
              type uint32 {
                range 1..1024 {
                  description 'The maximum value depends on the performance parameters.' ;
                }

              }

              default 1 ;
            }

            leaf active-limit {
              description 'The active limit of smartgroup, its maximum value and default value depend on the performance parameters.' ;
              type uint32 {
                range 0..1024 {
                  description 'The maximum value and default value depend on the performance parameters.' ;
                }

              }

              default 16 ;
            }

            leaf fast-respond {
              if-feature lacp-fast-respond ;

              description 'The fast respond of smartgroup. Only the value of bond-mode leaf is 802.3ad can this attribute be configured.' ;
              type empty ;

            }

            container restore {
              description 'The restore mode of smartgroup.' ;
              choice restore-choice {
                description 'The restore mode of smartgroup.' ;
                default immediately-case ;
                case revertive-case {
                  description 'The restore mode of smartgroup is revertive.' ;
                  leaf revertive {
                    description 'The restore mode of smartgroup is revertive.' ;
                    type empty ;

                    mandatory true ;
                  }

                  leaf restore-time {
                    description 'The revertive time of smartgroup.' ;
                    type uint32 {
                      range 1..65535 ;

                    }

                    units second ;
                    mandatory true ;
                  }

                }

                case immediately-case {
                  description 'The restore mode of smartgroup is immediately.' ;
                  leaf immediately {
                    description 'The restore mode of smartgroup is immediately.' ;
                    type empty ;

                  }

                }

                case non-revertive-case {
                  description 'The restore mode of smartgroup is non-revertive.' ;
                  leaf non-revertive {
                    description 'The restore mode of smartgroup is non-revertive.' ;
                    type empty ;

                  }

                }

              }

            }

            leaf smartgroup-priority {
              description 'The priority of smartgroup.' ;
              type uint16 {
                range 1..65535 ;

              }

              default 32768 ;
            }

            leaf agg-timeout {
              description 'The aggregator timeout of smartgroup.' ;
              type uint16 {
                range 10..500 ;

              }

              units second ;
              default 30 ;
            }

            leaf hold-off {
              description 'The hold-off time of smartgroup.' ;
              type uint32 {
                range 0..65535 ;

              }

              units second ;
              default 0 ;
            }

            container mclag {
              description 'Describe the parameters of MC-LAG to be configured.' ;
              container mclag-system {
                description 'Describe the parameters of MC-LAG system to be configured.' ;
                presence "system-id and system-priority should be mandatory" ;
                leaf system-id {
                  description 'The system MAC of MC-LAG.' ;
                  type ncd:mac-address ;

                  mandatory true ;
                }

                leaf system-priority {
                  description 'The system priority of MC-LAG.' ;
                  type uint16 {
                    range 1..65535 ;

                  }

                  mandatory true ;
                }

              }

              container mclag-roid {
                description 'Describe the parameters of MC-LAG identifier to be configured.' ;
                presence "roid should be mandatory" ;
                leaf roid {
                  description 'The roid of MC-LAG.' ;
                  type uint64 {
                    range 1..4294967293 ;

                  }

                  mandatory true ;
                }

                leaf node-id {
                  description 'The node id of MC-LAG.' ;
                  type uint32 {
                    range 0..7 ;

                  }

                  default 0 ;
                }

              }

              container mclag-iccp {
                description 'Describe the parameters of MC-LAG ICCP to be configured.' ;
                leaf iccp {
                  description 'The ICCP id of MC-LAG.' ;
                  type uint32 {
                    range 1..4294967293 ;

                  }

                }

              }

              container mclag-attr {
                description 'Describe the parameters of MC-LAG attributes to be configured.' ;
                leaf mode {
                  description 'The mode of MC-LAG. MC-LAG has three modes, auto and force-master and force-slave.' ;
                  type enumeration {
                    enum auto {
                      value 1 ;
                      description 'The MC-LAG mode is auto.' ;
                    }

                    enum force-master {
                      value 2 ;
                      description 'The MC-LAG mode is force-master.' ;
                    }

                    enum force-slave {
                      value 3 ;
                      description 'The MC-LAG mode is force-slave.' ;
                    }

                  }

                  default auto ;
                }

                leaf priority {
                  description 'The priority of MC-LAG.' ;
                  type uint32 {
                    range 1..65535 ;

                  }

                  default 32768 ;
                }

              }

              container mclag-track {
                status obsolete {
                  ncd:revise-date 2017-03-01 ;
                }

                description 'Describe the parameters of MC-LAG track to be configured.' ;
                presence "track-name and track-type should be mandatory" ;
                leaf track-name {
                  description 'The track name of MC-LAG.' ;
                  type string {
                    length 1..31 ;

                  }

                  mandatory true ;
                }

                leaf track-type {
                  description 'The track type of MC-LAG.' ;
                  type enumeration {
                    enum pw-type {
                      value 1 ;
                      description 'The track type of MC-LAG is pw-type.' ;
                    }

                  }

                  mandatory true ;
                }

              }

              container mclag-tracks {
                description 'Describe the parameters of MC-LAG track to be configured.' ;
                presence "track-type should be mandatory" ;
                list mclag-track {
                  description 'Describe the parameters of MC-LAG track to be configured.' ;
                  key track-name ;
                  leaf track-name {
                    description 'The track name of MC-LAG.' ;
                    type string {
                      length 1..31 ;

                    }

                  }

                  leaf track-type {
                    description 'The track type of MC-LAG.' ;
                    type enumeration {
                      enum pw-type {
                        value 1 ;
                        description 'The track type of MC-LAG is pw-type.' ;
                      }

                      enum peer-link-type {
                        value 2 ;
                        description 'The track type of MC-LAG is peer-link-type.' ;
                        status obsolete ;

                      }

                      enum peer-type {
                        value 3 ;
                        description 'The track type of MC-LAG is peer-type.' ;
                      }

                    }

                    mandatory true ;
                  }

                }

                ncd:revise-date 2017-03-01 ;
              }

              container mclag-multi-link-role {
                description 'Describe the parameters of MC-LAG multi-link-role to be configured.' ;
                leaf multi-link-role {
                  description 'The multi-link-role of MC-LAG.' ;
                  type enumeration {
                    enum master {
                      value 1 ;
                      description 'The MC-LAG multi-link-role is master.' ;
                    }

                    enum slave {
                      value 2 ;
                      description 'The MC-LAG multi-link-role is slave.' ;
                    }

                  }

                }

                ncd:revise-date 2018-01-08 ;
              }

              container mclag-receive-flag {
                status obsolete {
                  ncd:revise-date 2018-09-13 ;
                }

                description 'Describe the parameters of MC-LAG receive flag to be configured.' ;
                leaf receive-flag {
                  description 'The receive flag of MC-LAG.' ;
                  type empty ;

                }

                ncd:revise-date 2018-01-08 ;
              }

              container mclag-ip-use-global {
                if-feature mclag-ip-use-global ;

                description 'The IP address of MC-LAG uses the IP address configured globally.' ;
                leaf ip-use-global {
                  description 'The IP address of MC-LAG uses the IP address configured globally.' ;
                  type empty ;

                }

                ncd:revise-date 2020-04-24 ;
              }

              container mclag-ipv4-address {
                description 'Describe the parameters of MC-LAG IPv4 source and destination address to be configured.' ;
                presence "source-address and destination-address should be mandatory" ;
                leaf source-address {
                  description 'The IPv4 source address of MC-LAG.' ;
                  type ncd:ipv4-address ;

                  mandatory true ;
                }

                leaf destination-address {
                  description 'The IPv4 destination address of MC-LAG.' ;
                  type ncd:ipv4-address ;

                  mandatory true ;
                }

                container vrf {
                  description 'Describe the parameters of MC-LAG VRF name to be configured.' ;
                  choice vrf-choice {
                    description 'The VRF name of MC-LAG.' ;
                    case vrf-name-case {
                      description 'The VRF name of MC-LAG, whose name cannot be mng.' ;
                      leaf vrf-name {
                        description 'The VRF name of MC-LAG, whose name cannot be mng.' ;
                        type string {
                          length 1..32 ;

                        }

                      }

                    }

                    case vrf-mng-case {
                      description 'The VRF mng instance of MC-LAG.' ;
                      leaf vrf-mng {
                        description 'The VRF mng instance of MC-LAG.' ;
                        type empty ;

                      }

                    }

                  }

                }

                ncd:revise-date 2020-06-30 ;
              }

              container mclag-ipv6-address {
                description 'Describe the parameters of MC-LAG IPv6 source and destination address to be configured.' ;
                presence "source-address and destination-address should be mandatory" ;
                leaf source-address {
                  description 'The IPv6 source address of MC-LAG.' ;
                  type ncd:ipv6-address-none-zero ;

                  mandatory true ;
                }

                leaf destination-address {
                  description 'The IPv6 destination address of MC-LAG.' ;
                  type ncd:ipv6-address-none-zero ;

                  mandatory true ;
                }

                container vrf {
                  description 'Describe the parameters of MC-LAG VRF name to be configured.' ;
                  choice vrf-choice {
                    description 'The VRF name of MC-LAG.' ;
                    case vrf-name-case {
                      description 'The VRF name of MC-LAG, whose name cannot be mng.' ;
                      leaf vrf-name {
                        description 'The VRF name of MC-LAG, whose name cannot be mng.' ;
                        type string {
                          length 1..32 ;

                        }

                      }

                    }

                    case vrf-mng-case {
                      description 'The VRF mng instance of MC-LAG.' ;
                      leaf vrf-mng {
                        description 'The VRF mng instance of MC-LAG.' ;
                        type empty ;

                      }

                    }

                  }

                }

                ncd:revise-date 2020-06-30 ;
              }

            }

            leaf port-dispersion {
              description 'The port dispersion switch of smartgroup.' ;
              type enumeration {
                enum off {
                  value 0 ;
                  description 'Close the port dispersion switch.' ;
                }

                enum on {
                  value 1 ;
                  description 'Open the port dispersion switch.' ;
                }

              }

              default off ;
              ncd:revise-date 2016-03-28 ;
            }

            leaf negotiation-flag {
              description 'The negotiation flag of smartgroup.Only the value of bond-mode leaf is 802.3ad can this attribute be configured.' ;
              type uint8 {
                range 0..1 ;

              }

              default 0 ;
              if-feature negotiation-flag ;

              ncd:revise-date 2016-08-25 ;
            }

            leaf sd-detection {
              description 'The SD detection switch of smartgroup.' ;
              type enumeration {
                enum disable {
                  value 0 ;
                  description 'Close the SD detection switch.' ;
                }

                enum enable {
                  value 1 ;
                  description 'Open the SD detection switch.' ;
                }

              }

              default disable ;
              ncd:revise-date 2017-07-20 ;
            }

            leaf data-selector {
              description "The data receive mode of smartgroup's members. Smartgroup has two modes, selective and merging." ;
              type enumeration {
                enum selective {
                  value 0 ;
                  description 'Selective mode' ;
                }

                enum merging {
                  value 1 ;
                  description 'Merging mode' ;
                }

              }

              default selective ;
              ncd:revise-date 2018-09-13 ;
            }

            container protocol-packet {
              if-feature lacp-protocol-packet ;

              description 'The rule of the control plane sending protocol packet for smartgroup,its default value depends on the performance parameters.' ;
              choice protocol-packet-choice {
                description 'The rule of the control plane sending protocol packet for smartgroup,its default value depends on the performance parameters.' ;
                case load-balance-case {
                  description 'The rule of the control plane sending protocol packet for smartgroup is load balance mode.' ;
                  leaf load-balance {
                    description 'The rule of the control plane sending protocol packet for smartgroup is load balance mode.' ;
                    type empty ;

                    mandatory true ;
                  }

                  leaf mode {
                    description 'The load sharing strategy of smartgroup, its default value depends on the performance parameters.' ;
                    type enumeration {
                      enum per-destination {
                        value 10 ;
                        description 'The load-balance mode is per-destination.' ;
                      }

                      enum per-packet {
                        value 11 ;
                        description 'The load-balance mode is per-packet.' ;
                      }

                    }

                    mandatory true ;
                  }

                }

                case random-case {
                  description 'The rule of the control plane sending protocol packet for smartgroup is random selection.' ;
                  leaf random {
                    description 'The rule of the control plane sending protocol packet for smartgroup is random selection.' ;
                    type empty ;

                  }

                }

                case ip-fixed-case {
                  description 'The rule of the control plane sending protocol packet for smartgroup is fixed selection by destination.' ;
                  leaf ip-fixed {
                    description 'The rule of the control plane sending protocol packet for smartgroup is fixed selection by destination.' ;
                    type empty ;

                  }

                }

              }

              ncd:revise-date 2020-01-02 ;
            }

            leaf fsm-mode {
              description 'The finite state machine mode of smartgroup. Smartgroup has two modes, normal and fast. Its default value which is between [normal,fast] and generally normal, depends on product specification.' ;
              type enumeration {
                enum normal {
                  value 0 ;
                  description 'The finite state machine mode of smartgroup is normal.' ;
                }

                enum fast {
                  value 1 ;
                  description 'The finite state machine mode of smartgroup is fast.' ;
                }

              }

              ncd:revise-date 2020-06-30 ;
            }

            leaf speed-reassign {
              description 'The speed field reassignment of smartgroup.' ;
              type enumeration {
                enum disable {
                  value 0 ;
                  description 'The speed field reassignment of smartgroup is disable.' ;
                }

                enum enable {
                  value 1 ;
                  description 'The speed field reassignment of smartgroup is enable.' ;
                }

              }

              default disable ;
              ncd:revise-date 2020-06-30 ;
            }

            container lag-bfd {
              description 'The lag-bfd of smartgroup.' ;
              presence "destination should be mandatory" ;
              leaf source {
                description 'The source IP of lag-bfd.' ;
                type ncd:ipv4-address-none-zero ;

              }

              leaf destination {
                description 'The destination IP of lag-bfd.' ;
                type ncd:ipv4-address-none-zero ;

                mandatory true ;
              }

              container time-type {
                description 'The time or template parameters of lag-bfd.' ;
                choice time-type-choice {
                  description 'The time or template parameters of lag-bfd.' ;
                  case time-case {
                    description 'The time parameters of lag-bfd.' ;
                    container time {
                      description 'The time parameters of lag-bfd.' ;
                      presence "min-tx and min-rx and multiplier should be mandatory" ;
                      leaf min-tx {
                        description 'The minimum send interval of lag-bfd, its minimum value and maximum value depend on the performance parameters.' ;
                        type uint32 {
                          range 1..65535 ;

                        }

                        units millisecond ;
                        mandatory true ;
                      }

                      leaf min-rx {
                        description 'The minimum receive interval of lag-bfd, its minimum value and maximum value depend on the performance parameters.' ;
                        type uint32 {
                          range 1..65535 ;

                        }

                        units millisecond ;
                        mandatory true ;
                      }

                      leaf multiplier {
                        description 'The detect multiplier of lag-bfd.' ;
                        type uint8 {
                          range 3..50 ;

                        }

                        mandatory true ;
                      }

                    }

                  }

                  case template-case {
                    description 'The template parameters of lag-bfd.' ;
                    leaf template {
                      description 'The template parameters of lag-bfd.' ;
                      type string {
                        length 1..31 ;

                      }

                    }

                  }

                }

              }

              ncd:revise-date 2020-08-31 ;
            }

            container lag-bfd-ipv6 {
              description 'The lag-bfd ipv6 of smartgroup.' ;
              presence "destination should be mandatory" ;
              leaf source {
                description 'The source IP of lag-bfd ipv6.' ;
                type ncd:ipv6-address-none-zero ;

              }

              leaf destination {
                description 'The destination IP of lag-bfd ipv6.' ;
                type ncd:ipv6-address-none-zero ;

                mandatory true ;
              }

              container time-type {
                description 'The time or template parameters of lag-bfd ipv6.' ;
                choice time-type-choice {
                  description 'The time or template parameters of lag-bfd ipv6.' ;
                  case time-case {
                    description 'The time parameters of lag-bfd ipv6.' ;
                    container time {
                      description 'The time parameters of lag-bfd ipv6.' ;
                      presence "min-tx and min-rx and multiplier should be mandatory" ;
                      leaf min-tx {
                        description 'The minimum send interval of lag-bfd ipv6, its minimum value and maximum value depend on the performance parameters.' ;
                        type uint32 {
                          range 1..65535 {
                            description 'The minimum value and maximum value depend on the performance parameters.' ;
                          }

                        }

                        units millisecond ;
                        mandatory true ;
                      }

                      leaf min-rx {
                        description 'The minimum receive interval of lag-bfd ipv6, its minimum value and maximum value depend on the performance parameters.' ;
                        type uint32 {
                          range 1..65535 {
                            description 'The minimum value and maximum value depend on the performance parameters.' ;
                          }

                        }

                        units millisecond ;
                        mandatory true ;
                      }

                      leaf multiplier {
                        description 'The detect multiplier of lag-bfd ipv6.' ;
                        type uint8 {
                          range 3..50 ;

                        }

                        mandatory true ;
                      }

                    }

                  }

                  case template-case {
                    description 'The template parameters of lag-bfd ipv6.' ;
                    leaf template {
                      description 'The template parameters of lag-bfd ipv6.' ;
                      type string {
                        length 1..31 ;

                      }

                    }

                  }

                }

              }

              ncd:revise-date 2020-08-31 ;
            }

            leaf admin-status-linkage {
              description 'The admin status linkage switch of smartgroup, its default value depends on the performance parameters.' ;
              type enumeration {
                enum disable {
                  value 0 ;
                  description 'Disable admin status linkage.' ;
                }

                enum enable {
                  value 1 ;
                  description 'Enable admin status linkage.' ;
                }

              }

              default disable ;
              ncd:revise-date 2020-09-09 ;
            }

            leaf smartgroup-constant-up {
              description 'The protocol constant up flag of smartgroup.' ;
              type empty ;

              ncd:revise-date 2020-09-15 ;
            }

            leaf smartgroup-preferred-up {
              type empty ;

              description 'The protocol preferred up flag of smartgroup.' ;
              if-feature smartgroup-preferred-up ;

              ncd:revise-date 2024-12-09 ;
            }

            container preempt {
              description 'The preempt parameter of smartgroup.' ;
              leaf switch {
                description 'The preempt switch of smartgroup.' ;
                type enumeration {
                  enum disable {
                    value 0 ;
                    description 'The preempt switch of smartgroup is disable.' ;
                  }

                  enum enable {
                    value 1 ;
                    description 'The preempt switch of smartgroup is enable.' ;
                  }

                }

                default enable ;
              }

              leaf delay-time {
                description 'The preempt delay time of smartgroup.' ;
                type uint32 {
                  range 0..180 ;

                }

                units second ;
                default 0 ;
              }

              ncd:revise-date 2020-10-12 ;
            }

            leaf delay-down-time {
              description 'The delay down time of smartgroup. Its default value which is between 0-180 and generally 0, depends on product specification.' ;
              type uint32 {
                range 0..180 ;

              }

              units second ;
              ncd:revise-date 2020-12-28 ;
            }

            leaf system-mac {
              description 'The system MAC of smartgroup.' ;
              type ncd:mac-address-none-zero ;

              ncd:revise-date 2021-04-20 ;
            }

            leaf node-id {
              description 'The node ID of smartgroup.' ;
              type uint32 {
                range 0..7 ;

              }

              default 0 ;
              ncd:revise-date 2021-04-20 ;
            }

            leaf port-key {
              description 'The port key of smartgroup.' ;
              type uint16 {
                range 1..65535 ;

              }

              ncd:revise-date 2021-07-12 ;
            }

            leaf port-selection {
              type enumeration {
                enum speed {
                  description 'Port selection based on speed.' ;
                  value 1 ;
                }

              }

              description 'The port selection of smartgroup.' ;
              if-feature port-selection ;

              ncd:revise-date 2023-12-01 ;
            }

            leaf monitor-esi-df-election {
              type enumeration {
                enum enable {
                  value 1 ;
                  description 'Enable monitor ESI DF election.' ;
                }

                enum disable {
                  value 0 ;
                  description 'Disable monitor ESI DF election.' ;
                }

              }

              description 'The monitor ESI DF election of smartgroup.' ;
              default disable ;
              if-feature monitor-esi-df-election ;

              ncd:revise-date 2024-04-03 ;
            }

            container load-balance-factor {
              leaf src-ip {
                type empty ;

                description 'The IP address of the sending host or device.' ;
              }

              leaf dst-ip {
                type empty ;

                description 'The IP address of the receiving host or device.' ;
              }

              leaf l3-protocol {
                type empty ;

                description 'The transport layer protocol type.' ;
              }

              leaf src-port {
                type empty ;

                description 'The port number used by the application sending the packets.' ;
              }

              leaf dst-port {
                type empty ;

                description ' The port number used by the application receiving the packets.' ;
              }

              leaf src-mac {
                type empty ;

                description 'The MAC address of the sending host or device.' ;
              }

              leaf dst-mac {
                type empty ;

                description 'The MAC address of the receiving host or device.' ;
              }

              leaf outer-vlan {
                type empty ;

                description 'The outer vlan id of the receiving packet.' ;
              }

              description 'The load balance factor of smartgroup.' ;
              if-feature lacp-load-balance-factor ;

              ncd:revise-date 2024-08-09 ;
            }

            leaf state-dampening {
              type enumeration {
                enum enable {
                  value 1 ;
                  description 'Enable state dampening.' ;
                }

                enum disable {
                  value 0 ;
                  description 'Disable state dampening.' ;
                }

              }

              description 'The state dampening switch of smartgroup.' ;
              default disable ;
              ncd:revise-date 2024-11-25 ;
            }

            leaf lag-bfd-state-linkage {
              type enumeration {
                enum disable {
                  description 'Disable LAG BFD state linkage.' ;
                  value 0 ;
                }

                enum enable {
                  description 'Enable LAG BFD state linkage.' ;
                }

              }

              description 'LAG BFD state linkage.' ;
              default disable ;
              ncd:revise-date 2025-04-08 ;
            }

          }

        }

        container ports {
          description 'Describe the parameters of member port to be configured.' ;
          list port {
            description 'Describe the parameters of member port to be configured.' ;
            key interface-name ;
            leaf interface-name {
              description 'The interface name of member port.' ;
              type ncd:ifname ;

            }

            leaf smartgroup-id {
              description 'The group id bound by member port, its maximum value depends on the performance parameters.' ;
              type uint32 {
                range 1..99999999 {
                  description 'The maximum value depends on the performance parameters.
The minimum value(the second range) depends on the performance parameters.' ;
                }

              }

              mandatory true ;
            }

            leaf mode {
              description 'The bind mode of member port. Member port has three bind modes, on and passive and active.' ;
              type enumeration {
                enum passive {
                  value 1 ;
                  description 'The bind mode is passive.' ;
                }

                enum on {
                  value 2 ;
                  description 'The bind mode is on.' ;
                }

                enum active {
                  value 3 ;
                  description 'The bind mode is active.' ;
                }

              }

              mandatory true ;
            }

            leaf port-priority {
              description 'The priority of member port.' ;
              type uint16 {
                range 1..65535 ;

              }

              default 32768 ;
            }

            leaf timeout {
              description 'The timeout type of member port. Timeout has two types, long and short.' ;
              type enumeration {
                enum long {
                  value 0 ;
                  description 'The time-out type is long.' ;
                }

                enum short {
                  value 1 ;
                  description 'The time-out type is short.' ;
                }

              }

              default long ;
            }

            leaf back-up {
              description 'The backup attribute of member port. Only the value of bond-mode leaf is on can this attribute be configured.' ;
              type empty ;

            }

            leaf track {
              description 'The track name of member port.' ;
              type string {
                length 1..31 ;

              }

            }

            container lag-bfd {
              description 'The lag-bfd of member port.' ;
              presence "destination should be mandatory" ;
              leaf source {
                description 'The source IP of lag-bfd.' ;
                type ncd:ipv4-address-none-zero ;

              }

              leaf destination {
                description 'The destination IP of lag-bfd.' ;
                type ncd:ipv4-address-none-zero ;

                mandatory true ;
              }

              choice time-type-choice {
                description 'The time or template parameters of lag-bfd.' ;
                case time-case {
                  description 'The time parameters of lag-bfd.' ;
                  container time {
                    description 'The time parameters of lag-bfd.' ;
                    presence "min-tx and min-rx and multiplier should be mandatory" ;
                    leaf min-tx {
                      description 'The minimum send interval of lag-bfd, its minimum value and maximum value depend on the performance parameters.' ;
                      type uint32 {
                        range 1..65535 {
                          description 'The minimum value and maximum value depend on the performance parameters.' ;
                        }

                      }

                      units millisecond ;
                      mandatory true ;
                    }

                    leaf min-rx {
                      description 'The minimum receive interval of lag-bfd, its minimum value and maximum value depend on the performance parameters.' ;
                      type uint32 {
                        range 1..65535 {
                          description 'The minimum value and maximum value depend on the performance parameters.' ;
                        }

                      }

                      units millisecond ;
                      mandatory true ;
                    }

                    leaf multiplier {
                      description 'The detect multiplier of lag-bfd.' ;
                      type uint8 {
                        range 3..50 ;

                      }

                      mandatory true ;
                    }

                  }

                }

                case template-case {
                  description 'The template parameters of lag-bfd.' ;
                  leaf template {
                    description 'The template parameters of lag-bfd.' ;
                    type string {
                      length 1..31 ;

                    }

                  }

                  ncd:revise-date 2020-08-31 ;
                }

              }

              container discriminator {
                description 'The discriminator of lag-bfd.' ;
                presence "ld and rd should be mandatory" ;
                leaf ld {
                  description 'The local discriminator of lag-bfd. Its default range 1-4294967295, depends on product specification.' ;
                  type uint32 {
                    range 1..4294967295 ;

                  }

                  mandatory true ;
                }

                leaf rd {
                  description 'The remote discriminator of lag-bfd.' ;
                  type uint32 {
                    range 1..4294967295 ;

                  }

                  mandatory true ;
                }

                ncd:revise-date 2022-06-30 ;
              }

            }

            leaf negotiation-mac {
              description 'The negotiation MAC of member port.Only the value of bond-mode leaf is 802.3ad can this attribute be configured.' ;
              type ncd:mac-address-none-zero ;

              ncd:revise-date 2016-09-19 ;
            }

            leaf unconditional-active {
              description 'The unconditional active flag of member port.Only the value of bond-mode leaf is 802.3ad can this attribute be configured.' ;
              type empty ;

              ncd:revise-date 2016-10-10 ;
            }

            leaf description {
              description 'Member port description.' ;
              type ncd:string-with-blank {
                length 1..64 ;

              }

              ncd:revise-date 2020-06-19 ;
            }

            container lag-bfd-ipv6 {
              description 'The lag-bfd ipv6 of member port.' ;
              presence "destination should be mandatory" ;
              leaf source {
                description 'The source IP of lag-bfd ipv6.' ;
                type ncd:ipv6-address-none-zero ;

              }

              leaf destination {
                description 'The destination IP of lag-bfd ipv6.' ;
                type ncd:ipv6-address-none-zero ;

                mandatory true ;
              }

              container time-type {
                description 'The time or template parameters of lag-bfd ipv6.' ;
                choice time-type-choice {
                  description 'The time or template parameters of lag-bfd ipv6.' ;
                  case time-case {
                    description 'The time parameters of lag-bfd ipv6.' ;
                    container time {
                      description 'The time parameters of lag-bfd ipv6.' ;
                      presence "min-tx and min-rx and multiplier should be mandatory" ;
                      leaf min-tx {
                        description 'The minimum send interval of lag-bfd ipv6, its minimum value and maximum value depend on the performance parameters.' ;
                        type uint32 {
                          range 1..65535 {
                            description 'The minimum value and maximum value depend on the performance parameters.' ;
                          }

                        }

                        units millisecond ;
                        mandatory true ;
                      }

                      leaf min-rx {
                        description 'The minimum receive interval of lag-bfd ipv6, its minimum value and maximum value depend on the performance parameters.' ;
                        type uint32 {
                          range 1..65535 {
                            description 'The minimum value and maximum value depend on the performance parameters.' ;
                          }

                        }

                        units millisecond ;
                        mandatory true ;
                      }

                      leaf multiplier {
                        description 'The detect multiplier of lag-bfd ipv6.' ;
                        type uint8 {
                          range 3..50 ;

                        }

                        mandatory true ;
                      }

                    }

                  }

                  case template-case {
                    description 'The template parameters of lag-bfd ipv6.' ;
                    leaf template {
                      description 'The template parameters of lag-bfd ipv6.' ;
                      type string {
                        length 1..31 ;

                      }

                    }

                  }

                }

              }

              container discriminator {
                description 'The discriminator of lag-bfd ipv6.' ;
                presence "ld and rd should be mandatory" ;
                leaf ld {
                  description 'The local discriminator of lag-bfd ipv6. Its default range 1-4294967295, depends on product specification.' ;
                  type uint32 {
                    range 1..4294967295 ;

                  }

                  mandatory true ;
                }

                leaf rd {
                  description 'The remote discriminator of lag-bfd ipv6.' ;
                  type uint32 ;

                  mandatory true ;
                }

                ncd:revise-date 2022-06-30 ;
              }

              ncd:revise-date 2020-08-31 ;
            }

            leaf multi-backup {
              description 'The multi-backup attribute of member port.' ;
              type empty ;

              ncd:revise-date 2021-05-10 ;
            }

            leaf short-timeout-time {
              units second ;
              description 'The short timeout time of member port.' ;
              type uint32 {
                range 3..90 ;

              }

              default 3 ;
              ncd:revise-date 2021-10-08 ;
            }

            container lag-bfd-to-satellite {
              if-feature lag-bfd-to-satellite {
                ncd:revise-date 2024-04-08 ;
              }

              description 'The lag-bfd to-satellite of member port.' ;
              presence lag-bfd-to-satellite ;
              choice time-type-choice {
                description 'The time or template parameters of lag-bfd to-satellite.' ;
                case time-case {
                  description 'The time parameters of lag-bfd to-satellite.' ;
                  container time {
                    description 'The time parameters of lag-bfd to-satellite.' ;
                    presence "min-tx and min-rx and multiplier should be mandatory" ;
                    leaf min-tx {
                      description 'The minimum send interval of lag-bfd to-satellite, its minimum value and maximum value depend on the performance parameters.' ;
                      type uint32 {
                        range 1..65535 {
                          description 'The minimum value and maximum value depend on the performance parameters.' ;
                        }

                      }

                      units millisecond ;
                      mandatory true ;
                    }

                    leaf min-rx {
                      description 'The minimum receive interval of lag-bfd to-satellite, its minimum value and maximum value depend on the performance parameters.' ;
                      type uint32 {
                        range 1..65535 {
                          description 'The minimum value and maximum value depend on the performance parameters.' ;
                        }

                      }

                      units millisecond ;
                      mandatory true ;
                    }

                    leaf multiplier {
                      description 'The detect multiplier of lag-bfd to-satellite.' ;
                      type uint8 {
                        range 3..50 ;

                      }

                      mandatory true ;
                    }

                  }

                }

                case template-case {
                  description 'The template parameters of lag-bfd to-satellite.' ;
                  leaf template {
                    description 'The template parameters of lag-bfd to-satellite.' ;
                    type string {
                      length 1..31 ;

                    }

                  }

                }

              }

            }

          }

        }

      }

      container peer-link {
        description 'Describe the peer-link interface to be configured.' ;
        leaf interface-name {
          description 'The interface name of peer-link.' ;
          type ncd:ifname ;

        }

        leaf auto-mapping-vxlan {
          description 'Auto mapping VXLAN.' ;
          type empty ;

          if-feature auto-mapping-vxlan ;

          ncd:revise-date 2023-08-03 ;
        }

        ncd:revise-date 2017-07-12 ;
      }

    }

  }

  container state {
    config false ;
    description 'Describe the state of Link Aggregation Control Protocol.' ;
    container lacp {
      description 'Describe the state of LACP.' ;
      list smartgroup {
        description 'Describe the state of smartgroup.' ;
        key interface-name ;
        leaf interface-name {
          description 'The interface name of smartgroup.' ;
          type ncd:ifname ;

        }

        leaf mac {
          description 'The MAC of smartgroup.' ;
          type ncd:mac-address ;

        }

        leaf enable-mclag {
          description 'Is MC-LAG enabled by smartgroup.' ;
          type enumeration {
            enum enable {
              value 1 ;
              description 'The smartgroup has enabled MC-LAG.' ;
            }

            enum disable {
              value 2 ;
              description 'The smartgroup has not enabled MC-LAG.' ;
            }

          }

        }

        leaf protect-state {
          description 'The protect state of smartgroup.' ;
          type enumeration {
            enum "non-m/s-relation" {
              value 0 ;
              description 'Non master/slave relation.' ;
            }

            enum "m/s-relation" {
              value 1 ;
              description 'Master/slave relation.' ;
            }

            enum waiting-recovery {
              value 2 ;
              description 'Waiting for recovery.' ;
            }

            enum non-recovery {
              value 3 ;
              description 'Non recovery.' ;
            }

            enum master-signal-failure {
              value 4 ;
              description 'Master signal failure.' ;
            }

            enum slave-signal-failure {
              value 5 ;
              description 'Slave signal failure.' ;
            }

          }

          ncd:revise-date 2018-01-08 ;
        }

      }

      list port {
        description 'Describe the state of member port.' ;
        key interface-name ;
        leaf interface-name {
          description 'The interface name of member port.' ;
          type ncd:ifname ;

        }

        leaf smartgroup-id {
          description 'The group id bound by member port.' ;
          type uint32 ;

        }

        leaf actor-oper-key {
          description 'The actor operate key of member port.' ;
          type uint32 ;

        }

        leaf actor-oper-state {
          description 'The actor operate state of member port.' ;
          type uint32 ;

        }

        leaf partner-oper-key {
          description 'The partner operate key of member port.' ;
          type uint32 ;

        }

        leaf partner-oper-state {
          description 'The partner operate state of member port.' ;
          type uint32 ;

        }

        leaf partner-port-priority {
          description 'The partner port priority of member port.' ;
          type uint32 ;

        }

        leaf lacp-state {
          description 'The LACP port state of member port. LACP has two port states, active and inactive.' ;
          type enumeration {
            enum inactive {
              value 1 ;
              description 'The LACP port state is inactive.' ;
            }

            enum active {
              value 2 ;
              description 'The LACP port state is active.' ;
            }

          }

        }

        leaf partner-system-priority {
          description 'The partner system priority of member port.' ;
          type uint32 ;

        }

        leaf partner-system-mac {
          description 'The partner system MAC of member port.' ;
          type ncd:mac-address ;

        }

      }

      list mclag {
        description 'Describe the state of MC-LAG.' ;
        key interface-name ;
        leaf interface-name {
          description 'The interface name of smartgroup.' ;
          type ncd:ifname ;

        }

        leaf actor-roid {
          description 'The actor roid of MC-LAG.' ;
          type uint64 ;

          ncd:revise-date 2020-06-30 ;
        }

        leaf actor-node-id {
          description 'The actor node id of MC-LAG.' ;
          type uint32 ;

          ncd:revise-date 2020-06-30 ;
        }

        leaf actor-back-up {
          description 'The actor backup attribute of MC-LAG.' ;
          type enumeration {
            enum disable {
              value 1 ;
              description 'The MC-LAG actor has not configured backup attribute.' ;
            }

            enum enable {
              value 2 ;
              description 'The MC-LAG actor has configured backup attribute.' ;
            }

          }

        }

        leaf partner-system-mac {
          description 'The partner system MAC of MC-LAG.' ;
          type ncd:mac-address ;

        }

        leaf partner-system-priority {
          description 'The partner system priority of MC-LAG.' ;
          type uint32 ;

        }

        leaf partner-priority {
          description 'The partner priority of MC-LAG.' ;
          type uint32 ;

        }

        leaf partner-roid {
          description 'The partner roid of MC-LAG.' ;
          type uint64 ;

        }

        leaf parnter-node-id {
          description 'The partner node id of MC-LAG.' ;
          type uint32 ;

        }

        leaf work-mode {
          description 'The work mode of MC-LAG. Only the smartgroup with 802.3ad is effective.' ;
          type enumeration {
            enum none {
              value 0 ;
              description 'None mode' ;
            }

            enum auto {
              value 1 ;
              description 'Auto mode' ;
            }

            enum force-master {
              value 2 ;
              description 'Force-master mode' ;
            }

            enum force-backup {
              value 3 ;
              description 'Force-backup mode' ;
            }

            enum na {
              value 4 ;
              description 'Invalid mode' ;
            }

          }

          ncd:revise-date 2018-11-20 ;
        }

        leaf state {
          description 'The state of MC-LAG.' ;
          type enumeration {
            enum none {
              value 0 ;
              description 'The MC-LAG has not been established.' ;
            }

            enum ms {
              value 1 ;
              description 'The MC-LAG is in master and slave state.' ;
            }

            enum ms-nonRevertive {
              value 2 ;
              description 'The MC-LAG is in master and slave state, but cannot be revertive.' ;
            }

            enum ms-wtr {
              value 3 ;
              description 'The MC-LAG is in master and slave state, and is waiting for recovery.' ;
            }

            enum ms-continueToWtr {
              value 4 ;
              description 'The MC-LAG is in master and slave state, but needs to continue to wait for recovery.' ;
            }

            enum ms-manualSwitch {
              value 5 ;
              description 'The MC-LAG is in master and slave state, but is also in manual switch state.' ;
            }

            enum load-sharing {
              value 6 ;
              description 'The MC-LAG is in load-sharing state.' ;
            }

            enum abnormal {
              value 7 ;
              description 'The MC-LAG is in abnormal state.' ;
            }

            enum peer-unknown {
              value 8 ;
              description 'The MC-LAG is interrupted and cannot get peer information.' ;
            }

          }

          ncd:revise-date 2018-11-20 ;
        }

        leaf actor-smartgroup-state {
          description 'The actor smartgroup state of MC-LAG.' ;
          type enumeration {
            enum down {
              value 0 ;
              description 'The state is down.' ;
            }

            enum up {
              value 1 ;
              description 'The state is up.' ;
            }

          }

          ncd:revise-date 2018-11-20 ;
        }

        leaf partner-smartgroup-state {
          description 'The partner smartgroup state of MC-LAG.' ;
          type enumeration {
            enum down {
              value 0 ;
              description 'The state is down.' ;
            }

            enum up {
              value 1 ;
              description 'The state is up.' ;
            }

            enum unknown {
              value 2 ;
              description 'The state is unknown.' ;
            }

          }

          ncd:revise-date 2018-11-20 ;
        }

      }

      list member {
        description 'Describe the member port information of smartgroup.' ;
        key interface-name ;
        leaf interface-name {
          description 'The interface name of smartgroup.' ;
          type ncd:ifname ;

        }

        container ports {
          description 'Describe the information of member port.' ;
          list port {
            description 'Describe the information of member port.' ;
            key port-name ;
            leaf port-name {
              description 'The interface name of member port.' ;
              type ncd:ifname ;

            }

            leaf port-state {
              description 'The state of member port. LACP has two port states, active and inactive.' ;
              type enumeration {
                enum inactive {
                  value 1 ;
                  description 'The LACP port state is inactive.' ;
                }

                enum active {
                  value 2 ;
                  description 'The LACP port state is active.' ;
                }

              }

            }

            leaf port-mode {
              description 'The mode of member port.' ;
              type enumeration {
                enum passive {
                  value 1 ;
                  description 'The port mode is passive.' ;
                }

                enum on {
                  value 2 ;
                  description 'The port mode is on.' ;
                }

                enum active {
                  value 3 ;
                  description 'The port mode is active.' ;
                }

              }

              ncd:revise-date 2021-07-16 ;
            }

            leaf ptx-state {
              description 'The periodic transmission machine state of member port.' ;
              type enumeration {
                enum no-periodic {
                  value 1 ;
                  description 'Periodic transmissions are disabled.' ;
                }

                enum fast-periodic {
                  value 2 ;
                  description 'Periodic transmissions are enabled at a fast transmission rate.' ;
                }

                enum slow-periodic {
                  value 3 ;
                  description 'Periodic transmissions are enabled at a slow transmission rate.' ;
                }

                enum periodic-tx {
                  value 4 ;
                  description 'Transitory state entered on periodic timer expiry.' ;
                }

              }

              ncd:revise-date 2021-07-16 ;
            }

            leaf agg-state {
              description 'The aggregation state of member port.' ;
              type enumeration {
                enum active {
                  value 0 ;
                  description 'The LACP port aggregation state is active.' ;
                }

                enum inactive {
                  value 1 ;
                  description 'The LACP port aggregation state is inactive.' ;
                }

                enum loop {
                  value 2 ;
                  description 'The LACP port aggregation state is loop.' ;
                }

              }

              ncd:revise-date 2021-07-16 ;
            }

            leaf periodic-time {
              description 'The number of seconds between periodic transmissions of member port.' ;
              type uint16 ;

              units second ;
              ncd:revise-date 2021-07-16 ;
            }

            leaf port-priority {
              description 'The port priority of member port.' ;
              type uint16 ;

              ncd:revise-date 2021-07-16 ;
            }

            leaf oper-key {
              description 'The operational key of member port.' ;
              type uint16 ;

              ncd:revise-date 2021-07-16 ;
            }

            leaf oper-state {
              description 'The operational state of member port.' ;
              type uint8 ;

              ncd:revise-date 2021-07-16 ;
            }

            leaf rx-state {
              description 'The receive machine state of member port.' ;
              type enumeration {
                enum initialize {
                  value 1 ;
                  description 'The LACP port receive machine state is initialize.' ;
                }

                enum port-disabled {
                  value 2 ;
                  description 'The LACP port receive machine state is port disabled.' ;
                }

                enum lacp-disabled {
                  value 3 ;
                  description 'The LACP port receive machine state is LACP disabled.' ;
                }

                enum expired {
                  value 4 ;
                  description 'The LACP port receive machine state is expired.' ;
                }

                enum defaulted {
                  value 5 ;
                  description 'The LACP port receive machine state is defaulted.' ;
                }

                enum current {
                  value 6 ;
                  description 'The LACP port receive machine state is current.' ;
                }

              }

              ncd:revise-date 2021-07-16 ;
            }

            leaf mux-state {
              description 'The mux state of member port.' ;
              type enumeration {
                enum detached {
                  value 1 ;
                  description 'The LACP port mux machine state is detached.' ;
                }

                enum waiting {
                  value 2 ;
                  description 'The LACP port mux machine state is waiting.' ;
                }

                enum attached {
                  value 3 ;
                  description 'The LACP port mux machine state is attached.' ;
                }

                enum collecting {
                  value 4 ;
                  description 'The LACP port mux machine state is collecting.' ;
                }

                enum distributing {
                  value 5 ;
                  description 'The LACP port mux machine state is distributing.' ;
                }

                enum collecting-distributing {
                  value 6 ;
                  description 'The LACP port mux machine state is collecting and distributing.' ;
                }

              }

              ncd:revise-date 2021-07-16 ;
            }

          }

        }

        ncd:revise-date 2016-11-16 ;
      }

    }

  }

  container operation {
    config false ;
    description 'Describe the operation of Link Aggregation Control Protocol.' ;
    container lacp {
      description 'Describe the operation of LACP.' ;
      container clear {
        description 'Clear the packet count.' ;
        choice clear-choice {
          description 'Clear the packet count.' ;
          case group-id-case {
            description 'Clear the packet count of smartgroup.' ;
            leaf group-id {
              description 'Clear the packet count of smartgroup, its maximum value depends on the performance parameters.' ;
              type uint32 {
                range 1..99999999 {
                  description 'The maximum value depends on the performance parameters.
The minimum value(the second range) depends on the performance parameters.' ;
                }

              }

            }

          }

          case all-case {
            description 'Clear the packet count of all smartgroups.' ;
            leaf all {
              description 'Clear the packet count of all smartgroups.' ;
              type empty ;

            }

          }

        }

      }

      container forceswitch {
        description 'The force swith operation of smartgroup.' ;
        leaf interface-name {
          description 'The interface name of smartgroup.' ;
          type ncd:ifname ;

        }

      }

    }

  }

}
