module zxr10-pki {
  namespace "http://www.zte.com.cn/zxr10/netconf/schema/rosng/pki" ;
  prefix pki ;
  yang-version 1 ;
  import zxr10-netconf-defs {
    prefix ncd ;
  }

  organization "ZTE Corporation" ;
  contact "ZTE Corporation  
     Nanjing Institute of ZTE Corporation 
     No.68 Zijinghua Rd. Yuhuatai District, Nanjing, China 
     Tel: +86-25-52870000" ;
  description 'The netconf module to describe PKI.' ;
  revision 2023-07-27 {
    description 'Initial version.' ;
  }

  container configuration {
    description 'Configuration model info.' ;
    container pki {
      description 'PKI configuration.' ;
      container profile {
        description 'Configure PKI profile parameters.' ;
        list profile {
          description 'Configure PKI profile parameters' ;
          key profile-name ;
          leaf profile-name {
            description 'Profile name for PKI profile.' ;
            type string {
              length 1..31 {
                description 'Profile name for PKI profile.' ;
              }

            }

          }

        }

      }

    }

  }

  container state {
    config false ;
    description 'PKI state information.' ;
    container pki {
      container pki-ca-cert {
        list pki-ca-cert {
          key pki-profile-name ;
          leaf pki-profile-name {
            description 'The PKI profile name of ca certificate' ;
            type string {
              length 0..31 ;

            }

          }

          leaf version {
            description 'The version of ca certificate' ;
            type string {
              length 0..12 ;

            }

          }

          leaf serial-number {
            description 'The serial number of ca certificate' ;
            type string {
              length 0..72 ;

            }

          }

          leaf signature-algorithm {
            description 'The signature algorithm of ca certificate' ;
            type string {
              length 0..36 ;

            }

          }

          leaf issuer {
            description 'The issuer name of ca certificate' ;
            type string {
              length 0..200 ;

            }

          }

          leaf validity-not-before {
            description 'The starting validity time of ca certificate' ;
            type string {
              length 0..30 ;

            }

          }

          leaf validity-not-after {
            description 'The last validity time of ca certificate' ;
            type string {
              length 0..30 ;

            }

          }

          leaf subject {
            description 'The subject name of ca certificate' ;
            type string {
              length 0..200 ;

            }

          }

          leaf public-key-algorithm {
            description 'The public key algorithm of ca certificate' ;
            type string {
              length 0..36 ;

            }

          }

          leaf subject-public-key-info {
            description 'The public key algorithm information of ca certificate' ;
            type string {
              length 0..36 ;

            }

          }

          leaf x509v3-basic-constraints {
            description 'The basic constraints of ca certificate' ;
            type string {
              length 0..30 ;

            }

          }

          leaf x509v3-key-usage {
            description 'The key usage of ca certificate' ;
            type string {
              length 0..60 ;

            }

          }

          leaf x509v3-subject-key-identifier {
            description 'The subject key identifier of ca certificate' ;
            type string {
              length 0..96 ;

            }

          }

          leaf x509v3-authority-key-identifier {
            description 'The authority key identifier of ca certificate' ;
            type string {
              length 0..96 ;

            }

          }

          leaf x509v3-subject-alternative-name {
            description 'The subject alternative name of ca certificate' ;
            type string {
              length 0..96 ;

            }

          }

          ncd:select pki-profile-name ;
        }

      }

      container pki-local-cert {
        list pki-local-cert {
          key pki-profile-name ;
          leaf pki-profile-name {
            description 'The PKI profile name of local certificate' ;
            type string {
              length 0..31 ;

            }

          }

          leaf version {
            description 'The version of local certificate' ;
            type string {
              length 0..12 ;

            }

          }

          leaf serial-number {
            description 'The serial number of local certificate' ;
            type string {
              length 0..72 ;

            }

          }

          leaf signature-algorithm {
            description 'The signature algorithm of local certificate' ;
            type string {
              length 0..36 ;

            }

          }

          leaf issuer {
            description 'The issuer name of local certificate' ;
            type string {
              length 0..200 ;

            }

          }

          leaf validity-not-before {
            description 'The starting validity time of local certificate' ;
            type string {
              length 0..30 ;

            }

          }

          leaf validity-not-after {
            description 'The last validity time of local certificate' ;
            type string {
              length 0..30 ;

            }

          }

          leaf subject {
            description 'The subject name of local certificate' ;
            type string {
              length 0..200 ;

            }

          }

          leaf public-key-algorithm {
            description 'The public key algorithm of local certificate' ;
            type string {
              length 0..36 ;

            }

          }

          leaf subject-public-key-info {
            description 'The public key algorithm information of local certificate' ;
            type string {
              length 0..36 ;

            }

          }

          leaf x509v3-basic-constraints {
            description 'The basic constraints of local certificate' ;
            type string {
              length 0..30 ;

            }

          }

          leaf x509v3-key-usage {
            description 'The key usage of local certificate' ;
            type string {
              length 0..60 ;

            }

          }

          leaf x509v3-subject-key-identifier {
            description 'The subject key identifier of local certificate' ;
            type string {
              length 0..96 ;

            }

          }

          leaf x509v3-authority-key-identifier {
            description 'The authority key identifier of local certificate' ;
            type string {
              length 0..96 ;

            }

          }

          leaf x509v3-subject-alternative-name {
            description 'The subject alternative name of local certificate' ;
            type string {
              length 0..96 ;

            }

          }

          ncd:select pki-profile-name ;
        }

      }

    }

  }

  container operation {
    config false ;
    description 'The operation model of PKI.' ;
    container pki {
      description 'The parameters of PKI operation.' ;
      container import-pem-url {
        description 'The operation of importing certificate.' ;
        container cert-mode {
          list import-ca-cert {
            key 'import-mode disk-address pki-profile-name' ;
            leaf import-mode {
              type enumeration {
                enum disk {
                  value 3 ;
                }

              }

              description 'Import mode of ca certificate. Entering ‘disk’ represents importing a ca certificate from disk.' ;
            }

            leaf disk-address {
              type string {
                length 1..63 ;

              }

              description 'Disk address.' ;
            }

            leaf pki-profile-name {
              type string {
                length 1..31 ;

              }

              description 'Pki profile name.' ;
            }

            description 'Import ca certification.' ;
          }

          list import-local-cert {
            key 'import-mode disk-address pki-profile-name' ;
            leaf import-mode {
              type enumeration {
                enum disk {
                  value 3 ;
                }

              }

              description 'Import mode of local certificate. Entering ‘disk’ represents importing a local certificate from disk.' ;
            }

            leaf disk-address {
              type string {
                length 1..63 ;

              }

              description 'Disk address.' ;
            }

            leaf pki-profile-name {
              type string {
                length 1..31 ;

              }

              description 'Pki profile name.' ;
            }

            description 'Import local certification.' ;
          }

          list import-key {
            key 'import-mode disk-address pki-profile-name password' ;
            leaf import-mode {
              type enumeration {
                enum disk {
                  value 3 ;
                }

              }

              description 'Import mode of private key. Entering ‘disk’ represents importing a private key from disk.' ;
            }

            leaf disk-address {
              type string {
                length 1..63 ;

              }

              description 'Disk address.' ;
            }

            leaf pki-profile-name {
              type string {
                length 1..31 ;

              }

              description 'Pki profile name.' ;
            }

            leaf password {
              type string {
                length 1..31 ;

              }

              description 'Password used to protect the private key.' ;
            }

            description 'Import private key. ' ;
          }

          description 'The mode of certification.' ;
        }

      }

      container clear-certificate {
        container clear-ca-certificate {
          choice clear-type {
            description 'Type of clearing PKI  ca certificate.' ;
            case specify-cert {
              list clear-ca-cert {
                description 'Clear ca certificate with specified pki profile name.' ;
                key pki-profile-name ;
                leaf pki-profile-name {
                  description 'Specify the name of pki profile.' ;
                  type string {
                    length 1..31 ;

                  }

                }

              }

            }

            case all-cert {
              leaf clear-all-ca-cert {
                type empty ;
                mandatory true ;

                description 'Clear all ca certificate.' ;
              }

            }

          }

          description 'The operation of clearing ca certificate.' ;
        }

        container clear-local-certificate {
          choice clear-type {
            description 'Type of clearing PKI  local certificate.' ;
            case specify-cert {
              list clear-local-certificate {
                key pki-profile-name ;
                leaf pki-profile-name {
                  type string {
                    length 1..31 ;

                  }

                  description 'Specify the name of pki profile.' ;
                }

                description 'Clear local certificate with specified pki profile name.' ;
              }

            }

            case all-cert {
              leaf clear-all-local-cert {
                type empty ;
                mandatory true ;

                description 'Clear all local certificate.' ;
              }

            }

          }

          description 'The operation of clearing local certificate.' ;
        }

        description 'The operation of clearing certificate.' ;
      }

    }

  }

}
