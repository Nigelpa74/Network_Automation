module zxr10-mpls-te-dev-upn {
  namespace 'http://www.zte.com.cn/zxr10/netconf/schema/rosng/mpls-te-dev-upn'
            ;
  prefix mpls-te-dev-upn ;
  import zxr10-mpls-te {
    prefix te ;
    revision-date 2014-07-14 ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The mpls-te netconf module for ZSR,T8000,15K,M6000'
              ;
  revision 2016-09-27 {
    description 'Initial version.'
                ;
  }
  deviation '/te:configuration/te:mpls-te/te:dynamic-tunnel/te:wtr/te:installat'
          + 'ion-delay-time'
            {
    description 'Configuration of installation delay time.'
                ;
    deviate replace {
      default 10 ;
      type int16 {
        range 0..3600 ;
      }
      units seconds ;
    }
  }
}
