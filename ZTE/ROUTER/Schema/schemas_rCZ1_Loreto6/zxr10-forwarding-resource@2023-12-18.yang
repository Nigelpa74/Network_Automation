module zxr10-forwarding-resource {
  namespace "http://www.zte.com.cn/zxr10/netconf/schema/rosng/zxr10-forwarding-resource@2023-12-18"  ;
  prefix zxr10-forwarding-resource ;
  yang-version 1 ;
  import zxr10-netconf-defs {
    prefix ncd ;
    revision-date 2021-10-08 ;
  }

  organization "ZTE Corporation" ;
  contact "ZTE Corporation
  Nanjing Institute of ZTE Corporation
  No.68 Zijinghua Rd. Yuhuatai District, Nanjing, China
  Tel: +86-25-52870000" ;
  description 'The netconf module to describe MAC resource.' ;
  revision 2023-12-18 {
    description 'Add  MAC resource nodes' ;
  }

container state {
    config false ;
    container forwarding-resource {
      description 'Forwarding resource info.' ;
      container service-usages {
        description 'Service resource info.' ;
        list service-usage {
          description 'Service resource info.' ;
          key 'shelf slot subslot unit' ;
          leaf shelf {
            description 'shelf' ;
            type uint8 ;

          }

          leaf slot {
            description 'slot' ;
            type uint8 ;

          }

          leaf subslot {
            description 'subslot' ;
            type uint8 ;

          }

          leaf unit {
            description 'unit,4 is equal to N/A' ;
            type uint8 ;

          }

          list service-info {
            key name ;
            leaf name {
              description 'Service resource name.' ;
              type string ;

            }

            leaf total {
              description 'Total num.' ;
              type uint32 ;

            }

            leaf used {
              description 'Used num.' ;
              type uint32 ;

            }

            leaf free {
              description 'Free num.' ;
              type uint32 ;

            }

            leaf usage {
              description 'Usage.' ;
              type ncd:string-all ;

            }

          }

        }

      }

    }

    ncd:revise-date 2023-12-18 ;
  }

}
