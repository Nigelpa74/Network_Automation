module zxr10-mpls-te {
  namespace 'http://www.zte.com.cn/zxr10/netconf/schema/rosng/mpls-te' ;
  prefix te ;
  import zxr10-netconf-defs {
    prefix ncd ;
  }
  organization 'ZTE Corporation' ;
  contact "ZTE Corporation  
\n"
        + "   Nanjing Institute of ZTE Corporation 
\n"
        + "   No.68 Zijinghua Rd. Yuhuatai District, Nanjing, China 
\n"
        + '   Tel: +86-25-52870000'
          ;
  description 'The netconf model for mpls-te.' ;
  revision 2014-07-14 {
    description '1.Modify the value range of configuration\mpls-te\explicit-pat'
              + "h\name-based\name;
\n"
              + '2.Modify the value range of configuration\mpls-te\dynamic-tunn'
              + 'el\tunnels\tunnel\path-option-list\explicit-name\explicit-path'
              + "-name;
\n"
              + '3.Modify the value range of configuration\mpls-te\hotstandby\t'
              + "unnel\explicit-name\path-name;
\n"
              + '4.Modify the value range of configuration\mpls-te\static-tunne'
              + "ls\tunnel\track-name;
\n"
              + '5.Modify the value range of state\mpls-te\remote-tunnel\tunnel'
              + "\in-interface;
\n"
              + '6.Modify the value range of state\mpls-te\remote-tunnel\tunnel'
              + '\out-interface;'
                ;
  }
  revision 2014-06-11 {
    description '1.Modify the value range of configuration\mpls-te\auto-bandwid'
              + "th\tunnels\tunnel\adjust-enable leaf.
\n"
              + '2.Modify the value range and type of configuration\mpls-te\gra'
              + 'ceful-restart\enable leaf, and add its reset value.'
                ;
  }
  revision 2014-05-23 {
    description '1.Add backup-bw leaf to mpls-te/dynamic-tunnel/tunnels/tunnel.' ;
  }
  revision 2014-05-16 {
    description '1.modify the mandatory of addr-type and hop-type.' ;
  }
  revision 2014-05-08 {
    description '1.add the type of oper-status.' ;
  }
  revision 2014-04-02 {
    description 'Add ovreflow container.Move overflow-limit,overflow-percent an'
              + "d overflow-bandwidth to the ovreflow container.
\n"
              + 'Delete the default value and add the reset value of adjust-max'
              + '-value.'
                ;
  }
  revision 2014-03-24 {
    description '1. Move setup-priority and holding priority to priority contai'
              + "ner.
\n"
              + '2. Add default value to ds-te/model/value,access-tunnel/tunnel'
              + "/activation.
\n"
              + '3. Add reset value to static-tunnel/tunnel/lsps/positive(rever'
              + "se)-attribute next-hop share-tunnel pre-hop.
\n"
              + "4. Add convergence-ratio container.
\n"
              + "5. Add tunnel-bind.
\n"
              + '6. Add pathoption list,add egress tunnel,modify dynamic_tunnel'
              + ' list,modify tnnl-ar-hop.'
                ;
  }
  revision 2014-03-07 {
    description "1. Add performCode to ingress-tunnel-id and bfd.
\n"
              + "2. Add interface filter number to static tunnel name.
\n"
              + "3. Add frr-promotion unit.
\n"
              + "4. Add maximum instance number if-bandwidthes.
\n"
              + "5. Add maximum instance number of affinity.
\n"
              + "6. Modify protect-type Mandatory.
\n"
              + "7. Add dynamic case to hotstandby path type.
\n"
              + '8. Add default value to policy class.'
                ;
  }
  revision 2014-03-05 {
    description '1.add the range of bandwidth and delete performance of bandwid'
              + "th in dynamic-tunnel and static-tunnel.
\n"
              + '2.add reset value and delete default value of cbs, eir and ebs'
              + " in dynamic-tunnel.
\n"
              + "3.add the range of cir and pir in tnnl-rate-limit.
\n"
              + '4.add the reset value of inlabel and outlabel in positive-attr'
              + "ibute and reverse-attribute.
\n"
              + "5.modify the range of ar-relative-metric.
\n"
              + "6.modify the description of tunnel list.
\n"
              + "7.modify the name of remote tunnel.\n"
              + '8.Add dscp container.'
                ;
  }
  revision 2014-02-18 {
    description "1.remove filter of retran-config.
\n"
              + "2.add the invalid value of interval and frequency.
\n"
              + "3.add the range of explicit-path id.
\n"
              + '4.modify ar-enable wrong value.'
                ;
  }
  revision 2014-02-15 {
    description '1.add sd container' ;
  }
  revision 2014-01-23 {
    description 'Add the activation of dynamic tunnel. Modify the sequence of r'
              + 'ole-type and triple. Modify the  scope of the inlabel and outl'
              + 'abel. Delete the default value and default performance of out-'
              + 'bandwidth leaf.'
                ;
  }
  revision 2014-01-15 {
    description "Add te-trunk container.
\n"
              + "Move soft-preempt container from mpls-te to dynamic-tunnel.
\n"
              + "Remove resv-style and alias-name container.
\n"
              + 'Add filter to router-id and tunnel-destination.'
                ;
  }
  revision 2014-01-08 {
    description "Add container affinity and frr-promotion.
\n"
              + "Add the filter of invalid address and delete default value.
\n"
              + 'Add the UnactiveTime,delay_switch_over,delay_reactive,delay_li'
              + 'nkup,crankback.'
                ;
  }
  revision 2013-12-31 {
    description "modify te-metric range and add sample-enable reset value.
\n"
              + 'modify description of refresh-interval/restart-time/recovery-t'
              + "ime of graceful-restart function.
\n"
              + "modify description of srlg of interface.
\n"
              + "Add container for auto-bandwidth and ds-te.
\n"
              + 'Add filter for policy-class of static-tunnel.'
                ;
  }
  revision 2013-12-26 {
    description 'Add performance and interface filter. Add filter in policy-cla'
              + 'ss of access-tunnel.'
                ;
  }
  revision 2013-12-11 {
    description 'add resv-style,bw-protect,alias-name,soft-preemption,te-ecmp-g'
              + "roups,limit-hop-num,hop-prior,reopt-hsb-lsp to model.
\n"
              + 'modify retran-config/enable configuration value.'
                ;
  }
  revision 2013-12-05 {
    description 'Modify srlg container to add one-to-one, facility, auto-backup'
              + ' and hotstandby type.'
                ;
  }
  revision 2013-11-25 {
    description "add regular expression to admin-weight tunnel name.
\n"
              + 'add reset default value 0 to frr facility and one2one.'
                ;
  }
  revision 2013-11-10 {
    description 'Change the type of model from unit32 to enumeration, the type '
              + 'of percent from unit32 to unit8, the range of tunnel bfd enabl'
              + 'e and policy list of dynamic-tunnel and access-tunnel.'
                ;
  }
  revision 2013-09-24 {
    description 'Add the static tunnel model, see called "static-tunnels" of co'
              + 'ntainer.'
                ;
  }
  revision 2013-09-18 {
    description 'Add filter, change some choice to single container and modify '
              + 'some testing mistakes.'
                ;
  }
  revision 2013-08-01 {
    description 'Initial version.' ;
  }
  container configuration {
    description 'The branch of configuration model.' ;
    container mpls-te {
      description 'The configuration of MPLS TE.' ;
      leaf te-enable {
        description 'The global switch of TE.' ;
        type enumeration {
          enum disabled {
            value 0 ;
          }
          enum enabled {
            value 1 ;
          }
        }
        default disabled ;
      }
      container global-config {
        description 'TE global common configuration. Include refresh configurat'
                  + 'ion, retran and srefresh congiguration, explicit none cong'
                  + 'iguration and resv confirm congiguration.'
                    ;
        presence 'global configuration' ;
        container refresh-config {
          description 'The signalling packet containing path and resv refresh c'
                    + 'onfiguration.'
                      ;
          leaf interval {
            description 'Configuration of time interval for sending refresh mes'
                      + "sage, range: from 5000 to 65535000,
\n"
                      + 'units: ms, default value is 30000 ms.'
                        ;
            type uint32 {
              range 5000..65535000 ;
            }
            units ms ;
            default 30000 ;
          }
          leaf misses {
            description 'Configuration of miss number for refresh message, rang'
                      + 'e: from 2 to 10, default value is 4.'
                        ;
            type uint32 {
              range 2..10 ;
            }
            default 4 ;
          }
        }
        container retran-config {
          description 'The retransmit configuration.' ;
          leaf enable {
            description 'The switch of retransmit. Ref-reduction-enable is depe'
                      + 'nd on retran-config enable.'
                        ;
            type empty ;
          }
          leaf interval {
            description 'The interval of retransmit signalling message, range: '
                      + 'from 500 to 3000, unit: ms, default value: 1000 ms.'
                        ;
            type uint32 {
              range 500..3000 ;
            }
            units ms ;
            default 1000 ;
          }
          leaf limit {
            description 'The limit of signalling message retransmit, range: fro'
                      + 'm 2 to 10, default value: 3.'
                        ;
            type uint32 {
              range 2..10 ;
            }
            default 3 ;
          }
          leaf ref-reduction-enable {
            description 'Enable summary refresh function, default value is disa'
                      + "bled.
\n"
                      + 'Ref-reduction-enable is depend on retran-config enable'
                      + '.'
                        ;
            type enumeration {
              enum disabled {
                value 0 ;
              }
              enum enabled {
                value 1 ;
              }
            }
            default disabled ;
          }
        }
        container explicit-none {
          description 'The egress label management. The default label is implic'
                    + 'it-null.'
                      ;
          leaf explicit-null {
            description 'When this attribute is configured, it indicates that t'
                      + 'he label of egress node is explicit-null.'
                        ;
            type boolean ;
            default false ;
          }
          leaf none-null {
            description 'When this attribute is configured, it indicates that t'
                      + 'he label of egress node is none-null.'
                        ;
            type boolean ;
            default false ;
          }
        }
        container sd-config {
          description 'Configuration of SD.' ;
          leaf enable {
            description 'The switch of sd. default value is disabled.' ;
            type enumeration {
              enum disabled {
                value 0 ;
              }
              enum enabled {
                value 1 ;
              }
            }
            default disabled ;
          }
          leaf interval {
            description 'The interval of sd alarm, range: from 10 to 30, unit: '
                      + 's, default value: 10 s.'
                        ;
            type int16 {
              range 10..30 ;
            }
            units s ;
            default 10 ;
          }
        }
        container resv-confirm {
          description 'The resv confirm.' ;
          leaf enable {
            description 'Enable resv confirm function, default value is disable'
                      + "d.
\n"
                      + 'It is configured on egress.'
                        ;
            type enumeration {
              enum disabled {
                value 0 ;
              }
              enum enabled {
                value 1 ;
              }
            }
            default disabled ;
          }
        }
        container router-id {
          leaf route-id {
            description 'The TE route ID configuration. Must config router id b'
                      + 'efore any other configuration under dynamic-tunnl node'
                      + ' and ensure that router id is reachable in route.'
                        ;
            type ncd:ipv4-address {
              pattern '([1-9]|[1-9][0-9]|1[0-9][0-9]|2[0-4][0-9]|25[0-5])(.([0-'
                    + '9]|[1-9][0-9]|1[0-9][0-9]|2[0-4][0-9]|25[0-5])){3}'
                      ;
            }
          }
        }
        container tnnl-unact-time {
          description 'Tunnel reconstruction interval regularly.' ;
          leaf interval {
            description 'Tunnel reconstruction interval regularly.' ;
            type uint32 {
              range 30..300 ;
            }
            units seconds ;
          }
        }
        container delay {
          description 'Static TE delay function of management object.' ;
          leaf delay_switch_over {
            description 'Time delay back cut.' ;
            type uint32 {
              range 0..30 ;
            }
            units seconds ;
            default 0 ;
          }
          leaf delay_reactive {
            description 'Delay reactive time.' ;
            type uint32 {
              range 0..30 ;
            }
            units seconds ;
            default 10 ;
          }
          leaf delay_linkup {
            description 'The linkup of time delay response.' ;
            type uint32 {
              range 0..30 ;
            }
            units seconds ;
            default 0 ;
          }
        }
      }
      container explicit-path {
        description 'Configuration of explicit path.' ;
        presence 'Configuration of explicit-path' ;
        list name-based {
          description 'The explicit path name list' ;
          key name ;
          max-elements 8192 ;
          min-elements 0 ;
          leaf name {
            description 'The explicit path name.' ;
            type string {
              length 1..64 ;
            }
          }
          container path-paras {
            description 'Every explicit-path contains 32 hops.' ;
            list path-para {
              description 'Explicit path address information.' ;
              key index ;
              max-elements 131072 ;
              leaf index {
                description 'The explicit path index.' ;
                type uint8 {
                  range 1..64 ;
                }
              }
              leaf hop-ip {
                description 'Hop IP.' ;
                type ncd:ipv4-address ;
                mandatory true ;
              }
              leaf hop-type {
                description 'The hop type.' ;
                type enumeration {
                  enum include {
                    value 1 ;
                  }
                  enum exclude {
                    value 2 ;
                  }
                }
                mandatory true ;
              }
              leaf hop-attr {
                description 'The hop attribute. If hop type is include route, c'
                          + 'an configure strict route and loose route. If hop '
                          + 'type is exclude route, can configure exclude inter'
                          + 'face and exclude node.'
                            ;
                type enumeration {
                  enum strict-route {
                    value 1 ;
                  }
                  enum loose-route {
                    value 2 ;
                  }
                  enum exclude-intf {
                    value 3 ;
                  }
                  enum exclude-node {
                    value 4 ;
                  }
                }
                mandatory true ;
              }
            }
          }
        }
        list id-based {
          description 'The explicit path ID list.' ;
          key id ;
          max-elements 8192 ;
          min-elements 0 ;
          leaf id {
            description 'The explicit path ID.' ;
            type uint16 {
              range 1..65535 ;
            }
          }
          container path-paras {
            description 'Every explicit-path contains 32 hops.' ;
            list path-para {
              description 'Explicit path address information.' ;
              key index ;
              max-elements 131072 ;
              leaf index {
                description 'Explicit path index.' ;
                type uint8 {
                  range 1..64 ;
                }
              }
              leaf hop-ip {
                description 'Hop IP.' ;
                type ncd:ipv4-address ;
                mandatory true ;
              }
              leaf hop-type {
                description 'The hop type. Include include route and exclude ro'
                          + 'ute.'
                            ;
                type enumeration {
                  enum include {
                    value 1 ;
                  }
                  enum exclude {
                    value 2 ;
                  }
                }
                mandatory true ;
              }
              leaf hop-attr {
                description 'The hop attribute. If hop type is include route, c'
                          + 'an configure strict route and loose route. If hop '
                          + 'type is exclude route, can configure exclude inter'
                          + 'face and exclude node.'
                            ;
                type enumeration {
                  enum strict-route {
                    value 1 ;
                  }
                  enum loose-route {
                    value 2 ;
                  }
                  enum exclude-intf {
                    value 3 ;
                  }
                  enum exclude-node {
                    value 4 ;
                  }
                }
                mandatory true ;
              }
            }
          }
        }
      }
      container te-interfaces {
        description 'Enable interface to join in TE.All of the interface config'
                  + 'uration depend on TE interface.'
                    ;
        presence 'configuration of te-interface' ;
        list interface {
          description 'TE interface list.' ;
          key name ;
          max-elements 255 ;
          leaf name {
            description 'Interface name.' ;
            type ncd:ifname ;
          }
          leaf dscp {
            description 'DSCP value of TE interface, range: 0-63.' ;
            type uint8 {
              range 0..63 ;
            }
          }
          container convergence-ratio {
            description 'Interface convergence ratio.' ;
            leaf convergence-ratio-value {
              description 'Interface convergence ratio value.' ;
              type uint8 {
                range 1..100 ;
              }
              default 100 ;
            }
          }
        }
      }
      container dynamic-tunnel {
        description 'The dynamic tunnel.' ;
        presence 'configurationg of dynamic-tunnel' ;
        container reoptimize {
          description 'The global configuration of reoptimization.' ;
          presence 'Enable TECP reoptimize frequency.' ;
          leaf frequency {
            description 'The tunnels reoptimize timer frequency in global mode.'
                      + ' Configure tnnl-reoptimize enable node to specify whic'
                      + 'h tunnel uses reoptimize function.'
                        ;
            type int32 {
              range 30..604800 ;
            }
            units s ;
          }
          leaf event {
            description 'Specify which event can triger reoptimize.' ;
            type uint8 {
              range 0..1 {
                description 'linkup(1), none(0)' ;
              }
            }
            default 0 ;
          }
          leaf loose-node-enable {
            description 'Configuration of loose node reoptimize.' ;
            type enumeration {
              enum disabled {
                value 0 ;
              }
              enum enabled {
                value 1 ;
              }
            }
            default disabled ;
          }
        }
        container crankback {
          description 'Set the crankback retry count limit and information life'
                    + ' cycle.'
                      ;
          leaf limit_count {
            description 'Set the crankback retry count limit.' ;
            type uint8 {
              range 1..10 ;
            }
            default 5 ;
          }
          leaf ttl_value {
            description 'Set the crankback information life cycle.' ;
            type uint16 {
              range 30..300 ;
            }
            default 60 ;
          }
        }
        container tunnels {
          description 'Dynamic Tunnel Configuration.' ;
          list tunnel {
            description 'The dynamic tunnel configuration list.' ;
            key name ;
            max-elements 131070 ;
            leaf name {
              description 'The tunnel name.' ;
              type string {
                length 10..31 ;
                pattern 'te_tunnel[0-9]{1,22}' ;
              }
            }
            leaf hsb-lsp-frr {
              description 'To indicate that hotstandby lsp whether enable FRR o'
                        + 'r not.'
                          ;
              type enumeration {
                enum disabled {
                  value 0 ;
                }
                enum enabled {
                  value 1 ;
                }
              }
              default disabled ;
            }
            leaf destination {
              description 'The tunnel destination.' ;
              type ncd:ipv4-address {
                pattern '([1-9]|[1-9][0-9]|1[0-9][0-9]|2[0-4][0-9]|25[0-5])(.(['
                      + '0-9]|[1-9][0-9]|1[0-9][0-9]|2[0-4][0-9]|25[0-5])){3}'
                        ;
              }
            }
            leaf reoptimize {
              description 'Specify MPLS tunnel whether to open the timing re-op'
                        + 'timization.'
                          ;
              type enumeration {
                enum disabled {
                  value 0 ;
                }
                enum enabled {
                  value 1 ;
                }
              }
              default disabled ;
            }
            leaf limit-hop-num {
              description 'The maximum value of hops.' ;
              type uint8 {
                range 0..32 ;
              }
              default 0 ;
            }
            leaf hop-prior {
              description 'Enable the minimum hop priority function of a tunnel'
                        + '.'
                          ;
              type enumeration {
                enum enabled {
                  value 1 ;
                }
                enum disabled {
                  value 2 ;
                }
              }
              default disabled ;
            }
            leaf reopt-hsb-lsp {
              description 'Enable hsb-lsp auto-reoptimize.' ;
              type enumeration {
                enum disabled {
                  value 0 ;
                }
                enum enabled {
                  value 1 ;
                }
              }
              default disabled ;
            }
            leaf activation {
              description 'The activation of dynamic tunnel enable.' ;
              type enumeration {
                enum disabled {
                  value 0 ;
                }
                enum enabled {
                  value 1 ;
                }
              }
              default enabled ;
            }
            leaf crankback {
              description 'Tunnel crankback features enabled.' ;
              type enumeration {
                enum disabled {
                  value 0 ;
                }
                enum end-to-end {
                  value 1 ;
                }
              }
              default disabled ;
            }
            leaf resv-style {
              description "Configure resv-style in tunnel mode.
\n"
                        + 'You must noticed that ff style is confilct to frr co'
                        + 'nfiguration.If frr has been configured first in tunn'
                        + 'el mode,ff style can not be configured.If ff style h'
                        + 'as been configured,frr can not be configured.'
                          ;
              type enumeration {
                enum se {
                  value 1 ;
                  description 'se(Shared Explicit)' ;
                }
                enum ff {
                  value 2 ;
                  description 'ff(Fixed Filter)' ;
                }
              }
              default se ;
            }
            leaf alias-name {
              description 'Configuration of tunnel alias name.' ;
              type string {
                length 1..63 ;
              }
            }
            leaf track-name {
              description 'Configuration of tunnel track name,use for BFD detec'
                        + 'tion.'
                          ;
              type string {
                length 1..31 ;
              }
            }
            leaf soft-preemption-enable {
              description 'Enable soft-preemption in tunnel mode,and this tunne'
                        + 'l will be teared after the specifc time named timeou'
                        + 't configured under timeout container.'
                          ;
              type enumeration {
                enum disabled {
                  value 0 ;
                }
                enum enabled {
                  value 1 ;
                }
              }
              default disabled ;
            }
            list path-option-list {
              description 'Tunnel path option configuration.' ;
              key number ;
              max-elements 786420 ;
              leaf number {
                description 'Path option number which the specified tunnel is u'
                          + 'sed.'
                            ;
                type uint8 {
                  range 1..16 ;
                }
              }
              choice path-class {
                description 'Path Selection Type.' ;
                mandatory true ;
                case dynamic {
                  description 'Dynamic Path Selection.' ;
                  leaf dynamic {
                    description 'The path type is dynamic.' ;
                    type empty ;
                    mandatory true ;
                  }
                }
                case explicit-name {
                  description 'Based on the name of the explicit path selection'
                            + '.'
                              ;
                  leaf explicit-path-name {
                    description 'The related explicit path name.' ;
                    type string {
                      length 1..64 ;
                    }
                    mandatory true ;
                  }
                }
                case expilict-id {
                  description 'Id-based explicit path selection.' ;
                  leaf explicit-path-id {
                    description 'The related explicit path ID.' ;
                    type uint16 {
                      range 1..65535 ;
                    }
                    mandatory true ;
                  }
                }
              }
              leaf lockdown {
                description 'Lockdown switch is turned on.' ;
                type boolean ;
                default false ;
              }
            }
            container binary-tunnel {
              description 'Bidirectional Tunnel Setting.' ;
              leaf co-route {
                description 'The binary tunnel enable or disable.' ;
                type enumeration {
                  enum disabled {
                    value 0 ;
                  }
                  enum enabled {
                    value 1 ;
                  }
                }
                default disabled ;
              }
            }
            container policy-class {
              description 'The tunnel policy class.' ;
              leaf class {
                description 'The tunnel policy class configuration. From 0 to 7'
                          + ' represent normal configuration. Ingress and Egres'
                          + 's of co-tunnel uses 255 as its default value.'
                            ;
                type uint8 {
                  range '0..7 | 255' {
                    description '0-7 represent normal configuration. Ingress an'
                              + 'd Egress of co-tunnel uses 255 as its default '
                              + 'value.'
                                ;
                  }
                }
                default 255 ;
              }
            }
            container bandwidth {
              description 'The tunnel bandwidth.' ;
              presence 'Tunnel bandwidth allocation.' ;
              leaf bandwidth {
                description 'The tunnel bandwidth configuration.' ;
                type uint32 {
                  range 0..4294967295 ;
                }
                units kbps ;
                mandatory true ;
              }
              leaf cbs {
                description 'The tunnel CBS.' ;
                type uint32 {
                  range 1..4294967295 ;
                }
                units byte ;
              }
              leaf eir {
                description 'The tunnel EIR.' ;
                type uint32 {
                  range 1..4294967295 ;
                }
                units kbps ;
              }
              leaf ebs {
                description 'The tunnel EBS.' ;
                type uint32 {
                  range 1..4294967295 ;
                }
                units byte ;
              }
            }
            container ct-bandwidths {
              description 'Tunnel classtype and its request bandwidth. It is ex'
                        + 'clusive with common bandwidth and tunnel-rate-limit.'
                          ;
              list ct-bandwidth {
                description 'Tunnel classtype and its request bandwidth.' ;
                key class-type ;
                leaf class-type {
                  description 'The configuration of class type.' ;
                  type uint8 {
                    range 0..7 ;
                  }
                }
                leaf bandwidth {
                  description 'The bandwidth of class type.' ;
                  type uint32 {
                    range 1..4294967295 ;
                  }
                  mandatory true ;
                }
              }
            }
            container rros {
              description 'The RRO function of dynamic tunnel.' ;
              leaf rro-enable {
                description 'If this object is true, then it enables the Record'
                          + 'Route. Before to configure FRR or hotstandby, plea'
                          + 'se ensure that this leaf node is enabled.'
                            ;
                type enumeration {
                  enum disabled {
                    value 0 ;
                  }
                  enum enabled {
                    value 1 ;
                  }
                }
                default disabled ;
              }
            }
            container priority {
              description 'Configuration of tunnel priority.' ;
              presence 'priority of this tunnel' ;
              leaf setup-priority {
                description "The tunnel setup priority.This attribute can't be "
                          + "higher than the holding-priority.0 is the highest "
                          + "priority and 7 is the lowest priority."
                            ;
                type uint16 {
                  range 0..7 ;
                }
                mandatory true ;
              }
              leaf holding-priority {
                description 'The tunnel holding priority.The tunnel of lower ho'
                          + 'lding-priority will be preempted by the tunnel of '
                          + 'higher setup-priority.0 is the highest priority an'
                          + 'd 7 is the lowest priority.'
                            ;
                type uint16 {
                  range 0..7 ;
                }
                mandatory true ;
              }
            }
            container tunnel-bind {
              description 'The associated dynamic tunnel bind function.' ;
              presence 'Configure bound tunnel.' ;
              leaf associated-tunnel-id {
                description 'The associated tunnel id which is the tunnel id of'
                          + ' access tunnel. This function can only be configur'
                          + 'ed at ingress node.This attribute is determined by'
                          + ' product.'
                            ;
                type uint32 {
                  range 1..131072 ;
                }
                mandatory true ;
              }
            }
            leaf backup-bw {
              description 'The backup tunnel bandwidth configuration.' ;
              type uint32 {
                range 1..4294967295 ;
              }
              units kbps ;
            }
          }
        }
        container admin-weight {
          description 'Configuration of admin weight.' ;
          container if-based {
            description 'Configuration of admin-weight for the specified interf'
                      + 'ace.'
                        ;
            list interface {
              description 'An interface weight management.' ;
              key name ;
              max-elements 255 ;
              leaf name {
                description 'Interface name.' ;
                type ncd:ifname ;
              }
              leaf te-metric {
                description 'The configuration of metric for a mpls te interfac'
                          + 'e.'
                            ;
                type uint32 {
                  range 1..65535 ;
                }
              }
            }
          }
          container tunnel-based {
            description 'Configuration of admin-weight for the specified Tunnel'
                      + '.'
                        ;
            list tunnel {
              description 'The weight of a tunnel management.' ;
              key name ;
              max-elements 131070 ;
              min-elements 0 ;
              leaf name {
                description 'Tunnel name' ;
                type ncd:ifname ;
              }
              leaf te-metric {
                description 'The Configuration of traffic-eng metric for Tunnel'
                          + '.'
                            ;
                type uint32 {
                  range 1..4294967295 ;
                }
                mandatory true ;
              }
            }
          }
        }
        container wtr {
          leaf cleanup-delay-time {
            description 'Configuration of clean up delay time.' ;
            type int16 {
              range 0..600 ;
            }
            units s ;
            default 15 ;
          }
          leaf installation-delay-time {
            description 'Configuration of installation delay time.' ;
            type int16 {
              range 0..600 ;
            }
            units s ;
            default 10 ;
          }
        }
        container soft-preemption {
          description 'Configuration of soft preemption.' ;
          presence 'configuration of soft preemption' ;
          container timeout {
            leaf timeout {
              description 'Configure soft-preemption keep-alive time.' ;
              type int16 {
                range 1..300 {
                  description 'unit is second.' ;
                }
              }
              units s ;
              default 30 ;
            }
          }
        }
      }
      container ds-te {
        description 'The configuration of DS-TE.' ;
        presence 'configure ds-te' ;
        container model {
          description 'The bandwidth resv model.' ;
          leaf value {
            description 'The bandwidth resv model.The te-class and BC bandwidth'
                      + ' which depend on DS-TE model can only be configurated '
                      + 'at MAM,RDM or EXTEND-MAM model.'
                        ;
            type enumeration {
              enum RDM {
                value 0 ;
              }
              enum MAM {
                value 1 ;
              }
              enum MPLS-TE {
                value 2 ;
              }
              enum EXTEND-MAM {
                value 254 ;
              }
              enum NONE-TE {
                value 255 ;
              }
            }
            default MPLS-TE ;
          }
        }
        container te-classes {
          description 'Te-class configuration.' ;
          list te-class {
            description "Te-class configuration.If the class-type and priority "
                      + "of tunnel don't match the te-class,the tunnel path com"
                      + "pute can't be success."
                        ;
            key class-id ;
            max-elements 8 ;
            min-elements 0 ;
            leaf class-id {
              description 'TE class ID. Range is 0-7.' ;
              type uint8 {
                range 0..7 ;
              }
            }
            leaf type {
              description 'TE class type. Range is 0-7.' ;
              type uint8 {
                range 0..7 ;
              }
              mandatory true ;
            }
            leaf priority {
              description 'TE class priority. Range is 0-7.' ;
              type uint8 {
                range 0..7 ;
              }
              mandatory true ;
            }
          }
        }
        container if-bandwidthes {
          description 'The configuration of interface bandwidth.' ;
          list if-bandwidth {
            description 'The configuration of interface bandwidth.' ;
            key 'name reserve-tunnel-type' ;
            ncd:select 'name reserve-tunnel-type' ;
            max-elements 510 ;
            leaf name {
              description 'Interface name.' ;
              type ncd:ifname ;
            }
            leaf reserve-tunnel-type {
              description 'The reserve type of tunnel.' ;
              type enumeration {
                enum dynamic {
                  value 1 ;
                }
                enum static {
                  value 2 ;
                }
              }
            }
            leaf bandwidth {
              description 'Interface total resv bandwidth.' ;
              type uint32 {
                range 1..4294967295 ;
              }
              units kbps ;
              mandatory true ;
            }
            leaf bc0 {
              description "BC0 bandwidth.The sum of BC bandwidth can't be large"
                        + "r than interface bandwidth."
                          ;
              type uint32 {
                range 0..4294967295 ;
              }
              units kbps ;
              default 0 ;
            }
            leaf bc1 {
              description "BC1 bandwidth.The sum of BC bandwidth can't be large"
                        + "r than interface bandwidth."
                          ;
              type uint32 {
                range 0..4294967295 ;
              }
              units kbps ;
              default 0 ;
            }
            leaf bc2 {
              description "BC2 bandwidth.The sum of BC bandwidth can't be large"
                        + "r than interface bandwidth."
                          ;
              type uint32 {
                range 0..4294967295 ;
              }
              units kbps ;
              default 0 ;
            }
            leaf bc3 {
              description "BC3 bandwidth.The sum of BC bandwidth can't be large"
                        + "r than interface bandwidth."
                          ;
              type uint32 {
                range 0..4294967295 ;
              }
              units kbps ;
              default 0 ;
            }
            leaf bc4 {
              description "BC4 bandwidth.The sum of BC bandwidth can't be large"
                        + "r than interface bandwidth."
                          ;
              type uint32 {
                range 0..4294967295 ;
              }
              units kbps ;
              default 0 ;
            }
            leaf bc5 {
              description "BC5 bandwidth.The sum of BC bandwidth can't be large"
                        + "r than interface bandwidth."
                          ;
              type uint32 {
                range 0..4294967295 ;
              }
              units kbps ;
              default 0 ;
            }
            leaf bc6 {
              description "BC6 bandwidth.The sum of BC bandwidth can't be large"
                        + "r than interface bandwidth."
                          ;
              type uint32 {
                range 0..4294967295 ;
              }
              units kbps ;
              default 0 ;
            }
            leaf bc7 {
              description "BC7 bandwidth.The sum of BC bandwidth can't be large"
                        + "r than interface bandwidth."
                          ;
              type uint32 {
                range 0..4294967295 ;
              }
              units kbps ;
              default 0 ;
            }
            leaf per-flow-bw {
              description "The per flow bandwidth.The bandwidth of any bypassed"
                        + " tunnel of this interface can't be larger than this "
                        + "attribute.This attribute can't be larger than interf"
                        + "ace total bandwidth."
                          ;
              type uint32 {
                range 0..4294967295 ;
              }
              units kbps ;
              default 0 ;
            }
            leaf percent {
              description "The bandwidth occupied ratio.The dynamic percentage "
                        + "of interface speed and the static percentage of inte"
                        + "rface speed can't be over 100 percent."
                          ;
              type uint8 {
                range 0..100 ;
              }
              default 40 ;
            }
          }
        }
      }
      container passive-if {
        description 'The configuration of passive interface.Traffic engineering'
                  + ' flood the interface information to IGP-TE for OSPF path c'
                  + 'ompute at inter-area condition.'
                    ;
        presence 'configuration of passive-if' ;
        list cross-domain {
          description 'Passive interface list.' ;
          key 'if-name nbr-route-id' ;
          ncd:select 'if-name nbr-route-id' ;
          max-elements 2550 ;
          leaf if-name {
            description 'Interface name.' ;
            type ncd:ifname ;
          }
          leaf nbr-route-id {
            description 'The neighbor route ID.' ;
            type ncd:ipv4-address ;
          }
          leaf nbr-if-addr {
            description 'Neighbor interface address.' ;
            type ncd:ipv4-address {
              pattern '([1-9]|[1-9][0-9]|1[0-9][0-9]|2[0-4][0-9]|25[0-5])(.([0-'
                    + '9]|[1-9][0-9]|1[0-9][0-9]|2[0-4][0-9]|25[0-5])){3}'
                      {
                description 'To filter the invalid address.' ;
              }
            }
          }
          leaf nbr-ospf-node-id {
            description 'Neighbor OSPF node ID.' ;
            type ncd:ipv4-address {
              pattern '([1-9]|[1-9][0-9]|1[0-9][0-9]|2[0-4][0-9]|25[0-5])(.([0-'
                    + '9]|[1-9][0-9]|1[0-9][0-9]|2[0-4][0-9]|25[0-5])){3}'
                      {
                description 'To filter the invalid address.' ;
              }
            }
          }
          leaf nbr-isis-system-id {
            description 'Neighbor ISIS system ID.' ;
            type ncd:mac-address ;
            default 00:00:00:00:00:00 ;
          }
        }
      }
      container bfd {
        description 'Configuration of BFD.' ;
        presence 'configuration of bfd' ;
        container interfaces {
          description 'TE BFD interface configuration.' ;
          list interface {
            description 'The interface BFD list.' ;
            key name ;
            max-elements 100 ;
            min-elements 0 ;
            leaf name {
              description 'Interface name.' ;
              type ncd:ifname ;
            }
            leaf enable {
              description 'The interface BFD enable.' ;
              type enumeration {
                enum disabled {
                  value 0 ;
                }
                enum enabled {
                  value 1 ;
                }
              }
              mandatory true ;
            }
          }
        }
        container tunnels {
          description 'BFD tunnel settings.' ;
          list tunnel {
            description 'BFD is set in a tunnel.' ;
            key 'name enable' ;
            ncd:select 'name enable' ;
            max-elements 100 ;
            leaf name {
              description 'Tunnel name.' ;
              type ncd:ifname ;
            }
            leaf enable {
              description 'The tunnel BFD enable.This attribute depend on the t'
                        + 'unnel role and direction-type.'
                          ;
              type enumeration {
                enum master {
                  value 1 ;
                }
                enum slave {
                  value 2 ;
                }
              }
            }
            leaf min-tx-interval {
              description 'The tunnel BFD min transmit interval.' ;
              type uint32 {
                range 3..990 ;
              }
              units ms ;
              mandatory true ;
            }
            leaf min-rx-interval {
              description 'The tunnel BFD min receive interval.' ;
              type uint32 {
                range 3..990 ;
              }
              units ms ;
              mandatory true ;
            }
            leaf detect-multiple {
              description 'The tunnel BFD detecting multiple.' ;
              type uint16 {
                range 3..50 ;
              }
              mandatory true ;
            }
          }
        }
      }
      container access-tunnel {
        description 'The access tunnel,it is related with ingress tunnel.' ;
        presence 'configuration of access-tunnel' ;
        list tunnel {
          description 'The access tunnel list.' ;
          key name ;
          max-elements 131070 ;
          leaf name {
            description 'The tunnel name.' ;
            type ncd:ifname ;
          }
          leaf activation {
            description 'The activation of access-tunnel.Only the egress node o'
                      + 'f bidirectional access-tunnel can configure this attri'
                      + 'bute.'
                        ;
            type enumeration {
              enum disabled {
                value 0 ;
              }
              enum enabled {
                value 1 ;
              }
              enum invalid {
                value 2 ;
              }
            }
            default enabled ;
          }
          container role-type {
            description 'The tunnel role and direction type.' ;
            presence 'Configure tunnel role and type.' ;
            leaf role {
              description 'The access tunnel role.' ;
              type enumeration {
                enum transitNode {
                  value 2 ;
                }
                enum egressNode {
                  value 3 ;
                }
              }
              mandatory true ;
            }
            leaf direction-type {
              description 'The access tunnel direction type.' ;
              type enumeration {
                enum unidirectional {
                  value 1 ;
                }
                enum bidirectional {
                  value 2 ;
                }
              }
              mandatory true ;
            }
          }
          container triple {
            description 'The tunnel triple elements.' ;
            presence 'Configure tunnel triple.' ;
            leaf ingress-tunnel-id {
              description 'The ingress tunnel ID,it is used to locate ingress t'
                        + 'unnel.'
                          ;
              type uint32 {
                range 1..64511 ;
              }
              mandatory true ;
            }
            leaf ingress-lsr-id {
              description 'The ingress route ID.' ;
              type ncd:ipv4-address ;
              mandatory true ;
            }
            leaf egress-lsr-id {
              description 'The egress route ID.' ;
              type ncd:ipv4-address ;
              mandatory true ;
            }
          }
          container policy {
            description 'The tunnel policy class.' ;
            leaf policy-class {
              description 'The access tunnel policy class.It depend on directio'
                        + 'n-type and role,and only the bidirectional egress tu'
                        + 'nnel can configure this attribute.'
                          ;
              type uint8 {
                range '0..7 | 255' {
                  description '0-7 represent normal configuration. Ingress and '
                            + 'Egress of co-tunnel uses 255 as its default valu'
                            + 'e.'
                              ;
                }
              }
            }
          }
        }
      }
      container tnnl-rate-limit {
        description 'The configuration of tunnel rate limit, it is exclusive wi'
                  + 'th common bandwidth and class-type bandwidth. Only the ing'
                  + 'ress tunnel and the bidirectional egress tunnel can config'
                  + 'ure rate limit.'
                    ;
        presence 'configuration of tnnl-rate-limit' ;
        list tunnel {
          description 'The tunnel rate limit list.' ;
          key name ;
          max-elements 131072 ;
          min-elements 0 ;
          leaf name {
            description 'The tunnel name.' ;
            type ncd:ifname ;
          }
          leaf mode {
            description 'The tunnel rate limit mode.' ;
            type enumeration {
              enum blind {
                value 1 ;
              }
              enum aware {
                value 2 ;
              }
            }
            mandatory true ;
          }
          leaf cir {
            description CIR. ;
            type uint32 {
              range '0 | 8..20000000' ;
            }
            units kbps ;
            mandatory true ;
          }
          leaf cbs {
            description CBS. ;
            type uint32 {
              range 1..5120000 ;
            }
            units KB ;
            mandatory true ;
          }
          leaf pir {
            description "PIR.PIR can't be smaller than CIR." ;
            type uint32 {
              range '0 | 8..20000000' ;
            }
            units kbps ;
            mandatory true ;
          }
          leaf pbs {
            description PBS. ;
            type uint32 {
              range 1..5120000 ;
            }
            units KB ;
            mandatory true ;
          }
        }
      }
      container graceful-restart {
        description 'Configuration of Graceful-restart.Graceful-restart and frr'
                  + '-hello are mutual exclusion.'
                    ;
        presence 'The graceful-restart configuration for RSVP.' ;
        leaf enable {
          description 'Enable graceful restart and graceful-restart hello funct'
                    + 'ion, before to enable this node, please ensure that frr '
                    + 'hello is disabled for frr hello conflict to graceful-res'
                    + 'tart hello.'
                      ;
          type empty ;
        }
        leaf refresh-interval {
          description 'Graceful-restart hello refresh interval time, range 1000'
                    + '~30000 (ms), default value is 10000(ms).'
                      ;
          type uint32 {
            range 1000..30000 ;
          }
          units ms ;
          default 10000 ;
        }
        leaf refresh-misses {
          description 'Miss number of Graceful-restart hello, range: 4-10, defa'
                    + 'ult value is 4.'
                      ;
          type uint8 {
            range 4..10 ;
          }
          default 4 ;
        }
        leaf restart-time {
          description 'Restart time interval of Graceful-restart for this node,'
                    + ' range: 120000-600000(ms), default value is 120000(ms).'
                      ;
          type uint32 {
            range 120000..600000 ;
          }
          units ms ;
          default 120000 ;
        }
        leaf recovery-time {
          description 'Recovery time interval of Graceful-restart for this node'
                    + ', range:120000~600000 (ms), default value is 120000 (ms)'
                    + '.'
                      ;
          type uint32 {
            range 120000..600000 ;
          }
          units ms ;
          default 120000 ;
        }
        leaf node-hello-enable {
          description 'If this object is true, then it enables the Node Hello.I'
                    + 't depends graceful-restart enable.'
                      ;
          type enumeration {
            enum disabled {
              value 0 ;
            }
            enum enabled {
              value 1 ;
            }
          }
          default disabled ;
        }
        leaf extend-recovery-path {
          description 'If this object is true, then it enables the Gr Extend Re'
                    + 'covery Path. The node will send recovery-path with priva'
                    + 'te ero to all neighbours.'
                      ;
          type enumeration {
            enum disabled {
              value 0 ;
            }
            enum enabled {
              value 1 ;
            }
          }
          default disabled ;
        }
        list extend-nbr-rid-list {
          key extend-nbr-rid ;
          max-elements 32 ;
          min-elements 0 ;
          leaf extend-nbr-rid {
            description 'This leaf node specifies neighbor router id which reco'
                      + 'very path with private ero will be sent to. The maxium'
                      + ' number of neighbour address is 32.'
                        ;
            type ncd:ipv4-address ;
          }
        }
      }
      container authentication {
        description 'Configuration authentication for the specified interface.' ;
        presence 'configuration of authentication' ;
        list interface {
          description 'Interface list.' ;
          key name ;
          max-elements 255 ;
          leaf name {
            description 'The name of this interface.' ;
            type ncd:ifname ;
          }
          leaf enable {
            description 'If this interface enables RSVP cryptographic authentic'
                      + 'ation, this value is true, otherwise it is false. Defa'
                      + 'ult value of this node is disabled.'
                        ;
            type enumeration {
              enum disabled {
                value 0 ;
              }
              enum enabled {
                value 1 ;
              }
            }
            default disabled ;
          }
          leaf type {
            description 'Specifies the type of authentication algorithm on this'
                      + ' interface. Default value is md5.'
                        ;
            type enumeration {
              enum md5 {
                value 1 ;
              }
              enum sha {
                value 2 ;
              }
            }
            default md5 ;
          }
          leaf key {
            description 'Specifies shared secret key for all neighbors on this '
                      + "interface. Default value is
\n"
                      + 'RSVP-AUTH.'
                        ;
            type string {
              length 8..40 ;
            }
            default RSVP-AUTH ;
          }
          leaf window-size {
            description 'Specifies received window size for authenticated messa'
                      + 'ges on this interface. Range: from 1 to 64, default va'
                      + 'lue: 32.'
                        ;
            type uint8 {
              range 1..64 ;
            }
            default 32 ;
          }
          leaf challage-enable {
            description 'If this interface as a receiver to perform challenge/r'
                      + "esponse handshake with new
\n"
                      + 'RSVP neighbors enables rsvp authentication challenge, '
                      + 'this value is enabled,otherwise it is disabled.'
                        ;
            type enumeration {
              enum disabled {
                value 0 ;
              }
              enum enabled {
                value 1 ;
              }
            }
            default disabled ;
          }
          leaf challage-imp-enable {
            description 'If this interface as a sender  to perform challenge/re'
                      + "sponse handshake with new
\n"
                      + 'RSVP neighbors enables rsvp authentication challenge i'
                      + 'mp,this value is enabled, otherwise it is disabled.'
                        ;
            type enumeration {
              enum disabled {
                value 0 ;
              }
              enum enabled {
                value 1 ;
              }
            }
            default disabled ;
          }
        }
      }
      container frr {
        description 'Configuration of fast reroute. The function depend on rro-'
                  + 'enable.'
                    ;
        presence 'configuration of frr' ;
        list tunnel {
          description 'Tunnel list.' ;
          key name ;
          max-elements 131070 ;
          min-elements 0 ;
          leaf name {
            description 'The tunnel name.' ;
            type ncd:ifname ;
          }
          choice protect-type {
            description 'To assign protect type of FRR, including facility and '
                      + 'one-to-one.'
                        ;
            mandatory true ;
            case facility {
              leaf facility {
                description 'If this tunnel enables facility FRR,this value is '
                          + 'true, otherwise it is false. This configureation i'
                          + 's depend on rro-enable.'
                            ;
                type empty ;
              }
            }
            case one2one {
              leaf one2one {
                description 'If this tunnel enables detour FRR,this value is tr'
                          + 'ue,otherwise, it is false. This Configuration is d'
                          + 'epend on rro-enable.'
                            ;
                type empty ;
              }
            }
          }
          leaf bw-protect {
            description 'Configuration of bandwidth protection.You must configu'
                      + 're FRR protection method before configuring FRR bandwi'
                      + 'dth protection.'
                        ;
            type enumeration {
              enum disabled {
                value 0 ;
                description 'Disabled bw-protect.' ;
              }
              enum enabled {
                value 1 ;
                description 'Enable bw-protect.' ;
              }
            }
            default disabled ;
          }
        }
        container interface {
          container manual-backup-tunnels {
            description 'It conflicts to auto-backup-tunnels. A interface can b'
                      + 'e configured one type of backup tunnel.'
                        ;
            list manual-backup-tunnel {
              description 'List of interfaces configured manual backup tunnel.' ;
              key 'intf-name tunnel-id' ;
              max-elements 131070 ;
              leaf intf-name {
                description 'Interface name.' ;
                type ncd:ifname ;
              }
              leaf tunnel-id {
                description 'Configure a MPLSTE backup TE tunnel for this inter'
                          + 'face. The maximum number of MPLSTE backup TE tunne'
                          + 'l configured on this interface is 16. Please ensur'
                          + 'e that the MPLSTE backup TE tunnel does not use th'
                          + 'is interface as its output interface.'
                            ;
                type uint32 {
                  range 1..65535 ;
                }
              }
            }
          }
          container auto-backup-tunnels {
            description 'It conflicts to manual-backup-tunnels. A interface can'
                      + ' be configured one type of backup tunnel.'
                        ;
            list auto-backup-tunnel {
              description 'List of interface configured auto backup tunnel.' ;
              key intf-name ;
              max-elements 65535 ;
              leaf intf-name {
                type ncd:ifname ;
              }
              leaf nhop-only {
                description 'If this object is true, then it only requires LINK'
                          + '_PROTECT by autobackup tunnel.'
                            ;
                type enumeration {
                  enum disabled {
                    value 0 ;
                  }
                  enum enabled {
                    value 1 ;
                  }
                }
                default disabled ;
              }
              leaf auto-backup-enable {
                description 'If this object is true, then it prefers NODE_PROTE'
                          + 'CT to LINK_PROTECT by autobackup tunnel.'
                            ;
                type enumeration {
                  enum disabled {
                    value 0 ;
                  }
                  enum enabled {
                    value 1 ;
                  }
                }
                default disabled ;
              }
            }
          }
        }
        container auto-backup-tnnl-id-range {
          description 'The auto backup tunnel ID scope.' ;
          leaf min {
            description 'The auto backup min tunnel ID depend on product specif'
                      + 'ication.'
                        ;
            type uint32 ;
            default 64512 ;
          }
          leaf max {
            description 'The auto backup max tunnel ID depend on product specif'
                      + 'ication.'
                        ;
            type uint32 ;
            default 65535 ;
          }
        }
        container frr-hello {
          description 'Graceful-restart and frr-hello are mutual exclusion.' ;
          leaf frr-hello-enable {
            description 'Enables or disables hello message in global mode which'
                      + ' is defined in RFC3209.  This leaf node is conflict to'
                      + ' graceful-restart enable. Before configure this leaf n'
                      + 'ode,please make sure that graceful-restart is disabled'
                      + ' and configure frr hello at specified interface.'
                        ;
            type enumeration {
              enum disabled {
                value 0 ;
              }
              enum enabled {
                value 1 ;
              }
            }
            default disabled ;
          }
          list interface {
            description 'Interface list.' ;
            key name ;
            max-elements 255 ;
            leaf name {
              description 'Interface name.' ;
              type ncd:ifname ;
            }
            leaf enable {
              description 'If this object is enabled, then the interface hello '
                        + 'refresh is enable. Before this configure, please mak'
                        + 'e sure that frr-hello-enable is enabled.'
                          ;
              type enumeration {
                enum disabled {
                  value 0 ;
                }
                enum enabled {
                  value 1 ;
                }
              }
              default disabled ;
            }
            leaf refresh-interval {
              description 'Configuration of hello refresh interval (1000-30000 '
                        + 'ms) on interface.'
                          ;
              type uint32 {
                range 1000..30000 ;
              }
              units ms ;
              default 10000 ;
            }
            leaf refresh-misses {
              description 'Configuration of hello refresh misses (4..10) on int'
                        + 'erface.'
                          ;
              type uint8 {
                range 4..10 ;
              }
              default 4 ;
            }
          }
        }
        container frr-promotion {
          presence 'frr promotion configuration' ;
          leaf timer-en {
            description 'Enable timer for frr promotion.' ;
            type enumeration {
              enum disabled {
                value 0 ;
                description 'disable frr promotion' ;
              }
              enum enabled {
                value 1 ;
                description 'enable frr promotion' ;
              }
            }
            default disabled ;
          }
          leaf timer-interval {
            description 'Configuration of seconds between promotions.' ;
            type uint32 {
              range 60..604800 ;
            }
            units s ;
            default 300 ;
          }
        }
      }
      container auto-bandwidth {
        description 'The configuration of auto bandwidth adjustment.' ;
        presence 'For auto bandwidth adjustment.' ;
        container global {
          description 'The global configuration of auto-bandwidth.' ;
          presence 'The global configuration.' ;
          leaf sample-enable {
            description 'The global switch of sample.' ;
            type enumeration {
              enum disabled {
                value 0 ;
              }
              enum enabled {
                value 1 ;
              }
            }
            mandatory true ;
          }
          leaf sample-frequency {
            description 'Auto bandwidth adjustment timer frequency 60~604800 (s'
                      + ').'
                        ;
            type uint32 {
              range 60..604800 ;
            }
            units s ;
            default 300 ;
          }
        }
        container tunnels {
          description 'The tunnel configuration of auto-bandwidth.' ;
          presence 'The tunnel configuration.' ;
          list tunnel {
            description 'The configuration list.' ;
            key name ;
            max-elements 131070 ;
            min-elements 0 ;
            leaf name {
              description 'The tunnel name.' ;
              type ncd:ifname ;
            }
            leaf adjust-enable {
              description 'The adjust switch of tunnel ABW.' ;
              type enumeration {
                enum enabled {
                  value 1 ;
                }
              }
              mandatory true ;
            }
            leaf adjust-frequency {
              description 'Adjust frequence of this tunnel.This attribute depen'
                        + 'd on adjust-enable.'
                          ;
              type uint32 {
                range 300..604800 ;
              }
              units s ;
              default 86400 ;
            }
            leaf adjust-max-value {
              description 'Maximum bandwidth of adjustment.This attribute depen'
                        + 'd on adjust-enable.'
                          ;
              type uint32 {
                range 1..4294967295 ;
              }
              units kbps ;
            }
            leaf adjust-min-value {
              description 'Minimum bandwidth of adjustment.This attribute depen'
                        + 'd on adjust-max-value.'
                          ;
              type uint32 {
                range 0..4294967295 ;
              }
              units kbps ;
              default 0 ;
            }
            leaf adjust-multiple {
              description 'The mutiple of adjustment.This attribute depend on a'
                        + 'djust-enable.'
                          ;
              type uint16 {
                range 50..100 ;
              }
              default 100 ;
            }
            leaf collect-bandwidth {
              description "The collection bandwidth switch.If this attribute is"
                        + " setup,the tunnel just sample bandwidth and don't ad"
                        + "just bandwidth."
                          ;
              type uint8 {
                range 0..1 ;
              }
              default 0 ;
            }
            container overflow {
              presence 'overflow configuration' ;
              leaf overflow-limit {
                description 'The bandwidth overflow limits.When the overflow ti'
                          + 'me of sampled bandwidth is over the configurated l'
                          + 'imit during adjustment period,the tunnel will trig'
                          + 'ger a bandwidth adjustment.'
                            ;
                type uint16 {
                  range 1..10 ;
                }
                mandatory true ;
              }
              leaf overflow-percent {
                description 'Bandwidth change percent to trigger an overflow.' ;
                type uint32 {
                  range 1..100 ;
                }
                mandatory true ;
              }
              leaf overflow-bandwidth {
                description 'The value of overflow bandwidth.When the sampled b'
                          + 'andwidth is over this value,the overflow will be t'
                          + 'riggered.'
                            ;
                type uint32 {
                  range 10..4294967295 ;
                }
                units kbps ;
                default 10 ;
              }
            }
          }
        }
      }
      container auto-route {
        description 'Auto route of TE tunnel.' ;
        container forwarding-adjacency {
          description 'The forwarding-adjacency function. This function is excl'
                    + 'usive with short-cut.'
                      ;
          list tunnel {
            description 'Forwarding-adjacency list.' ;
            key name ;
            max-elements 131070 ;
            min-elements 0 ;
            leaf name {
              description 'The tunnel name.' ;
              type ncd:ifname ;
            }
            leaf fa-enable {
              description 'Forwarding-adjacency enable.This attribute depend on'
                        + ' the tunnel role and direction-type,it just can be c'
                        + 'onfigured at ingress or bidirectional egress.'
                          ;
              type enumeration {
                enum disabled {
                  value 0 ;
                }
                enum enabled {
                  value 1 ;
                }
              }
              default disabled ;
            }
            leaf fa-holdtime {
              description 'Forwarding-adjacency holdtime.' ;
              type uint32 {
                range 0..4294967295 ;
              }
              default 0 ;
            }
          }
        }
        container short-cut {
          description 'The short-cut function. This function is exclusive with '
                    + 'forwarding-adjacency.'
                      ;
          list tunnel {
            description 'The tunnel AR list.' ;
            key name ;
            max-elements 131070 ;
            min-elements 0 ;
            leaf name {
              description 'The tunnel name.' ;
              type ncd:ifname ;
            }
            leaf ar-enable {
              description 'The tunnel auto route switch.This attribute depend o'
                        + 'n the tunnel role.It just can be confitured at ingre'
                        + 'ss.'
                          ;
              type enumeration {
                enum disabled {
                  value 0 ;
                }
                enum enabled {
                  value 1 ;
                }
              }
              default disabled ;
            }
            leaf ar-metric-type {
              description 'Auto route metric type.' ;
              type enumeration {
                enum igp {
                  value 0 ;
                }
                enum defaulAbsolute {
                  value 1 ;
                }
                enum absolute {
                  value 2 ;
                }
                enum relative {
                  value 3 ;
                }
              }
              default igp ;
            }
            leaf ar-relative-metric {
              description 'The relative metric of AR,it is relative to IGP metr'
                        + 'ic.'
                          ;
              type int32 {
                range -10..10 ;
              }
              default 0 ;
            }
            leaf ar-absolute-metric {
              description 'The absolute metric of AR.' ;
              type uint32 {
                range 0..4294967295 ;
              }
              default 0 ;
            }
          }
        }
      }
      container srlg {
        description 'Configuration of srlg.' ;
        container one-to-one {
          description 'The one-to-one type of srlg. The enable and mode should '
                    + 'configure together.'
                      ;
          leaf enable {
            description 'One-to-one type enable.' ;
            type enumeration {
              enum disabled {
                value 0 ;
              }
              enum enabled {
                value 1 ;
              }
            }
            default disabled ;
          }
          leaf mode {
            description 'The mode of one-to-one type.' ;
            type enumeration {
              enum none {
                value 0 ;
              }
              enum force {
                value 1 ;
              }
              enum prefer {
                value 2 ;
              }
            }
            default none ;
          }
        }
        container facility {
          description 'The facility type of srlg. The enable and mode should co'
                    + 'nfigure together.'
                      ;
          leaf enable {
            description 'Facility type enable.' ;
            type enumeration {
              enum disabled {
                value 0 ;
              }
              enum enabled {
                value 1 ;
              }
            }
            default disabled ;
          }
          leaf mode {
            description 'The mode of facility type.' ;
            type enumeration {
              enum none {
                value 0 ;
              }
              enum force {
                value 1 ;
              }
              enum prefer {
                value 2 ;
              }
            }
            default none ;
          }
        }
        container auto-backup {
          description 'The auto-backup type of srlg. The enable and mode should'
                    + ' configure together.'
                      ;
          leaf enable {
            description 'Auto-backup type enable.' ;
            type enumeration {
              enum disabled {
                value 0 ;
              }
              enum enabled {
                value 1 ;
              }
            }
            default disabled ;
          }
          leaf mode {
            description 'The mode of auto-backup type.' ;
            type enumeration {
              enum none {
                value 0 ;
              }
              enum force {
                value 1 ;
              }
              enum prefer {
                value 2 ;
              }
            }
            default none ;
          }
        }
        container hotstandby {
          description 'The hotstandy type of srlg. The enable and mode should c'
                    + 'onfigure together.'
                      ;
          leaf enable {
            description 'Auto-backup type enable.' ;
            type enumeration {
              enum disabled {
                value 0 ;
              }
              enum enabled {
                value 1 ;
              }
            }
            default disabled ;
          }
          leaf mode {
            description 'The mode of hotstandby type.' ;
            type enumeration {
              enum none {
                value 0 ;
              }
              enum force {
                value 1 ;
              }
              enum prefer {
                value 2 ;
              }
            }
            default none ;
          }
        }
        list interface {
          description 'Interface list for SRLG.' ;
          key 'name value' ;
          ncd:select 'name value' ;
          max-elements 765 ;
          leaf name {
            description 'Interface name.' ;
            type ncd:ifname ;
          }
          leaf value {
            description 'Configure SRLG value on specified interface. Every TE '
                      + 'interface can configure 3 SRLG value. The value range '
                      + 'from 0 to 4294967295.'
                        ;
            type uint32 {
              range 0..4294967295 ;
            }
          }
        }
      }
      container hotstandby {
        description 'The configuration of hotstandby.This function depend on rr'
                  + 'o-enable.'
                    ;
        presence 'configuration of hotstandby' ;
        list tunnel {
          description 'The tunnel configuration of hotstandby function.' ;
          key 'name path-option-id' ;
          max-elements 131070 ;
          leaf name {
            description 'The tunnel name.' ;
            type ncd:ifname ;
          }
          leaf path-option-id {
            description 'The attribute is the path-option which is protected.' ;
            type uint8 {
              range 1..16 ;
            }
          }
          choice pathtype {
            description 'To assign path type of backup lsp. Three types.' ;
            mandatory true ;
            case dynamic {
              description 'Dynamic Path Selection.' ;
              leaf dynamic {
                description 'The path type is dynamic.' ;
                type empty ;
                mandatory true ;
              }
              leaf prefer {
                description "If this attribute is configured, the backup path o"
                          + "nly can't be completely duplicated with primary pa"
                          + "th, otherwise the backup path must be different fr"
                          + "om primary path."
                            ;
                type boolean ;
                default false ;
              }
            }
            case explicit-id {
              description 'Id-based explicit path selection.' ;
              leaf path-id {
                description 'The configured explicit path ID.' ;
                type uint16 {
                  range 1..65535 ;
                }
                mandatory true ;
              }
              leaf id-exclude {
                description 'This attribute can be used to indicate whether bac'
                          + 'kup path need exclude primary path strictly.'
                            ;
                type boolean ;
                default false ;
              }
            }
            case explicit-name {
              description 'Based on the name of the explicit path selection.' ;
              leaf path-name {
                description 'The configured explicit path name.' ;
                type string {
                  length 1..64 ;
                }
                mandatory true ;
              }
              leaf name-exclude {
                description 'This attribute can be used to indicate whether bac'
                          + 'kup path need exclude primary path strictly.'
                            ;
                type boolean ;
                default false ;
              }
            }
          }
        }
      }
      container static-tunnels {
        description 'The configuration of static tunnel.' ;
        presence 'configuration of static tunnel' ;
        list tunnel {
          description 'The static tunnel list.' ;
          key name ;
          max-elements 131070 ;
          leaf name {
            description 'The tunnel name.' ;
            type ncd:ifname ;
          }
          leaf activation {
            description 'The activation of static tunnel enable.' ;
            type enumeration {
              enum disabled {
                value 0 ;
              }
              enum enabled {
                value 1 ;
              }
            }
            default enabled ;
          }
          leaf sd {
            description 'The switch of static tunnel sd.' ;
            type enumeration {
              enum enabled {
                value 1 ;
              }
              enum disabled {
                value 2 ;
              }
            }
            default disabled ;
          }
          leaf performance-switch {
            description 'The switch of static tunnel performance statistics.' ;
            type enumeration {
              enum off {
                value 0 ;
              }
              enum on {
                value 1 ;
              }
            }
            default off ;
          }
          leaf track-name {
            description 'The track name.' ;
            type string {
              length 1..31 ;
            }
          }
          container role-type {
            description 'The tunnel role and direction type.' ;
            presence 'Configure tunnel role and type.' ;
            leaf role {
              description 'The static tunnel role including ingress,transit and'
                        + ' egress.'
                          ;
              type enumeration {
                enum ingressNode {
                  value 1 ;
                }
                enum transitNode {
                  value 2 ;
                }
                enum egressNode {
                  value 3 ;
                }
              }
              mandatory true ;
            }
            leaf direction-type {
              description 'The static tunnel direction type including unidirect'
                        + 'ional and bidirectional.'
                          ;
              type enumeration {
                enum unidirectional {
                  value 1 ;
                }
                enum bidirectional {
                  value 2 ;
                }
              }
              mandatory true ;
            }
          }
          container triple {
            description 'The tunnel triple elements.' ;
            presence 'Configure tunnel triple.' ;
            leaf ingress-tunnel-id {
              description 'The ingress tunnel ID,it is used to locate ingress t'
                        + 'unnel. This attribute is determined by product.'
                          ;
              type uint32 {
                range 1..65535 ;
              }
              mandatory true ;
            }
            leaf ingress-id {
              description 'The ingress route ID.' ;
              type ncd:ipv4-address ;
              mandatory true ;
            }
            leaf egress-id {
              description 'The egress route ID.' ;
              type ncd:ipv4-address ;
              mandatory true ;
            }
          }
          container policy {
            description 'The static tunnel policy class.This attribute depend o'
                      + 'n the tunnel role and direction-type,it just can be co'
                      + 'nfigured at ingress or bidirectional egress.'
                        ;
            leaf class {
              description 'The tunnel policy class configuration. From 0 to 7 r'
                        + 'epresent normal configuration. Ingress and egress of'
                        + ' co-tunnel use 255 as its default value.'
                          ;
              type uint8 {
                range '0..7 | 255' ;
              }
            }
          }
          container tunnel-bind {
            description 'The associated static tunnel bind function.' ;
            presence 'Configure bound tunnel.' ;
            leaf associated-tunnel-id {
              description 'The associated tunnel id which is the tunnel id of a'
                        + 'ccess tunnel. This function can only be configured a'
                        + 't ingress node.This attribute is determined by produ'
                        + 'ct.'
                          ;
              type uint32 {
                range 1..131072 ;
              }
              mandatory true ;
            }
          }
          container lsps {
            description 'The configured lsp of static tunnel.' ;
            list lsp {
              description 'Lsp list.' ;
              key 'tunnel-id lsp-id' ;
              max-elements 1 ;
              leaf tunnel-id {
                description 'The tunnel ID. This attribute is determined by pro'
                          + 'duct.'
                            ;
                type uint32 {
                  range 1..131072 ;
                }
              }
              leaf lsp-id {
                description "The tunnel's lsp ID." ;
                type uint16 {
                  range 1..65535 ;
                }
              }
              container positive-attribute {
                description 'The configuration of positive out-section and in-s'
                          + 'ection.'
                            ;
                leaf inport {
                  description 'The positive in-port.This attribute must be conf'
                            + 'igured with inlabel at the same time.'
                              ;
                  type ncd:ifname ;
                }
                leaf inlabel {
                  description 'The positive in-label. This attribute must be co'
                            + 'nfigured with inport at the same time.'
                              ;
                  type uint32 {
                    range '0 | 3 | 16..1048575' ;
                  }
                }
                leaf outport {
                  description 'The positive out-port.This attribute must be con'
                            + 'figured with outlabel at the same time.'
                              ;
                  type ncd:ifname ;
                }
                leaf outlabel {
                  description 'The positive out-label.This attribute must be co'
                            + 'nfigured with outport at the same time.'
                              ;
                  type uint32 {
                    range '0 | 3 | 16..1048575' ;
                  }
                }
                leaf next-hop {
                  description 'The positive next-hop.' ;
                  type ncd:ipv4-address {
                    pattern '([1-9]|[1-9][0-9]|1[0-9][0-9]|2[0-4][0-9]|25[0-5])'
                          + '(.([0-9]|[1-9][0-9]|1[0-9][0-9]|2[0-4][0-9]|25[0-5'
                          + '])){3}'
                            ;
                  }
                }
                leaf out-bandwidth {
                  description 'The positive out bandwidth which is exclusive wi'
                            + 'th ct-bandwidth.  The min, max and default value'
                            + ' of this attribute are determined by product.'
                              ;
                  type uint32 {
                    range 0..4294967295 ;
                  }
                  units kbps ;
                  default 0 ;
                }
                leaf out-burst {
                  description 'The burst of out bandwidth. This attribute must '
                            + 'be configure after out-bandwidth.  The min, max '
                            + 'and default value of this attribute are determin'
                            + 'ed by product.'
                              ;
                  type uint32 {
                    range 1..4294967295 ;
                  }
                  units byte ;
                }
                leaf out-peak {
                  description "The peak of out bandwidth. This attribute can't "
                            + "be less than out-bandwidth.This attribute must b"
                            + "e configure after out-bandwidth.  The min, max a"
                            + "nd default value of this attribute are determine"
                            + "d by product."
                              ;
                  type uint32 {
                    range 0..4294967295 ;
                  }
                  units kpbs ;
                  default 0 ;
                }
                leaf out-excess-burst {
                  description 'The excess-burst of out bandwidth. This attribut'
                            + 'e must be configure after out-bandwidth.  The mi'
                            + 'n, max and default value of this attribute are d'
                            + 'etermined by product.'
                              ;
                  type uint32 {
                    range 0..4294967295 ;
                  }
                  units byte ;
                }
                leaf share-tunnel {
                  description 'The tunnel of bandwidth share, The out port of s'
                            + 'hared tunnel must be the same with the out port '
                            + 'of this tunnel, and the shared tunnel must confi'
                            + 'gure bandwidth first.'
                              ;
                  type string {
                    length 1..31 ;
                  }
                }
                leaf pre-hop {
                  description 'The pre-hop of  positive in-section.' ;
                  type ncd:ipv4-address {
                    pattern '([1-9]|[1-9][0-9]|1[0-9][0-9]|2[0-4][0-9]|25[0-5])'
                          + '(.([0-9]|[1-9][0-9]|1[0-9][0-9]|2[0-4][0-9]|25[0-5'
                          + '])){3}'
                            ;
                  }
                }
                leaf convergence-ratio-mode {
                  description 'The bandwidth convergence ratio mode. the conver'
                            + 'gence ratio mode can only be configurated at inh'
                            + 'erit or config mode.'
                              ;
                  type enumeration {
                    enum inherit {
                      value 1 ;
                    }
                    enum config {
                      value 2 ;
                    }
                  }
                }
                leaf convergence-ratio-value {
                  description 'The bandwidth convergence ratio value. the conve'
                            + 'rgence ratio value can only be configurated betw'
                            + 'een 1 and 100 pecent.'
                              ;
                  type uint8 {
                    range 1..100 ;
                  }
                  default 100 ;
                }
              }
              container reverse-attribute {
                description 'The configuration of reverse out-section in-sectio'
                          + 'n and.'
                            ;
                leaf inport {
                  description 'The reverse in-port.This attribute must be confi'
                            + 'gured with inlabel at the same time.'
                              ;
                  type ncd:ifname ;
                }
                leaf inlabel {
                  description 'The reverse in-label. This attribute must be con'
                            + 'figured with inport at the same time.'
                              ;
                  type uint32 {
                    range '0 | 3 | 16..1048575' ;
                  }
                }
                leaf outport {
                  description 'The reverse out-port.This attribute must be conf'
                            + 'igured with outlabel at the same time.'
                              ;
                  type ncd:ifname ;
                }
                leaf outlabel {
                  description 'The reverse out-label.This attribute must be con'
                            + 'figured with outport at the same time.'
                              ;
                  type uint32 {
                    range '0 | 3 | 16..1048575' ;
                  }
                }
                leaf next-hop {
                  description 'The reverse next-hop.' ;
                  type ncd:ipv4-address {
                    pattern '([1-9]|[1-9][0-9]|1[0-9][0-9]|2[0-4][0-9]|25[0-5])'
                          + '(.([0-9]|[1-9][0-9]|1[0-9][0-9]|2[0-4][0-9]|25[0-5'
                          + '])){3}'
                            ;
                  }
                }
                leaf out-bandwidth {
                  description 'The reverse out bandwidth which is exclusive wit'
                            + 'h ct-bandwidth. The min, max and default value o'
                            + 'f this attribute are determined by product.'
                              ;
                  type uint32 {
                    range 0..4294967295 ;
                  }
                  units kbps ;
                  default 0 ;
                }
                leaf out-burst {
                  description 'The burst of out bandwidth. This attribute must '
                            + 'be configure after out-bandwidth.  The min, max '
                            + 'and default value of this attribute are determin'
                            + 'ed by product.'
                              ;
                  type uint32 {
                    range 0..4294967295 ;
                  }
                  units byte ;
                }
                leaf out-peak {
                  description "The peak of out bandwidth. This attribute can't "
                            + "be less than out-bandwitdth.This attribute must "
                            + "be configure after out-bandwidth.  The min, max "
                            + "and default value of this attribute are determin"
                            + "ed by product."
                              ;
                  type uint32 {
                    range 0..4294967295 ;
                  }
                  units kbps ;
                  default 0 ;
                }
                leaf out-excess-burst {
                  description 'The excess-burst of out bandwidth. This attribut'
                            + 'e must be configure after out-bandwidth.  The mi'
                            + 'n, max and default value of this attribute are d'
                            + 'etermined by product.'
                              ;
                  type uint32 {
                    range 0..4294967295 ;
                  }
                  units byte ;
                }
                leaf share-tunnel {
                  description 'The tunnel of bandwidth share, The out port of s'
                            + 'hared tunnel must be the same with the out port '
                            + 'of this tunnel, and the shared tunnel must confi'
                            + 'gure bandwidth first.'
                              ;
                  type string {
                    length 1..31 ;
                  }
                }
                leaf pre-hop {
                  description 'The pre-hop of  reverse in-section.' ;
                  type ncd:ipv4-address {
                    pattern '([1-9]|[1-9][0-9]|1[0-9][0-9]|2[0-4][0-9]|25[0-5])'
                          + '(.([0-9]|[1-9][0-9]|1[0-9][0-9]|2[0-4][0-9]|25[0-5'
                          + '])){3}'
                            ;
                  }
                }
                leaf convergence-ratio-mode {
                  description 'The bandwidth convergence ratio mode. the conver'
                            + 'gence ratio mode can only be configurated at inh'
                            + 'erit or config mode.'
                              ;
                  type enumeration {
                    enum inherit {
                      value 1 ;
                    }
                    enum config {
                      value 2 ;
                    }
                  }
                }
                leaf convergence-ratio-value {
                  description 'The bandwidth convergence ratio value. the conve'
                            + 'rgence ratio value can only be configurated betw'
                            + 'een 1 and 100 pecent.'
                              ;
                  type uint8 {
                    range 1..100 ;
                  }
                  default 100 ;
                }
              }
              container positive-ct-bandwidths {
                description 'The positive ct-bandwidth of static tunnel which i'
                          + 's exclusive with positive out-bandwidth and tunnel'
                          + '-rate-limit.'
                            ;
                list positive-ct-bandwidth {
                  description 'The positive ct-bandwidth list.' ;
                  key class-type ;
                  max-elements 131070 ;
                  leaf class-type {
                    description 'The configuration of class type.' ;
                    type uint8 {
                      range '0..7 | 255' ;
                    }
                  }
                  leaf bandwidth {
                    description 'The bandwidth of class type.' ;
                    type uint32 {
                      range 1..4294967295 ;
                    }
                    units kbps ;
                    mandatory true ;
                  }
                }
              }
              container reverse-ct-bandwidths {
                description 'The reverse ct-bandwidth of static tunnel which is'
                          + ' exclusive with reverse out-bandwidth and tunnel-r'
                          + 'ate-limit.'
                            ;
                list reverse-ct-bandwidth {
                  description 'The positive ct-bandwidth list.' ;
                  key class-type ;
                  max-elements 131070 ;
                  leaf class-type {
                    description 'The configuration of class type.' ;
                    type uint8 {
                      range '0..7 | 255' ;
                    }
                  }
                  leaf bandwidth {
                    description 'The bandwidth of class type.' ;
                    type uint32 {
                      range 1..4294967295 ;
                    }
                    units kbps ;
                    mandatory true ;
                  }
                }
              }
            }
          }
        }
      }
      container te-ecmp-groups {
        description 'The configuration of ECMP-GROUP.' ;
        presence 'configuration of ECMP-GROUP.' ;
        list te-ecmp-group {
          description 'The ECMP-GROUP list.' ;
          key group-id ;
          max-elements 128 ;
          min-elements 1 ;
          leaf group-id {
            description 'ECMP-GROUP id.' ;
            type uint16 {
              range 1..65535 ;
            }
          }
          leaf load-share-policy {
            description 'Load-sharing policy of ECMP-GROUP.' ;
            type enumeration {
              enum per-stream {
                value 1 ;
              }
              enum per-packet {
                value 2 ;
              }
            }
            default per-stream ;
          }
          container te-ecmp-tunnels {
            description 'The configuration of ECMP-GROUP tunnels.' ;
            list te-ecmp-tunnel {
              description 'The ECMP-GROUP tunnel list.' ;
              key tunnel-id ;
              leaf tunnel-id {
                description 'Configure ECMP-GROUP tunnel.' ;
                type uint32 {
                  range 1..131072 ;
                }
              }
            }
          }
        }
      }
      container affinity {
        description 'Configuration of affinity.' ;
        presence 'configuration of affinity' ;
        container tunnels {
          description 'The tunnel configuration of affinity function.' ;
          list tunnel {
            description 'The tunnel list configuration of affinity function.' ;
            key 'name affinity-type bit-position' ;
            max-elements 131070 ;
            leaf name {
              description 'Tunnel name.' ;
              type ncd:ifname ;
            }
            leaf affinity-type {
              description 'The tunnel configuration of affinity type,exclude-an'
                        + 'y(1)/include-any(2)/include-all(3).'
                          ;
              type enumeration {
                enum exclude-any {
                  value 1 ;
                  description 'Configure the exclude-any affinity' ;
                }
                enum include-any {
                  value 2 ;
                  description 'Configure the include-any affinity' ;
                }
                enum include-all {
                  value 3 ;
                  description 'Configure the include-all affinity' ;
                }
              }
            }
            leaf bit-position {
              description 'The tunnel configuration of affinity bit position.' ;
              type uint8 {
                range 0..31 ;
              }
            }
          }
        }
        container interfaces {
          description 'The TE interface configuration of affinity function.' ;
          list interface {
            description 'The TE interface list configuration of affinity functi'
                      + 'on.'
                        ;
            key 'name bit-position' ;
            max-elements 8160 ;
            leaf name {
              description 'Interface name.' ;
              type ncd:ifname ;
            }
            leaf bit-position {
              description 'The TE interface configuration of affinity bit posit'
                        + 'ion.'
                          ;
              type uint8 {
                range 0..31 ;
              }
            }
          }
        }
      }
      container te-trunk {
        description 'The configuration of te-trunk.' ;
        presence 'configuration of te-trunk' ;
        list interface {
          description 'Interface list.' ;
          key name ;
          max-elements 255 ;
          leaf name {
            description 'The name of this interface.' ;
            type ncd:ifname ;
          }
        }
      }
    }
  }
  container state {
    description 'The branch of dynamic data model.' ;
    config false ;
    container mpls-te {
      description 'The state of MPLS-TE.' ;
      container dynamic-tunnel {
        description 'The dynamic tunnel information.' ;
        list tunnel {
          description 'The dynamic tunnel list.' ;
          key tunnel-id ;
          leaf tunnel-id {
            description 'The tunnel ID.' ;
            type uint16 ;
          }
          leaf in-use-pathoption {
            description 'The in use path option.' ;
            type uint32 ;
          }
          leaf oper-status {
            description 'The operation status of tunnel.' ;
            type enumeration {
              enum UNKNOWN {
                value 0 ;
              }
              enum UP {
                value 1 ;
              }
              enum DOWN {
                value 2 ;
              }
              enum WTR {
                value 4 ;
              }
            }
          }
          leaf inuselsp-chop-table-index {
            description 'This attribute is used to record chop table index of t'
                      + 'his tunnel.'
                        ;
            type uint32 ;
          }
          leaf inuselsp-arhop-table-index {
            description 'This attribute is used to record arhop table index of '
                      + 'this tunnel.'
                        ;
            type uint32 ;
          }
          leaf hotlsp-chop-table-index {
            description 'This attribute is used to record chop table index of t'
                      + 'his tunnel.'
                        ;
            type uint32 ;
          }
          leaf hotlsp-arhop-table-index {
            description 'This attribute is used to record arhop table index of '
                      + 'this tunnel.'
                        ;
            type uint32 ;
          }
          leaf wtrlsp-chop-table-index {
            description 'This attribute is used to record chop table index of t'
                      + 'his tunnel.'
                        ;
            type uint32 ;
          }
          leaf wtrlsp-arhop-table-index {
            description 'This attribute is used to record arhop table index of '
                      + 'this tunnel.'
                        ;
            type uint32 ;
          }
          leaf hsb-status {
            description 'The hsb status of tunnel.' ;
            type enumeration {
              enum UNKNOWN {
                value 0 ;
              }
              enum READY {
                value 1 ;
              }
              enum ACTIVE {
                value 2 ;
              }
            }
          }
          leaf inuse-lsp-id {
            description 'The lsp identifier inuse.' ;
            type uint16 ;
          }
          leaf hsb-lsp-id {
            description 'The lsp identifier of hsb.' ;
            type uint16 ;
          }
          leaf wtr-lsp-id {
            description 'The lsp identifier of wtr.' ;
            type uint16 ;
          }
        }
        container tunnel-chop {
          description 'The tunnel ERO,it is the path-compute result of ROUTE.' ;
          list ero {
            description 'The tunnel ERO list.' ;
            key 'hop-table-index hop-index' ;
            ncd:select 'hop-table-index hop-index' ;
            leaf hop-table-index {
              description 'The table index of chop.' ;
              type uint32 ;
            }
            leaf hop-index {
              description 'The index of ERO hop.' ;
              type uint32 ;
            }
            leaf addr-type {
              description 'The hop address type.' ;
              type enumeration {
                enum IPV4 {
                  value 1 ;
                }
                enum IPV6 {
                  value 2 ;
                }
                enum AS_NUM {
                  value 3 ;
                }
                enum UNNUM_IF {
                  value 4 ;
                }
                enum LSP_ID {
                  value 5 ;
                }
                enum UNNUM_V6 {
                  value 6 ;
                }
              }
            }
            leaf ip-addr {
              description 'The ip address of hop.' ;
              type ncd:ipv4-address ;
              default 0.0.0.0 ;
            }
            leaf prefix-len {
              description 'The prefix length of ip address.' ;
              type uint8 {
                range 0..64 ;
              }
              default 0 ;
            }
            leaf as-number {
              description 'AS number.' ;
              type uint16 ;
              default 0 ;
            }
            leaf addr-unnum {
              description 'The unnumbered ID.' ;
              type uint32 ;
              default 0 ;
            }
            leaf hop-type {
              description 'The hop type.' ;
              type enumeration {
                enum strictly {
                  value 1 ;
                }
                enum loose {
                  value 2 ;
                }
              }
            }
          }
        }
        container tnnl-ar-hop {
          description 'The tunnel RRO hop,It records the bypassed path informat'
                    + 'ion of tunnel.'
                      ;
          list rro {
            description 'The tunnel RRO hop list.' ;
            key 'hop-table-index hop-index' ;
            ncd:select 'hop-table-index hop-index' ;
            leaf hop-table-index {
              description 'The table index of arhop.' ;
              type uint32 ;
            }
            leaf hop-index {
              description 'The hop index of RRO.' ;
              type uint32 ;
            }
            leaf lsr-id {
              description 'The router id.' ;
              type ncd:ipv4-address ;
            }
            leaf if-ipaddr {
              description 'The in interface address of tunnel.' ;
              type ncd:ipv4-address ;
            }
            leaf if-ipmask {
              description 'The in interface mask of tunnel.' ;
              type uint32 ;
            }
            leaf path-inlabel {
              description 'The in label of the tunnel path.' ;
              type uint32 ;
            }
            leaf path-outlabel {
              description 'The out label of the tunnel path.' ;
              type uint32 ;
            }
            leaf resv-inlabel {
              description 'The in label of the tunnel resv.' ;
              type uint32 ;
            }
            leaf resv-outlabel {
              description 'The out label of the tunnel resv.' ;
              type uint32 ;
            }
          }
        }
      }
      container remote-tunnel {
        description 'The remote tunnel,it is related with ingress tunnel.' ;
        list tunnel {
          description 'The remote tunnel list.' ;
          key 'local-tunnel-id lsp-id ingress-id egress-id' ;
          ncd:select 'local-tunnel-id lsp-id ingress-id egress-id' ;
          leaf local-tunnel-id {
            description 'The local tunnel ID of remote tunnel.' ;
            type uint16 ;
          }
          leaf lsp-id {
            description 'The lsp id of remote tunnel.' ;
            type uint16 ;
          }
          leaf ingress-id {
            description 'The ingress LSR ID' ;
            type ncd:ipv4-address ;
          }
          leaf egress-id {
            description 'The egress LSR ID.' ;
            type ncd:ipv4-address ;
          }
          leaf in-interface {
            description 'The in interface of remote tunnel.' ;
            type string {
              length 1..31 ;
            }
            default unknown ;
          }
          leaf in-label {
            description 'The in label of remote tunnel.' ;
            type uint32 ;
            default 4294967295 ;
          }
          leaf out-interface {
            description 'The out interface of remote tunnel.' ;
            type string {
              length 1..31 ;
            }
            default unknown ;
          }
          leaf out-label {
            description 'The out label of remote tunnel.' ;
            type uint32 {
              range 0..4294967295 ;
            }
            default 4294967295 ;
          }
          leaf oper-status {
            description 'The operation status of remote tunnel.' ;
            type enumeration {
              enum down {
                value 0 ;
              }
              enum up {
                value 1 ;
              }
            }
            default down ;
          }
        }
      }
      container static-tunnel {
        description 'The state data of static tunnel.' ;
        list tunnel {
          description 'The static tunnel list.' ;
          key tunnel-id ;
          leaf tunnel-id {
            description 'The tunnel ID.' ;
            type uint32 ;
          }
          leaf oper-status {
            description 'The operation status of tunnel.' ;
            type enumeration {
              enum down {
                value 0 ;
              }
              enum up {
                value 1 ;
              }
            }
            default down ;
          }
          leaf admin-status {
            description 'The admin status of tunnel.' ;
            type enumeration {
              enum down {
                value 0 ;
              }
              enum up {
                value 1 ;
              }
            }
            default down ;
          }
          leaf associated-status {
            description 'The associated status of static tunnel.' ;
            type enumeration {
              enum disabled {
                value 1 ;
              }
              enum unbond {
                value 2 ;
              }
              enum bond {
                value 3 ;
              }
            }
            default disabled ;
          }
          leaf sample-bandwidth {
            description 'The sampled bandwidth of static tunnel.' ;
            type uint32 ;
            units kbps ;
            default 0 ;
          }
        }
      }
      container egress-tunnel {
        description 'The egress tunnel information.' ;
        list tunnel {
          description 'The egress tunnel list.' ;
          key 'tunnel-id ingress-id egress-id lsp-id' ;
          leaf tunnel-id {
            description 'The tunnel ID of egress tunnel.' ;
            type uint16 ;
          }
          leaf ingress-id {
            description 'The ingress LSR ID' ;
            type ncd:ipv4-address ;
          }
          leaf egress-id {
            description 'The egress LSR ID.' ;
            type ncd:ipv4-address ;
          }
          leaf lsp-id {
            description 'The lsp id of remote tunnel.' ;
            type uint16 ;
          }
          leaf lsp-arhop-index {
            description 'The arhop index of arhop.' ;
            type uint32 ;
          }
        }
      }
      container pathoption-addition {
        description 'The additional information of pathoption.' ;
        list pathoption {
          description 'The list of pathoption.' ;
          key 'tunnel-id option-id' ;
          ncd:select 'tunnel-id option-id' ;
          leaf tunnel-id {
            description 'The identifier of tunnel.' ;
            type uint16 ;
          }
          leaf option-id {
            description 'The option identifier of tunnel.' ;
            type uint8 ;
          }
          leaf last-time-rst {
            description 'The result of creat the lsp.' ;
            type uint8 ;
          }
          leaf lsp-id {
            description 'The lsp id of successed creat.' ;
            type uint16 ;
          }
          leaf errcode {
            description 'The type of wrong.' ;
            type uint16 ;
          }
          leaf errvalue {
            description 'The value of last failed creat.' ;
            type uint16 ;
          }
          leaf last-try-time {
            description 'The time of creat the lsp.' ;
            type ncd:datetime ;
          }
          leaf fail-node-ipaddr {
            description 'The wrong value of the failed creat.' ;
            type ncd:ipv4-address ;
          }
        }
      }
    }
  }
}
