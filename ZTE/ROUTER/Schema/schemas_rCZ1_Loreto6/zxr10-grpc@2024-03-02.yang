module zxr10-grpc {
  namespace "http://www.zte.com.cn/zxr10/netconf/schema/rosng/grpc" ;
  prefix grpc ;
  yang-version 1 ;
  organization "ZTE Corporation" ;
  contact "ZTE Corporation
  Nanjing Institute of ZTE Corporation
  No.68 Zijinghua Rd. Yuhuatai District, Nanjing, China
  Tel: +86-25-52870000" ;
  description 'The netconf model to describe grpc.' ;
  revision 2024-03-02 {
    description 'Initial version.' ;
  }

  container configuration {
    description 'Configuration model info.' ;
    container grpc {
      description 'Configure gRPC parameters.' ;
      container grpc-server {
        leaf enabled {
          type boolean ;

          default false ;
          description 'Enable gRPC service' ;
        }

        container keepalive {
          leaf enabled {
            type boolean ;

            default true ;
            description 'Configure keepalive of gRPC service' ;
          }

          description 'Configure keepalive of gRPC service.' ;
        }

        description 'gRPC server configuration mode' ;
      }

    }

  }

  container state {
    description 'State model info.' ;
    config false ;
  }

}
