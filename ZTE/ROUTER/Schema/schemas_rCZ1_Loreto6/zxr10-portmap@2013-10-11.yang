module zxr10-portmap {
  namespace 'http://www.zte.com.cn/zxr10/netconf/schema/rosng/portmap' ;
  prefix portmap ;
  import zxr10-netconf-defs {
    prefix ncd ;
    revision-date 2013-11-22 ;
  }
  organization 'ZTE Corporation' ;
  contact "ZTE Corporation  
\n"
        + "   Nanjing Institute of ZTE Corporation 
\n"
        + "   No.68 Zijinghua Rd. Yuhuatai District, Nanjing, China 
\n"
        + '   Tel: +86-25-52870000'
          ;
  description 'The netconf module to describe the Interface Relation.Like the m'
            + 'apping relation between pos interface and ulei interface.'
              ;
  revision 2013-10-11 {
    description 'The initial version' ;
  }
  container configuration {
    description 'Configure the mapping relation between interfaces' ;
    container portmap {
      description 'Describe the parameters of interface mapping relation to be '
                + 'configured'
                  ;
      container portmap-configuration {
        description 'Describe the parameters of interface mapping relation to b'
                  + 'e configured'
                    ;
        list interface {
          description 'The list of interfaces for configuring parameters' ;
          key src-interface ;
          leaf src-interface {
            description 'Source interface name' ;
            type ncd:ifname ;
          }
          leaf dst-interface {
            description 'Destination interface name' ;
            type ncd:ifname ;
            mandatory true ;
          }
        }
      }
    }
  }
}
