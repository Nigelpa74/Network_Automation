module of-config1.1.1 {
  namespace "urn:onf:of111:config:yang";
  prefix of11-config;
  yang-version 1;
  import ietf-yang-types {
    prefix yang;
  }

  import ietf-inet-types {
    prefix inet;
  }

  import zxr10-netconf-defs {
    prefix ncd;
  }

  organization "ONF Config Management Group";
  contact
    "tbd";

  description
    "NETCONF Operational Considerations
    Elements that are configurable, optional and have a default
    value MAY be reported by repliesto NETCONF <get-config>
    requests. All non-configurable values SHOULD be reported by
    replies to NETCONF <get> requests.
    Attempsto modify non-configurable elements with a NETCONF
    <edit-config> operation MUST result in an
    'operation-not-supported' error with type 'application'.
    When validating an <edit??config> operation the following
    errors MUST be detected:
    * Delete requests fornon-existent data. In this case a
    'data-missing' error is returned.
    * Create requests for existent data. In this case a
    'data-exists' error is returned.
    * If the NETCONF operation creates data nodes under a
    'choice', any existing nodes from other branches are
    deleted.";

  revision 2025-03-31 {
    description
      "Del the project FN.C89E for all.";

  }

  revision 2018-09-10 {
    description
      "Add case v6-endpoints and leaf local-endpoint-ipv6-adress, leaf remote-endpoint-ipv6-adress.";

  }

  revision 2017-08-02 {
    description
      "Delete leaf-list node and leaf port and leaf number.";

  }

  revision 2017-07-05 {
    description
      "Add leaf-list node and leaf port and leaf number.";

  }

  revision 2016-09-06 {
    description
      "Add leaf node,capable-switch->logical-switches->resources->certificate";

  }

  revision 2016-07-27 {
    description
      "Add port features, include current/advertised/supported/advertised-peer";

  }

  revision 2016-07-22 {
    description
      "Add list owned-certificate leaf resource-id,leaf certificate,container private-key,choice key-type,case rsa,leaf modulus,leaf exponent; list external-certificate,leaf resource-id,leaf certificate.";

  }

  revision 2016-03-16 {
    description
      "Add list packets-port-statistics and leaf port->number,name";

  }

  revision 2011-12-07 {
    description
      "First Version";

    reference "tbd";
  }

  typedef OFConfigId {
    type inet:uri;

    description
      "Generic type of an identifier in OF-CONFIG";

  }

  typedef OFConfigurationPointProtocolType {
    type enumeration {
      enum ssh {
        value 0;
      }

    }

    description
      "Possible protocols to connect ot an OF
      Configuration Point";

  }

  typedef OFOpenFlowVersionType {
    type enumeration {
      enum not-applicable {
        value 0;
      }

      enum 1.0 {
        value 1;
      }

      enum 1.0.1 {
        value 2;
      }

      enum 1.1 {
        value 3;
      }

      enum 1.2 {
        value 4;
      }

      enum 1.3 {
        value 5;
      }

      enum 1.3.1 {
        value 6;
      }

    }

    description
      "This enumeration contains the all OpenFlow
      versions released so far.";

  }

  typedef datapath-id-type {
    type string {
      pattern "[0-9a-fA-F]{2}(:[0-9a-fA-F]{2}){7}";

    }

    description
      "The datapath-id type represents an OpenFlow
      datapath identifier.";

  }

  typedef OFTenthOfAPercentType {
    type uint16 {
      range 0..1000;

    }

    units "1/10 of a percent";
    description
      "This type defines a value in tenth of a percent.";

  }

  typedef OFUpDownStateType {
    type enumeration {
      enum up {
        value 0;
      }

      enum down {
        value 1;
      }

    }

    description
      "Type to specify state information for a port or a
      connection.";

  }

  typedef OFPortRateType {
    type enumeration {
      enum 10Mb-HD {
        value 0;
      }

      enum 10Mb-FD {
        value 1;
      }

      enum 100Mb-HD {
        value 2;
      }

      enum 100Mb-FD {
        value 3;
      }

      enum 1Gb-HD {
        value 4;
      }

      enum 1Gb-FD {
        value 5;
      }

      enum 10Gb {
        value 6;
      }

      enum 40Gb {
        value 7;
      }

      enum 100Gb {
        value 8;
      }

      enum 1Tb {
        value 9;
      }

      enum other {
        value 10;
      }

    }

    description
      "Type to specify the rate of a port including the
      duplex transmission feature. Possible rates are 10Mb, 100Mb,
      1Gb, 10Gb, 40Gb, 100Gb, 1Tb or other. Rates of 10Mb, 100Mb
      and 1 Gb can support half or full duplex transmission.";

  }

  typedef OFActionType {
    type enumeration {
      enum output {
        value 0;
      }

      enum copy-ttl-out {
        value 1;
      }

      enum copy-ttl-in {
        value 2;
      }

      enum set-mpls-ttl {
        value 3;
      }

      enum dec-mpls-ttl {
        value 4;
      }

      enum push-vlan {
        value 5;
      }

      enum pop-vlan {
        value 6;
      }

      enum push-mpls {
        value 7;
      }

      enum pop-mpls {
        value 8;
      }

      enum set-queue {
        value 9;
      }

      enum group {
        value 10;
      }

      enum set-nw-ttl {
        value 11;
      }

      enum dec-nw-ttl {
        value 12;
      }

      enum set-field {
        value 13;
      }

      enum push-pbb {
        value 14;
      }

      enum pop-pbb {
        value 15;
      }

    }

    description
      "The types of actions defined in OpenFlow Switch
      Specification versions 1.2, 1.3, and 1.3.1";

  }

  typedef OFInstructionType {
    type enumeration {
      enum apply-actions {
        value 0;
      }

      enum clear-actions {
        value 1;
      }

      enum write-actions {
        value 2;
      }

      enum write-metadata {
        value 3;
      }

      enum goto-table {
        value 4;
      }

      enum meter {
        value 5;
      }

      enum experimenter {
        value 6;
      }

    }

    description
      "The types of instructions defined in OpenFlow
      Switch Specification versions 1.2, 1.3, and 1.3.1.";

  }

  typedef OFMatchFieldType {
    type enumeration {
      enum input-port {
        value 0;
      }

      enum physical-input-port {
        value 1;
      }

      enum metadata {
        value 2;
      }

      enum ethernet-dest {
        value 3;
      }

      enum ethernet-src {
        value 4;
      }

      enum ethernet-frame-type {
        value 5;
      }

      enum vlan-id {
        value 6;
      }

      enum vlan-priority {
        value 7;
      }

      enum ip-dscp {
        value 8;
      }

      enum ip-ecn {
        value 9;
      }

      enum ip-protocol {
        value 10;
      }

      enum ipv4-src {
        value 11;
      }

      enum ipv4-dest {
        value 12;
      }

      enum tcp-src {
        value 13;
      }

      enum tcp-dest {
        value 14;
      }

      enum udp-src {
        value 15;
      }

      enum udp-dest {
        value 16;
      }

      enum sctp-src {
        value 17;
      }

      enum sctp-dest {
        value 18;
      }

      enum icmpv4-type {
        value 19;
      }

      enum icmpv4-code {
        value 20;
      }

      enum arp-op {
        value 21;
      }

      enum arp-src-ip-address {
        value 22;
      }

      enum arp-target-ip-address {
        value 23;
      }

      enum arp-src-hardware-address {
        value 24;
      }

      enum arp-target-hardware-address {
        value 25;
      }

      enum ipv6-src {
        value 26;
      }

      enum ipv6-dest {
        value 27;
      }

      enum ipv6-flow-label {
        value 28;
      }

      enum icmpv6-type {
        value 29;
      }

      enum icmpv6-code {
        value 30;
      }

      enum ipv6-nd-target {
        value 31;
      }

      enum ipv6-nd-source-link-layer {
        value 32;
      }

      enum ipv6-nd-target-link-layer {
        value 33;
      }

      enum mpls-label {
        value 34;
      }

      enum mpls-tc {
        value 35;
      }

      enum mpls-bos {
        value 36;
      }

      enum pbb-isid {
        value 37;
      }

      enum tunnel-id {
        value 38;
      }

      enum ipv6-exthdr {
        value 39;
      }

      enum pbb-uca {
        value 41;
      }

      enum tcp-flags {
        value 42;
      }

      enum actset_output {
        value 43;
      }

      enum packet_type {
        value 44;
      }

    }

    description
      "The types of match field defined in OpenFlow
      Switch Specification versions 1.2, 1.3, and 1.3.1.";

  }

  typedef hex-binary {
    type binary;

    description
      "hex binary encoded string";

    reference "http://www.w3.org/TR/2004/REC-xmlschema-2-
    20041028/datatypes.html#hexBinary";
  }

  container capable-switch {
    description
      "The OpenFlow Capable Switch serves as the root
      element for an OpenFlow configuration. It contains logical
      switches and resources that can be assigned to logical
      switches. It may have relations to OpenFlow Configuration
      Points.";

    presence capable-switch-0-default;
    leaf id {
      description
        "A unique but locally arbitrary identifier that

        uniquely identifies a Capable Switch within the context of

        potential OpenFlow Configuration Points. It MUST be

        persistent across reboots of the OpenFlow Capable Switch.

        This element MUST be present in the NETCONF data store.

        If this element is not present in a NETCONF <edit-config>

        operation 'create', 'merge' or 'replace' and the parent

        element does not exist, a 'data-missing'error is

        returned.";

      type inet:uri {
        length 1..63;

      }

      mandatory true;
    }

    leaf config-version {
      config false;
      description
        "The maximum supported OF-CONFIG version that is
        supported by the OpenFlow Capable Switch. For switches
        implementing this version of the OF-CONFIG protocol this
        MUST always be 1.1.1.
        This object can be used to identify the OF-CONFIG version
        a capable switch supports beginning with version 1.1.1 of
        OF-CONFIG. In addtion the supported version can be
        determined by the namespace the OpenFlow Capable Switch
        returns to configuration request of an element (like
        capable-switch) that is present in all OF-CONFIG versions
        specified so far. This is the only possiblity to identify
        OF-CONFIG versions prior to OF-CONFIG 1.1.1.";

      type string {
        length 1..63;

      }

    }

    container configuration-points {
      description
        "The list of all Configuration Points.";

      list configuration-point {
        description
          "The list of all Configuration Points known to

          the OpenFlow Capable Switch that may manage it using

          OF-CONFIG.

          The element 'id' of OFConfigurationType MUST be unique

          within this list.";

        key id;
        leaf id {
          description
            "A unique but locally arbitrary identifier that
            identifies a Configuration Point within the context of an
            OpenFlow Capable Switch.
            This element MUST be present to identify the configuration
            point.";

          type OFConfigId {
            length 1..63;

          }

          mandatory true;
        }

        leaf uri {
          description
            "A locator of the Configuration Point. It

            identifies the location of the Configuration Point as a

            service resource andMUST include all information necessary



            for the OpenFlowCapable Switch to connect to the

            Configuration Point or re-connect to it should it become

            disconnected. Such information MAY include, for example,

            protocol, fully qualified domain name, IP address, port

            number, etc.

            This element MUSTbe present in the NETCONF data store.

            If this element is not present in a NETCONF <edit-config>

            operation 'create', 'merge' or 'replace' and the parent

            element does not exist, a 'data-missing' error is

            returned.";

          type inet:uri {
            length 1..63;

          }

          mandatory true;
        }

        leaf protocol {
          description
            "The transport protocol that the Configuration

            Point uses when communicating via NETCONF with the OpenFlow

            Capable Switch.

            This element is optional. If it is not present its value

            defaults to 'ssh'.";

          reference "The mappings of NETCONF to different transport
          protocols are defined in RFC 6242 for SSH, RFC 4743 for
          SOAP, RFC 4744 for BEEP, and RFC 5539 for TLS";
          type OFConfigurationPointProtocolType;

          default ssh;
        }

      }

    }

    container resources {
      description
        "A lists containing all resources of the OpenFlow
        Capable Switch that can be used by OpenFlow Logical
        Switches. Resources are listed here independent of their
        actual assignment to OpenFlow Logical Switches. They may
        be available to be assigned to an OpenFlow Logical Switch
        or already in use by an OpenFlow Logical Switch.";

      list port {
        description
          "The list contains all port resources of the

          OpenFlow Capable Switch.

          The element 'resource-id' of OFPortType MUST be unique

          within this list.";

        key resource-id;
        leaf resource-id {
          description
            "A unique but locally arbitrary identifier that
            uniquely identifies an OpenFlow Port within the context
            of an OpenFlow Logical Switch. It MUST be persistent
            across reboots of the OpenFlow Capable Switch.
            This element MUST be present to identify the OpenFlow

            resource.";

          type ncd:ifname {
            length 1..31;

          }

          mandatory true;
        }

        leaf number {
          config false;
          description
            "This number identifies the OpenFlow Port to OpenFlow Controllers. It is assigned to an OpenFlow Port latest when the OpenFlow Port is associated with and OpenFlow Logical Switch. If the OpenFlow Port is associated with an OpenFlow Logical Switch, this element MUST be unique within the context of the OpenFlow Logical Switch. OpenFlow Capable Switch implementations may choose to assign values to OpenFlow Ports that are unique within the context of the OpenFlow Logical Switch. These numbers can be used independent of assignments to OpenFlow Logical Switches. Other implementations may assign values to this element only if the OpenFlow Port is assigned to an OpenFlow Logical Switch. If no value is currently assigned to this element then this element MUST NOT be included in replies to NETCONF <get> requests. Since this element is not configurable with the NETCONF protocol it MUST NOT be included in replies to NETCONF <get-config> requests.";

          type uint32;

          ncd:revise-date 2016-03-16;
        }

        leaf name {
          config false;
          description
            "This element assists OpenFlow Controllers in identifying OpenFlow Ports. This element is not to be set by the OP-CONFIG protocol, but it is set by the switch implementation. It may be set at start-up time of an OpenFlow Capable Switch or when the OpenFlow Port is assigned to an OpenFlow Logical Switch. It MAY also be not set at all. If this element is set to a value other than the empty string when being assigned to an OpenFlow Logical Switch, then the value of this element MUST be unique within the context of the OpenFlow Logical Switch. If no value or the empty string is currently assigned to this element then this element MUST not be included in replies to NETCONF <get> requests. Since this element is not configurable with the NETCONF protocol it MUST NOT be included in replies to NETCONF <get-config> requests.";

          type string {
            length 1..31;

          }

          ncd:revise-date 2016-03-16;
        }

        choice tunnel-type {
          description
            "Tunnels are modeled as logical ports.

            Elements in this choice are not configurable and can only

            be retrieved by NETCONF <get> operations. Attemps to modify

            this element and itschildren with a NETCONF <edit-config>

            operation MUST result in an 'operation-not-supported' error

            with type 'application'.

            Only elements from one choice must exist at a time.";

          case vxlan-tunnel {
            description
              "Properties of a VxLAN tunnel.";

            container vxlan-tunnel {
              description
                "Properties of a VxLAN tunnel.";

              presence vxlan-tunnel;
              choice endpoints {
                description
                  "VxLAN tunnel endpoints.";

                mandatory true;
                case v4-endpoints {
                  description
                    "VxLAN tunnel IPv4 endpoints.";

                  leaf local-endpoint-ipv4-adress {
                    description
                      "The IPv4 address of the local tunnel endpoint.";

                    type inet:ipv4-address;

                  }

                  leaf remote-endpoint-ipv4-adress {
                    description
                      "The IPv4 address of the remote tunnel endpoint.";

                    type inet:ipv4-address;

                  }

                }

                case v6-endpoints {
                  description
                    "VxLAN tunnel IPv6 endpoints.";

                  leaf local-endpoint-ipv6-adress {
                    description
                      "The IPv6 address of the local tunnel endpoint.";

                    type inet:ipv6-address;

                  }

                  leaf remote-endpoint-ipv6-adress {
                    description
                      "The IPv6 address of the remote tunnel endpoint.";

                    type inet:ipv6-address;

                  }

                  ncd:revise-date 2018-09-10;
                }

              }

            }

          }

        }

        container features {
          config false;
          container current {
            description
              "The features (rates, duplex, etc.) of the port, that are currently in use. Children of this element are not configurable and can only be retrieved by NETCONF <get> operations. Attemps to modify this element and its children with a NETCONF <edit-config> operation MUST result in an 'operation-not-supported' error with type 'application'.";

            leaf rate {
              description
                "The transmission rate that is currently used.The value MUST indicate a valid forwarding rate.The current Port Feature set MUST contain this element exactly once. The other Port Feature sets MAY contain this element more than once. If this element appears more than once in a Port Feature set than the value MUST be unique within the Port Feature set.";

              type OFPortRateType;

            }

            leaf auto-negotiate {
              description
                "Specifies the administrative state of the forwarding rate auto-negotiation protocol at this OpenFlow Port.";

              type boolean;

              default true;
            }

            leaf medium {
              description
                "This element MUST indicate a valid physical medium used by the OpenFlow Port. The current Port Feature set MUST contain this element exactly once. The other Port Feature sets MAY contain this element more than once. If this element appears more than once in a Port Feature set than the value MUST be unique within the Port Feature set.";

              type enumeration {
                enum copper {
                  value 0;
                }

                enum fiber {
                  value 1;
                }

              }

            }

            leaf pause {
              description
                "Specifies if pausing of transmission is supported at all and if yes if it is asymmetric or symmetric.";

              type enumeration {
                enum unsupported {
                  value 0;
                }

                enum symmetric {
                  value 1;
                }

                enum asymmetric {
                  value 2;
                }

              }

            }

          }

          container advertised {
            description
              "The features (rates, duplex, etc.) of the port, that are advertised to the peer port. NETCONF <edit-config> operations MUST be implemented as follows: * The 'resource-id' element of OFResoureType MUST be present in the path or in the filter at all <edit-config> operations to identify the port. * Ifthe operation is 'merge' or 'replace', the element is created if it does not exist, and its value is set to the value found in the XML RPC data. * If the operation is 'create', the element is created if it does not exist. If the element already exists, a 'data exists' error is returned. * If the operation is 'delete', the element is deleted if it exists. Ifthe element does not exist, a 'data missing' error is returned.";

            leaf-list rate {
              description
                "The transmission rate that is supported or advertised. Multiple transmissions rates are allowed.At least one element MUST be present in the NETCONF data store. If none of this elements is are present in a NETCONF <edit-config> operation 'create', 'merge' or 'replace' and the parent element does not exist, a 'data-missing' error is returned.";

              type OFPortRateType;

              min-elements 1;
            }

            leaf auto-negotiate {
              description
                "Specifies if auto-negotiation of transmission parameters is enabled for the port. This element is optional. If this element is not present it defaults to 'true'.";

              type boolean;

              default true;
            }

            leaf-list medium {
              description
                "The transmission medium used by the port. Multiple media are allowed. At least one element MUST be present in the NETCONF data store. If none of this elements is are present ina NETCONF <edit-config> operation 'create', 'merge' or 'replace' and the parent element does not exist, a 'data-missing' error is returned.";

              type enumeration {
                enum copper {
                  value 0;
                }

                enum fiber {
                  value 1;
                }

              }

              min-elements 1;
            }

            leaf pause {
              description
                "Specifies if pausing of transmission is supported at all and if yes if it is asymmetric or symmetric. This element MUST be present in the NETCONF data store. If this element isnot present in a NETCONF <edit-config> operation 'create','merge' or 'replace' and the parent element does not exist, a 'data-missing' error is returned.";

              type enumeration {
                enum unsupported {
                  value 0;
                }

                enum symmetric {
                  value 1;
                }

                enum asymmetric {
                  value 2;
                }

              }

              mandatory true;
            }

          }

          container supported {
            description
              "The features (rates, duplex, etc.) of the port, that are supported on the port. Children of this element are not configurable and can only be retrieved by NETCONF <get> operations. Attemps to modify this element and its children with a NETCONF <edit-config> operation MUST result in an 'operation-not-supported' error with type 'application'.";

            leaf-list rate {
              description
                "The transmission rate that is supported or advertised. Multiple transmissions rates are allowed.At least one element MUST be present in the NETCONF data store. If none of this elements is are present in a NETCONF <edit-config> operation 'create', 'merge' or 'replace' and the parent element does not exist, a 'data-missing' error is returned.";

              type OFPortRateType;

              min-elements 1;
            }

            leaf auto-negotiate {
              description
                "Specifies if auto-negotiation of transmission parameters is enabled for the port. This element is optional. If this element is not present it defaults to 'true'.";

              type boolean;

              default true;
            }

            leaf-list medium {
              description
                "The transmission medium used by the port. Multiple media are allowed. At least one element MUST be present in the NETCONF data store. If none of this elements is are present ina NETCONF <edit-config> operation 'create', 'merge' or 'replace' and the parent element does not exist, a 'data-missing' error is returned.";

              type enumeration {
                enum copper {
                  value 0;
                }

                enum fiber {
                  value 1;
                }

              }

              min-elements 1;
            }

            leaf pause {
              description
                "Specifies if pausing of transmission is supported at all and if yes if it is asymmetric or symmetric. This element MUST be present in the NETCONF data store. If this element isnot present in a NETCONF <edit-config> operation 'create','merge' or 'replace' and the parent element does not exist, a 'data-missing' error is returned.";

              type enumeration {
                enum unsupported {
                  value 0;
                }

                enum symmetric {
                  value 1;
                }

                enum asymmetric {
                  value 2;
                }

              }

              mandatory true;
            }

          }

          container advertised-peer {
            description
              "The features (rates, duplex, etc.) of the port, that are supported on the port. Children of this element are not configurable and can only be retrieved by NETCONF <get> operations. Attemps to modify this element and its children with a NETCONF <edit-config> operation MUST result in an 'operation-not-supported' error with type 'application'.";

            leaf-list rate {
              description
                "The transmission rate that is supported or advertised. Multiple transmissions rates are allowed.At least one element MUST be present in the NETCONF data store. If none of this elements is are present in a NETCONF <edit-config> operation 'create', 'merge' or 'replace' and the parent element does not exist, a 'data-missing' error is returned.";

              type OFPortRateType;

              min-elements 1;
            }

            leaf auto-negotiate {
              description
                "Specifies if auto-negotiation of transmission parameters is enabled for the port. This element is optional. If this element is not present it defaults to 'true'.";

              type boolean;

              default true;
            }

            leaf-list medium {
              description
                "The transmission medium used by the port. Multiple media are allowed. At least one element MUST be present in the NETCONF data store. If none of this elements is are present ina NETCONF <edit-config> operation 'create', 'merge' or 'replace' and the parent element does not exist, a 'data-missing' error is returned.";

              type enumeration {
                enum copper {
                  value 0;
                }

                enum fiber {
                  value 1;
                }

              }

              min-elements 1;
            }

            leaf pause {
              description
                "Specifies if pausing of transmission is supported at all and if yes if it is asymmetric or symmetric. This element MUST be present in the NETCONF data store. If this element isnot present in a NETCONF <edit-config> operation 'create','merge' or 'replace' and the parent element does not exist, a 'data-missing' error is returned.";

              type enumeration {
                enum unsupported {
                  value 0;
                }

                enum symmetric {
                  value 1;
                }

                enum asymmetric {
                  value 2;
                }

              }

              mandatory true;
            }

          }

          ncd:revise-date 2016-07-27;
        }

      }

      list queue {
        description
          "The list contains all queue resources of the

          OpenFlow Capable Switch.

          The element 'resource-id' of OFQueueType MUST be unique

          within this list.";

        key resource-id;
        leaf resource-id {
          description
            "A unique but locally arbitrary identifier that
            uniquely identifies an OpenFlow Port within the context
            of an OpenFlow Logical Switch. It MUST be persistent
            across reboots of the OpenFlow Capable Switch.
            This element MUST be present to identify the OpenFlow

            resource.";

          type inet:uri {
            length 1..31;

          }

          mandatory true;
        }

        leaf id {
          description
            "This id identifies the OpenFlow Queue to
            OpenFlow Controllers. It is assigned to an OpenFlow Queue
            latest when the OpenFlow Queue is associated with and
            OpenFlow Logical Switch. If the OpenFlow Queue is
            associated with an OpenFlow Logical Switch, this element
            MUST be unique within the context of the OpenFlow Logical
            Switch.
            OpenFlow Capable Switch implementations may choose to
            assign values to OpenFlow Queues that are unique within the
            context of the OpenFlow Logical Switch. These id can be
            used independent of assignments to OpenFlow Logical
            Switches.
            Other implementations may assign values to this element
            only if the OpenFlow Queue is assigned to an OpenFlow
            Logical Switch. If no value is currently assigned to this
            element then this element MUST NOT be included in replies
            to NETCONF <get> requests. Since this element is not
            configurable with the NETCONF protocol it MUST NOT be
            included in replies to NETCONF <get-config> requests.";

          type uint32 {
            range 0..4294967294;

          }

          mandatory true;
        }

        leaf port {
          description
            "Reference to port resources in the Capable
            Switch.
            This element associates an OpenFlow Queue with an OpenFlow
            Port. If the OpenFlow Queue is associated with an OpenFlow
            Logical Switch S and this element is present, then it MUST
            be set to the value of element resource-id of an OpenFlow
            Port which is associated with the OpenFlow Logical Switch
            S.
            The element MUST refer to an element at the following path:
            /capable-switch/resources/port/resource-id";

          type leafref {
            path "/capable-switch/resources/port/resource-id";
          }

          mandatory true;
        }

        container properties {
          description
            "The queue properties currently configured.";

          leaf min-rate {
            description
              "The minimal rate that is reserved for this
              queue in 1/10 of a percent of the actual rate.
              This element is optional. If not present a min-rate is
              not set.";

            type OFTenthOfAPercentType {
              range 0..1000;

            }

          }

          leaf max-rate {
            description
              "The maximum rate that is reserved for this
              queue in 1/10 of a percent of the actual rate.
              This element is optional. If not present the max-rate is
              not set.";

            type OFTenthOfAPercentType {
              range 0..1000;

            }

          }

          leaf-list experimenter {
            description
              "A list of experimenter identifiers of queue
              properties used.
              This element is optional.";

            type uint32 {
              range 0..4294967295;

            }

            min-elements 0;
            ncd:revise-date 2016-03-16;
          }

        }

      }

      list flow-table {
        config false;
        description
          "The list contains all flow table resources of

          the OpenFlow Capable Switch.

          The element 'resource-id' of OFFlowTableTypeMUST be

          unique within this list.";

        key resource-id;
        leaf resource-id {
          description
            "A unique but locally arbitrary identifier that
            uniquely identifies an OpenFlow Port within the context
            of an OpenFlow Logical Switch. It MUST be persistent
            across reboots of the OpenFlow Capable Switch.
            This element MUST be present to identify the OpenFlow

            resource.";

          type inet:uri {
            length 1..31;

          }

        }

        leaf max-entries {
          description
            "The maximum number of flow entries supported by
            the flow table.";

          type uint8;

        }

        container next-tables {
          description
            "An array of resource-ids of all flow tables that

            can be directly reached from this table using the

            'goto-table' instruction.";

          leaf-list table-id {
            description
              "An array of resource-ids of all flow tables that

              can be directly reached from this table using the

              'goto-table' instruction.";

            type inet:uri;

            ncd:revise-date 2016-03-16;
          }

        }

        container instructions {
          description
            "The list of all instruction types supported by
            the flow table.";

          leaf-list type {
            description
              "The list of all instruction types supported by
              the flow table.";

            type OFInstructionType;

            ncd:revise-date 2016-03-16;
          }

        }

        container matches {
          description
            "The list of all match types supported by the
                            flow table.";

          leaf-list type {
            description
              "The list of all match types supported by the
                              flow table.";

            type OFMatchFieldType;

            ncd:revise-date 2016-03-16;
          }

        }

        container write-actions {
          description
            "The list of all write action types supported by
            the flow table.";

          leaf-list type {
            description
              "The list of all write action types supported by
              the flow table.";

            type OFActionType;

            ncd:revise-date 2016-03-16;
          }

        }

        container apply-actions {
          description
            "The list of all apply action types supported by
            the flow table.";

          leaf-list type {
            description
              "The list of all apply action types supported by
              the flow table.";

            type OFActionType;

            ncd:revise-date 2016-03-16;
          }

        }

        container write-setfields {
          description
            "The list of all 'set-field' action types

            supported by the table using write actions.";

          leaf-list type {
            description
              "The list of all 'set-field' action types

              supported by thetable using write actions.";

            type OFMatchFieldType;

            ncd:revise-date 2016-03-16;
          }

        }

        container apply-setfields {
          description
            "The list of all 'set-field' action types

            supported by the table using apply actions.";

          leaf-list type {
            description
              "The list of all 'set-field' action types

              supported by thetable using apply actions.";

            type OFMatchFieldType;

            ncd:revise-date 2016-03-16;
          }

        }

        container wildcards {
          description
            "The list of all fields for which the table
            supports wildcarding.";

          leaf-list type {
            description
              "The list of all fields for which the table
              supports wildcarding.";

            type OFMatchFieldType;

            ncd:revise-date 2016-03-16;
          }

        }

        leaf metadata-match {
          description
            "This element indicates the bits of the metadata
            field on which the flow table can match. It is represented
            as 64-bit integer in hexadecimal digits([0-9a-fA-F])
            format.";

          type hex-binary;

        }

        leaf metadata-write {
          description
            "This element indicates the bits of the metadata

            field on which flow table can write using the

            'write-metadata' instruction. It is represented as

            64-bit integer in hexadecimal digits([0-9a-fA-F]) format.";

          type hex-binary;

        }

      }

      list owned-certificate {
        description
          "This grouping specifies a certificate and a
          private key. It can be used by an OpenFlow Logical Switch for
          authenticating itself to a controller when a TLS connection
          is established.";

        key resource-id;
        leaf resource-id {
          description
            "A unique but locally arbitrary identifier that uniquely identifies an OpenFlow Port within the context of an OpenFlow Logical Switch. It MUST be persistent across reboots of the OpenFlow Capable Switch. This element MUST be present to identify the OpenFlow resource.";

          type inet:uri {
            length 1..31;

          }

          mandatory true;
        }

        leaf certificate {
          description
            "An X.509 certificate in DER format base64 encoded. This element MUST be present in the NETCONF data store. If this element is not present in a NETCONF <edit-config> operation 'create', 'merge' or 'replace' and the parent element does not exist, a 'data-missing' error is returned.";

          type ncd:long-text {
            length 1..4095;

          }

          mandatory true;
        }

        container private-key {
          description
            "This element contains the private key corresponding to the certificate. The private key is encoded as specified in XML-Signature Syntax and Processing (http://www.w3.org/TR/2001/PR-xmldsig-core-20010820/). Currently the specification only support DSA and RSA keys. This element MUST be present in the NETCONF data store. If this element is not present in a NETCONF <edit-config> operation 'create', 'merge' or 'replace' and the parent element does not exist, a 'data-missing' error is returned.";

          choice key-type {
            description
              "The KeyValue element contains a single public key
              that may be useful in validating the signature.";

            mandatory true;
            case rsa {
              description
                "RSA key values have two fields: Modulus and Exponent.";

              leaf Modulus {
                description
                  "This element MUST be present in the NETCONF data store. If this element is not present in a NETCONF <edit-config> operation 'create', 'merge' or 'replace' and the parent element does not exist, a 'data-missing' error is returned.";

                type binary {
                  length 1..256;

                }

                mandatory true;
              }

              leaf Exponent {
                description
                  "This element MUST be present in the NETCONF data store. If this element is not present in a NETCONF <edit-config> operation 'create', 'merge' or 'replace' and the parent element does not exist, a 'data-missing' error is returned.";

                type binary {
                  length 1..256;

                }

                mandatory true;
              }

            }

          }

        }

        ncd:revise-date 2016-07-22;
      }

      list external-certificate {
        description
          "This grouping specifies a certificate that can be used by an OpenFlow Logical Switch for authenticating a controller when a TLS connection is established.";

        key resource-id;
        leaf resource-id {
          description
            "A unique but locally arbitrary identifier that uniquely identifies an OpenFlow Port within the context of an OpenFlow Logical Switch. It MUST be persistent across reboots of the OpenFlow Capable Switch. This element MUST be present to identify the OpenFlow resource.";

          type inet:uri {
            length 1..31;

          }

          mandatory true;
        }

        leaf certificate {
          description
            "An X.509 certificate in DER format base64 encoded. This element MUST be present in the NETCONF data store. If this element is not present in a NETCONF <edit-config> operation 'create', 'merge' or 'replace' and the parent \"element does not exist, a 'data-missing' error is returned.";

          type ncd:long-text {
            length 1..4095;

          }

          mandatory true;
        }

        ncd:revise-date 2016-07-22;
      }

    }

    container logical-switches {
      description
        "This element contains a list of all OpenFlow
        Logical Switches available at the OpenFlow Capable
        Switch.";

      list switch {
        description
          "The list of all OpenFlow Logical Switches on

          the OpenFlow Capable Switch.

          The element 'resource-id' of OFLogicalSwitchType MUST be

          unique within this list.";

        key id;
        leaf id {
          description
            "A unique but locally arbitrary identifier that
            identifies a Logical Switch within the context of an
            OpenFlow Capable Switch. It MUST be persistent across
            reboots of the OpenFlow Capable Switch.
            This element MUST be present to identify the OpenFlow
            Logical Switch.";

          type OFConfigId {
            length 1..63;

          }

          mandatory true;
        }

        container capabilities {
          config false;
          description
            "This element contains all capability items that
            an OpenFlow Logical Switch MAY implement.
            This element and its children can only be retrieved by
            NETCONF <get> operation since it contain no configuration
            data.";

          leaf max-buffered-packets {
            description
              "The maximum number of packets the logical switch
              can buffer when sending packets to the controller using
              packet-in messages.";

            type uint32;

          }

          leaf max-tables {
            description
              "The number of flow tables supported by the
                                  logical switch.";

            type uint8;

          }

          leaf max-ports {
            description
              "The number of flow tables supported by the
                                  logical switch.";

            type uint32;

          }

          leaf flow-statistics {
            description
              "Specifies if the logical switch supports flow
                                  statistics.";

            type boolean;

            default false;
          }

          leaf table-statistics {
            description
              "Specifies if the logical switch supports table statistics.";

            type boolean;

            default false;
          }

          leaf port-statistics {
            description
              "Specifies if the logical switch supports port
                                  statistics.";

            type boolean;

            default false;
          }

          leaf group-statistics {
            description
              "Specifies if the logical switch supports group
                                  statistics.";

            type boolean;

            default false;
          }

          leaf queue-statistics {
            description
              "Specifies if the logical switch supports queue
                                  statistics.";

            type boolean;

            default false;
          }

          leaf reassemble-ip-fragments {
            description
              "Specifies if the logical switch supports
              reassemble IP fragments.";

            type boolean;

            default false;
          }

          leaf block-looping-ports {
            description
              "'true' indicates that a switch protocol outside

              of OpenFlow, such as 802.1D Spanning Tree, will detect

              topology loops and block ports to prevent packet loops.";

            type boolean;

            default false;
          }

          container reserved-port-types {
            description
              "Specify generic forwarding actions such as

              sending to thecontroller, flooding, or forwarding using

              non-OpenFlow methods, such as 'normal' switch processing.";

            reference "The types of reserved ports are defined in
            OpenFlow Switch Specification versions 1.2, 1.3, and
            1.3.1.";
            leaf-list type {
              description
                "Specify generic forwarding actions such as

                sending to the controller, flooding, or forwarding using

                non-OpenFlow methods, such as 'normal' switch processing.";

              type enumeration {
                enum all {
                  value 0;
                }

                enum controller {
                  value 1;
                }

                enum table {
                  value 2;
                }

                enum inport {
                  value 3;
                }

                enum any {
                  value 4;
                }

                enum normal {
                  value 5;
                }

                enum flood {
                  value 6;
                }

              }

              ncd:revise-date 2016-03-16;
            }

          }

          container group-types {
            description
              "Specify the group types supported by the logical
                                  switch.";

            reference "The types of groups are defined in OpenFlow Switch
            Specification versions 1.2, 1.3, and 1.3.1.";
            leaf-list type {
              description
                "Specify the group types supported by the logical
                                    switch.";

              type enumeration {
                enum all {
                  value 0;
                }

                enum select {
                  value 1;
                }

                enum indirect {
                  value 2;
                }

                enum fast-failover {
                  value 3;
                }

              }

              ncd:revise-date 2016-03-16;
            }

          }

          container group-capabilities {
            description
              "Specify the group capabilities supported by the
              logical switch.";

            reference "The types of group capability are defined in
            OpenFlow Switch Specification versions 1.2, 1.3, and
            1.3.1.";
            leaf-list capability {
              description
                "Specify the group capabilities supported by the
                logical switch.";

              type enumeration {
                enum select-weight {
                  value 0;
                }

                enum select-liveness {
                  value 1;
                }

                enum chaining {
                  value 2;
                }

                enum chaining-check {
                  value 3;
                }

              }

              ncd:revise-date 2016-03-16;
            }

          }

          container action-types {
            description
              "Specify the action types supported by the
                                  logical switch.";

            leaf-list type {
              description
                "Specify the action types supported by the
                                    logical switch.";

              type OFActionType;

              ncd:revise-date 2016-03-16;
            }

          }

          container instruction-types {
            description
              "Specify the instruction types supported by the
              logical switch.";

            leaf-list type {
              description
                "Specify the instruction types supported by the
                logical switch.";

              type OFInstructionType;

              ncd:revise-date 2016-03-16;
            }

          }

        }

        leaf datapath-id {
          description
            "The datapath identifier of the Logical Switch

            that uniquely identifies this Logical Switch within the

            context of all OpenFlow Controllers associated with the

            OpenFlow Logical Switch. The datapath identifier is a

            string value that MUST be formatted as a sequence of 8

            2-digit hexadecimal numbersthat are separated by colons,

            for example, '01:23:45:67:89:ab:cd:ef'. When processing a

            datapath identifier, the caseof the decimal digits MUST be

            ignored.

            This element MUSTbe present in the NETCONF data store.

            If this element is not present in a NETCONF <edit-config>

            operation 'create', 'merge' or 'replace' and the parent

            element does not exist, a 'data-missing' error is

            returned.";

          type datapath-id-type {
            length 23;

          }

          mandatory true;
        }

        leaf enabled {
          description
            "This element indicates the administrative state

            of the OpenFlow Logical Switch. A value of 'false' means

            the OpenFlowLogical Switch MUST NOT communicate with any

            OpenFlow Controllers, MUST NOT conduct any OpenFlow

            processing, and SHOULD NOT be utilizing computational or

            network resources of the underlying platform.

            This element is optional. If this element is not present it

            defaults to 'true'.";

          type boolean;

          default true;
        }

        leaf lost-connection-behavior {
          description
            "This element indicates the the behavior of the

            OpenFlow Logical Switch in case it loses contact with all

            OpenFlow Controllers. There are two alternative modes in

            such a case: fails secure mode and fail standalone mode as

            defined by theOpenFlow protocol specification version 1.2,

            section 6.4. These are the only allowed values for this

            element. Defaultis the fail secure mode.

            This element is optional. If thiselement is not present it

            defaults to 'failSecureMode'.";

          type enumeration {
            enum failSecureMode {
              value 0;
            }

            enum failStandaloneMode {
              value 1;
            }

          }

          default failSecureMode;
        }

        container controllers {
          description
            "The list of controllers for this Logical switch.

            The element 'id' of OFControllerType MUST be unique within

            this list.";

          list controller {
            description
              "The list of OpenFlow Controllers that are

              assigned to theOpenFlow Logical Switch. The switch MUST

              NOT connect to any OpenFlow Controller that is not

              contained in this list.
              NETCONF <edit-config> operations MUST be implemented as

              follows:

              * The 'id' element MUST be present at all <edit-config>

              operations to identify the controller.

              * If the operation is 'merge' or 'replace', the element



              is created if it does not exist, and its value is set

              to the valuefound in the XML RPC data.

              * If the operation is 'create', the element is created if

              it does not exist. If the element already exists, a

              'data??exists' error is returned.

              * If the operation is 'delete', the element is deleted if

              it exists. If the element does not exist, a

              'data??missing' error is returned.";

            key id;
            leaf id {
              description
                "A unique but locally arbitrary identifier that
                uniquely identifies an OpenFlow Controller within the
                context of an OpenFlow Capable Switch. It MUST be
                persistent across reboots of the OpenFlow Capable Switch.
                This element MUST be present to identify the OpenFlow
                controller.";

              type OFConfigId {
                length 1..63;

              }

              mandatory true;
            }

            leaf role {
              description
                "This element indicates the role of the OpenFlow

                Controller. Semantics of these roles are specified in the

                OpenFlow specifications 1.0 - 1.3.1. It is RECOMMENDED

                that the roles of controllers are not configured by

                OF-CONFIG 1.1.1 but determined using the OpenFlow protocol.

                OpenFlow Controllers configured by OF-CONFIG 1.1.1 have the

                default role 'equal'. A role other than 'equal' MAY be

                assigned to a controller. Roles 'slave' and 'equal' MAY be



                assigned to multiple controllers. Role 'master' MUST NOT

                be assigned to more than one controller.

                This element is optional. If this element is not present it

                defaults to 'equal'.";

              type enumeration {
                enum master {
                  value 0;
                }

                enum slave {
                  value 1;
                }

                enum equal {
                  value 2;
                }

              }

              default equal;
            }

            leaf ip-address {
              description
                "The IP address of the OpenFlow Controller. This

                IP address is used by the OpenFlow Logical Switch when

                connectingto the OpenFlow Controller.

                This element MUST be presentin the NETCONF data store.

                If this element is not present in a NETCONF <edit-config>

                operation 'create', 'merge' or 'replace' and the parent

                element does not exist, a 'data-missing' error is

                returned.";

              type inet:ipv4-address;

              mandatory true;
            }

            leaf port {
              description
                "The TCP port number at the OpenFlow Controller.
                This port number is used by the OpenFlow Logical Switch
                when connecting to the OpenFlow Controller using TCP or
                TLS. The default value is 6633.
                This element is optional. If this element is not present it
                defaults to 6633.";

              type inet:port-number {
                range 1..65535;

              }

              default 6653;
            }

            leaf local-ip-address {
              description
                "The local IP address of the OpenFlow Logical

                Switch whenconnecting to this OpenFlow Controller. It is

                the sourceIP address of packets sent to this OpenFlow

                Controller. If present, this element overrides any default

                IP address.

                This element is optional. Attempts to set this element to

                an IP address that cannot be used by the OpenFlow Logical

                Switch MUST result in an 'bad-element' error with type

                'application'. The <error-info> element MUST contain the

                name of this element in the <bad-element> element.";

              type inet:ipv4-address;

            }

            leaf local-port {
              description
                "The local TCP port number of the OpenFlow

                Logical Switchwhen connecting to this OpenFlow Controller.

                It is the source TCP port number of packets sent to this

                OpenFlow Controller. If this element is not present, then

                the port number is chosen arbitrarily by the OpenFlow

                Logical Switch.

                This element is optional. Attempts to set this elementto a

                port number that cannot be used by the OpenFlow Logical

                Switch MUST result in an 'bad-element' error with type

                'application'. The <error-info> element MUST contain the

                name of this element in the <bad-element> element.";

              type inet:port-number {
                range 0..65535;

              }

            }

            leaf protocol {
              description
                "The default protocol tha the OpenFlow Logical

                Switch uses to connect to this OpenFlow Controller. 'tls'

                is the default value.

                This element is optional. If this element isnot present it

                defaults to 'tls'.";

              type enumeration {
                enum tcp {
                  value 0;
                }

                enum tls {
                  value 1;
                }

              }

              default tls;
            }

            container state {
              config false;
              description
                "This container holds connection state

                information that indicate the connection state of the

                OpenFlow Logical Switch and the OpenFlow protocol version

                used for the connection.

                Children of this element are not configurable and can only

                be retrieved by NETCONF <get> operations. Attemps to modify

                this element and its children with a NETCONF <edit-config>

                operation MUST result in an 'operation-not-supported' error

                with type 'application'.";

              leaf connection-state {
                description
                  "This object indicates the connections state of
                  the OpenFlow Logical Switch to this controller.";

                type OFUpDownStateType;

              }

              leaf current-version {
                description
                  "This object indicates the version of the

                  OpenFlow protocol used between the OpenFlow Logical

                  Switch and this Controller. If element connection-state

                  has value 'up', then this element indicates the actual

                  version in use. If element connection-state has value

                  'down', then this element indicates the version number of

                  the last established connection with this OpenFlow

                  Controller. The value ofthis element MAY be persistent

                  across reboots of the OpenFlow Logical Switch in such a

                  case. If element connection-state has value 'down'and

                  there is no information about previous connections to

                  this OpenFlow controller, then this element is not

                  present or has the value '0'.";

                type OFOpenFlowVersionType;

              }

              leaf-list supported-versions {
                description
                  "This list of elements includes one entry for
                  each OpenFlow protocol version that this OpenFlow
                  controller supports. It SHOULD contain all";

                type OFOpenFlowVersionType;

                ncd:revise-date 2016-03-16;
              }

              leaf local-ip-address-in-use {
                description
                  "The local IP address of the OpenFlow Logical
                  Switch when connecting to this OpenFlow Controller. It
                  is the source IP address of packets sent to this OpenFlow
                  Controller. If present, this element overrides any
                  default IP address.";

                type inet:ipv4-address;

              }

              leaf local-port-in-use {
                description
                  "The local TCP port number of the OpenFlow

                  Logical Switch. If element connection-state has value

                  'up', then thiselement indicates the actual port number

                  in use. If element connection-state has value 'down',

                  then this element indicates the port number used for the

                  last attempt toestablish a connection with this OpenFlow

                  Controller.???

                  When connecting to this OpenFlow Controller, it is the
                  source TCP port number of packets sent to this OpenFlow
                  Controller. If this element has its defaqult value 0,

                  then port number is chosen arbitrarily by the OpenFlow

                  Logical Switch.";

                type inet:port-number {
                  range 0..65535;

                }

              }

            }

          }

        }

        container bfd-sessions {
          description
            "Configure BFD instance parameters.";

          list bfd-session {
            description
              "Configure BFD instance parameters.";

            key ld;
            leaf ld {
              description
                "Local discriminator for BFD.";

              type uint32 {
                range 1..4294967295 {
                  description
                    "Local discriminator for BFD.";

                }

              }

            }

            leaf rd {
              description
                "Remote discriminator for BFD.";

              type uint32 {
                range 1..4294967295 {
                  description
                    "Remote discriminator for BFD.";

                }

              }

              mandatory true;
            }

            leaf xmt-time {
              description
                "BFD control packets TX interval.";

              type uint32;

              units ms;
              mandatory true;
            }

            leaf detect-time {
              description
                "Detect time of BFD session.";

              type uint32;

              units ms;
              mandatory true;
            }

            leaf port-no {
              description
                "Output interface index for BFD session.";

              type uint32;

              mandatory true;
            }

            leaf payload-length {
              description
                "Packet len of BFD session.";

              type uint32;

              mandatory true;
            }

            leaf payload {
              description
                "The packet content of BFD session.";

              type binary {
                length 1..255;

              }

              mandatory true;
            }

          }

        }

        container resources {
          description
            "The list of identifiers of all resources of the
            OpenFlow Capable Switch that the OpenFlow Logical Switch
            has exclusive or non-exclusive access to. A resource is
            identified by the value of its resource-identifier element.
            For each resource identifier value in this list, there MUST
            be an element witha matching resource identifier value in
            the resources list of the OpenFlow Capable Switch.
            Identifiers of this list arecontained in elements
            indicating the type of resource: 'port', 'queue',
            'certificate', or 'flow-table'. Depending on the type,
            different constraints apply. These are specified in
            separate descriptions per type.
            At present the elements in this lists are not configurable
            and can only be retrieved byNETCONF <get> or <get-config>
            operations. Attemps to modifythis element and its children
            with a NETCONF <edit-config> operation MUST result in an
            'operation-not-supported' error with type 'application'.";

          leaf-list port {
            description
              "A resource identifier of a port of the
              OpenFlow Capable Switch that the OpenFlow Logical Switch
              has exclusive access to.
              The elements in this list MUST refer to elements at the
              following path:
              /capable-switch/resources/port/resource-id
              Elements in this list MUST be unique. This means each
              port element can only be referenced once.";

            type leafref {
              path "/capable-switch/resources/port/resource-id";
            }

            ncd:revise-date 2016-03-16;
          }

          leaf-list queue {
            description
              "A resource identifier of a queue of the
              OpenFlow Capable Switch that the OpenFlow Logical Switch
              has exclusive access to.
              The elements in this list MUST refer to elements at the
              following path:

              /capable-switch/resources/queue/resource-id
              Elements in this list MUST be unique. This means each
              queue element can only be referenced once.";

            type leafref {
              path "/capable-switch/resources/queue/resource-id";
            }

            ncd:revise-date 2016-07-27;
          }

          leaf-list flow-table {
            description
              "A resource identifier of a flow table of the
              OpenFlow Capable Switch that the OpenFlow Logical Switch
              has exclusive access to.
              The elements in this list MUST refer to elements at the
              following path:
              /capable-switch/resources/flow-table/resource-id
              Elements in this list MUST be unique. This means each
              flow-table element can only be referenced once.";

            type string {
              length 1..31;

            }

            ncd:revise-date 2016-03-16;
          }

          leaf certificate {
            description
              "The resource identifier of the owned

              certificate in the OpenFlow Capable Switch that the

              OpenFlow Logical Switch uses to identify itself. This

              element MUST NOT occur more than once in an OpenFlow

              Logical Switch's resource list.

              If no such element is in an OpenFlow Logical Switch's

              resource list, then the OpenFlow Logical Switch does not

              authenticate itself towards an OpenFloe Controller with a

              certificate. If this element is present, then the

              OpenFlow Logical Switch MUST provide this certificate for

              authenticationto an OpenFlow Controller when setting up

              a TLS connection.

              For TCP connections this element is irrelevant.

              The element MUST refer to an element at the following

              path:

              /capable-switch/resources/owned-certificate/resource-id";

            type leafref {
              path "/capable-switch/resources/owned-certificate/resource-id";
            }

          }

        }

        list packets-port-statistics {
          description
            "Port statistics of  packet-in and packet-out.";

          key protocol-type;
          leaf protocol-type {
            description
              "Type of protocol for port statistics.";

            type enumeration {
              enum arp {
                value 1;
              }

            }

          }

          list port {
            config false;
            description
              "Port statistics";

            key resource-id;
            leaf resource-id {
              description
                "The resource id of port.";

              type ncd:ifname;

            }

            container statistics {
              description
                "Statistics information";

              container packet-out {
                description
                  "Statistics information of packet-out.";

                leaf packets {
                  description
                    "Packets of packet-out.";

                  type uint64;

                }

                leaf bytes {
                  description
                    "Bytes of packet-out.";

                  type uint64;

                }

              }

              container packet-in {
                description
                  "Statistics information of packet-in.";

                leaf packets {
                  description
                    "Packets of packet-in.";

                  type uint64;

                }

                leaf bytes {
                  description
                    "Bytes of packet-in.";

                  type uint64;

                }

              }

            }

          }

          ncd:revise-date 2016-03-16;
        }

      }

    }

  }

}
