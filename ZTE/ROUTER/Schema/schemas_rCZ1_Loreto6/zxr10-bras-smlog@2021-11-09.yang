module zxr10-bras-smlog {
  namespace 'http://www.zte.com.cn/zxr10/netconf/schema/bras/bras-smlog'
            ;
  prefix bras-smlog ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  revision 2021-11-09 ;
  revision 2020-05-13 ;
  revision 2020-04-13 {
    description 'create smlog yang'
                ;
  }
  container configuration {
    container subscriber-manager {
      leaf information-log {
        description 'Configure user information log switch.'
                    ;
        type enumeration {
          enum disable {
            value 0 ;
            description 'Close user information log switch.'
                        ;
          }
          enum enable {
            value 1 ;
            description 'Open user information log switch.'
                        ;
          }
        }
      }
      leaf online-failed-record {
        type enumeration {
          enum disable {
            value 0 ;
          }
          enum enable {
            value 1 ;
          }
        }
        default enable ;
      }
      leaf offline-exception-record {
        type enumeration {
          enum disable {
            value 0 ;
          }
          enum enable {
            value 1 ;
          }
        }
        default enable ;
      }
      leaf online-abnormal-event-log {
        type enumeration {
          enum enable {
            value 1 ;
            description 'online abnoral event log switch enable'
                        ;
          }
          enum disable {
            value 0 ;
            description 'online abnoral event log switch disable'
                        ;
          }
        }
        default enable ;
      }
      leaf event-log-num {
        type uint32 {
          range 4000..512000 ;
        }
        default 256000 ;
      }
      leaf offline-abnormal-event-log {
        type enumeration {
          enum enable {
            value 1 ;
            description 'offline abnoral event log switch enable'
                        ;
          }
          enum disable {
            value 0 ;
            description 'offline abnoral event log switch disable'
                        ;
          }
        }
        default enable ;
      }
      leaf normal-event-log {
        type enumeration {
          enum enable {
            value 1 ;
            description 'normal event log switch enable'
                        ;
          }
          enum disable {
            value 0 ;
            description 'normal event log switch disable'
                        ;
          }
        }
        default disable ;
      }
    }
  }
}
