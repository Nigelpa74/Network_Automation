module zxr10-ietf-yang-push-dev {
  namespace "http://www.zte.com.cn/zxr10/netconf/schema/rosng/ietf-yang-push-dev" ;
  prefix yp-dev ;
  yang-version 1.1 ;
  import ietf-yang-push {
    prefix yp ;
  }

  organization "ZTE Corporation" ;
  contact "ZTE Corporation  
     Nanjing Institute of ZTE Corporation 
     No.68 Zijinghua Rd. Yuhuatai District, Nanjing, China 
     Tel: +86-25-52870000" ;
  revision 2025-04-17 {
    description 'Remove deviation /yp:push-update.' ;
  }

  revision 2022-12-10 ;

  deviation "/yp:resync-subscription" {
    deviate not-supported ;

  }

}
