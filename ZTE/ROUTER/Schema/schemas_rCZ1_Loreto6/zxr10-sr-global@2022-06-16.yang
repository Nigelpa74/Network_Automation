module zxr10-sr-global {
  namespace 'http://www.zte.com.cn/zxr10/netconf/schema/rosng/sr-global'
            ;
  prefix sr-global ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The netconf model for sr global configuration.'
              ;
  revision 2022-06-16 {
    description '1.Add the default value /configuration/segment-routing/srv6-pa'
              + 'th-mtu/path-mtu-value.'+"\n"
              + '2.Remove the default value /configuration/segment-routing/srv6'
              + '-path-mtu/path-mtu-reserved/value.'
                ;
  }
  revision 2022-02-11 {
    description 'Initial version.'
                ;
  }
  container configuration {
    description 'The branch of configuration model.'
                ;
    container segment-routing {
      container srv6-path-mtu {
        description 'The configuration of SRv6 global path MTU.'
                    ;
        leaf path-mtu-value {
          description 'The configuration of SRv6 global path MTU value.'
                      ;
          type uint16 {
            range 1280..9600 ;
          }
          units bytes ;
          default 9600 ;
        }
        container path-mtu-reserved {
          description 'The configuration of SRv6 global reserved path MTU.'
                      ;
          presence 'configure path mtu reserved value'
                   ;
          leaf value {
            description 'The configuration of SRv6 global path MTU reserved val'
                      + 'ue.'
                        ;
            type uint16 {
              range 1..9600 ;
            }
          }
        }
      }
    }
  }
}
