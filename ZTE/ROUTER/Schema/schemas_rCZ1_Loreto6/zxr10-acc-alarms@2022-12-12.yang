module zxr10-acc-alarms {
  namespace "http://www.zte.com.cn/zxr10/netconf/schema/rosng/alarm" ;
  prefix zxr10-acc-alm ;
  yang-version 1.1 ;
  import acc-yang-types {
    prefix acc-type ;
  }

  import acc-alarms {
    prefix acc-alm ;
  }

  import zxr10-netconf-defs {
    prefix ncd ;
  }

  organization "ZTE Corporation" ;
  contact "ZTE Corporation
        Nanjing Institute of ZTE Corporation
        No.68 Zijinghua Rd. Yuhuatai District, Nanjing, China
        Tel: +86-25-52870000" ;
  description 'This module augments the acc-alarms module.' ;
  revision 2022-12-12 {
    description 'Initial revision.' ;
  }

  augment "/acc-alm:tca-parameters" {
    description 'Add tca-parameters query node.' ;
    list tca-parameter-state {
      config false ;
      description 'Tca parameter state.' ;
      key "object-name pm-parameter-name granularity" ;
      leaf object-name {
        description 'Object name.' ;
        type string {
          length 1..64 ;

        }

      }

      leaf pm-parameter-name {
        description 'Performance parameter name.' ;
        type string {
          length 1..64 ;

        }

      }

      leaf granularity {
        description 'Granularity.' ;
        type acc-type:granularity ;

      }

      leaf object-type {
        description 'Object type.' ;
        type string {
          length 1..64 ;

        }

      }

      leaf threshold-value-high {
        description 'High threshold value.' ;
        type acc-type:real ;

      }

      leaf threshold-value-low {
        description 'Low threshold value.' ;
        type acc-type:real ;

      }

      ncd:select "object-name granularity" ;
      ncd:select "object-name pm-parameter-name granularity" ;
    }

  }

}
