module zxr10-rpm-srt {
  namespace "http://www.zte.com.cn/zxr10/netconf/schema/rosng/rpm-srt" ;
  prefix rpm-srt ;
  yang-version 1 ;
  import zxr10-netconf-defs {
    prefix ncd ;
  }

  organization "ZTE Corporation" ;
  contact "ZTE Corporation
  Nanjing Institute of ZTE Corporation
  No.68 Zijinghua Rd. Yuhuatai District, Nanjing, China
  Tel: +86-25-52870000" ;
  description 'The netconf module to describe the function of IPv4-STATIC-ROUTE and IPv6-STATIC-ROUTE in the route protocol module.' ;
  revision 2024-12-03 {
    description '1. Add range definitions for nodes "template-name" and "vrf-name". The paths are:
"configuration/rpm-srt/rpm-srtv4/bfd/multi-bfds/multi-bfd/template-name",
"configuration/rpm-srt/rpm-srtv4/bfd/multi-bfds-vrf/multi-bfd-vrf/vrfname",
"configuration/rpm-srt/rpm-srtv4/bfd/multi-bfds-vrf/multi-bfd-vrf/template-name",
"configuration/rpm-srt/rpm-srtv4/recursion-l3evpns/recursion-l3evpn/vrf-name",
"configuration/rpm-srt/rpm-srtv4/track-actions/track-action/track-name",
"configuration/rpm-srt/rpm-srtv6/bfd/multi-bfds/multi-bfd/template-name",
"configuration/rpm-srt/rpm-srtv6/bfd/multi-bfds-vrf/multi-bfd-vrf/vrfname",
"configuration/rpm-srt/rpm-srtv6/bfd/multi-bfds-vrf/multi-bfd-vrf/template-name",
"configuration/rpm-srt/rpm-srtv6/recursion-l3evpns/recursion-l3evpn/vrf-name",
"configuration/rpm-srt/rpm-srtv/track-actions/track-action/track-name"
2. Remove the mandatory attribute from the key node. paths are "configuration/rpm-srt/rpm-srtv4/route-config/private-net/nexthop-vrfs/nexthop-vrf/nh-vrf-name" and “configuration/rpm-srt/rpm-srtv6/route-config/private-net/nexthop-vrfs/nexthop-vrf/nh-vrf-name”' ;
  }

  revision 2024-06-26 {
    description 'FRR WTR support minute with second. The paths are "".' ;
  }

  revision 2024-01-04 {
    description 'Add presence for fast reroute. The paths are "/configuration/rpm-srt/rpm-srtv4/fast-reroute/public-net" and "/configuration/rpm-srt/rpm-srtv6/fast-reroute/public-net"' ;
  }

  revision 2023-11-30 {
    description 'Add choice-case of wtr-second' ;
  }

  revision 2023-04-24 {
    description 'Add leaves "no-install" to support set no-install static route. The path are "configuration/rpm-srt/rpm-srtv4" and "configuration/rpm-srt/rpm-srtv6".' ;
  }

  revision 2023-01-30 {
    description 'Support showing the information of of IPv6 static routes. The path is "state/rpm-srt/rpm-srtv6".' ;
  }

  revision 2022-12-01 {
    description 'Add project label "All" in feature "ipv4-dest-with-ipv6-global-nh", "nexthop-resolving-delay" and "bfd-template".' ;
  }

  revision 2022-10-20 {
    description 'Add range for nexthop VPN nodes, the paths are "configuration/rpm-srt/rpm-srtv4/route-config/private-net/nh-with-vrfs/nh-with-vrf/nh-vrf-name" and "configuration/rpm-srt/rpm-srtv6/route-config/private-net/nh-with-vrfs/nh-with-vrf/nh-vrf-name".' ;
  }

  revision 2022-09-20 {
    description 'Support configurations of static route in VPN import another VPN.The path are "configuration/rpm-srt/rpm-srtv4/route-config/private-net/nexthop-vrfs" and "configuration/rpm-srt/rpm-srtv6/route-config/private-net/nexthop-vrfs".' ;
  }

  revision 2022-09-07 {
    description 'Support dynamic IPv6 tunnel in IPv6 static route, the path is configuration/rpm-srt/rpm-srtv4/route-vxlan/dynamic-tunnels-ipv6.
Support dynamic IPv4 tunnel in IPv4 static route, the path is configuration/rpm-srt/rpm-srtv6/route-vxlan/dynamic-tunnels-ipv4.' ;
  }

  revision 2022-07-14 {
    description 'Support the public IPv6 static route with IPv4 nexthop.The path is "configuration/rpm-srt/rpm-srtv6/route-config/public-net/ipv4-nhs".' ;
  }

  revision 2022-06-02 {
    description 'Support the VPN instance of nexthop.' ;
  }

  revision 2021-12-10 {
    description 'Modify the fixkeys of route-config.' ;
  }

  revision 2021-05-08 {
    description 'Add nodes sr-policy for static route.
Modify the fixkeys of route-config.' ;
  }

  revision 2021-04-13 {
    description 'Add nodes for restriction of  static route recursion.' ;
  }

  revision 2021-01-07 {
    description 'Add nodes for static route track action.' ;
  }

  revision 2020-08-19 {
    description 'Add nodes for VRF of nexthop.' ;
  }

  revision 2020-08-13 {
    description 'Add a new node to configure recursion l3evpn for IPv4 static route and IPv6 static route.
The paths are "configuration/rpm-srt/rpm-srtv4/recursion-l3evpn" and "configuration/rpm-srt/rpm-srtv6/recursion-l3evpn".' ;
  }

  revision 2020-04-26 {
    description 'Add a new node to configure recursion l3vpn for IPv6 static route.
The paths are "configuration/rpm-srt/rpm-srtv6/recursion-l3vpn".' ;
  }

  revision 2020-04-03 {
    description 'Add a new node to configure bfd template of IPv4 static route.
Add a new node to configure bfd template of IPv6 static route.
The paths are "configuration/rpm-srt/rpm-srtv4/bfd","configuration/rpm-srt/rpm-srtv6/bfd".' ;
  }

  revision 2020-01-09 {
    description 'Add new containers to configure nexthop of IPv4 static route resolving delay.
Add new containers to configure nexthop of IPv6 static route resolving delay.
The paths are "configuration/rpm-srt/rpm-srtv4/nexthop/trigger/delay","configuration/rpm-srt/rpm-srtv6/nexthop/trigger/delay".
Update the attribute id of IPv4 destination and mask.' ;
  }

  revision 2019-10-29 {
    description 'Add new project label of V6000.vRouter and V6000.vBras-C in features "ipv6-global-nh".' ;
  }

  revision 2019-09-04 {
    description 'Add new project label of SWITCH.5960 and SWITCH.99 in features "ipv6-global-nh".' ;
  }

  revision 2019-08-21 {
    description 'Add new project label of T8000 in feature "ipv4-dest-with-ipv6-global-nh".' ;
  }

  revision 2019-06-26 {
    description 'Add new project label of PTN.6100 in features "ipv6-global-nh" and "ipv4-dest-with-ipv6-global-nh".' ;
  }

  revision 2019-04-01 {
    description 'Add a features of ipv4-dest-with-ipv6-global-nh.global-v6-nhs
Add a new node global-v6-nhs in IPv4-STATIC-ROUTE to configure ipv6 global nexthop.
The paths are "configuration/rpm-srt/rpm-srtv4/private-net/global-v6-nhs","configuration/rpm-srt/rpm-srtv4/mng-net/global-v6-nhs".
Add a leaf "ipv6-nexthop" in state/rpm-srt/route-status/view-list.' ;
  }

  revision 2019-03-25 {
    description 'Add new project label of OTN 9700/8700 to support IPv6 static route.' ;
  }

  revision 2019-02-21 {
    description 'Add new project label of 65v5 to support ipv6-route.' ;
  }

  revision 2019-01-23 {
    description 'Add project label V6000(vRouter/vBras-C) on features of public-dest-address.' ;
  }

  revision 2018-12-04 {
    description 'Add the route-vxlan node for IPv6-STATIC-ROUTE. The path is "configuration/rpm-srt/rpm-srtv6/route-vxlan".
Add a feature "ipv6-vxlan" for IPv6 vxlan route.' ;
  }

  revision 2018-10-31 {
    description 'Add a new leaf global in IPv6-STATIC-ROUTE to configure IPv6 nexthop to be global.
The paths are "configuration/rpm-srt/rpm-srtv6/private-net/only-nhs/only-nh" and "configuration/rpm-srt/rpm-srtv6/mng-net/only-nhs/only-nh".
Add a feature "ipv6-global-nh" for IPv6 static route global function.' ;
  }

  revision 2018-10-28 {
    description 'Add project label PTN(6100) on features of ipv4-global-nh and ipv6-permanent.' ;
  }

  revision 2018-08-02 {
    description 'Add the permanent node for IPv6-STATIC-ROUTE to set permanent attribute. The path is "configuration/rpm-srt/rpm-srtv6/route-config".' ;
  }

  revision 2018-07-26 {
    description 'Add one enumeration value (PUBLIC) to the leaf node nhtype. The path is "state/rpm-srt/rpm-srtv4/route-status/view-list/nhtype".' ;
  }

  revision 2018-06-28 {
    description 'Add the leaf track-name for route-vxlan to support relating track-detection. The path is "configuration/rpm-srt/rpm-srtv4/route-vxlan/static-tunnels/static-tunnel".
Add the container dynamic-tunnels for route-vxlan to support dynamic tunnel route. The path is "configuration/rpm-srt/rpm-srtv4/route-vxlan/dynamic-tunnels".' ;
  }

  revision 2018-05-30 {
    description 'Add a new node global-v4-nhs in IPv6-STATIC-ROUTE to configure IPv4 nexthop to be global.
The paths are "configuration/rpm-srt/rpm-srtv6/private-net/global-v4-nhs" and "configuration/rpm-srt/rpm-srtv6/mng-net/global-v4-nhs".
Add a feature "ipv4-global-nh-feature" for IPv6 static route global function.' ;
  }

  revision 2018-05-10 {
    description 'Add a new node publics in IPv4-STATIC-ROUTE and IPv6-STATIC-ROUTE to configure nexthop to be public.
The paths are "configuration/rpm-srt/rpm-srtv4/private-net/publics","configuration/rpm-srt/rpm-srtv4/mng-net/publics","configuration/rpm-srt/rpm-srtv6/private-net/publics",and "configuration/rpm-srt/rpm-srtv6/mng-net/publics".
Add a feature "public-dest-address" for public dest-address function.' ;
  }

  revision 2018-01-26 {
    description 'Modify the leaf name l3vni-label to vni-label for static VXLAN route.' ;
  }

  revision 2017-11-30 {
    description 'Add the route-vxlan node for IPv4-STATIC-ROUTE. The path is "configuration/rpm-srt/rpm-srtv4/route-vxlan".' ;
  }

  revision 2016-05-26 {
    description 'Add the recursion-l3vpn node for IPv4-STATIC-ROUTE. The path is "configuration/rpm-srt/rpm-srtv4/recursion-l3vpn".' ;
  }

  revision 2015-11-03 {
    description 'Add the source-nexthop-vrf node for IPv4-STATIC-ROUTE to set vpn peer-bfd local address. The path is "configuration/rpm-srt/rpm-srtv4/source-nexthop-vrf".' ;
  }

  revision 2015-07-28 {
    description 'Modify the "config" attribute of the state node and its leaf nodes.' ;
  }

  revision 2015-04-03 {
    description 'Add the preference-decrement node for IPv4-STATIC-ROUTE to set preference decrement when the route has been related with track detection. The path is "configuration/rpm-srt/rpm-srtv4/route-config".' ;
  }

  revision 2015-04-02 {
    description 'Add the tag-value node for IPv6-STATIC-ROUTE to set tag value. The path is "configuration/rpm-srt/rpm-srtv6/route-config".' ;
  }

  revision 2015-02-28 {
    description 'Add the dynamic-protect node for IPv6-STATIC-ROUTE to protect the dynamic route. The path is "configuration/rpm-srt/rpm-srtv6/dynamic-protect".' ;
  }

  revision 2014-08-07 {
    description 'Add the update-delay node for IPv4-STATIC-ROUTE to set update-delay time. The path is "configuration/rpm-srt/rpm-srtv4/update-delay".' ;
  }

  revision 2014-07-01 {
    description 'Add the dynamic-protect node for IPv4-STATIC-ROUTE to protect the dynamic route. The path is "configuration/rpm-srt/rpm-srtv4/dynamic-protect".' ;
  }

  revision 2014-05-08 {
    description 'Modify the description of fast-reroute node in rpm-srtv4 module.' ;
  }

  revision 2014-04-22 {
    description 'Add the routing status query function for IPV4-STATIC-ROUTE module.' ;
  }

  revision 2014-03-19 {
    description "Modify the attribute's length of track-name and description." ;
  }

  revision 2014-03-18 {
    description '1.Add a new attribute ifnh-flag for IPv4-STATIC-ROUTE and IPv6-STATIC-ROUTE to label both-if-nh node.
2.Delete the regular expression of if-nexthop and the ipv6-if-nh node.' ;
  }

  revision 2013-08-15 {
    description 'The initial version.' ;
  }

  feature public-dest-address {
    description 'The anycast-mac-address configuration is used to configure nexthop to be public.' ;
  }

  feature ipv4-global-nh {
    description 'This configuration is used to configure IPv4 global nexthop for IPv6 static route.' ;
  }

  feature ipv6-permanent {
    description 'This configuration is used to specify permanent IPv6 static route.' ;
  }

  feature ipv6-global-nh {
    reference "This configuration is used to configure IPv6 global nexthop for IPv6 static route." ;
  }

  feature ipv6-vxlan {
    description 'The feature is for IPv6 vxlan route.' ;
  }

  feature ipv4-dest-with-ipv6-global-nh {
    description 'This configuration is used to configure IPv6 global nexthop for IPv4 static route.' ;
  }

  feature nexthop-resolving-delay {
    description 'This configuration is used to configure IPv4 and IPv6 static route nexthop resolving delay.' ;
  }

  feature bfd-template {
    description "This configuration is used to configure IPv4 and IPv6 static route BFD's template." ;
  }

  typedef protect-type {
    type enumeration {
      enum RIP {
        value 1 ;
        description 'Static route protect RIP route.' ;
      }

      enum OSPF {
        value 2 ;
        description 'Static route protect OSPFv2 route.' ;
      }

      enum BGP {
        value 4 ;
        description 'Static route protect BGP route.' ;
      }

      enum ISIS {
        value 8 ;
        description 'Static route protect ISIS route.' ;
      }

    }

    description 'Define the route type which the static route can protect.' ;
  }

  typedef recursion-type {
    type enumeration {
      enum DIRECT {
        value 1 ;
        description 'Static route can recurse direct route only.' ;
      }

    }

    description 'Define the route type which the static route can recurse.' ;
  }

  typedef address-family {
    type enumeration {
      enum IPv4 {
        value 2 ;
      }

      enum IPv6 {
        value 24 ;
      }

    }

  }

  typedef network-type {
    type enumeration {
      enum MAIN {
        value 1 ;
      }

      enum VRF {
        value 2 ;
        description 'The private static routes.' ;
      }

      enum MNG {
        value 3 ;
        description 'The mng static routes.' ;
      }

      enum ALL {
        value 4 ;
        description 'All static routes.' ;
      }

    }

  }

  typedef interface-status {
    type enumeration {
      enum none {
        value 0 ;
      }

      enum up {
        value 1 ;
      }

      enum down {
        value 2 ;
      }

    }

  }

  container configuration {
    description 'The configuration information processing of IPv4-STATIC-ROUTE and IPv6-STATIC-ROUTE module.' ;
    container rpm-srt {
      description 'The configuration information processing of IPv4-STATIC-ROUTE and IPv6-STATIC-ROUTE module.' ;
      container rpm-srtv4 {
        description "The total node for IPV4-STATIC-ROUTE's all configuration commands." ;
        container route-config {
          description 'Basic configuration information for IPv4 static routes, including destination address, subnet mask, outbound interface, next hop, priority (pref), metric value (metric), tag, BFD detection, track detection, route description (name), and permanent attribute, etc.' ;
          container public-net {
            description 'The configuration for public static route.' ;
            container only-ifs {
              description 'The configuration for static route which only specifies the interface.' ;
              list only-if {
                description 'The configuration for static route which only specifies the interface.' ;
                key 'dest-addr mask-addr interface' ;
                leaf dest-addr {
                  description 'The destination address of route.' ;
                  type ncd:ipv4-address ;

                }

                leaf mask-addr {
                  description 'The mask of route.' ;
                  type ncd:ipv4-address ;

                }

                leaf interface {
                  description 'The interface name of route.' ;
                  type ncd:ifname {
                    length 1..31 ;

                  }

                }

                leaf preference {
                  description 'The route priority and the default value is 1. The range is 1-255.' ;
                  type uint8 {
                    range 1..255 ;

                  }

                  default 1 ;
                }

                leaf metric {
                  description 'The route metric, and the default value is 0. The range is 0-255.' ;
                  type uint8 {
                    range 0..255 ;

                  }

                  default 0 ;
                }

                leaf tag-value {
                  description 'The route tag, and the default value is 0. The range is 0-4294967295.' ;
                  type uint32 {
                    range 0..4294967295 ;

                  }

                  default 0 ;
                }

                leaf track-name {
                  description "The track object name which the static route track-detection related. The default value is null, means that don't relate track-detection." ;
                  type string {
                    length 1..31 ;

                  }

                }

                leaf preference-decrement {
                  description 'The preference decrement can be set when the route has been related with track detection.' ;
                  type uint8 {
                    range 0..255 ;

                  }

                  default 0 ;
                  ncd:revise-date 2015-04-03 ;
                }

                leaf description {
                  description 'The description of the static route information. The default value is empty, means no description information.' ;
                  type string {
                    length 1..64 ;

                  }

                }

                leaf permanent {
                  description 'Whether a permanent static route, the default is 0 means no, and 1 means yes. The range is 0-1.' ;
                  type uint8 {
                    range 0..1 ;

                  }

                  default 0 ;
                }

                leaf no-install {
                  type uint8 {
                    range 0..1 ;

                  }

                  description 'Indicates whether the static route does not deliver the forwarding table, the default is 0 means delivered to the forwarding table, and 1 means not delivered to the forwarding table. The range is 0-1.' ;
                  ncd:revise-date 2023-04-24 ;
                }

              }

            }

            container only-nhs {
              description 'The configuration for static route which only specifies the nexthop.' ;
              list only-nh {
                description 'The configuration for static route which only specifies the nexthop.' ;
                key 'dest-addr mask-addr nexthop' ;
                leaf dest-addr {
                  description 'The destination address of route.' ;
                  type ncd:ipv4-address ;

                }

                leaf mask-addr {
                  description 'The mask of route.' ;
                  type ncd:ipv4-address ;

                }

                leaf nexthop {
                  description 'The nexthop of route.' ;
                  type ncd:ipv4-address ;

                }

                leaf preference {
                  description 'The route priority, and the default value is 1. The range is 1-255.' ;
                  type uint8 {
                    range 1..255 ;

                  }

                  default 1 ;
                }

                leaf metric {
                  description 'The route metric, and the default value is 0. The range is 0-255.' ;
                  type uint8 {
                    range 0..255 ;

                  }

                  default 0 ;
                }

                leaf tag-value {
                  description 'The route tag, and the default value is 0. The range is 0-4294967295.' ;
                  type uint32 {
                    range 0..4294967295 ;

                  }

                  default 0 ;
                }

                leaf bfd-button {
                  description 'Whether associated BFD detection, the default is 0 means no, and 1 means yes. The range is 0-1.' ;
                  type uint8 {
                    range 0..1 ;

                  }

                  default 0 ;
                }

                leaf track-name {
                  description "The track object which the static route track-detection related. The default value is null, means that don't relate track-detection." ;
                  type string {
                    length 1..31 ;

                  }

                }

                leaf preference-decrement {
                  description 'The preference decrement can be set when the route has been related with track detection.' ;
                  type uint8 {
                    range 0..255 ;

                  }

                  default 0 ;
                  ncd:revise-date 2015-04-03 ;
                }

                leaf description {
                  description 'The description of the static route information. The default value is empty, means no description information.' ;
                  type string {
                    length 1..64 ;

                  }

                }

                leaf permanent {
                  description 'Whether a permanent static route, the default is 0 means no, and 1 means yes. The range is 0-1.' ;
                  type uint8 {
                    range 0..1 ;

                  }

                  default 0 ;
                }

                leaf no-install {
                  type uint8 {
                    range 0..1 ;

                  }

                  default 0 ;
                  description 'Indicates whether the static route does not deliver the forwarding table, the default is 0 means delivered to the forwarding table, and 1 means not delivered to the forwarding table. The range is 0-1.' ;
                  ncd:revise-date 2023-04-24 ;
                }

              }

            }

            container both-if-nhs {
              description 'The configuration for static route which both specify the interface and the nexthop.' ;
              list both-if-nh {
                description 'The configuration for static route which both specify the interface and the nexthop.' ;
                key 'dest-addr mask-addr interface if-nexthop' ;
                leaf dest-addr {
                  description 'The destination address.' ;
                  type ncd:ipv4-address ;

                }

                leaf mask-addr {
                  description 'The mask.' ;
                  type ncd:ipv4-address ;

                }

                leaf interface {
                  description 'The interface.' ;
                  type ncd:ifname {
                    length 1..31 ;

                  }

                }

                leaf if-nexthop {
                  description 'The nexthop of route.' ;
                  type ncd:ipv4-address ;

                }

                leaf preference {
                  description 'The route priority, and the default value is 1. The range is 1-255.' ;
                  type uint8 {
                    range 1..255 ;

                  }

                  default 1 ;
                }

                leaf metric {
                  description 'The route metric, and the default value is 0. The range is 0-255.' ;
                  type uint8 {
                    range 0..255 ;

                  }

                  default 0 ;
                }

                leaf tag-value {
                  description 'The route tag, and the default value is 0. The range is 0-4294967295.' ;
                  type uint32 {
                    range 0..4294967295 ;

                  }

                  default 0 ;
                }

                leaf bfd-button {
                  description 'Whether associated BFD detection, the default is 0 means no, and 1 means yes. The range is 0-1.' ;
                  type uint8 {
                    range 0..1 ;

                  }

                  default 0 ;
                }

                leaf track-name {
                  description "The track object which the static route track-detection related. The default value is null, means that don't relate track-detection." ;
                  type string {
                    length 1..31 ;

                  }

                }

                leaf preference-decrement {
                  description 'The preference decrement can be set when the route has been related with track detection.' ;
                  type uint8 {
                    range 0..255 ;

                  }

                  default 0 ;
                  ncd:revise-date 2015-04-03 ;
                }

                leaf description {
                  description 'The description of the static route information. The default value is empty, means no description information.' ;
                  type string {
                    length 1..64 ;

                  }

                }

                leaf permanent {
                  description 'Whether a permanent static route, the default is 0 means no, and 1 means yes. The range is 0-1.' ;
                  type uint8 {
                    range 0..1 ;

                  }

                  default 0 ;
                }

                leaf no-install {
                  type uint8 {
                    range 0..1 ;

                  }

                  default 0 ;
                  description 'Indicates whether the static route does not deliver the forwarding table, the default is 0 means delivered to the forwarding table, and 1 means not delivered to the forwarding table. The range is 0-1.' ;
                  ncd:revise-date 2023-04-24 ;
                }

              }

            }

            container nexthop-vrfs {
              description 'Configure static routes with nexthop in VPN instance.' ;
              list nexthop-vrf {
                description 'Configure static routes with nexthop in VPN instance.' ;
                key 'dest-addr mask-addr' ;
                leaf dest-addr {
                  description 'The destination address.' ;
                  type ncd:ipv4-address ;

                }

                leaf mask-addr {
                  description 'The mask.' ;
                  type ncd:ipv4-address ;

                }

                leaf nh-vrf-name {
                  description 'The name of the private network VPN.' ;
                  type ncd:string-all {
                    length 1..32 ;

                  }

                  mandatory true ;
                }

                leaf preference {
                  description 'The route priority, and the default value is 1. The range is 1-255.' ;
                  type uint8 {
                    range 1..255 ;

                  }

                  default 1 ;
                }

                leaf description {
                  description 'The description of the static route information. The default value is empty, means no description information.' ;
                  type string {
                    length 1..64 ;

                  }

                }

                leaf metric {
                  description 'The route metric, and the default value is 0. The range is 0-255.' ;
                  type uint8 {
                    range 0..255 ;

                  }

                  default 0 ;
                  ncd:revise-date 2022-09-20 ;
                }

                leaf track-name {
                  description "The track object which the static route track-detection related. The default value is null, means that don't relate track-detection." ;
                  type string {
                    length 1..31 ;

                  }

                  ncd:revise-date 2022-09-20 ;
                }

                leaf no-install {
                  type uint8 {
                    range 0..1 ;

                  }

                  default 0 ;
                  description 'Indicates whether the static route does not deliver the forwarding table, the default is 0 means delivered to the forwarding table, and 1 means not delivered to the forwarding table. The range is 0-1.' ;
                  ncd:revise-date 2023-04-24 ;
                }

              }

              ncd:revise-date 2020-08-19 ;
            }

            container sr-policys {
              description 'The configuration for static route which only specifies the SR Policy.' ;
              list sr-policy {
                description 'The configuration for static route which only specifies the SR Policy.' ;
                key 'dest-addr mask-addr color end-point' ;
                leaf dest-addr {
                  description 'The destination address of route.' ;
                  type ncd:ipv4-address ;

                }

                leaf mask-addr {
                  description 'The mask of route.' ;
                  type ncd:ipv4-address ;

                }

                leaf color {
                  description 'The color of SR Policy. Its range is 1-4294967295.' ;
                  type uint32 {
                    range 1..4294967295 ;

                  }

                }

                leaf end-point {
                  description 'The end-point of SR Policy.' ;
                  type string {
                    length 1..39 ;

                  }

                }

                leaf end-point-afi {
                  description 'The address family of end-point.The value is IPv4 or IPv6.' ;
                  type address-family ;

                  mandatory true ;
                }

                leaf srv6-sid {
                  description 'The SRv6 SID of SRv6 Policy.' ;
                  type ncd:ipv6-address-none-zero ;

                  default :: ;
                }

                leaf preference {
                  description 'The route priority, and the default value is 1. The range is 1-255.' ;
                  type uint8 {
                    range 1..255 ;

                  }

                  default 1 ;
                }

                leaf metric {
                  description 'The route metric, and the default value is 0. The range is 0-255.' ;
                  type uint8 {
                    range 0..255 ;

                  }

                  default 0 ;
                }

                leaf tag-value {
                  description 'The route tag, and the default value is 0. The range is 0-4294967295.' ;
                  type uint32 {
                    range 0..4294967295 ;

                  }

                  default 0 ;
                }

                leaf track-name {
                  description "The track object which the static route track-detection related. The default value is null, means that don't relate track-detection." ;
                  type string {
                    length 1..31 ;

                  }

                }

                leaf preference-decrement {
                  description 'The preference decrement can be set when the route has been related with track detection.' ;
                  type uint8 {
                    range 0..255 ;

                  }

                  default 0 ;
                }

                leaf description {
                  description 'The description of the static route information. The default value is empty, means no description information.' ;
                  type string {
                    length 1..64 ;

                  }

                }

                leaf no-install {
                  type uint8 {
                    range 0..1 ;

                  }

                  default 0 ;
                  description 'Indicates whether the static route does not deliver the forwarding table, the default is 0 means delivered to the forwarding table, and 1 means not delivered to the forwarding table. The range is 0-1.' ;
                  ncd:revise-date 2023-04-24 ;
                }

              }

              ncd:revise-date 2021-05-08 ;
            }

          }

          container private-net {
            description 'The configuration for private static route.' ;
            container only-ifs {
              description 'The configuration for static route which only specifies the interface.' ;
              list only-if {
                description 'The configuration for static route which only specifies the interface.' ;
                key 'vrf-name dest-addr mask-addr interface' ;
                leaf vrf-name {
                  description 'The name of the private network VPN.' ;
                  type ncd:string-all {
                    length 1..32 ;

                  }

                }

                leaf dest-addr {
                  description 'The destination address.' ;
                  type ncd:ipv4-address ;

                }

                leaf mask-addr {
                  description 'The mask.' ;
                  type ncd:ipv4-address ;

                }

                leaf interface {
                  description 'Specify the interface name.' ;
                  type ncd:ifname {
                    length 1..31 ;

                  }

                }

                leaf preference {
                  description 'The route priority, and the default value is 1. The range is 1-255.' ;
                  type uint8 {
                    range 1..255 ;

                  }

                  default 1 ;
                }

                leaf metric {
                  description 'The route metric, and the default value is 0. The range is 0-255.' ;
                  type uint8 {
                    range 0..255 ;

                  }

                  default 0 ;
                }

                leaf tag-value {
                  description 'The route tag, and the default value is 0. The range is 0-4294967295.' ;
                  type uint32 {
                    range 0..4294967295 ;

                  }

                  default 0 ;
                }

                leaf track-name {
                  description "The track object which the static route track-detection related. The default value is null, means that don't relate track-detection." ;
                  type string {
                    length 1..31 ;

                  }

                }

                leaf preference-decrement {
                  description 'The preference decrement can be set when the route has been related with track detection.' ;
                  type uint8 {
                    range 0..255 ;

                  }

                  default 0 ;
                  ncd:revise-date 2015-04-03 ;
                }

                leaf description {
                  description 'The description of the static route information. The default value is empty, means no description information.' ;
                  type string {
                    length 1..64 ;

                  }

                }

                leaf permanent {
                  description 'Whether a permanent static route, the default is 0 means no, and 1 means yes. The range is 0-1.' ;
                  type uint8 {
                    range 0..1 ;

                  }

                  default 0 ;
                }

                leaf no-install {
                  type uint8 {
                    range 0..1 ;

                  }

                  default 0 ;
                  description 'Indicates whether the static route does not deliver the forwarding table, the default is 0 means delivered to the forwarding table, and 1 means not delivered to the forwarding table. The range is 0-1.' ;
                  ncd:revise-date 2023-04-24 ;
                }

              }

            }

            container only-nhs {
              description 'The configuration for static route which only specifies the nexthop.' ;
              list only-nh {
                description 'The configuration for static route which only specifies the nexthop.' ;
                key 'vrf-name dest-addr mask-addr nexthop' ;
                leaf vrf-name {
                  description 'The name of the private network VPN.' ;
                  type ncd:string-all {
                    length 1..32 ;

                  }

                }

                leaf dest-addr {
                  description 'The destination address.' ;
                  type ncd:ipv4-address ;

                }

                leaf mask-addr {
                  description 'The mask.' ;
                  type ncd:ipv4-address ;

                }

                leaf nexthop {
                  description 'The nexthop.' ;
                  type ncd:ipv4-address ;

                }

                leaf global {
                  description 'Whether a global static route, the default is 0 means no, and 1 means yes. The range is 0-1.' ;
                  type uint8 {
                    range 0..1 ;

                  }

                  default 0 ;
                }

                leaf preference {
                  description 'The route priority, and the default value is 1. The range is 1-255.' ;
                  type uint8 {
                    range 1..255 ;

                  }

                  default 1 ;
                }

                leaf metric {
                  description 'The route metric, and the default value is 0. The range is 0-255.' ;
                  type uint8 {
                    range 0..255 ;

                  }

                  default 0 ;
                }

                leaf tag-value {
                  description 'The route tag, and the default value is 0. The range is 0-4294967295.' ;
                  type uint32 {
                    range 0..4294967295 ;

                  }

                  default 0 ;
                }

                leaf bfd-button {
                  description 'Whether associated BFD detection, the default is 0 means no, and 1 means yes. The range is 0-1.' ;
                  type uint8 {
                    range 0..1 ;

                  }

                  default 0 ;
                }

                leaf track-name {
                  description "The track object which the static route track-detection related. The default value is null, means that don't relate track-detection." ;
                  type string {
                    length 1..31 ;

                  }

                }

                leaf preference-decrement {
                  description 'The preference decrement can be set when the route has been related with track detection.' ;
                  type uint8 {
                    range 0..255 ;

                  }

                  default 0 ;
                  ncd:revise-date 2015-04-03 ;
                }

                leaf description {
                  description 'The description of the static route information. The default value is empty, means no description information.' ;
                  type string {
                    length 1..64 ;

                  }

                }

                leaf permanent {
                  description 'Whether a permanent static route, the default is 0 means no, and 1 means yes. The range is 0-1.' ;
                  type uint8 {
                    range 0..1 ;

                  }

                  default 0 ;
                }

                leaf no-install {
                  type uint8 {
                    range 0..1 ;

                  }

                  default 0 ;
                  description 'Indicates whether the static route does not deliver the forwarding table, the default is 0 means delivered to the forwarding table, and 1 means not delivered to the forwarding table. The range is 0-1.' ;
                  ncd:revise-date 2023-04-24 ;
                }

              }

            }

            container both-if-nhs {
              description 'The configuration for static route which both specify the interface and the nexthop.' ;
              list both-if-nh {
                description 'The configuration for static route which both specify the interface and the nexthop.' ;
                key 'vrf-name dest-addr mask-addr interface if-nexthop' ;
                leaf vrf-name {
                  description 'The name of the private network VPN.' ;
                  type ncd:string-all {
                    length 1..32 ;

                  }

                }

                leaf dest-addr {
                  description 'The destination address.' ;
                  type ncd:ipv4-address ;

                }

                leaf mask-addr {
                  description 'The mask.' ;
                  type ncd:ipv4-address ;

                }

                leaf interface {
                  description 'The interface.' ;
                  type ncd:ifname {
                    length 1..31 ;

                  }

                }

                leaf if-nexthop {
                  description 'The nexthop.' ;
                  type ncd:ipv4-address ;

                }

                leaf preference {
                  description 'The route priority, and the default value is 1. The range is 1-255' ;
                  type uint8 {
                    range 1..255 ;

                  }

                  default 1 ;
                }

                leaf metric {
                  description 'The route metric, and the default value is 0. The range is 0-255.' ;
                  type uint8 {
                    range 0..255 ;

                  }

                  default 0 ;
                }

                leaf tag-value {
                  description 'The route tag, and the default value is 0. The range is 0-4294967295.' ;
                  type uint32 {
                    range 0..4294967295 ;

                  }

                  default 0 ;
                }

                leaf bfd-button {
                  description 'Whether associated BFD detection, the default is 0 means no, and 1 means yes. The range is 0-1.' ;
                  type uint8 {
                    range 0..1 ;

                  }

                  default 0 ;
                }

                leaf track-name {
                  description "The track object which the static route track-detection related. The default value is null, means that don't relate track-detection." ;
                  type string {
                    length 1..31 ;

                  }

                }

                leaf preference-decrement {
                  description 'The preference decrement can be set when the route has been related with track detection.' ;
                  type uint8 {
                    range 0..255 ;

                  }

                  default 0 ;
                  ncd:revise-date 2015-04-03 ;
                }

                leaf description {
                  description 'The description of the static route information. The default value is empty, means no description information.' ;
                  type string {
                    length 1..64 ;

                  }

                }

                leaf permanent {
                  description 'Whether a permanent static route, the default is 0 means no, and 1 means yes. The range is 0-1.' ;
                  type uint8 {
                    range 0..1 ;

                  }

                  default 0 ;
                }

                leaf no-install {
                  type uint8 {
                    range 0..1 ;

                  }

                  default 0 ;
                  description 'Indicates whether the static route does not deliver the forwarding table, the default is 0 means delivered to the forwarding table, and 1 means not delivered to the forwarding table. The range is 0-1.' ;
                  ncd:revise-date 2023-04-24 ;
                }

              }

            }

            container publics {
              description 'The configuration for static route which specifies the nexthop to be public.' ;
              list public {
                description 'The configuration for static route which specifies the nexthop to be public.' ;
                key 'vrf-name dest-addr mask-addr' ;
                leaf vrf-name {
                  description 'The name of the private network VPN.' ;
                  type ncd:string-all {
                    length 1..32 ;

                  }

                }

                leaf dest-addr {
                  description 'The destination address.' ;
                  type ncd:ipv4-address ;

                }

                leaf mask-addr {
                  description 'The mask.' ;
                  type ncd:ipv4-address ;

                }

                leaf preference {
                  description 'The route priority, and the default value is 1. The range is 1-255' ;
                  type uint8 {
                    range 1..255 ;

                  }

                  default 1 ;
                  ncd:revise-date 2022-09-20 ;
                }

                leaf metric {
                  description 'The route metric, and the default value is 0. The range is 0-255.' ;
                  type uint8 {
                    range 0..255 ;

                  }

                  default 0 ;
                  ncd:revise-date 2022-09-20 ;
                }

                leaf track-name {
                  description "The track object which the static route track-detection related. The default value is null, means that don't relate track-detection." ;
                  type string {
                    length 1..31 ;

                  }

                  ncd:revise-date 2022-09-20 ;
                }

                leaf description {
                  description 'The description of the static route information. The default value is empty, means no description information.' ;
                  type string {
                    length 1..64 ;

                  }

                  ncd:revise-date 2022-09-20 ;
                }

                leaf no-install {
                  type uint8 {
                    range 0..1 ;

                  }

                  default 0 ;
                  description 'Indicates whether the static route does not deliver the forwarding table, the default is 0 means delivered to the forwarding table, and 1 means not delivered to the forwarding table. The range is 0-1.' ;
                  ncd:revise-date 2023-04-24 ;
                }

              }

              ncd:revise-date 2018-05-10 ;
            }

            container global-v6-nhs {
              if-feature ipv4-dest-with-ipv6-global-nh ;

              description 'The configuration for static route which only specifies the IPv6 global nexthop.' ;
              list global-v6-nh {
                description 'The configuration for static route which only specifies the IPv6 global nexthop.' ;
                key 'vrf-name dest-addr mask-addr ipv6-nh' ;
                leaf vrf-name {
                  description 'The name of the private network VPN.' ;
                  type ncd:string-all {
                    length 1..32 ;

                  }

                }

                leaf dest-addr {
                  description 'The destination address.' ;
                  type ncd:ipv4-address ;

                }

                leaf mask-addr {
                  description 'The mask.' ;
                  type ncd:ipv4-address ;

                }

                leaf ipv6-nh {
                  description 'The IPv6 nexthop.' ;
                  type ncd:ipv6-address ;

                }

                leaf preference {
                  description 'The route priority, and the default value is 1. The range is 1-255.' ;
                  type uint8 {
                    range 1..255 ;

                  }

                  default 1 ;
                }

                leaf metric {
                  description 'The route metric, and the default value is 0. The range is 0-255.' ;
                  type uint8 {
                    range 0..255 ;

                  }

                  default 0 ;
                }

                leaf tag-value {
                  description 'The route tag, and the default value is 0. The range is 0-4294967295.' ;
                  type uint32 {
                    range 0..4294967295 ;

                  }

                  default 0 ;
                }

                leaf track-name {
                  description "The track object which the static route track-detection related. The default value is null, means that don't relate track-detection." ;
                  type string {
                    length 1..31 ;

                  }

                }

                leaf preference-decrement {
                  description 'The preference decrement can be set when the route has been related with track detection.' ;
                  type uint8 {
                    range 0..255 ;

                  }

                  default 0 ;
                }

                leaf description {
                  description 'The description of the static route information. The default value is empty, means no description information.' ;
                  type string {
                    length 1..64 ;

                  }

                }

                leaf permanent {
                  description 'Whether a permanent static route, the default is 0 means no, and 1 means yes. The range is 0-1.' ;
                  type uint8 {
                    range 0..1 ;

                  }

                  default 0 ;
                }

                leaf no-install {
                  type uint8 {
                    range 0..1 ;

                  }

                  default 0 ;
                  description 'Indicates whether the static route does not deliver the forwarding table, the default is 0 means delivered to the forwarding table, and 1 means not delivered to the forwarding table. The range is 0-1.' ;
                  ncd:revise-date 2023-04-24 ;
                }

              }

              ncd:revise-date 2019-04-01 ;
            }

            container sr-policys {
              description 'The configuration for static route which only specifies the SR Policy.' ;
              list sr-policy {
                description 'The configuration for static route which only specifies the SR Policy.' ;
                key 'vrf-name dest-addr mask-addr color end-point' ;
                leaf vrf-name {
                  description 'The name of the private network VPN.' ;
                  type ncd:string-all {
                    length 1..32 ;

                  }

                }

                leaf dest-addr {
                  description 'The destination address of route.' ;
                  type ncd:ipv4-address ;

                }

                leaf mask-addr {
                  description 'The mask of route.' ;
                  type ncd:ipv4-address ;

                }

                leaf color {
                  description 'The color of SR Policy. Its range is 1-4294967295.' ;
                  type uint32 {
                    range 1..4294967295 ;

                  }

                }

                leaf end-point {
                  description 'The end-point of SR Policy.' ;
                  type string {
                    length 1..39 ;

                  }

                }

                leaf end-point-afi {
                  description 'The address family of end-point.The value is IPv4 or IPv6.' ;
                  type address-family ;

                  mandatory true ;
                }

                leaf srv6-sid {
                  description 'The SRv6 SID of SRv6 Policy.' ;
                  type ncd:ipv6-address-none-zero ;

                  default :: ;
                }

                leaf preference {
                  description 'The route priority, and the default value is 1. The range is 1-255.' ;
                  type uint8 {
                    range 1..255 ;

                  }

                  default 1 ;
                }

                leaf metric {
                  description 'The route metric, and the default value is 0. The range is 0-255.' ;
                  type uint8 {
                    range 0..255 ;

                  }

                  default 0 ;
                }

                leaf tag-value {
                  description 'The route tag, and the default value is 0. The range is 0-4294967295.' ;
                  type uint32 {
                    range 0..4294967295 ;

                  }

                  default 0 ;
                }

                leaf track-name {
                  description "The track object which the static route track-detection related. The default value is null, means that don't relate track-detection." ;
                  type string {
                    length 1..31 ;

                  }

                }

                leaf preference-decrement {
                  description 'The preference decrement can be set when the route has been related with track detection.' ;
                  type uint8 {
                    range 0..255 ;

                  }

                  default 0 ;
                }

                leaf description {
                  description 'The description of the static route information. The default value is empty, means no description information.' ;
                  type string {
                    length 1..64 ;

                  }

                }

                leaf no-install {
                  type uint8 {
                    range 0..1 ;

                  }

                  default 0 ;
                  description 'Indicates whether the static route does not deliver the forwarding table, the default is 0 means delivered to the forwarding table, and 1 means not delivered to the forwarding table. The range is 0-1.' ;
                  ncd:revise-date 2023-04-24 ;
                }

              }

              ncd:revise-date 2021-05-08 ;
            }

            container nh-with-vrfs {
              list nh-with-vrf {
                description 'The configuration for static route which specifies the nexthop to another VPN.' ;
                key 'vrf-name dest-addr mask-addr nexthop nh-vrf-name' ;
                leaf vrf-name {
                  description 'The name of the private network VPN.' ;
                  type ncd:string-all {
                    length 1..32 ;

                  }

                }

                leaf dest-addr {
                  type ncd:ipv4-address ;

                  description 'The destination address of route.' ;
                }

                leaf mask-addr {
                  type ncd:ipv4-address ;

                  description 'The mask of route.' ;
                }

                leaf nexthop {
                  type ncd:ipv4-address-none-zero ;

                  description 'The nexthop of the static route in another VRF.' ;
                }

                leaf nh-vrf-name {
                  type string {
                    length 1..32 ;

                  }

                  description 'VRF name of the next hop in another VRF.If this parameter is not set, the VRF of the next hop is the same as that of the route.' ;
                }

                leaf preference {
                  description 'The route priority, and the default value is 1. The range is 1-255.' ;
                  type uint8 {
                    range 1..255 ;

                  }

                  default 1 ;
                }

                leaf metric {
                  description 'The route metric, and the default value is 0. The range is 0-255.' ;
                  type uint8 {
                    range 0..255 ;

                  }

                  default 0 ;
                }

                leaf tag-value {
                  description 'The route tag, and the default value is 0. The range is 0-4294967295.' ;
                  type uint32 {
                    range 0..4294967295 ;

                  }

                  default 0 ;
                }

                leaf bfd-button {
                  description 'Whether associated BFD detection, the default is 0 means no, and 1 means yes. The range is 0-1.' ;
                  type uint8 {
                    range 0..1 ;

                  }

                  default 0 ;
                }

                leaf track-name {
                  description "The track object which the static route track-detection related. The default value is null, means that don't relate track-detection." ;
                  type string {
                    length 1..31 ;

                  }

                }

                leaf preference-decrement {
                  description 'The preference decrement can be set when the route has been related with track detection.' ;
                  type uint8 {
                    range 0..255 ;

                  }

                  default 0 ;
                }

                leaf description {
                  description 'The description of the static route information. The default value is empty, means no description information.' ;
                  type string {
                    length 1..64 ;

                  }

                }

                leaf no-install {
                  type uint8 {
                    range 0..1 ;

                  }

                  default 0 ;
                  description 'Indicates whether the static route does not deliver the forwarding table, the default is 0 means delivered to the forwarding table, and 1 means not delivered to the forwarding table. The range is 0-1.' ;
                  ncd:revise-date 2023-04-24 ;
                }

              }

              description 'The configuration for static route which specifies the nexthop to another VPN.' ;
              ncd:revise-date 2022-06-02 ;
            }

            container nexthop-vrfs {
              description 'Configure static routes with nexthop in VPN instance.' ;
              list nexthop-vrf {
                description 'Configure static routes with nexthop in VPN instance.' ;
                key 'vrf-name dest-addr mask-addr nh-vrf-name import' ;
                leaf vrf-name {
                  description 'The name of the private network VPN.' ;
                  type ncd:string-all {
                    length 1..32 ;

                  }

                }

                leaf dest-addr {
                  description 'The destination address.' ;
                  type ncd:ipv4-address ;

                }

                leaf mask-addr {
                  description 'The mask.' ;
                  type ncd:ipv4-address ;

                }

                leaf nh-vrf-name {
                  description 'The name of the private network VPN.' ;
                  type ncd:string-all {
                    length 1..32 ;

                  }

                }

                leaf import {
                  description 'Import support flag. Only can be set to 0.' ;
                  type uint32 {
                    range 0 ;

                  }

                }

                leaf preference {
                  description 'The route priority, and the default value is 1. The range is 1-255.' ;
                  type uint8 {
                    range 1..255 ;

                  }

                  default 1 ;
                }

                leaf metric {
                  description 'The route metric, and the default value is 0. The range is 0-255.' ;
                  type uint8 {
                    range 0..255 ;

                  }

                  default 0 ;
                }

                leaf tag-value {
                  description 'The route tag, and the default value is 0. The range is 0-4294967295.' ;
                  type uint32 {
                    range 0..4294967295 ;

                  }

                  default 0 ;
                }

                leaf track-name {
                  description "The track object which the static route track-detection related. The default value is null, means that don't relate track-detection." ;
                  type string {
                    length 1..31 ;

                  }

                }

                leaf description {
                  description 'The description of the static route information. The default value is empty, means no description information.' ;
                  type string {
                    length 1..64 ;

                  }

                }

                leaf no-install {
                  type uint8 {
                    range 0..1 ;

                  }

                  default 0 ;
                  description 'Indicates whether the static route does not deliver the forwarding table, the default is 0 means delivered to the forwarding table, and 1 means not delivered to the forwarding table. The range is 0-1.' ;
                  ncd:revise-date 2023-04-24 ;
                }

              }

              ncd:revise-date 2022-09-20 ;
            }

          }

          container mng-net {
            description 'The configuration for mng static route.' ;
            container only-nhs {
              description 'The configuration for static route which only specifies the nexthop.' ;
              list only-nh {
                description 'The configuration for static route which only specifies the nexthop.' ;
                key 'dest-addr mask-addr nexthop' ;
                leaf dest-addr {
                  description 'The destination address.' ;
                  type ncd:ipv4-address ;

                }

                leaf mask-addr {
                  description 'The mask.' ;
                  type ncd:ipv4-address ;

                }

                leaf nexthop {
                  description 'The nexthop.' ;
                  type ncd:ipv4-address ;

                }

                leaf global {
                  description 'Whether a global static route, the default is 0 means no, and 1 means yes. The range is 0-1.' ;
                  type uint8 {
                    range 0..1 ;

                  }

                  default 0 ;
                }

                leaf preference {
                  description 'The route priority, and the default value is 1. The range is 1-255.' ;
                  type uint8 {
                    range 1..255 ;

                  }

                  default 1 ;
                }

                leaf metric {
                  description 'The route metric, and the default value is 0. The range is 0-255.' ;
                  type uint8 {
                    range 0..255 ;

                  }

                  default 0 ;
                }

                leaf tag-value {
                  description 'The route tag, and the default value is 0. The range is 0-4294967295.' ;
                  type uint32 {
                    range 0..4294967295 ;

                  }

                  default 0 ;
                }

                leaf bfd-button {
                  description 'Whether associated BFD detection, the default is 0 means no, and 1 means yes. The range is 0-1.' ;
                  type uint8 {
                    range 0..1 ;

                  }

                  default 0 ;
                }

                leaf track-name {
                  description "The track object which the static route track-detection related. The default value is null, means that don't relate track-detection." ;
                  type string {
                    length 1..31 ;

                  }

                }

                leaf preference-decrement {
                  description 'The preference decrement can be set when the route has been related with track detection.' ;
                  type uint8 {
                    range 0..255 ;

                  }

                  default 0 ;
                  ncd:revise-date 2015-04-03 ;
                }

                leaf description {
                  description 'The description of the static route information. The default value is empty, means no description information.' ;
                  type string {
                    length 1..64 ;

                  }

                }

                leaf permanent {
                  description 'Whether a permanent static route, the default is 0 means no, and 1 means yes. The range is 0-1.' ;
                  type uint8 {
                    range 0..1 ;

                  }

                  default 0 ;
                }

                leaf no-install {
                  type uint8 {
                    range 0..1 ;

                  }

                  default 0 ;
                  description 'Indicates whether the static route does not deliver the forwarding table, the default is 0 means delivered to the forwarding table, and 1 means not delivered to the forwarding table. The range is 0-1.' ;
                  ncd:revise-date 2023-04-24 ;
                }

              }

            }

            container publics {
              description 'The configuration for static route which specifies the nexthop to be public.' ;
              list public {
                description 'The configuration for static route which specifies the nexthop to be public.' ;
                key 'dest-addr mask-addr' ;
                leaf dest-addr {
                  description 'The destination address.' ;
                  type ncd:ipv4-address ;

                }

                leaf mask-addr {
                  description 'The mask.' ;
                  type ncd:ipv4-address ;

                }

                leaf preference {
                  description 'The route priority, and the default value is 1. The range is 1-255.' ;
                  type uint8 {
                    range 1..255 ;

                  }

                  default 1 ;
                  ncd:revise-date 2022-09-20 ;
                }

                leaf metric {
                  description 'The route metric, and the default value is 0. The range is 0-255.' ;
                  type uint8 {
                    range 0..255 ;

                  }

                  default 0 ;
                  ncd:revise-date 2022-09-20 ;
                }

                leaf track-name {
                  description "The track object which the static route track-detection related. The default value is null, means that don't relate track-detection." ;
                  type string {
                    length 1..31 ;

                  }

                  ncd:revise-date 2022-09-20 ;
                }

                leaf description {
                  description 'The description of the static route information. The default value is empty, means no description information.' ;
                  type string {
                    length 1..64 ;

                  }

                  ncd:revise-date 2022-09-20 ;
                }

                leaf no-install {
                  type uint8 {
                    range 0..1 ;

                  }

                  default 0 ;
                  description 'Indicates whether the static route does not deliver the forwarding table, the default is 0 means delivered to the forwarding table, and 1 means not delivered to the forwarding table. The range is 0-1.' ;
                  ncd:revise-date 2023-04-24 ;
                }

              }

              ncd:revise-date 2018-05-10 ;
            }

            container global-v6-nhs {
              if-feature ipv4-dest-with-ipv6-global-nh ;

              description 'The configuration for static route which only specifies the IPv6 global nexthop.' ;
              list global-v6-nh {
                description 'The configuration for static route which only specifies the IPv6 global nexthop.' ;
                key 'dest-addr mask-addr ipv6-nh' ;
                leaf dest-addr {
                  description 'The destination address.' ;
                  type ncd:ipv4-address ;

                }

                leaf mask-addr {
                  description 'The mask.' ;
                  type ncd:ipv4-address ;

                }

                leaf ipv6-nh {
                  description 'The IPv6 nexthop.' ;
                  type ncd:ipv6-address ;

                }

                leaf preference {
                  description 'The route priority, and the default value is 1. The range is 1-255.' ;
                  type uint8 {
                    range 1..255 ;

                  }

                  default 1 ;
                }

                leaf metric {
                  description 'The route metric, and the default value is 0. The range is 0-255.' ;
                  type uint8 {
                    range 0..255 ;

                  }

                  default 0 ;
                }

                leaf tag-value {
                  description 'The route tag, and the default value is 0. The range is 0-4294967295.' ;
                  type uint32 {
                    range 0..4294967295 ;

                  }

                  default 0 ;
                }

                leaf track-name {
                  description "The track object which the static route track-detection related. The default value is null, means that don't relate track-detection." ;
                  type string {
                    length 1..31 ;

                  }

                }

                leaf preference-decrement {
                  description 'The preference decrement can be set when the route has been related with track detection.' ;
                  type uint8 {
                    range 0..255 ;

                  }

                  default 0 ;
                }

                leaf description {
                  description 'The description of the static route information. The default value is empty, means no description information.' ;
                  type string {
                    length 1..64 ;

                  }

                }

                leaf permanent {
                  description 'Whether a permanent static route, the default is 0 means no, and 1 means yes. The range is 0-1.' ;
                  type uint8 {
                    range 0..1 ;

                  }

                  default 0 ;
                }

                leaf no-install {
                  type uint8 {
                    range 0..1 ;

                  }

                  default 0 ;
                  description 'Indicates whether the static route does not deliver the forwarding table, the default is 0 means delivered to the forwarding table, and 1 means not delivered to the forwarding table. The range is 0-1.' ;
                  ncd:revise-date 2023-04-24 ;
                }

              }

              ncd:revise-date 2019-04-01 ;
            }

            container sr-policys {
              description 'The configuration for static route which only specifies the SR Policy.' ;
              list sr-policy {
                description 'The configuration for static route which only specifies the SR Policy.' ;
                key 'dest-addr mask-addr color end-point' ;
                leaf dest-addr {
                  description 'The destination address of route.' ;
                  type ncd:ipv4-address ;

                }

                leaf mask-addr {
                  description 'The mask of route.' ;
                  type ncd:ipv4-address ;

                }

                leaf color {
                  description 'The color of SR Policy. Its range is 1-4294967295.' ;
                  type uint32 {
                    range 1..4294967295 ;

                  }

                }

                leaf end-point {
                  description 'The end-point of SR Policy.' ;
                  type string {
                    length 1..39 ;

                  }

                }

                leaf end-point-afi {
                  description 'The address family of end-point.The value is IPv4 or IPv6.' ;
                  type address-family ;

                  mandatory true ;
                }

                leaf srv6-sid {
                  description 'The SRv6 SID of SRv6 Policy.' ;
                  type ncd:ipv6-address-none-zero ;

                  default :: ;
                }

                leaf preference {
                  description 'The route priority, and the default value is 1. The range is 1-255.' ;
                  type uint8 {
                    range 1..255 ;

                  }

                  default 1 ;
                }

                leaf metric {
                  description 'The route metric, and the default value is 0. The range is 0-255.' ;
                  type uint8 {
                    range 0..255 ;

                  }

                  default 0 ;
                }

                leaf tag-value {
                  description 'The route tag, and the default value is 0. The range is 0-4294967295.' ;
                  type uint32 {
                    range 0..4294967295 ;

                  }

                  default 0 ;
                }

                leaf track-name {
                  description "The track object which the static route track-detection related. The default value is null, means that don't relate track-detection." ;
                  type string {
                    length 1..31 ;

                  }

                }

                leaf preference-decrement {
                  description 'The preference decrement can be set when the route has been related with track detection.' ;
                  type uint8 {
                    range 0..255 ;

                  }

                  default 0 ;
                }

                leaf description {
                  description 'The description of the static route information. The default value is empty, means no description information.' ;
                  type string {
                    length 1..64 ;

                  }

                }

                leaf no-install {
                  type uint8 {
                    range 0..1 ;

                  }

                  default 0 ;
                  description 'Indicates whether the static route does not deliver the forwarding table, the default is 0 means delivered to the forwarding table, and 1 means not delivered to the forwarding table. The range is 0-1.' ;
                  ncd:revise-date 2023-04-24 ;
                }

              }

              ncd:revise-date 2021-05-08 ;
            }

          }

        }

        container source-nexthop {
          description 'To specify the original address for static route, using for creating multiple-hops BFD session in some scenarios.' ;
          presence source-nexthop ;
          leaf loopback-name {
            description 'The loopback name specified.' ;
            type ncd:ifname {
              length 1..31 ;

            }

            mandatory true ;
          }

        }

        container source-nexthop-vrf {
          description 'To specify the original address for vpn static route, using for creating vpn multiple-hops BFD session in some scenarios.' ;
          presence source-nexthop-vrf ;
          list private-net {
            description 'To specify the original address for vpn static route, using for creating vpn multiple-hops BFD session in some scenarios.' ;
            key vrf-name ;
            leaf vrf-name {
              description 'Specifying the VPN name.' ;
              type ncd:string-all {
                length 1..32 ;

              }

            }

            leaf loopback-name {
              description 'To specify the loopback name, which must be in the same vpn instance.' ;
              type ncd:ifname {
                length 1..31 ;

              }

              mandatory true ;
            }

          }

          ncd:revise-date 2015-11-02 ;
        }

        container fast-reroute {
          description "The node for IPv4-STATIC-ROUTE's FRR function." ;
          container public-net {
            description 'Enable or disable the switch of FRR function in public network.' ;
            presence enable ;
            leaf wtr-value {
              type uint8 {
                range 0..12 ;

              }

              description 'Set the WTR(WaitToRestore) time in minute, the range is 0-12.' ;
              default 0 ;
              units mins ;
            }

            leaf wtr-second-with-minute {
              description 'Set the WTR(WaitToRestore) time in second, the range is 0-59. This leaf must set with the leaf "wtr-value".' ;
              type uint32 {
                range 0..59 ;

              }

              units sec ;
              ncd:revise-date 2024-06-26 ;
            }

            leaf wtr-second {
              type uint32 {
                range 1..720 ;

              }

              description 'Set the WTR(WaitToRestore) time in second, the range is 0-720.' ;
              units sec ;
              ncd:revise-date 2023-11-30 ;
            }

            ncd:revise-date 2013-08-15 ;
          }

          container private-nets {
            description 'Enable or disable the switch of FRR function in private network.' ;
            list private-net {
              description 'Enable or disable the switch of FRR function in private network.' ;
              key vrf-name ;
              leaf vrf-name {
                description 'Specifying the VPN name' ;
                type ncd:string-all {
                  length 1..32 ;

                }

              }

              leaf wtr-value {
                type uint8 {
                  range 0..12 ;

                }

                default 0 ;
                units mins ;
                description 'Set the WTR(WaitToRestore) time in minute, the range is 0-12.' ;
              }

              leaf wtr-second-with-minute {
                type uint32 {
                  range 0..59 ;

                }

                units sec ;
                description 'Set the WTR(WaitToRestore) time in second, the range is 0-720.' ;
                ncd:revise-date 2024-06-26 ;
              }

              leaf wtr-second {
                type uint32 {
                  range 1..720 ;

                }

                description 'Set the WTR(WaitToRestore) time in second, the range is 0-720.' ;
                units sec ;
                ncd:revise-date 2023-11-30 ;
              }

            }

            ncd:revise-date 2013-08-15 ;
          }

        }

        container dynamic-protect {
          description 'The function node for IPv4-STATIC-ROUTE to protect the dynamic route(RIP, OSPFv2, ISIS, BGP etc).' ;
          container public-nets {
            description 'Enable or disable the function of dynamic-route-protection in public network.' ;
            list public-net {
              description 'Enable or disable the function of dynamic-route-protection in public network.' ;
              key route-type ;
              leaf route-type {
                description 'Specify the route type (RIP, OSPF, BGP, ISIS) which is needed to protect.' ;
                type protect-type ;

              }

            }

          }

          container private-nets {
            description 'Enable or disable the function of dynamic-route-protection in private network.' ;
            list private-net {
              description 'Enable or disable the function of dynamic-route-protection in private network.' ;
              key 'vrf-name route-type' ;
              leaf vrf-name {
                description 'Specify the VPN name.' ;
                type string {
                  length 1..32 ;

                }

              }

              leaf route-type {
                description 'Specify the route type (RIP, OSPF, BGP, ISIS) which is needed to protect.' ;
                type protect-type ;

              }

            }

          }

        }

        container update-delay {
          description 'The node for STATIC-ROUTE to set update-delay time.' ;
          leaf time-interval {
            description 'The update-delay time interval, the default value is 0, the range is 0 to 1200, and the unit is second.' ;
            type uint16 {
              range 0..1200 ;

            }

            units second ;
            default 0 ;
          }

        }

        container recursion-l3vpn {
          description 'The recursion-l3vpn function for IPv4-STATIC-ROUTE.' ;
          list private-net {
            description 'The recursion-l3vpn function for IPv4-STATIC-ROUTE.' ;
            key vrf-name ;
            leaf vrf-name {
              description 'Specifying the VPN name.' ;
              type string {
                length 1..32 ;

              }

            }

          }

          ncd:revise-date 2016-05-26 ;
        }

        container route-vxlan {
          description 'The configuration for static VXLAN route.' ;
          container static-tunnels {
            description 'Routing configuration in static tunnel scene.' ;
            list static-tunnel {
              description 'Routing configuration in static tunnel scene.' ;
              key 'vrf-name dest-addr mask-addr vxlan-if' ;
              leaf vrf-name {
                description 'The name of the private network VPN.' ;
                type string {
                  length 1..32 ;

                }

              }

              leaf dest-addr {
                description 'The destination address.' ;
                type ncd:ipv4-address ;

              }

              leaf mask-addr {
                description 'The mask address.' ;
                type ncd:ipv4-address ;

              }

              leaf vxlan-if {
                description 'The VXLAN interface name.' ;
                type ncd:ifname {
                  length 1..31 ;

                }

              }

              leaf vni-label {
                description 'The VNI label value, and the invalid value is 0. The range is 1-16777215.' ;
                type uint32 {
                  range 1..16777215 ;

                }

                ncd:revise-date 2018-01-26 ;
              }

              leaf router-mac {
                description 'The router MAC value.' ;
                type ncd:mac-address ;

              }

              leaf distance {
                description 'The route priority, and the default value is 1. The range is 1-255.' ;
                type uint8 {
                  range 1..255 ;

                }

                default 1 ;
              }

              leaf metric {
                description 'The route metric, and the default value is 0. The range is 0-255.' ;
                type uint8 {
                  range 0..255 ;

                }

                default 0 ;
              }

              leaf description {
                description 'The description information of the route.' ;
                type string {
                  length 0..64 ;

                }

              }

              leaf track-name {
                description "The track object which the static route track-detection related. The default value is null, means that don't relate track-detection." ;
                type string {
                  length 1..31 ;

                }

                ncd:revise-date 2018-06-28 ;
              }

            }

          }

          container dynamic-tunnels {
            description 'Routing configuration in IPv4 dynamic tunnel scene.' ;
            list dynamic-tunnel {
              description 'Routing configuration in IPv4 dynamic tunnel scene.' ;
              key 'vrf-name dest-addr mask-addr local-ip remote-ip' ;
              leaf vrf-name {
                description 'The name of the private network VPN.' ;
                type string {
                  length 1..32 ;

                }

              }

              leaf dest-addr {
                description 'The destination address.' ;
                type ncd:ipv4-address ;

              }

              leaf mask-addr {
                description 'The mask address.' ;
                type ncd:ipv4-address ;

              }

              leaf local-ip {
                description 'The local ip address.' ;
                type ncd:ipv4-address ;

              }

              leaf remote-ip {
                description 'The remote ip address.' ;
                type ncd:ipv4-address ;

              }

              leaf vni-label {
                description 'The VNI label value, and the invalid value is 0. The range is 1-16777215.' ;
                type uint32 {
                  range 1..16777215 ;

                }

              }

              leaf router-mac {
                description 'The router MAC value.' ;
                type ncd:mac-address ;

              }

              leaf distance {
                description 'The route priority, and the default value is 1. The range is 1-255.' ;
                type uint8 {
                  range 1..255 ;

                }

                default 1 ;
              }

              leaf metric {
                description 'The route metric, and the default value is 0. The range is 0-255.' ;
                type uint8 {
                  range 0..255 ;

                }

                default 0 ;
              }

              leaf description {
                description 'The description information of the route.' ;
                type string {
                  length 0..64 ;

                }

              }

              leaf track-name {
                description "The track object which the static route track-detection related. The default value is null, means that don't relate track-detection." ;
                type string {
                  length 1..31 ;

                }

              }

            }

            ncd:revise-date 2018-06-28 ;
          }

          container dynamic-tunnels-ipv6 {
            description 'Routing configuration in IPv6 dynamic tunnel scene.' ;
            presence dynamic-ipv6 ;
            list dynamic-tunnel {
              description 'Routing configuration in IPv6 dynamic tunnel scene.' ;
              key 'vrf-name dest-addr mask-addr local-ipv6 remote-ipv6' ;
              leaf vrf-name {
                description 'The name of the private network VPN.' ;
                type string {
                  length 1..32 ;

                }

              }

              leaf dest-addr {
                description 'The destination address.' ;
                type ncd:ipv4-address ;

              }

              leaf mask-addr {
                description 'The mask address.' ;
                type ncd:ipv4-address ;

              }

              leaf local-ipv6 {
                description 'The local IPv6 address of VXLAN tunnel.' ;
                type ncd:ipv6-address-none-zero ;

              }

              leaf remote-ipv6 {
                description 'The remote IPv6 address of VXLAN tunnel.' ;
                type ncd:ipv6-address-none-zero ;

              }

              leaf vni-label {
                description 'The VNI label value, and the invalid value is 0. The range is 1-16777215.' ;
                type uint32 {
                  range 1..16777215 ;

                }

                mandatory true ;
              }

              leaf router-mac {
                description 'The router MAC value.' ;
                type ncd:mac-address ;

                mandatory true ;
              }

              leaf distance {
                description 'The route priority, and the default value is 1. The range is 1-255.' ;
                type uint8 {
                  range 1..255 ;

                }

                default 1 ;
              }

              leaf metric {
                description 'The route metric, and the default value is 0. The range is 0-255.' ;
                type uint8 {
                  range 0..255 ;

                }

                default 0 ;
              }

              leaf description {
                description 'The description information of the route.' ;
                type string {
                  length 0..64 ;

                }

              }

              leaf track-name {
                description "The track object which the static route track-detection related. The default value is null, means that don't relate track-detection." ;
                type string {
                  length 1..31 ;

                }

              }

            }

            ncd:revise-date 2022-09-07 ;
          }

          ncd:revise-date 2017-11-30 ;
        }

        container nexthop {
          if-feature nexthop-resolving-delay ;

          description 'The node for IPv4 static route to set related nexthop features.' ;
          container trigger {
            description 'The node to trigger nexthop resolving.' ;
            container delay {
              description 'The node to set delay time.' ;
              leaf time {
                description 'The nexthop resolving delay time , the default value is 0, the range is 0 to 300, and the unit is second.' ;
                type uint32 {
                  range 0..300 {
                    description 'Delay-time value.' ;
                  }

                }

                units second ;
                default 0 ;
              }

            }

          }

          ncd:revise-date 2020-01-09 ;
        }

        container bfd {
          if-feature bfd-template ;

          description "The configuration for IPv4 static route to set BFD's attribute." ;
          container single-bfds {
            description "The configuration for IPv4 static route to set single-hop BFD's attributes." ;
            presence template-name ;
            list single-bfd {
              description "The configuration for single-hop BFD's template name." ;
              key 'ifname nexthop' ;
              leaf ifname {
                description 'The interface name specified.' ;
                type ncd:ifname {
                  length 1..31 ;

                }

              }

              leaf nexthop {
                description 'The nexthop address specified.' ;
                type ncd:ipv4-address ;

              }

              leaf template-name {
                description "The template name of single-hop BFD.
                These characters's ASCII unicode must be between 0x21-0x3E / 0x40-0x7E." ;
                type string {
                  length 1..31 ;

                }

                mandatory true ;
              }

            }

          }

          container multi-bfds {
            description "The configuration for IPv4 static route to set public multi-hop BFD's attributes." ;
            presence template-name ;
            list multi-bfd {
              description "The configuration for multi-hop BFD's template name." ;
              key 'nexthop local-address' ;
              leaf local-address {
                description 'The original address specified.' ;
                type ncd:ipv4-address ;

              }

              leaf nexthop {
                description 'The nexthop address specified.' ;
                type ncd:ipv4-address ;

              }

              leaf template-name {
                description "The template name of public multi-hop BFD.
                These characters's ASCII unicode must be between 0x21-0x3E / 0x40-0x7E." ;
                type string {
                  length 1..31 ;

                }

                mandatory true ;
              }

            }

          }

          container multi-bfds-vrf {
            description "The configuration for IPv4 static route to set private multi-hop BFD's attributes." ;
            presence template-name ;
            list multi-bfd-vrf {
              description "The configuration for private multi-hop BFD's template name." ;
              key 'vrfname nexthop local-address' ;
              leaf vrfname {
                description "The name of the private network VPN.
                These characters's ASCII unicode must be between 0x20-0x7E." ;
                type ncd:string-all {
                  length 1..32 ;

                }

              }

              leaf local-address {
                description 'The original address specified.' ;
                type ncd:ipv4-address ;

              }

              leaf nexthop {
                description 'The nexthop address specified.' ;
                type ncd:ipv4-address ;

              }

              leaf template-name {
                description "The template name of private multi-hop BFD.
                These characters's ASCII unicode must be between 0x21-0x3E / 0x40-0x7E." ;
                type string {
                  length 1..31 ;

                }

                mandatory true ;
              }

            }

          }

          ncd:revise-date 2020-04-03 ;
        }

        container recursion-l3evpns {
          description 'The recursion-l3evpn function for IPv4-STATIC-ROUTE.' ;
          list recursion-l3evpn {
            description 'The recursion-l3evpn function for IPv4-STATIC-ROUTE.' ;
            key vrf-name ;
            leaf vrf-name {
              description 'Specifying the VPN name.' ;
              type string {
                length 1..32 ;

              }

            }

            leaf status {
              description 'Set static route recursion L3EVPN enable or disable.' ;
              type enumeration {
                enum ENABLE {
                  value 1 ;
                  description 'Set static route recursion L3EVPN enable.' ;
                }

                enum DISABLE {
                  value 0 ;
                  description 'Set static route recursion L3EVPN disable.' ;
                }

              }

              mandatory true ;
            }

          }

          ncd:revise-date 2020-08-13 ;
        }

        container track-actions {
          description 'Static route track configuration.' ;
          list track-action {
            description 'Static route track configuration.' ;
            key 'track-name track-state' ;
            leaf track-name {
              description 'Specifying the track name.' ;
              type string {
                length 1..31 ;

              }

            }

            leaf track-state {
              description 'The track state.' ;
              type enumeration {
                enum ADMIN-DOWN {
                  value 1 ;
                  description 'Administratively down.' ;
                }

              }

            }

            leaf action {
              description 'Set static route invalid or not with the track state.' ;
              type enumeration {
                enum VALID {
                  value 1 ;
                  description 'Set static route valid.' ;
                }

                enum INVALID {
                  value 0 ;
                  description 'Set static route invalid.' ;
                }

              }

              mandatory true ;
            }

          }

          ncd:revise-date 2021-01-07 ;
        }

        container only-recurse {
          description 'The only recursion function for IPv4 static route.' ;
          container public-net {
            description 'The only recursion function for IPv4 static route in public net.' ;
            presence route-type ;
            leaf route-type {
              description 'Set the special route type of static route rescure only.' ;
              type recursion-type ;

              mandatory true ;
            }

          }

          container private-nets {
            description 'The only recursion function for IPv4 static route in private net.' ;
            list private-net {
              description 'The only recursion function for IPv4 static route in private net.' ;
              key vrf-name ;
              leaf vrf-name {
                description 'Specifying the VPN name.' ;
                type ncd:string-all {
                  length 1..32 ;

                }

              }

              leaf route-type {
                description 'Set the special route type of static route rescure only.' ;
                type recursion-type ;

                mandatory true ;
              }

            }

          }

          container mng-net {
            description 'The only recursion function for IPv4 static route in mng net.' ;
            presence route-type ;
            leaf route-type {
              description 'Set the special route type of static route rescure only.' ;
              type recursion-type ;

              mandatory true ;
            }

          }

          ncd:revise-date 2021-04-13 ;
        }

      }

      container rpm-srtv6 {
        description "The total node for IPV6-STATIC-ROUTE's all configuration commands." ;
        container route-config {
          description 'Basic configuration information for IPv6 static routes, including destination address, subnet mask, outbound interface, next hop, priority (pref), metric value (metric), tag, BFD detection, track detection, route description (name), and permanent attribute, etc.' ;
          container public-net {
            description 'The configuration for public static route.' ;
            container only-ifs {
              description 'The configuration for static route which only specifies the interface.' ;
              list only-if {
                description 'The configuration for static route which only specifies the interface.' ;
                key 'ipv6-dest-addr mask-len interface' ;
                leaf interface {
                  description 'Specify the interface name.' ;
                  type ncd:ifname {
                    length 1..31 ;

                  }

                }

                leaf ipv6-dest-addr {
                  description 'The destination address.' ;
                  type ncd:ipv6-address ;

                }

                leaf mask-len {
                  description 'The mask length.' ;
                  type uint8 {
                    range 0..128 ;

                  }

                }

                leaf preference {
                  description 'The route priority, and the default value is 1. The range is 1-255.' ;
                  type uint8 {
                    range 1..255 ;

                  }

                  default 1 ;
                }

                leaf metric {
                  description 'The route metric, and the default value is 0. The range is 0-255.' ;
                  type uint8 {
                    range 0..255 ;

                  }

                  default 0 ;
                }

                leaf tag-value {
                  description 'The route tag, and the default value is 0. The range is 0-4294967295.' ;
                  type uint32 {
                    range 0..4294967295 ;

                  }

                  default 0 ;
                  ncd:revise-date 2015-04-02 ;
                }

                leaf track-name {
                  description "The track object which the static route track-detection related. The default value is null, means that don't relate track-detection." ;
                  type string {
                    length 1..31 ;

                  }

                }

                leaf description {
                  description 'The description of the static route information. The default value is empty, means no description information.' ;
                  type string {
                    length 1..64 ;

                  }

                }

                leaf permanent {
                  if-feature ipv6-permanent ;

                  description 'Whether a permanent static route, the default is 0 means no, and 1 means yes. The range is 0-1.' ;
                  type uint8 {
                    range 0..1 ;

                  }

                  default 0 ;
                  ncd:revise-date 2018-08-02 ;
                }

                leaf no-install {
                  type uint8 {
                    range 0..1 ;

                  }

                  default 0 ;
                  description 'Indicates whether the static route does not deliver the forwarding table, the default is 0 means delivered to the forwarding table, and 1 means not delivered to the forwarding table. The range is 0-1.' ;
                  ncd:revise-date 2023-04-24 ;
                }

              }

            }

            container only-nhs {
              description 'The configuration for static route which only specifies the nexthop.' ;
              list only-nh {
                description 'The configuration for static route which only specifies the nexthop.' ;
                key 'ipv6-dest-addr ipv6-nh mask-len' ;
                leaf ipv6-dest-addr {
                  description 'The destination address.' ;
                  type ncd:ipv6-address ;

                }

                leaf ipv6-nh {
                  description 'The route nexthop.' ;
                  type ncd:ipv6-address ;

                }

                leaf mask-len {
                  description 'The mask length.' ;
                  type uint8 {
                    range 0..128 ;

                  }

                }

                leaf preference {
                  description 'The route priority, and the default value is 1. The range is 1-255.' ;
                  type uint8 {
                    range 1..255 ;

                  }

                  default 1 ;
                }

                leaf metric {
                  description 'The route metric, and the default value is 0. The range is 0-255.' ;
                  type uint8 {
                    range 0..255 ;

                  }

                  default 0 ;
                }

                leaf tag-value {
                  description 'The route tag, and the default value is 0. The range is 0-4294967295.' ;
                  type uint32 {
                    range 0..4294967295 ;

                  }

                  default 0 ;
                  ncd:revise-date 2015-04-02 ;
                }

                leaf bfd-button {
                  description 'Whether associated BFD detection, the default is 0 means no, and 1 means yes. The range is 0-1.' ;
                  type uint8 {
                    range 0..1 ;

                  }

                  default 0 ;
                }

                leaf track-name {
                  description "The track object which the static route track-detection related. The default value is null, means that don't relate track-detection." ;
                  type string {
                    length 1..31 ;

                  }

                }

                leaf description {
                  description 'The description of the static route information. The default value is empty, means no description information.' ;
                  type string {
                    length 1..64 ;

                  }

                }

                leaf permanent {
                  if-feature ipv6-permanent ;

                  description 'Whether a permanent static route, the default is 0 means no, and 1 means yes. The range is 0-1.' ;
                  type uint8 {
                    range 0..1 ;

                  }

                  default 0 ;
                  ncd:revise-date 2018-08-02 ;
                }

                leaf no-install {
                  type uint8 {
                    range 0..1 ;

                  }

                  default 0 ;
                  description 'Indicates whether the static route does not deliver the forwarding table, the default is 0 means delivered to the forwarding table, and 1 means not delivered to the forwarding table. The range is 0-1.' ;
                  ncd:revise-date 2023-04-24 ;
                }

              }

            }

            container both-if-nhs {
              description 'The configuration for static route which both specify the interface and the nexthop.' ;
              list both-if-nh {
                description 'The configuration for static route which both specify the interface and the nexthop.' ;
                key 'interface ipv6-dest-addr ipv6-if-nh mask-len' ;
                leaf interface {
                  description 'Specify the interface name.' ;
                  type ncd:ifname {
                    length 1..31 ;

                  }

                }

                leaf ipv6-dest-addr {
                  description 'The destination address.' ;
                  type ncd:ipv6-address ;

                }

                leaf ipv6-if-nh {
                  description 'The route nexthop.' ;
                  type ncd:ipv6-address ;

                }

                leaf mask-len {
                  description 'The mask length.' ;
                  type uint8 {
                    range 0..128 ;

                  }

                }

                leaf preference {
                  description 'The route priority, and the default value is 1. The range is 1-255.' ;
                  type uint8 {
                    range 1..255 ;

                  }

                  default 1 ;
                }

                leaf metric {
                  description 'The route metric, and the default value is 0. The range is 0-255.' ;
                  type uint8 {
                    range 0..255 ;

                  }

                  default 0 ;
                }

                leaf tag-value {
                  description 'The route tag, and the default value is 0. The range is 0-4294967295.' ;
                  type uint32 {
                    range 0..4294967295 ;

                  }

                  default 0 ;
                  ncd:revise-date 2015-04-02 ;
                }

                leaf bfd-button {
                  description 'Whether associated BFD detection, the default is 0 means no, and 1 means yes. The range is 0-1.' ;
                  type uint8 {
                    range 0..1 ;

                  }

                  default 0 ;
                }

                leaf track-name {
                  description "The track object which the static route track-detection related. The default value is null, means that don't relate track-detection." ;
                  type string {
                    length 1..31 ;

                  }

                }

                leaf description {
                  description 'The description of the static route information. The default value is empty, means no description information.' ;
                  type string {
                    length 1..64 ;

                  }

                }

                leaf permanent {
                  if-feature ipv6-permanent ;

                  description 'Whether a permanent static route, the default is 0 means no, and 1 means yes. The range is 0-1.' ;
                  type uint8 {
                    range 0..1 ;

                  }

                  default 0 ;
                  ncd:revise-date 2018-08-02 ;
                }

                leaf no-install {
                  type uint8 {
                    range 0..1 ;

                  }

                  default 0 ;
                  description 'Indicates whether the static route does not deliver the forwarding table, the default is 0 means delivered to the forwarding table, and 1 means not delivered to the forwarding table. The range is 0-1.' ;
                  ncd:revise-date 2023-04-24 ;
                }

              }

            }

            container nexthop-vrfs {
              description 'Configure static routes with nexthop in VPN instance.' ;
              list nexthop-vrf {
                description 'Configure static routes with nexthop in VPN instance.' ;
                key 'ipv6-dest-addr mask-len' ;
                leaf ipv6-dest-addr {
                  description 'The destination address.' ;
                  type ncd:ipv6-address ;

                }

                leaf mask-len {
                  description 'The mask length.' ;
                  type uint8 {
                    range 0..128 ;

                  }

                }

                leaf nh-vrf-name {
                  description 'The name of the private network VPN.' ;
                  type ncd:string-all {
                    length 1..32 ;

                  }

                  mandatory true ;
                }

                leaf preference {
                  description 'The route priority, and the default value is 1. The range is 1-255.' ;
                  type uint8 {
                    range 1..255 ;

                  }

                  default 1 ;
                }

                leaf description {
                  description 'The description of the static route information. The default value is empty, means no description information.' ;
                  type string {
                    length 1..64 ;

                  }

                }

                leaf metric {
                  description 'The route metric, and the default value is 0. The range is 0-255.' ;
                  type uint8 {
                    range 0..255 ;

                  }

                  default 0 ;
                  ncd:revise-date 2022-09-20 ;
                }

                leaf track-name {
                  description "The track object which the static route track-detection related. The default value is null, means that don't relate track-detection." ;
                  type string {
                    length 1..31 ;

                  }

                  ncd:revise-date 2022-09-20 ;
                }

                leaf no-install {
                  type uint8 {
                    range 0..1 ;

                  }

                  default 0 ;
                  description 'Indicates whether the static route does not deliver the forwarding table, the default is 0 means delivered to the forwarding table, and 1 means not delivered to the forwarding table. The range is 0-1.' ;
                  ncd:revise-date 2023-04-24 ;
                }

              }

              ncd:revise-date 2020-08-19 ;
            }

            container sr-policys {
              description 'The configuration for static route which only specifies the SR Policy.' ;
              list sr-policy {
                description 'The configuration for static route which only specifies the SR Policy.' ;
                key 'ipv6-dest-addr mask-len color end-point' ;
                leaf ipv6-dest-addr {
                  description 'The destination address.' ;
                  type ncd:ipv6-address ;

                }

                leaf mask-len {
                  description 'The mask length.' ;
                  type uint8 {
                    range 0..128 ;

                  }

                }

                leaf color {
                  description 'The color of SR Policy. Its range is 1-4294967295.' ;
                  type uint32 {
                    range 1..4294967295 ;

                  }

                }

                leaf end-point {
                  description 'The end-point of SR Policy.' ;
                  type string {
                    length 1..39 ;

                  }

                }

                leaf end-point-afi {
                  description 'The address family of end-point.The value is IPv4 or IPv6.' ;
                  type address-family ;

                  mandatory true ;
                }

                leaf srv6-sid {
                  description 'The SRv6 SID of SRv6 Policy.' ;
                  type ncd:ipv6-address-none-zero ;

                  default :: ;
                }

                leaf preference {
                  description 'The route priority, and the default value is 1. The range is 1-255.' ;
                  type uint8 {
                    range 1..255 ;

                  }

                  default 1 ;
                }

                leaf metric {
                  description 'The route metric, and the default value is 0. The range is 0-255.' ;
                  type uint8 {
                    range 0..255 ;

                  }

                  default 0 ;
                }

                leaf tag-value {
                  description 'The route tag, and the default value is 0. The range is 0-4294967295.' ;
                  type uint32 {
                    range 0..4294967295 ;

                  }

                  default 0 ;
                }

                leaf track-name {
                  description "The track object which the static route track-detection related. The default value is null, means that don't relate track-detection." ;
                  type string {
                    length 1..31 ;

                  }

                }

                leaf description {
                  description 'The description of the static route information. The default value is empty, means no description information.' ;
                  type string {
                    length 1..64 ;

                  }

                }

                leaf no-install {
                  type uint8 {
                    range 0..1 ;

                  }

                  default 0 ;
                  description 'Indicates whether the static route does not deliver the forwarding table, the default is 0 means delivered to the forwarding table, and 1 means not delivered to the forwarding table. The range is 0-1.' ;
                  ncd:revise-date 2023-04-24 ;
                }

              }

              ncd:revise-date 2021-05-08 ;
            }

            container ipv4-nhs {
              description 'The configuration for static route which only specifies the IPv4 global nexthop.' ;
              list ipv4-nh {
                description 'The configuration for IPv6 static route with IPv4 nexthop.' ;
                key 'ipv6-dest-addr ipv4-nh mask-len' ;
                leaf ipv6-dest-addr {
                  description 'The destination address.' ;
                  type ncd:ipv6-address ;

                }

                leaf ipv4-nh {
                  description 'The route nexthop.' ;
                  type ncd:ipv4-address ;

                }

                leaf mask-len {
                  description 'The mask length.' ;
                  type uint8 {
                    range 0..128 ;

                  }

                }

                leaf preference {
                  description 'The route priority, and the default value is 1. The range is 1-255.' ;
                  type uint8 {
                    range 1..255 ;

                  }

                  default 1 ;
                }

                leaf metric {
                  description 'The route metric, and the default value is 0. The range is 0-255.' ;
                  type uint8 {
                    range 0..255 ;

                  }

                  default 0 ;
                }

                leaf tag-value {
                  description 'The route tag, and the default value is 0. The range is 0-4294967295.' ;
                  type uint32 {
                    range 0..4294967295 ;

                  }

                  default 0 ;
                }

                leaf track-name {
                  description "The track object which the static route track-detection related. The default value is null, means that don't relate track-detection." ;
                  type string {
                    length 1..31 ;

                  }

                }

                leaf description {
                  description 'The description of the static route information. The default value is empty, means no description information.' ;
                  type string {
                    length 1..64 ;

                  }

                }

                leaf permanent {
                  if-feature ipv6-permanent ;

                  description 'Whether a permanent static route, the default is 0 means no, and 1 means yes. The range is 0-1.' ;
                  type uint8 {
                    range 0..1 ;

                  }

                  default 0 ;
                }

                leaf no-install {
                  type uint8 {
                    range 0..1 ;

                  }

                  default 0 ;
                  description 'Indicates whether the static route does not deliver the forwarding table, the default is 0 means delivered to the forwarding table, and 1 means not delivered to the forwarding table. The range is 0-1.' ;
                  ncd:revise-date 2023-04-24 ;
                }

              }

              ncd:revise-date 2022-07-14 ;
            }

          }

          container private-net {
            description 'The configuration for private static route.' ;
            container only-ifs {
              description 'The configuration for static route which only specifies the interface.' ;
              list only-if {
                description 'The configuration for static route which only specifies the interface.' ;
                key 'vrf-name interface ipv6-dest-addr mask-len' ;
                leaf vrf-name {
                  description 'The name of the private network VPN.' ;
                  type ncd:string-all {
                    length 1..32 ;

                  }

                }

                leaf interface {
                  description 'Specify the interface name.' ;
                  type ncd:ifname {
                    length 1..31 ;

                  }

                }

                leaf ipv6-dest-addr {
                  description 'The destination address.' ;
                  type ncd:ipv6-address ;

                }

                leaf mask-len {
                  description 'The mask length.' ;
                  type uint8 {
                    range 0..128 ;

                  }

                }

                leaf preference {
                  description 'The route priority, and the default value is 1. The range is 1-255.' ;
                  type uint8 {
                    range 1..255 ;

                  }

                  default 1 ;
                }

                leaf metric {
                  description 'The route metric, and the default value is 0. The range is 0-255.' ;
                  type uint8 {
                    range 0..255 ;

                  }

                  default 0 ;
                }

                leaf tag-value {
                  description 'The route tag, and the default value is 0. The range is 0-4294967295.' ;
                  type uint32 {
                    range 0..4294967295 ;

                  }

                  default 0 ;
                  ncd:revise-date 2015-04-02 ;
                }

                leaf track-name {
                  description "The track object which the static route track-detection related. The default value is null, means that don't relate track-detection." ;
                  type string {
                    length 1..31 ;

                  }

                }

                leaf description {
                  description 'The description of the static route information. The default value is empty, means no description information.' ;
                  type string {
                    length 1..64 ;

                  }

                }

                leaf permanent {
                  if-feature ipv6-permanent ;

                  description 'Whether a permanent static route, the default is 0 means no, and 1 means yes. The range is 0-1.' ;
                  type uint8 {
                    range 0..1 ;

                  }

                  default 0 ;
                  ncd:revise-date 2018-08-02 ;
                }

                leaf no-install {
                  type uint8 {
                    range 0..1 ;

                  }

                  default 0 ;
                  description 'Indicates whether the static route does not deliver the forwarding table, the default is 0 means delivered to the forwarding table, and 1 means not delivered to the forwarding table. The range is 0-1.' ;
                  ncd:revise-date 2023-04-24 ;
                }

              }

            }

            container only-nhs {
              description 'The configuration for static route which only specifies the nexthop.' ;
              list only-nh {
                description 'The configuration for static route which only specifies the nexthop.' ;
                key 'vrf-name ipv6-dest-addr ipv6-nh mask-len' ;
                leaf vrf-name {
                  description 'The name of the private network VPN.' ;
                  type ncd:string-all {
                    length 1..32 ;

                  }

                }

                leaf ipv6-dest-addr {
                  description 'The destination address.' ;
                  type ncd:ipv6-address ;

                }

                leaf ipv6-nh {
                  description 'The route nexthop.' ;
                  type ncd:ipv6-address ;

                }

                leaf mask-len {
                  description 'The mask length.' ;
                  type uint8 {
                    range 0..128 ;

                  }

                }

                leaf preference {
                  description 'The route priority, and the default value is 1. The range is 1-255.' ;
                  type uint8 {
                    range 1..255 ;

                  }

                  default 1 ;
                }

                leaf metric {
                  description 'The route metric, and the default value is 0. The range is 0-255.' ;
                  type uint8 {
                    range 0..255 ;

                  }

                  default 0 ;
                }

                leaf tag-value {
                  description 'The route tag, and the default value is 0. The range is 0-4294967295.' ;
                  type uint32 {
                    range 0..4294967295 ;

                  }

                  default 0 ;
                  ncd:revise-date 2015-04-02 ;
                }

                leaf bfd-button {
                  description 'Whether associated BFD detection, the default is 0 means no, and 1 means yes. The range is 0-1.' ;
                  type uint8 {
                    range 0..1 ;

                  }

                  default 0 ;
                }

                leaf track-name {
                  description "The track object which the static route track-detection related. The default value is null, means that don't relate track-detection." ;
                  type string {
                    length 1..31 ;

                  }

                }

                leaf description {
                  description 'The description of the static route information. The default value is empty, means no description information.' ;
                  type string {
                    length 1..64 ;

                  }

                }

                leaf permanent {
                  if-feature ipv6-permanent ;

                  description 'Whether a permanent static route, the default is 0 means no, and 1 means yes. The range is 0-1.' ;
                  type uint8 {
                    range 0..1 ;

                  }

                  default 0 ;
                  ncd:revise-date 2018-08-02 ;
                }

                leaf global {
                  if-feature ipv6-global-nh ;

                  description 'Whether a global static route, the default is 0 means no, and 1 means yes. The range is 0-1.' ;
                  type uint8 {
                    range 0..1 ;

                  }

                  default 0 ;
                  ncd:revise-date 2018-10-31 ;
                }

                leaf no-install {
                  type uint8 {
                    range 0..1 ;

                  }

                  default 0 ;
                  description 'Indicates whether the static route does not deliver the forwarding table, the default is 0 means delivered to the forwarding table, and 1 means not delivered to the forwarding table. The range is 0-1.' ;
                  ncd:revise-date 2023-04-24 ;
                }

              }

            }

            container both-if-nhs {
              description 'The configuration for static route which both specify the interface and the nexthop.' ;
              list both-if-nh {
                description 'The configuration for static route which both specify the interface and the nexthop.' ;
                key 'vrf-name interface ipv6-dest-addr ipv6-if-nh mask-len' ;
                leaf vrf-name {
                  description 'The name of the private network VPN.' ;
                  type ncd:string-all {
                    length 1..32 ;

                  }

                }

                leaf interface {
                  description 'Specify the interface name.' ;
                  type ncd:ifname {
                    length 1..31 ;

                  }

                }

                leaf ipv6-dest-addr {
                  description 'The destination address.' ;
                  type ncd:ipv6-address ;

                }

                leaf ipv6-if-nh {
                  description 'The route nexthop.' ;
                  type ncd:ipv6-address ;

                }

                leaf mask-len {
                  description 'The mask length.' ;
                  type uint8 {
                    range 0..128 ;

                  }

                }

                leaf preference {
                  description 'The route priority, and the default value is 1. The range is 1-255.' ;
                  type uint8 {
                    range 1..255 ;

                  }

                  default 1 ;
                }

                leaf metric {
                  description 'The route metric, and the default value is 0. The range is 0-255.' ;
                  type uint8 {
                    range 0..255 ;

                  }

                  default 0 ;
                }

                leaf tag-value {
                  description 'The route tag, and the default value is 0. The range is 0-4294967295.' ;
                  type uint32 {
                    range 0..4294967295 ;

                  }

                  default 0 ;
                  ncd:revise-date 2015-04-02 ;
                }

                leaf bfd-button {
                  description 'Whether associated BFD detection, the default is 0 means no, and 1 means yes. The range is 0-1.' ;
                  type uint8 {
                    range 0..1 ;

                  }

                  default 0 ;
                }

                leaf track-name {
                  description "The track object which the static route track-detection related. The default value is null, means that don't relate track-detection." ;
                  type string {
                    length 1..31 ;

                  }

                }

                leaf description {
                  description 'The description of the static route information. The default value is empty, means no description information.' ;
                  type string {
                    length 1..64 ;

                  }

                }

                leaf permanent {
                  if-feature ipv6-permanent ;

                  description 'Whether a permanent static route, the default is 0 means no, and 1 means yes. The range is 0-1.' ;
                  type uint8 {
                    range 0..1 ;

                  }

                  default 0 ;
                  ncd:revise-date 2018-08-02 ;
                }

                leaf no-install {
                  type uint8 {
                    range 0..1 ;

                  }

                  default 0 ;
                  description 'Indicates whether the static route does not deliver the forwarding table, the default is 0 means delivered to the forwarding table, and 1 means not delivered to the forwarding table. The range is 0-1.' ;
                  ncd:revise-date 2023-04-24 ;
                }

              }

            }

            container publics {
              description 'The configuration for static route which specifies the nexthop to be public.' ;
              list public {
                description 'The configuration for static route which specifies the nexthop to be public.' ;
                key 'vrf-name ipv6-dest-addr mask-len' ;
                leaf vrf-name {
                  description 'The name of the private network VPN.' ;
                  type ncd:string-all {
                    length 1..32 ;

                  }

                }

                leaf ipv6-dest-addr {
                  description 'The destination address.' ;
                  type ncd:ipv6-address ;

                }

                leaf mask-len {
                  description 'The mask length.' ;
                  type uint8 {
                    range 0..128 ;

                  }

                }

                leaf preference {
                  description 'The route priority, and the default value is 1. The range is 1-255.' ;
                  type uint8 {
                    range 1..255 ;

                  }

                  default 1 ;
                  ncd:revise-date 2022-09-20 ;
                }

                leaf metric {
                  description 'The route metric, and the default value is 0. The range is 0-255.' ;
                  type uint8 {
                    range 0..255 ;

                  }

                  default 0 ;
                  ncd:revise-date 2022-09-20 ;
                }

                leaf track-name {
                  description "The track object which the static route track-detection related. The default value is null, means that don't relate track-detection." ;
                  type string {
                    length 1..31 ;

                  }

                  ncd:revise-date 2022-09-20 ;
                }

                leaf description {
                  description 'The description of the static route information. The default value is empty, means no description information.' ;
                  type string {
                    length 1..64 ;

                  }

                  ncd:revise-date 2022-09-20 ;
                }

                leaf no-install {
                  type uint8 {
                    range 0..1 ;

                  }

                  default 0 ;
                  description 'Indicates whether the static route does not deliver the forwarding table, the default is 0 means delivered to the forwarding table, and 1 means not delivered to the forwarding table. The range is 0-1.' ;
                  ncd:revise-date 2023-04-24 ;
                }

              }

              ncd:revise-date 2018-05-10 ;
            }

            container global-v4-nhs {
              if-feature ipv4-global-nh ;

              description 'The configuration for static route which only specifies the IPv4 global nexthop.' ;
              list global-v4-nh {
                description 'The configuration for static route which only specifies the IPv4 global nexthop.' ;
                key 'vrf-name ipv6-dest-addr ipv4-nh mask-len' ;
                leaf vrf-name {
                  description 'The name of the private network VPN.' ;
                  type ncd:string-all {
                    length 1..32 ;

                  }

                }

                leaf ipv6-dest-addr {
                  description 'The destination address.' ;
                  type ncd:ipv6-address ;

                }

                leaf ipv4-nh {
                  description 'The route nexthop.' ;
                  type ncd:ipv4-address ;

                }

                leaf mask-len {
                  description 'The mask length.' ;
                  type uint8 {
                    range 0..128 ;

                  }

                }

                leaf preference {
                  description 'The route priority, and the default value is 1. The range is 1-255.' ;
                  type uint8 {
                    range 1..255 ;

                  }

                  default 1 ;
                }

                leaf metric {
                  description 'The route metric, and the default value is 0. The range is 0-255.' ;
                  type uint8 {
                    range 0..255 ;

                  }

                  default 0 ;
                }

                leaf tag-value {
                  description 'The route tag, and the default value is 0. The range is 0-4294967295.' ;
                  type uint32 {
                    range 0..4294967295 ;

                  }

                  default 0 ;
                }

                leaf track-name {
                  description "The track object which the static route track-detection related. The default value is null, means that don't relate track-detection." ;
                  type string {
                    length 1..31 ;

                  }

                }

                leaf description {
                  description 'The description of the static route information. The default value is empty, means no description information.' ;
                  type string {
                    length 1..64 ;

                  }

                }

                leaf permanent {
                  if-feature ipv6-permanent ;

                  description 'Whether a permanent static route, the default is 0 means no, and 1 means yes. The range is 0-1.' ;
                  type uint8 {
                    range 0..1 ;

                  }

                  default 0 ;
                  ncd:revise-date 2018-08-02 ;
                }

                leaf no-install {
                  type uint8 {
                    range 0..1 ;

                  }

                  default 0 ;
                  description 'Indicates whether the static route does not deliver the forwarding table, the default is 0 means delivered to the forwarding table, and 1 means not delivered to the forwarding table. The range is 0-1.' ;
                  ncd:revise-date 2023-04-24 ;
                }

              }

              ncd:revise-date 2018-05-30 ;
            }

            container sr-policys {
              description 'The configuration for static route which only specifies the SR Policy.' ;
              list sr-policy {
                description 'The configuration for static route which only specifies the SR Policy.' ;
                key 'vrf-name ipv6-dest-addr mask-len color end-point' ;
                leaf vrf-name {
                  description 'The name of the private network VPN.' ;
                  type ncd:string-all {
                    length 1..32 ;

                  }

                }

                leaf ipv6-dest-addr {
                  description 'The destination address.' ;
                  type ncd:ipv6-address ;

                }

                leaf mask-len {
                  description 'The mask length.' ;
                  type uint8 {
                    range 0..128 ;

                  }

                }

                leaf color {
                  description 'The color of SR Policy. Its range is 1-4294967295.' ;
                  type uint32 {
                    range 1..4294967295 ;

                  }

                }

                leaf end-point {
                  description 'The end-point of SR Policy.' ;
                  type string {
                    length 1..39 ;

                  }

                }

                leaf end-point-afi {
                  description 'The address family of end-point.The value is IPv4 or IPv6.' ;
                  type address-family ;

                  mandatory true ;
                }

                leaf srv6-sid {
                  description 'The SRv6 SID of SRv6 Policy.' ;
                  type ncd:ipv6-address-none-zero ;

                  default :: ;
                }

                leaf preference {
                  description 'The route priority, and the default value is 1. The range is 1-255.' ;
                  type uint8 {
                    range 1..255 ;

                  }

                  default 1 ;
                }

                leaf metric {
                  description 'The route metric, and the default value is 0. The range is 0-255.' ;
                  type uint8 {
                    range 0..255 ;

                  }

                  default 0 ;
                }

                leaf tag-value {
                  description 'The route tag, and the default value is 0. The range is 0-4294967295.' ;
                  type uint32 {
                    range 0..4294967295 ;

                  }

                  default 0 ;
                }

                leaf track-name {
                  description "The track object which the static route track-detection related. The default value is null, means that don't relate track-detection." ;
                  type string {
                    length 1..31 ;

                  }

                }

                leaf description {
                  description 'The description of the static route information. The default value is empty, means no description information.' ;
                  type string {
                    length 1..64 ;

                  }

                }

                leaf no-install {
                  type uint8 {
                    range 0..1 ;

                  }

                  default 0 ;
                  description 'Indicates whether the static route does not deliver the forwarding table, the default is 0 means delivered to the forwarding table, and 1 means not delivered to the forwarding table. The range is 0-1.' ;
                  ncd:revise-date 2023-04-24 ;
                }

              }

              ncd:revise-date 2021-05-08 ;
            }

            container nh-with-vrfs {
              list nh-with-vrf {
                description 'The configuration for static route which specifies the nexthop to another VPN.' ;
                key 'vrf-name ipv6-dest-addr ipv6-nh mask-len nh-vrf-name' ;
                leaf vrf-name {
                  description 'The name of the private network VPN.' ;
                  type ncd:string-all {
                    length 1..32 ;

                  }

                }

                leaf ipv6-dest-addr {
                  description 'The destination address.' ;
                  type ncd:ipv6-address ;

                }

                leaf ipv6-nh {
                  description 'The route nexthop.' ;
                  type ncd:ipv6-address ;

                }

                leaf mask-len {
                  description 'The mask length.' ;
                  type uint8 {
                    range 0..128 ;

                  }

                }

                leaf nh-vrf-name {
                  type string {
                    length 1..32 ;

                  }

                  description 'VRF name of the next hop in another VRF.If this parameter is not set, the VRF of the next hop is the same as that of the route.' ;
                }

                leaf preference {
                  description 'The route priority, and the default value is 1. The range is 1-255.' ;
                  type uint8 {
                    range 1..255 ;

                  }

                  default 1 ;
                }

                leaf metric {
                  description 'The route metric, and the default value is 0. The range is 0-255.' ;
                  type uint8 {
                    range 0..255 ;

                  }

                  default 0 ;
                }

                leaf tag-value {
                  description 'The route tag, and the default value is 0. The range is 0-4294967295.' ;
                  type uint32 {
                    range 0..4294967295 ;

                  }

                  default 0 ;
                }

                leaf bfd-button {
                  description 'Whether associated BFD detection, the default is 0 means no, and 1 means yes. The range is 0-1.' ;
                  type uint8 {
                    range 0..1 ;

                  }

                  default 0 ;
                }

                leaf track-name {
                  description "The track object which the static route track-detection related. The default value is null, means that don't relate track-detection." ;
                  type string {
                    length 1..31 ;

                  }

                }

                leaf description {
                  description 'The description of the static route information. The default value is empty, means no description information.' ;
                  type string {
                    length 1..64 ;

                  }

                }

                leaf no-install {
                  type uint8 {
                    range 0..1 ;

                  }

                  default 0 ;
                  description 'Indicates whether the static route does not deliver the forwarding table, the default is 0 means delivered to the forwarding table, and 1 means not delivered to the forwarding table. The range is 0-1.' ;
                  ncd:revise-date 2023-04-24 ;
                }

              }

              description 'The configuration for static route which specifies the nexthop to another VPN.' ;
              ncd:revise-date 2022-06-02 ;
            }

            container nexthop-vrfs {
              description 'The configuration for static route which specifies the nexthop to be another VPN.' ;
              list nexthop-vrf {
                description 'The configuration for static route which specifies the nexthop to other VPN.' ;
                key 'vrf-name ipv6-dest-addr mask-len nh-vrf-name' ;
                leaf vrf-name {
                  description 'The name of the private network VPN.' ;
                  type ncd:string-all {
                    length 1..32 ;

                  }

                }

                leaf ipv6-dest-addr {
                  description 'The destination address.' ;
                  type ncd:ipv6-address ;

                }

                leaf mask-len {
                  description 'The mask length.' ;
                  type uint8 {
                    range 0..128 ;

                  }

                }

                leaf nh-vrf-name {
                  description 'The name of the private network VPN.' ;
                  type ncd:string-all {
                    length 1..32 ;

                  }

                }

                leaf preference {
                  description 'The route priority, and the default value is 1. The range is 1-255.' ;
                  type uint8 {
                    range 1..255 ;

                  }

                  default 1 ;
                }

                leaf metric {
                  description 'The route metric, and the default value is 0. The range is 0-255.' ;
                  type uint8 {
                    range 0..255 ;

                  }

                  default 0 ;
                }

                leaf tag-value {
                  description 'The route tag, and the default value is 0. The range is 0-4294967295.' ;
                  type uint32 {
                    range 0..4294967295 ;

                  }

                  default 0 ;
                }

                leaf track-name {
                  description "The track object which the static route track-detection related. The default value is null, means that don't relate track-detection." ;
                  type string {
                    length 1..31 ;

                  }

                }

                leaf description {
                  description 'The description of the static route information. The default value is empty, means no description information.' ;
                  type string {
                    length 1..64 ;

                  }

                }

                leaf no-install {
                  type uint8 {
                    range 0..1 ;

                  }

                  default 0 ;
                  description 'Indicates whether the static route does not deliver the forwarding table, the default is 0 means delivered to the forwarding table, and 1 means not delivered to the forwarding table. The range is 0-1.' ;
                  ncd:revise-date 2023-04-24 ;
                }

              }

              ncd:revise-date 2022-09-20 ;
            }

          }

          container mng-net {
            description 'The configuration for mng static route.' ;
            container only-nhs {
              description 'The configuration for static route which only specifies the nexthop.' ;
              list only-nh {
                description 'The configuration for static route which only specifies the nexthop.' ;
                key 'ipv6-dest-addr ipv6-nh mask-len' ;
                leaf ipv6-dest-addr {
                  description 'The destination address.' ;
                  type ncd:ipv6-address ;

                }

                leaf ipv6-nh {
                  description 'The route nexthop.' ;
                  type ncd:ipv6-address ;

                }

                leaf mask-len {
                  description 'The mask length.' ;
                  type uint8 {
                    range 0..128 ;

                  }

                }

                leaf preference {
                  description 'The route priority, and the default value is 1. The range is 1-255.' ;
                  type uint8 {
                    range 1..255 ;

                  }

                  default 1 ;
                }

                leaf metric {
                  description 'The route metric, and the default value is 0. The range is 0-255.' ;
                  type uint8 {
                    range 0..255 ;

                  }

                  default 0 ;
                }

                leaf tag-value {
                  description 'The route tag, and the default value is 0. The range is 0-4294967295.' ;
                  type uint32 {
                    range 0..4294967295 ;

                  }

                  default 0 ;
                  ncd:revise-date 2015-04-02 ;
                }

                leaf bfd-button {
                  description 'Whether associated BFD detection, the default is 0 means no, and 1 means yes. The range is 0-1.' ;
                  type uint8 {
                    range 0..1 ;

                  }

                  default 0 ;
                }

                leaf track-name {
                  description "The track object which the static route track-detection related. The default value is null, means that don't relate track-detection." ;
                  type string {
                    length 1..31 ;

                  }

                }

                leaf description {
                  description 'The description of the static route information. The default value is empty, means no description information.' ;
                  type string {
                    length 1..64 ;

                  }

                }

                leaf permanent {
                  if-feature ipv6-permanent ;

                  description 'Whether a permanent static route, the default is 0 means no, and 1 means yes. The range is 0-1.' ;
                  type uint8 {
                    range 0..1 ;

                  }

                  default 0 ;
                  ncd:revise-date 2018-08-02 ;
                }

                leaf global {
                  if-feature ipv6-global-nh ;

                  description 'Whether a global static route, the default is 0 means no, and 1 means yes. The range is 0-1.' ;
                  type uint8 {
                    range 0..1 ;

                  }

                  default 0 ;
                  ncd:revise-date 2018-10-31 ;
                }

                leaf no-install {
                  type uint8 {
                    range 0..1 ;

                  }

                  default 0 ;
                  description 'Indicates whether the static route does not deliver the forwarding table, the default is 0 means delivered to the forwarding table, and 1 means not delivered to the forwarding table. The range is 0-1.' ;
                  ncd:revise-date 2023-04-24 ;
                }

              }

            }

            container publics {
              description 'The configuration for static route which specifies the nexthop to be public.' ;
              list public {
                description 'The configuration for static route which specifies the nexthop to be public.' ;
                key 'ipv6-dest-addr mask-len' ;
                leaf ipv6-dest-addr {
                  description 'The destination address.' ;
                  type ncd:ipv6-address ;

                }

                leaf mask-len {
                  description 'The mask length.' ;
                  type uint8 {
                    range 0..128 ;

                  }

                }

                leaf preference {
                  description 'The route priority, and the default value is 1. The range is 1-255.' ;
                  type uint8 {
                    range 1..255 ;

                  }

                  default 1 ;
                  ncd:revise-date 2022-09-20 ;
                }

                leaf metric {
                  description 'The route metric, and the default value is 0. The range is 0-255.' ;
                  type uint8 {
                    range 0..255 ;

                  }

                  default 0 ;
                  ncd:revise-date 2022-09-20 ;
                }

                leaf track-name {
                  description "The track object which the static route track-detection related. The default value is null, means that don't relate track-detection." ;
                  type string {
                    length 1..31 ;

                  }

                  ncd:revise-date 2022-09-20 ;
                }

                leaf description {
                  description 'The description of the static route information. The default value is empty, means no description information.' ;
                  type string {
                    length 1..64 ;

                  }

                  ncd:revise-date 2022-09-20 ;
                }

                leaf no-install {
                  type uint8 {
                    range 0..1 ;

                  }

                  default 0 ;
                  description 'Indicates whether the static route does not deliver the forwarding table, the default is 0 means delivered to the forwarding table, and 1 means not delivered to the forwarding table. The range is 0-1.' ;
                  ncd:revise-date 2023-04-24 ;
                }

              }

              ncd:revise-date 2018-05-10 ;
            }

            container global-v4-nhs {
              if-feature ipv4-global-nh ;

              description 'The configuration for static route which only specifies the IPv4 global nexthop.' ;
              list global-v4-nh {
                description 'The configuration for static route which only specifies the IPv4 global nexthop.' ;
                key 'ipv6-dest-addr ipv4-nh mask-len' ;
                leaf ipv6-dest-addr {
                  description 'The destination address.' ;
                  type ncd:ipv6-address ;

                }

                leaf ipv4-nh {
                  description 'The route nexthop.' ;
                  type ncd:ipv4-address ;

                }

                leaf mask-len {
                  description 'The mask length.' ;
                  type uint8 {
                    range 0..128 ;

                  }

                }

                leaf preference {
                  description 'The route priority, and the default value is 1. The range is 1-255.' ;
                  type uint8 {
                    range 1..255 ;

                  }

                  default 1 ;
                }

                leaf metric {
                  description 'The route metric, and the default value is 0. The range is 0-255.' ;
                  type uint8 {
                    range 0..255 ;

                  }

                  default 0 ;
                }

                leaf tag-value {
                  description 'The route tag, and the default value is 0. The range is 0-4294967295.' ;
                  type uint32 {
                    range 0..4294967295 ;

                  }

                  default 0 ;
                }

                leaf track-name {
                  description "The track object which the static route track-detection related. The default value is null, means that don't relate track-detection." ;
                  type string {
                    length 1..31 ;

                  }

                }

                leaf description {
                  description 'The description of the static route information. The default value is empty, means no description information.' ;
                  type string {
                    length 1..64 ;

                  }

                }

                leaf permanent {
                  if-feature ipv6-permanent ;

                  description 'Whether a permanent static route, the default is 0 means no, and 1 means yes. The range is 0-1.' ;
                  type uint8 {
                    range 0..1 ;

                  }

                  default 0 ;
                  ncd:revise-date 2018-08-02 ;
                }

                leaf no-install {
                  type uint8 {
                    range 0..1 ;

                  }

                  default 0 ;
                  description 'Indicates whether the static route does not deliver the forwarding table, the default is 0 means delivered to the forwarding table, and 1 means not delivered to the forwarding table. The range is 0-1.' ;
                  ncd:revise-date 2023-04-24 ;
                }

              }

              ncd:revise-date 2018-05-30 ;
            }

            container sr-policys {
              description 'The configuration for static route which only specifies the SR Policy.' ;
              list sr-policy {
                description 'The configuration for static route which only specifies the SR Policy.' ;
                key 'ipv6-dest-addr mask-len color end-point' ;
                leaf ipv6-dest-addr {
                  description 'The destination address.' ;
                  type ncd:ipv6-address ;

                }

                leaf mask-len {
                  description 'The mask length.' ;
                  type uint8 {
                    range 0..128 ;

                  }

                }

                leaf color {
                  description 'The color of SR Policy. Its range is 1-4294967295.' ;
                  type uint32 {
                    range 1..4294967295 ;

                  }

                }

                leaf end-point {
                  description 'The end-point of SR Policy.' ;
                  type string {
                    length 1..39 ;

                  }

                }

                leaf end-point-afi {
                  description 'The address family of end-point.The value is IPv4 or IPv6.' ;
                  type address-family ;

                  mandatory true ;
                }

                leaf srv6-sid {
                  description 'The SRv6 SID of SRv6 Policy.' ;
                  type ncd:ipv6-address-none-zero ;

                  default :: ;
                }

                leaf preference {
                  description 'The route priority, and the default value is 1. The range is 1-255.' ;
                  type uint8 {
                    range 1..255 ;

                  }

                  default 1 ;
                }

                leaf metric {
                  description 'The route metric, and the default value is 0. The range is 0-255.' ;
                  type uint8 {
                    range 0..255 ;

                  }

                  default 0 ;
                }

                leaf tag-value {
                  description 'The route tag, and the default value is 0. The range is 0-4294967295.' ;
                  type uint32 {
                    range 0..4294967295 ;

                  }

                  default 0 ;
                }

                leaf track-name {
                  description "The track object which the static route track-detection related. The default value is null, means that don't relate track-detection." ;
                  type string {
                    length 1..31 ;

                  }

                }

                leaf description {
                  description 'The description of the static route information. The default value is empty, means no description information.' ;
                  type string {
                    length 1..64 ;

                  }

                }

                leaf no-install {
                  type uint8 {
                    range 0..1 ;

                  }

                  default 0 ;
                  description 'Indicates whether the static route does not deliver the forwarding table, the default is 0 means delivered to the forwarding table, and 1 means not delivered to the forwarding table. The range is 0-1.' ;
                  ncd:revise-date 2023-04-24 ;
                }

              }

              ncd:revise-date 2021-05-08 ;
            }

          }

        }

        container source-nexthop {
          description 'To specify the original address for static route, using for creating multiple-hops BFD session in some scenarios.' ;
          presence source-nexthop ;
          leaf loopback-name {
            description 'The loopback name specified.' ;
            type ncd:ifname {
              length 1..31 ;

            }

            mandatory true ;
          }

        }

        container fast-reroute {
          description "The node for IPv6-STATIC-ROUTE's FRR function." ;
          container public-net {
            description 'Enable or disable the switch of FRR function in public network.' ;
            presence enable ;
            leaf wtr-value {
              type uint8 {
                range 0..12 ;

              }

              description 'Set the WTR(WaitToRestore) time in minute, the range is 0-12.' ;
              default 0 ;
              units mins ;
            }

            leaf wtr-second-with-minute {
              description 'Set the WTR(WaitToRestore) time in second, the range is 0-720.' ;
              type uint32 {
                range 0..59 ;

              }

              units sec ;
              ncd:revise-date 2024-06-26 ;
            }

            leaf wtr-second {
              type uint32 {
                range 1..720 ;

              }

              description 'Set the WTR(WaitToRestore) time in second, the range is 0-720.' ;
              units sec ;
              ncd:revise-date 2023-11-30 ;
            }

            ncd:revise-date 2013-08-15 ;
          }

          container private-nets {
            description 'Enable or disable the switch of FRR function in private network.' ;
            list private-net {
              description 'Enable or disable the switch of FRR function in private network.' ;
              key vrf-name ;
              leaf vrf-name {
                description 'Specifying the VPN name.' ;
                type ncd:string-all {
                  length 1..32 ;

                }

              }

              leaf wtr-value {
                type uint8 {
                  range 0..12 ;

                }

                description 'Set the WTR(WaitToRestore) time in minute, the range is 0-12.' ;
                default 0 ;
                units mins ;
              }

              leaf wtr-second-with-minute {
                type uint32 {
                  range 0..59 ;

                }

                description 'Set the WTR(WaitToRestore) time in second, the range is 0-720.' ;
                units sec ;
                ncd:revise-date 2024-06-26 ;
              }

              leaf wtr-second {
                type uint32 {
                  range 1..720 ;

                }

                description 'Set the WTR(WaitToRestore) time in second, the range is 0-720.' ;
                units sec ;
                ncd:revise-date 2023-11-30 ;
              }

            }

            ncd:revise-date 2013-08-15 ;
          }

        }

        container dynamic-protect {
          description 'The function node for IPv6-STATIC-ROUTE to protect the dynamic route(RIPng, OSPFv3, ISIS, BGP etc).' ;
          container public-nets {
            description 'Enable or disable the function of dynamic-route-protection in public network.' ;
            list public-net {
              description 'Enable or disable the function of dynamic-route-protection in public network.' ;
              key route-type ;
              leaf route-type {
                description 'Specify the route type (RIPng, OSPFv3, BGP, ISIS) which is needed to protect.' ;
                type protect-type ;

              }

            }

          }

          container private-nets {
            description 'Enable or disable the function of dynamic-route-protection in private network.' ;
            list private-net {
              description 'Enable or disable the function of dynamic-route-protection in private network.' ;
              key 'vrf-name route-type' ;
              leaf vrf-name {
                description 'Specify the VPN name.' ;
                type string {
                  length 1..32 ;

                }

              }

              leaf route-type {
                description 'Specify the route type (RIPng, OSPFv3, BGP, ISIS) which is needed to protect.' ;
                type protect-type ;

              }

            }

          }

        }

        container recursion-l3vpn {
          description 'The recursion l3vpn function for IPv6 static route.' ;
          list private-net {
            description 'The recursion l3vpn function for IPv6 private static route.' ;
            key vrf-name ;
            leaf vrf-name {
              description 'Specifying the VPN name.' ;
              type string {
                length 1..32 ;

              }

            }

          }

          ncd:revise-date 2020-04-26 ;
        }

        container route-vxlan {
          if-feature ipv6-vxlan ;

          description 'The configuration for static VXLAN route.' ;
          container static-tunnels {
            description 'Routing configuration in static tunnel scene.' ;
            list static-tunnel {
              description 'Routing configuration in static tunnel scene.' ;
              key 'vrf-name ipv6-dest-addr mask-len vxlan-if' ;
              leaf vrf-name {
                description 'The name of the private network VPN.' ;
                type string {
                  length 1..32 ;

                }

              }

              leaf ipv6-dest-addr {
                description 'The destination address.' ;
                type ncd:ipv6-address ;

              }

              leaf mask-len {
                description 'The mask lenth.' ;
                type uint8 ;

              }

              leaf vxlan-if {
                description 'The VXLAN interface name.' ;
                type ncd:ifname {
                  length 1..31 ;

                }

              }

              leaf vni-label {
                description 'The VNI label value, and the invalid value is 0. The range is 1-16777215.' ;
                type uint32 {
                  range 1..16777215 ;

                }

              }

              leaf router-mac {
                description 'The router MAC value.' ;
                type ncd:mac-address ;

              }

              leaf distance {
                description 'The route priority, and the default value is 1. The range is 1-255.' ;
                type uint8 {
                  range 1..255 ;

                }

                default 1 ;
              }

              leaf metric {
                description 'The route metric, and the default value is 0. The range is 0-255.' ;
                type uint8 {
                  range 0..255 ;

                }

                default 0 ;
              }

              leaf description {
                description 'The description information of the route.' ;
                type string {
                  length 0..64 ;

                }

              }

              leaf track-name {
                description "The track object which the static route track-detection related. The default value is null, means that don't relate track-detection." ;
                type string {
                  length 1..31 ;

                }

              }

            }

          }

          container dynamic-tunnels {
            description 'Routing configuration in IPv6 dynamic tunnel scene.' ;
            list dynamic-tunnel {
              description 'Routing configuration in IPv6 dynamic tunnel scene.' ;
              key 'vrf-name ipv6-dest-addr mask-len local-ipv6 remote-ipv6' ;
              leaf vrf-name {
                description 'The name of the private network VPN.' ;
                type string {
                  length 1..32 ;

                }

              }

              leaf ipv6-dest-addr {
                description 'The destination address.' ;
                type ncd:ipv6-address ;

              }

              leaf mask-len {
                description 'The mask lenth.' ;
                type uint8 ;

              }

              leaf local-ipv6 {
                description 'The local IPv6 address.' ;
                type ncd:ipv6-address ;

              }

              leaf remote-ipv6 {
                description 'The remote IPv6 address.' ;
                type ncd:ipv6-address ;

              }

              leaf vni-label {
                description 'The VNI label value, and the invalid value is 0. The range is 1-16777215.' ;
                type uint32 {
                  range 1..16777215 ;

                }

              }

              leaf router-mac {
                description 'The router MAC value.' ;
                type ncd:mac-address ;

              }

              leaf distance {
                description 'The route priority, and the default value is 1. The range is 1-255.' ;
                type uint8 {
                  range 1..255 ;

                }

                default 1 ;
              }

              leaf metric {
                description 'The route metric, and the default value is 0. The range is 0-255.' ;
                type uint8 {
                  range 0..255 ;

                }

                default 0 ;
              }

              leaf description {
                description 'The description information of the route.' ;
                type string {
                  length 0..64 ;

                }

              }

              leaf track-name {
                description "The track object which the static route track-detection related. The default value is null, means that don't relate track-detection." ;
                type string {
                  length 1..31 ;

                }

              }

            }

          }

          container dynamic-tunnels-ipv4 {
            description 'Routing configuration in IPv4 dynamic tunnel scene.' ;
            presence dynamic-ipv4 ;
            list dynamic-tunnel {
              description 'Routing configuration in IPv4 dynamic tunnel scene.' ;
              key 'vrf-name ipv6-dest-addr mask-len local-ip remote-ip' ;
              leaf vrf-name {
                description 'The name of the private network VPN.' ;
                type string {
                  length 1..32 ;

                }

              }

              leaf ipv6-dest-addr {
                description 'The destination address.' ;
                type ncd:ipv6-address ;

              }

              leaf mask-len {
                description 'The mask lenth.' ;
                type uint8 ;

              }

              leaf local-ip {
                description 'The local IP address of VXLAN tunnel.' ;
                type ncd:ipv4-address-none-zero ;

              }

              leaf remote-ip {
                description 'The remote IP address of VXLAN tunnel.' ;
                type ncd:ipv4-address-none-zero ;

              }

              leaf vni-label {
                description 'The VNI label value, and the invalid value is 0. The range is 1-16777215.' ;
                type uint32 {
                  range 1..16777215 ;

                }

                mandatory true ;
              }

              leaf router-mac {
                description 'The router MAC value.' ;
                type ncd:mac-address ;

                mandatory true ;
              }

              leaf distance {
                description 'The route priority, and the default value is 1. The range is 1-255.' ;
                type uint8 {
                  range 1..255 ;

                }

                default 1 ;
              }

              leaf metric {
                description 'The route metric, and the default value is 0. The range is 0-255.' ;
                type uint8 {
                  range 0..255 ;

                }

                default 0 ;
              }

              leaf description {
                description 'The description information of the route.' ;
                type string {
                  length 0..64 ;

                }

              }

              leaf track-name {
                description "The track object which the static route track-detection related. The default value is null, means that don't relate track-detection." ;
                type string {
                  length 1..31 ;

                }

              }

            }

            ncd:revise-date 2022-09-07 ;
          }

          ncd:revise-date 2018-12-04 ;
        }

        container nexthop {
          if-feature nexthop-resolving-delay ;

          description 'The node for IPv6 static route to set related nexthop features.' ;
          container trigger {
            description 'The node to trigger nexthop resolving.' ;
            container delay {
              description 'The node to set delay time.' ;
              leaf time {
                description 'The nexthop resolving delay time , the default value is 0, the range is 0 to 300, and the unit is second.' ;
                type uint32 {
                  range 0..300 {
                    description 'Delay-time value.' ;
                  }

                }

                units second ;
                default 0 ;
              }

            }

          }

          ncd:revise-date 2020-01-09 ;
        }

        container bfd {
          if-feature bfd-template ;

          description "The configuration for IPv6 static route to set BFD's attribute." ;
          container single-bfds {
            description "The configuration for IPv6 static route to set single-hop BFD's attributes." ;
            presence template-name ;
            list single-bfd {
              description "The configuration for IPv6 static route to set single-hop BFD's attributes." ;
              key 'ifname nexthop' ;
              leaf ifname {
                description 'The interface name specified.' ;
                type ncd:ifname {
                  length 1..31 ;

                }

              }

              leaf nexthop {
                description 'The nexthop address specified.' ;
                type ncd:ipv6-address ;

              }

              leaf template-name {
                description "The template name of single-hop BFD.
                These characters's ASCII unicode must be between 0x21-0x3E / 0x40-0x7E." ;
                type string {
                  length 1..31 ;

                }

                mandatory true ;
              }

            }

          }

          container multi-bfds {
            description "The configuration for IPv6 static route to set public multi-hop BFD's attributes." ;
            presence template-name ;
            list multi-bfd {
              description "The configuration for public multi-hop BFD's template name." ;
              key 'nexthop local-address' ;
              leaf local-address {
                description 'The original address specified.' ;
                type ncd:ipv6-address ;

              }

              leaf nexthop {
                description 'The nexthop address specified.' ;
                type ncd:ipv6-address ;

              }

              leaf template-name {
                description "The template name of public multi-hop BFD.
                These characters's ASCII unicode must be between 0x21-0x3E / 0x40-0x7E." ;
                type string {
                  length 1..31 ;

                }

                mandatory true ;
              }

            }

          }

          container multi-bfds-vrf {
            description "The configuration for IPv6 static route to set multi-hop BFD's attributes." ;
            presence template-name ;
            list multi-bfd-vrf {
              description "The configuration for private multi-hop BFD's template name." ;
              key 'vrfname nexthop local-address' ;
              leaf vrfname {
                description "The name of the private network VPN.
                These characters's ASCII unicode must be between 0x20-0x7E." ;
                type ncd:string-all {
                  length 1..32 ;

                }

              }

              leaf local-address {
                description 'The original address specified.' ;
                type ncd:ipv6-address ;

              }

              leaf nexthop {
                description 'The nexthop address specified.' ;
                type ncd:ipv6-address ;

              }

              leaf template-name {
                description "The template name of private multi-hop BFD.
                These characters's ASCII unicode must be between 0x21-0x3E / 0x40-0x7E." ;
                type string {
                  length 1..31 ;

                }

                mandatory true ;
              }

            }

          }

          ncd:revise-date 2020-04-03 ;
        }

        container recursion-l3evpns {
          description 'The recursion-l3evpn function for IPv6-STATIC-ROUTE.' ;
          list recursion-l3evpn {
            description 'The recursion-l3evpn function for IPv6-STATIC-ROUTE.' ;
            key vrf-name ;
            leaf vrf-name {
              description 'Specifying the VPN name.' ;
              type string {
                length 1..32 ;

              }

            }

            leaf status {
              description 'Set static route recursion L3EVPN enable or disable.' ;
              type enumeration {
                enum ENABLE {
                  value 1 ;
                  description 'Set static route recursion L3EVPN enable.' ;
                }

                enum DISABLE {
                  value 0 ;
                  description 'Set static route recursion L3EVPN disable.' ;
                }

              }

              mandatory true ;
            }

          }

          ncd:revise-date 2020-08-13 ;
        }

        container track-actions {
          description 'Static route track configuration.' ;
          list track-action {
            description 'Static route track configuration.' ;
            key 'track-name track-state' ;
            leaf track-name {
              description 'Specifying the track name.' ;
              type string {
                length 1..31 ;

              }

            }

            leaf track-state {
              description 'The track state.' ;
              type enumeration {
                enum ADMIN-DOWN {
                  value 1 ;
                  description 'Administratively down.' ;
                }

              }

            }

            leaf action {
              description 'Set static route invalid or not with the track state.' ;
              type enumeration {
                enum VALID {
                  value 1 ;
                  description 'Set static route valid.' ;
                }

                enum INVALID {
                  value 0 ;
                  description 'Set static route invalid.' ;
                }

              }

              mandatory true ;
            }

          }

          ncd:revise-date 2021-01-07 ;
        }

        container only-recurse {
          description 'The only recursion function for IPv6 static route.' ;
          container public-net {
            description 'The only recursion function for IPv6 static route in public net.' ;
            presence route-type ;
            leaf route-type {
              description 'Set the special route type of static route rescure only.' ;
              type recursion-type ;

              mandatory true ;
            }

          }

          container private-nets {
            description 'The only recursion function for IPv6 static route in private net.' ;
            list private-net {
              description 'The only recursion function for IPv6 static route in private net.' ;
              key vrf-name ;
              leaf vrf-name {
                description 'Specifying the VPN name.' ;
                type ncd:string-all {
                  length 1..32 ;

                }

              }

              leaf route-type {
                description 'Set the special route type of static route rescure only.' ;
                type recursion-type ;

                mandatory true ;
              }

            }

          }

          container mng-net {
            description 'The only recursion function for IPv6 static route in mng net.' ;
            presence route-type ;
            leaf route-type {
              description 'Set the special route type of static route rescure only.' ;
              type recursion-type ;

              mandatory true ;
            }

          }

          ncd:revise-date 2021-04-13 ;
        }

      }

    }

  }

  container state {
    config false ;
    description 'The information query of IPv4-STATIC-ROUTE and IPv6-STATIC-ROUTE module.' ;
    container rpm-srt {
      description 'The information query of IPv4-STATIC-ROUTE and IPv6-STATIC-ROUTE module.' ;
      container rpm-srtv4 {
        description 'The information query of IPv4-STATIC-ROUTE module.' ;
        container route-status {
          description 'The routing status query.' ;
          list view-list {
            description 'The list of routing status query.' ;
            key 'objtype vrfname addr mask nhtype nexthop ifname' ;
            leaf objtype {
              description 'The route type. The "MAIN" means the public route, the "VRF" means private route, the "MNG" means mng route, and the "ALL" means all routes (which is not used now).' ;
              type enumeration {
                enum MAIN {
                  value 1 ;
                  description 'The public static routes.' ;
                }

                enum VRF {
                  value 2 ;
                  description 'The private static routes.' ;
                }

                enum MNG {
                  value 3 ;
                  description 'The mng static routes.' ;
                }

                enum ALL {
                  value 4 ;
                  description 'All static routes.' ;
                }

              }

            }

            leaf vrfname {
              description 'The name of the private network VPN. The "" means public route.' ;
              type ncd:string-all {
                length 0..32 ;

              }

            }

            leaf addr {
              description 'The destination address.' ;
              type ncd:ipv4-address ;

            }

            leaf mask {
              description 'The mask.' ;
              type ncd:ipv4-address ;

            }

            leaf nhtype {
              description 'The nexthop type. The "IP" means configuration only with nexthop, the "IF" means configuration only with interface, the "IFIP" means configuration both with interface and nexthop, the "PUBLIC" means configuration with public.' ;
              type enumeration {
                enum IP {
                  value 1 ;
                  description 'Only has nexthop.' ;
                }

                enum IF {
                  value 2 ;
                  description 'Only has interface.' ;
                }

                enum IFIP {
                  value 3 ;
                  description 'Both have nexthop and interface.' ;
                }

                enum PUBLIC {
                  value 4 ;
                  description 'The nexthop is public.' ;
                }

              }

            }

            leaf nexthop {
              description 'The route nexthop.' ;
              type ncd:ipv4-address ;

            }

            leaf ifname {
              description 'The interface name of route.' ;
              type ncd:string-all ;

            }

            leaf route-status {
              description 'The route status. The "VALID" means that route is valid, the "INVALID" means that route is invalid, and the "NOTEXIST" means route is not exist (which is not used now).' ;
              type enumeration {
                enum VALID {
                  value 0 ;
                  description 'Route is valid.' ;
                }

                enum INVALID {
                  value 1 ;
                  description 'Route is invalid.' ;
                }

                enum NOTEXIST {
                  value 2 ;
                  description 'Route is not exist.' ;
                }

              }

              default VALID ;
            }

            leaf route-tag {
              description 'The route tag, and the default value is 0. The range is 0-4294967295' ;
              type uint32 {
                range 0..4294967295 ;

              }

              default 0 ;
            }

            leaf is-used-backup {
              description 'The route is backup route or not. The "YES" means yes, and the "NO" means no.' ;
              type enumeration {
                enum NO {
                  value 0 ;
                  description 'The route is not backup route.' ;
                }

                enum YES {
                  value 1 ;
                  description 'The route is backup route.' ;
                }

              }

              default NO ;
            }

            leaf ipv6-nexthop {
              if-feature ipv4-dest-with-ipv6-global-nh ;

              description 'The route IPv6 nexthop.' ;
              type ncd:ipv6-address ;

              ncd:revise-date 2019-04-01 ;
            }

            leaf preference {
              type uint8 ;

              ncd:revise-date 2023-01-30 ;
            }

            leaf interface-status {
              type interface-status ;

              ncd:revise-date 2023-01-30 ;
            }

            leaf tunnel-id {
              type uint32 ;

              ncd:revise-date 2023-01-30 ;
            }

          }

        }

      }

      container rpm-srtv6 {
        container route-status {
          list view-list {
            key 'objtype vrfname prefix prefix-length ipv6-nexthop ifname nexthop' ;
            leaf objtype {
              type network-type ;

            }

            leaf vrfname {
              type string ;

            }

            leaf prefix {
              type ncd:ipv6-address ;

            }

            leaf prefix-length {
              type uint8 ;

            }

            leaf ipv6-nexthop {
              type ncd:ipv6-address ;

            }

            leaf ifname {
              type ncd:string-all ;

            }

            leaf nexthop {
              type ncd:ipv4-address ;

            }

            leaf route-status {
              description 'The route status. The "VALID" means that route is valid, the "INVALID" means that route is invalid, and the "NOTEXIST" means route is not exist (which is not used now).' ;
              type enumeration {
                enum VALID {
                  value 0 ;
                  description 'Route is valid.' ;
                }

                enum INVALID {
                  value 1 ;
                  description 'Route is invalid.' ;
                }

                enum NOTEXIST {
                  value 2 ;
                  description 'Route is not exist.' ;
                }

              }

              default VALID ;
            }

            leaf preference {
              type uint8 ;

            }

            leaf interface-status {
              type interface-status ;

            }

            leaf tunnel-id {
              type uint32 ;

            }

          }

        }

        ncd:revise-date 2023-01-30 ;
      }

    }

  }

}
