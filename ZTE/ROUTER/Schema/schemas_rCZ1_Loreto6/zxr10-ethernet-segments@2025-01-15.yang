module zxr10-ethernet-segments {
  namespace "http://www.zte.com.cn/zxr10/netconf/schema/rosng/ethernet-segments" ;
  prefix ethernet-segments ;
  yang-version 1 ;
  import zxr10-netconf-defs {
    prefix ncd ;
  }

  organization "ZTE Corporation" ;
  contact "ZTE Corporation
  Nanjing Institute of ZTE Corporation
  No.68 Zijinghua Rd. Yuhuatai District, Nanjing, China
  Tel: +86-25-52870000" ;
  description 'The netconf module to describe ethernet segment info.' ;
  revision 2025-01-15 {
    description '1.Add the port-active-compatible leaf which in configuration/ethernet-segments.
2.Add the port-active case which in configuration/ethernet-segments/ethernet-segment.' ;
  }

  revision 2024-11-13 {
    description '1.Add the ndf-mac-flush leaf node in configuration/ethernet-segments/ethernet-segment.' ;
  }

  revision 2024-08-13 {
    description '1.Delete the wtr-params choice and add the wtr , wtr-second-with-minute , wtr-second leaf which in configuration/ethernet-segments/ethernet-segment.' ;
  }

  revision 2024-07-09 {
    description '1.Modify the second node range from 0-3600 to 0-720 which in configuration/ethernet-segments/ethernet-segment.' ;
  }

  revision 2024-06-19 {
    description '1.Modify the description of the yang node.' ;
  }

  revision 2024-03-11 {
    description '1.Add the evpn-redirect-label-srv6 container node which in configuration/ethernet-segments.' ;
  }

  revision 2024-03-01 {
    description '1.Modify the wtr-time leaf default value from 3 minutes to 0 minutes which in configuration/ethernet-segments/ethernet-segment.' ;
  }

  revision 2023-12-12 {
    description '1.Add the wtr-params choice and wtr-minute case wtr-second case wtr-time node second node which in configuration/ethernet-segments/ethernet-segment.' ;
  }

  revision 2023-08-16 {
    description '1.Obsolete the leaf of pbb-b-mac which in configuration/ethernet-segments/ethernet-segment-global.
2.Obsolete the leaf of pbb-b-mac which in configuration/ethernet-segments/ethernet-segment.' ;
  }

  revision 2023-04-17 {
    description '1.Modify the rt-value leaf type from mac-address-none-zero to mac-address which in configuration/ethernet-segments/ethernet-segment/import-rt-params.' ;
  }

  revision 2022-12-14 {
    description '1.Add the evpn-pw case node which in configuration/ethernet-segments/ethernet-segment.' ;
  }

  revision 2022-10-10 {
    description '1.Add the esi-proxy-instances containter node which in configuration/ethernet-segments.' ;
  }

  revision 2022-02-15 {
    description '1.Add the df-timer leaf node in configuration/ethernet-segments/ethernet-segment.' ;
  }

  revision 2021-08-09 {
    description '1.Add the df-election container node in configuration/ethernet-segments.' ;
  }

  revision 2021-06-24 {
    description '1.Add the dcb container node in configuration/ethernet-segments/ethernet-segment.' ;
  }

  revision 2021-03-15 {
    description '1.Add the es-topology leaf node which in configuration/ethernet-segments/ethernet-segment.' ;
  }

  revision 2020-12-02 {
    description '1.Add the df-algorithm leaf which in configuration/ethernet-segments/ethernet-segment.' ;
  }

  revision 2020-07-23 {
    description '1.Add asnd-nn type in rd node which in configuration/ethernet-segments/ethernet-segments-rd.
2.Add asnd-nn type in rt-value node which in configuration/ethernet-segments/route-target-params/route-target.' ;
  }

  revision 2020-07-01 {
    description '1.The range of suspicion-time leaf which in configuration/ethernet-segments/ethernet-segment changed from 3-1200 to 0-1200.' ;
  }

  revision 2020-06-08 {
    description '1.Add the es-import-rt and es-rt-choice-clear case nodes which in configuration/ethernet-segments/ethernet-segment.
2.Add the srv6-args container node which in configuration/ethernet-segments.' ;
  }

  revision 2020-05-27 {
    description '1.Add the ac-or-pw-choice-clear case which in configuration/ethernet-segments/ethernet-segments/ac-or-pw.' ;
  }

  revision 2020-05-15 {
    description '1.Add the eth-seg-id-choice-clear case which in configuration/ethernet-segments/ethernet-segments/eth-seg-id.' ;
  }

  revision 2020-04-18 {
    description '1.Add the inst-description leaf node in configuration/ethernet-segments/ethernet-segment.' ;
  }

  revision 2019-10-29 {
    description '1.Add the es-label container node in configuration/ethernet-segments/ethernet-segment.' ;
  }

  revision 2019-07-09 {
    description '1.Add the pw case node in configuration/ethernet-segments/ethernet-segment/ac-or-pw.
2.Add auto-derived case node in configuration/ethernet-segments/ethernet-segment/eth-seg-id.' ;
  }

  revision 2019-06-18 {
    description '1.Add suspicion-time leaf in configuration/ethernet-segments/ethernet-segment.
2.Add the service case node in configuration/ethernet-segments/ethernet-segment/ac-or-pw.' ;
  }

  revision 2019-06-05 {
    description '1.Modify the order of the ac-or-pw choice,it must be the last node in the ethernet-segment list.because the mim object is different with the other node,or the merge-replace will not be correct.' ;
  }

  revision 2019-02-15 {
    description '1.Add wtr-time leaf in configuration/ethernet-segments/ethernet-segment.
2.Add the admin-instance-params container node in configuration/ethernet-segments/ethernet-segment.' ;
  }

  revision 2019-01-16 {
    description '1.Add the etree-advertise container in configuration/ethernet-segments.' ;
  }

  revision 2018-07-12 {
    description '1.Add the ethernet-segment-global container in configuration/ethernet-segments.
2.Add the pbb-b-mac leaf node in configuration/ethernet-segments/ethernet-segment.' ;
  }

  revision 2018-07-08 {
    description '1.Add the ethernet-segments-rd and route-target-params containers in configuration/ethernet-segments/ethernet-segment.
2.Add the df-election leaf node in configuration/ethernet-segments/ethernet-segment.
3.active-mode node which in configuration/ethernet-segments/ethernet-segment delete the mandatory attribute and add the default value.' ;
  }

  revision 2017-04-26 {
    description 'Create ethernet segment module.' ;
  }

  container configuration {
    description 'Ethernet segment configuration information.' ;
    container ethernet-segments {
      description 'Ethernet segment information.' ;
      list ethernet-segment {
        description 'Ethernet segment instance info.' ;
        key name ;
        leaf name {
          description 'Name of the ethernet segment instance.' ;
          type string {
            length 1..32 {
              description 'The length of ethernet instance.' ;
            }

          }

        }

        choice eth-seg-id {
          description 'Ethernet segment identification.' ;
          case static-octets {
            description 'Static octets.' ;
            leaf static-octets-string {
              description 'Ethernet segment ID.' ;
              type string {
                length 1..26 {
                  description 'The length of ethernet segment ID.' ;
                }

              }

            }

          }

          case auto-derived {
            description 'Auto derived ethernet segment identification.' ;
            leaf auto-derived-type {
              description 'Auto derived ESI type.' ;
              type enumeration {
                enum mac-based {
                  value 3 ;
                  description 'The ESI type is MAC based.' ;
                }

              }

            }

            ncd:revise-date 2019-07-09 ;
          }

          case eth-seg-id-choice-clear {
            description 'Remove value of any entities which belong to any case within this choice.' ;
            container eth-seg-id-all-clear {
              description 'Remove this entity means to remove value of any entities which belong to any case within this choice.' ;
              presence eth-seg-id-all-clear ;
            }

            ncd:revise-date 2020-05-15 ;
          }

        }

        choice active-mode {
          description 'Choice of active mode.' ;
          default all-active ;
          case single-active {
            description 'Single active mode.' ;
            leaf single-active-mode {
              description 'Single active mode.' ;
              type empty ;

            }

          }

          case all-active {
            description 'All active mode.' ;
            leaf all-active-mode {
              description 'All active mode.' ;
              type empty ;

            }

          }

          case port-active {
            description 'Port active mode.' ;
            leaf port-active-mode {
              type empty ;

              description 'Port active mode.' ;
            }

            ncd:revise-date 2025-01-15 ;
          }

        }

        leaf df-election {
          description 'The DF election priority.' ;
          type uint16 {
            range 0..65535 {
              description 'The range of DF election value.' ;
            }

          }

          default 32767 ;
          ncd:revise-date 2018-07-08 ;
        }

        leaf suspicion-time {
          description 'The DF suspicion time,the uint is second.' ;
          type uint16 {
            range 0..1200 {
              description 'The value of suspicion time.' ;
            }

          }

          units second ;
          default 3 ;
          ncd:revise-date 2019-06-18 ;
        }

        leaf pbb-b-mac {
          status obsolete {
            ncd:revise-date 2023-08-16 ;
          }

          description 'The PBB-B-MAC of ES instance.' ;
          type ncd:mac-address-none-zero ;

          ncd:revise-date 2018-07-12 ;
        }

        leaf wtr-time {
          type uint8 {
            range 0..12 {
              description 'The length of WTR time in minute.' ;
            }

          }

          description 'Set minutes in WTR. Requires setting wtr-second-with-minute node simultaneously. The range is 0-12(minutes).' ;
          default 0 ;
          units min ;
          ncd:revise-date 2019-02-15 ;
        }

        leaf wtr-second-with-minute {
          type uint8 {
            range 0..59 {
              description 'The length of WTR second time in minute.' ;
            }

          }

          description 'Set seconds in WTR. Requires setting wtr-time node simultaneously. The range is 0-59(seconds).' ;
          units second ;
          ncd:revise-date 2024-08-13 ;
        }

        leaf second {
          type uint32 {
            range 0..720 {
              description 'The length of WTR time in second.' ;
            }

          }

          description 'Set seconds in WTR. Cannot be configured simultaneously with wtr-time node or wtr-second-with-minute node. The range is 0-720(seconds). ' ;
          units second ;
          ncd:revise-date 2023-12-12 ;
        }

        leaf inst-description {
          description 'The description of the ES instance.' ;
          type ncd:string-with-blank {
            length 1..104 {
              description 'The description range of instance.' ;
            }

          }

          ncd:revise-date 2020-04-18 ;
        }

        leaf df-algorithm {
          description 'Specify DF election algorithm.' ;
          type enumeration {
            enum modulus-based {
              value 0 ;
              description 'DF Alg 0 (Modulus-based algorithm [RFC7432]).' ;
            }

            enum preference-based {
              value 2 ;
              description 'DF Alg 2 (Preference algorithm [evpn-pref-df]).' ;
            }

            enum none {
              value 254 ;
              description 'None of the BGP-based DF algorithms will be used.' ;
            }

          }

          default preference-based ;
          ncd:revise-date 2020-12-02 ;
        }

        leaf es-topology {
          description 'The type of ES topology.' ;
          type enumeration {
            enum mhn {
              value 1 ;
              description 'Multi-homed network.' ;
            }

          }

          ncd:revise-date 2021-03-15 ;
        }

        leaf port-active-compatible {
          type enumeration {
            enum port-active-compatible {
              value 1 ;
              description 'Revert to default algorithm when a remote PE is not port-active.' ;
            }

          }

          description 'Compatibility configuration for port active.' ;
          ncd:revise-date 2025-01-15 ;
        }

        leaf ndf-mac-flush {
          description 'NDF triggers MAC flush.' ;
          type enumeration {
            enum ndf-mac-flush {
              value 1 ;
            }

          }

          ncd:revise-date 2024-11-13 ;
        }

        container df-timer-params {
          description 'DF timer parameters.' ;
          presence df-timer-params ;
          leaf df-timer {
            description 'The timer which wait for other PEs to receive this ES route.' ;
            type uint16 {
              range 1..5000 {
                description 'The range of DF timer.' ;
              }

            }

            units ms ;
            mandatory true ;
          }

          leaf smoothly {
            description 'Temporary standby drops packets smoothly.' ;
            type empty ;

          }

          ncd:revise-date 2022-02-15 ;
        }

        container es-label {
          description 'Ethernet segment label.' ;
          leaf assigned-mode {
            description 'Ethernet segment label assigned mode.' ;
            type enumeration {
              enum downstream-assigned-mode {
                value 0 ;
                description 'Ethernet segment label assigned mode is downstream.' ;
              }

              enum upstream-assigned-mode {
                value 1 ;
                description 'Ethernet segment label assigned mode is upstream.' ;
              }

            }

            default downstream-assigned-mode ;
          }

          ncd:revise-date 2019-10-29 ;
        }

        container dcb {
          description 'Domain-wide common block.' ;
          leaf label {
            description 'Domain-wide common block label.' ;
            type uint32 {
              range 16..1048575 {
                description 'The range of domain-wide common block label.' ;
              }

            }

          }

          ncd:revise-date 2021-06-24 ;
        }

        choice ac-or-pw {
          description 'Choice of AC or PW.' ;
          case ac {
            description 'Attachment Circuit definition.' ;
            leaf ac {
              description 'Bind an interface to the ethernet segment instance.' ;
              type ncd:ifname ;

            }

          }

          case pw {
            description 'PW entry definition.' ;
            container pw-params {
              description 'The PW entry parameters.' ;
              list pw-entry {
                description 'The PW entry.' ;
                key pw-name ;
                leaf pw-name {
                  description 'Bind a PW to the ethernet segment instance.' ;
                  type ncd:ifname ;

                }

              }

            }

            ncd:revise-date 2019-07-09 ;
          }

          case service {
            description 'Service definition.' ;
            container service-params {
              description 'The service instance parameters.' ;
              list service-instance {
                description 'The service instance.' ;
                key service-instance-name ;
                leaf service-instance-name {
                  description 'Bind a service instance to the ethernet segment instance.' ;
                  type string {
                    length 1..32 {
                      description 'The length of instance name.' ;
                    }

                  }

                }

              }

            }

            ncd:revise-date 2019-06-18 ;
          }

          case ac-or-pw-choice-clear {
            description 'Remove value of any entities which belong to any case within this choice.' ;
            container ac-pw-service-all-clear {
              description 'Remove this entity means to remove value of any entities which belong to any case within this choice.' ;
              presence ac-pw-service-all-clear ;
            }

            ncd:revise-date 2020-05-27 ;
          }

          case evpn-pw {
            description 'EVPN-PW definition.' ;
            container evpn-pw-params {
              description 'The EVPN-PW parameters.' ;
              list evpn-pw {
                description 'The EVPN-PW.' ;
                key pw-name ;
                leaf pw-name {
                  description 'The name of EVPN-PW.' ;
                  type ncd:ifname ;

                }

              }

            }

            ncd:revise-date 2022-12-14 ;
          }

        }

        container ethernet-segments-rd {
          description 'Ethernet segments route distinguisher parameters.' ;
          presence ethernet-segments-rd ;
          leaf rd {
            description 'The route distinguisher.' ;
            type union {
              type ncd:asn-nn ;

              type ncd:ipadd-nn ;

              type ncd:asnd-nn ;

            }

            mandatory true ;
          }

          ncd:revise-date 2018-07-08 ;
        }

        choice es-rt {
          description 'Choice of ES route target.' ;
          case es-rt-params {
            description 'ES route target parameters.' ;
            container route-target-params {
              description 'The route target parameters.' ;
              list route-target {
                description 'The route target configuration.' ;
                key 'rt-value effect-type' ;
                leaf rt-value {
                  description 'RT attribute value.' ;
                  type union {
                    type ncd:asn-nn ;

                    type ncd:ipadd-nn ;

                    type ncd:asnd-nn ;

                  }

                }

                leaf effect-type {
                  description 'The route target effect type.' ;
                  type enumeration {
                    enum export {
                      value 2 ;
                      description 'The route target effect type is export.' ;
                    }

                    enum import {
                      value 3 ;
                      description 'The route target effect type is import.' ;
                    }

                  }

                }

              }

              ncd:revise-date 2018-07-08 ;
            }

          }

          case es-import-rt {
            description 'ES import route target parameters.' ;
            container import-rt-params {
              description 'The import route target parameters.' ;
              leaf rt-value {
                description 'Import RT attribute value.' ;
                type ncd:mac-address ;

              }

            }

            ncd:revise-date 2020-06-08 ;
          }

          case es-rt-choice-clear {
            description 'Remove value of any entities which belong to any case within this choice.' ;
            container es-rt-all-clear {
              description 'Remove this entity means to remove value of any entities which belong to any case within this choice.' ;
              presence es-rt-all-clear ;
            }

            ncd:revise-date 2020-06-08 ;
          }

        }

        container admin-instance-params {
          description 'The admin instance parameters.' ;
          list admin-instance {
            description 'The admin instance list.' ;
            key admin-evpn-vpls-name ;
            leaf admin-evpn-vpls-name {
              description 'Bind a EVPN VPLS instance as an admin instance to the ethernet segment instance.' ;
              type string {
                length 1..32 {
                  description 'The length of instance name.' ;
                }

              }

            }

          }

          ncd:revise-date 2019-02-15 ;
        }

      }

      container ethernet-segment-global {
        leaf pbb-b-mac {
          status obsolete {
            ncd:revise-date 2023-08-16 ;
          }

          description 'The global PBB-B-MAC of ES.' ;
          type ncd:mac-address-none-zero ;

        }

        description 'Global ethernet segment configuration.' ;
        ncd:revise-date 2018-07-12 ;
      }

      container etree-advertise {
        description 'E-tree advertisement parameters.' ;
        presence etree-advertise ;
        leaf leaf-label {
          description 'Advertise leaf label for e-tree.' ;
          type empty ;

          mandatory true ;
        }

        ncd:revise-date 2019-01-16 ;
      }

      container srv6-args {
        description 'SRv6 args length configuration.' ;
        leaf esi-label-length {
          description 'The length of ESI label.' ;
          type uint8 {
            range 4..20 {
              description 'The range of ESI label length.' ;
            }

          }

          default 16 ;
        }

        ncd:revise-date 2020-06-08 ;
      }

      container df-election {
        description 'Specify DF election mode per ESI.' ;
        presence df-election ;
        leaf capability-negotiate {
          description 'Capability negotiation parameters for DF algorithm.' ;
          type empty ;

          mandatory true ;
        }

        ncd:revise-date 2021-08-09 ;
      }

      container esi-proxy-instances {
        description 'ES instances for null-ESI-ACs to be viewed as normal ESIs by external PEs.' ;
        list esi-proxy-instance {
          description 'An ES instance for null-ESI-ACs to be viewed as a normal ESI by external PEs.' ;
          key mode ;
          leaf mode {
            description 'ESI proxy mode.' ;
            type enumeration {
              enum single-active {
                value 1 ;
                description 'Viewed as single-active (S-A) by PEs behind SPEs.' ;
              }

              enum all-active {
                value 2 ;
                description 'Viewed as all-active (A-A) by PEs behind SPEs' ;
              }

            }

          }

          container es-id-params {
            description 'Ethernet segment ID parameters.' ;
            leaf es-id {
              description 'Ethernet segment ID.' ;
              type string {
                length 1..26 {
                  description 'The length of ethernet segment ID.' ;
                }

              }

            }

          }

        }

        ncd:revise-date 2022-10-10 ;
      }

      container evpn-redirect-label-srv6 {
        leaf srv6 {
          type empty ;

          description 'ERL as argument of DT2U.Reroute/DX2.Reroute SID.' ;
          mandatory false ;
        }

        description ' Configure EVPN Redirect Label (ERL) of SRv6 parameters.' ;
        ncd:revise-date 2024-03-11 ;
      }

    }

  }

}
