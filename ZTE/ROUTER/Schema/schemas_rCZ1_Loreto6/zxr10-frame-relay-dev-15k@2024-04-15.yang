module zxr10-frame-relay-dev-15k {
  namespace "http://www.zte.com.cn/zxr10/netconf/schema/rosng/frame-relay-dev-15k" ;
  yang-version 1 ;
  prefix frame-relay-dev-15k ;
  import zxr10-frame-relay {
    prefix frame-relay ;
  }

  organization "ZTE Corporation" ;
  contact "ZTE Corporation  
     Nanjing Institute of ZTE Corporation 
     No.68 Zijinghua Rd. Yuhuatai District, Nanjing, China 
     Tel: +86-25-52870000" ;
  revision 2024-04-15 {
    description 'Add deviation for lmi-type.' ;
  }

  deviation "/frame-relay:configuration/frame-relay:frame-relay/frame-relay:base-instance/frame-relay:base/frame-relay:lmi-type" {
    description 'LMI type of ANSI/Q933A.' ;
    deviate replace {
      type enumeration {
        enum q933a {
          value 0 ;
          description 'q933a' ;
        }

        enum ansi {
          value 2 ;
          description 'ansi' ;
        }

      }

      default q933a ;
    }

  }

}
