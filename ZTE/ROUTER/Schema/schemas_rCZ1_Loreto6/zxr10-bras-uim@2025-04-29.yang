module zxr10-bras-uim {
  namespace "http://www.zte.com.cn/zxr10/netconf/schema/bras/uim" ;
  prefix bras-uim ;
  yang-version 1 ;
  import zxr10-netconf-defs {
    prefix ncd ;
  }

  organization "ZTE Corporation" ;
  contact "ZTE Corporation  
     Nanjing Institute of ZTE Corporation 
     No.68 Zijinghua Rd. Yuhuatai District, Nanjing, China 
     Tel: +86-25-52870000" ;
  description 'The netconf module to describe the bras-uim' ;
  revision 2025-04-29 {
    description 'dhcp username' ;
  }

  revision 2025-04-18 {
    description 'iphost vrf change' ;
  }

  revision 2023-05-17 {
    description 'netconf encrypted-password <datatype>ciphertext</datatype>  add <log-type>password</log-type>' ;
  }

  revision 2022-11-16 {
    description 'leaf case add filter' ;
  }

  revision 2022-10-21 {
    description 'Add global-arp-safeguard.' ;
  }

  revision 2022-07-21 {
    description 'The minimum value of vxlan end-id is changed from 1 to 0.' ;
  }

  revision 2022-05-19 {
    description 'leaf "nas-basi""force""trackName""vxlan/start-id""vxlan/end-id" add range' ;
  }

  revision 2021-12-22 {
    description 'access-circuit-insert nas-user-def-text and ani-user-def-text length 31' ;
  }

  revision 2021-12-01 {
    description 'Configure access delay groups.' ;
  }

  revision 2021-05-27 {
    description 'leaf "userQos" delete enum user-classify-car.' ;
  }

  revision 2021-04-16 {
    description 'Add agent-circuit-id format ignore-ipox.' ;
  }

  revision 2021-04-14 {
    description 'add access-circuit-insert none-info' ;
  }

  revision 2021-02-26 {
    description 'L3 add dhcpv6 authen type' ;
  }

  revision 2021-02-20 {
    description 'Add ipox-basic-service leaf.' ;
  }

  revision 2021-02-08 {
    description 'Add access-delay-mac-offset leaf.' ;
  }

  revision 2021-02-03 {
    description 'Add dhcp-v6 suppress ia-nata in l3-access' ;
  }

  revision 2020-12-16 {
    description 'Encryption algorithm upgrade.' ;
  }

  revision 2020-08-04 {
    description 'Add qos-mode if-queue user-queue-car.
Add four kinds of mac format.' ;
  }

  revision 2020-05-18 {
    description 'add dhcpv6-slaac slaac access policy' ;
  }

  revision 2020-02-20 {
    description 'Change the maximum-time of access-delay from 2000 to 20000' ;
  }

  revision 2020-01-07 {
    description 'ipoxv6 user-detect command add no-flowcheck option
iphost user-detect command add no-flowcheck option' ;
  }

  revision 2019-11-20 {
    description 'nas-port-id' ;
  }

  revision 2019-08-14 {
    description 'Add dhcpv6 authentication option parse configuration of username,domain,password.Add dhcpv6 authentication type of mac-option16' ;
  }

  revision 2019-07-10 {
    description 'Add authentication option parse configuration of username,domain,password' ;
  }

  revision 2019-02-23 {
    description 'Add smartgroup-master container node.' ;
  }

  revision 2019-01-15 {
    description 'dhcp user-detect command add no-flowcheck option' ;
  }

  revision 2019-01-09 {
    description 'add username-type mac-option60 default option60 content' ;
  }

  revision 2018-05-14 {
    description 'add track command and vxlan configure' ;
  }

  revision 2018-01-19 {
    description 'modify max-vlan-session default 64000 to 128000' ;
  }

  revision 2016-12-28 {
    description 'Change dslam.' ;
  }

  revision 2016-12-08 {
    description 'Change the value of list access-delay,add 0 enum' ;
  }

  revision 2016-08-19 {
    description 'Change the reset value of container /configuration/uim/vbuis/vbui/iphost-detect, /configuration/uim/vbuis/vbui/ipoxv6-detect, /configuration/uim/vbuis/vbui/dhcp-user-detect' ;
  }

  revision 2016-04-08 {
    description 'Initial version' ;
  }

  container configuration {
    description 'configuration model info.' ;
    container uim {
      description 'Configure BRAS interface parameters.' ;
      container vccs {
        description 'Configure VCC parameters.' ;
        list vcc {
          description 'The port configure VCC info.' ;
          key vcc-name ;
          leaf vcc-name {
            description 'The interface will be configure VCC.' ;
            type ncd:ifname ;

          }

          leaf per-mac-multi-ipv4 {
            description 'Set per mac multi ipv4 flag' ;
            type enumeration {
              enum disable {
                value 0 ;
                description 'Disable per mac multi ip' ;
              }

              enum enable {
                value 1 ;
                description 'Enable per mac multi ip' ;
              }

            }

            default enable ;
          }

          leaf ip-access-type {
            description 'ip-access-type info of this port.' ;
            type enumeration {
              enum ipv4 {
                value 1 ;
                description 'IPv4 access' ;
              }

              enum ipv6 {
                value 2 ;
                description 'IPv6 access' ;
              }

              enum dual {
                value 3 ;
                description 'IP dual stack access' ;
              }

            }

            default ipv4 ;
          }

          leaf pppox-template {
            description 'Configure PPPoX template' ;
            type uint32 {
              range 1..1000 ;

            }

          }

          leaf encapsulation {
            description 'Set encapsulation type for interface' ;
            type enumeration {
              enum ppp-over-ethernet {
                value 1 ;
              }

              enum ip-over-ethernet {
                value 4 ;
              }

              enum multi {
                value 7 ;
              }

            }

          }

          leaf pre-domain {
            description 'authentication pre-domain name' ;
            type string {
              length 1..31 ;

            }

          }

          leaf max-vlan-session {
            description 'access max sessions per VLAN ID' ;
            type uint32 {
              range 0..128000 ;

            }

            default 128000 ;
          }

          leaf ipox-max-vlan-session {
            description 'ipox subscriber access max sessions per VLAN ID' ;
            type uint32 {
              range 0..128000 ;

            }

            default 128000 ;
          }

          leaf pppox-max-vlan-session {
            description 'pppox subscriber access max sessions per VLAN ID' ;
            type uint32 {
              range 0..128000 ;

            }

            default 128000 ;
          }

          leaf subscriber-check-location {
            description 'Subscriber location information' ;
            type enumeration {
              enum none {
                value 0 ;
                description 'Use BRAS information only' ;
              }

              enum vbas {
                value 1 ;
                description 'Use VBAS protocol' ;
              }

              enum pppoe-plus {
                value 2 ;
                description 'Use PPPoE+ protocol' ;
              }

              enum dhcp-option82 {
                value 3 ;
                description 'Use DHCP option82 protocol' ;
              }

              enum "o82|pppoe-plus" {
                value 4 ;
                description 'Use PPPoE+ or option82 protocol' ;
              }

              enum "o82|vbas" {
                value 5 ;
                description 'Use option82 or VBAS protocol' ;
              }

            }

            default none ;
          }

          leaf radius-proxy {
            description 'Radius proxy switch' ;
            type enumeration {
              enum disable {
                value 0 ;
                description 'Disable radius proxy' ;
              }

              enum enable {
                value 3 ;
                description 'Enable radius proxy' ;
              }

            }

            default disable ;
          }

          leaf bind-sal {
            description 'Bind SAL in VCC' ;
            type string {
              length 1..32 ;

            }

          }

          leaf server-discover-timer {
            description 'dhcp server discover timer' ;
            type enumeration {
              enum 60 {
                value 1 ;
                description 'Dhcp-server-discover-timer 60s' ;
              }

              enum 300 {
                value 5 ;
                description 'Dhcp-server-discover-timer 300s' ;
              }

              enum 3600 {
                value 60 ;
                description 'Dhcp-server-discover-timer 3600s' ;
              }

            }

          }

          leaf hostV4AuthType {
            description 'Iphostv4 authentication-type' ;
            type enumeration {
              enum web {
                value 3 ;
                description 'Web authentication' ;
              }

            }

          }

          leaf hostDualAuthType {
            description 'iphost user authentication-type' ;
            type enumeration {
              enum web {
                value 3 ;
                description 'Web authentication' ;
              }

            }

          }

          leaf ipv4-transmitmodeswitchCopy {
            description 'IPv4 multicast copy mode' ;
            type enumeration {
              enum user {
                value 1 ;
                description 'Set IPoE multicast copy mode by user' ;
              }

            }

          }

          leaf ipv6-transmitmodeswitch {
            description 'IPv6 multicast copy mode' ;
            type enumeration {
              enum user {
                value 1 ;
                description 'Set IPoE multicast copy mode by user' ;
              }

            }

          }

          leaf ipox-v4-authen {
            description 'Configure ipv4 user authentication-type' ;
            type enumeration {
              enum cir-map {
                value 1 ;
                description 'Circuit authentication' ;
              }

              enum option {
                value 2 ;
                description 'Option authentication' ;
              }

              enum web {
                value 3 ;
                description 'Web authentication' ;
              }

              enum option-web {
                value 4 ;
                description 'Option and web mixed authentication' ;
              }

            }

          }

          leaf ipoxv6-access-type {
            description 'ipox IPv6 access type' ;
            type enumeration {
              enum dhcpv6 {
                value 1 ;
                description 'DHCPv6 access type' ;
              }

              enum dhcpv6-slaac {
                value 2 ;
                description 'DHCPv6 and SLAAC multiple access type' ;
              }

              enum slaac {
                value 3 ;
                description 'SLAAC access type' ;
              }

            }

          }

          leaf slaac-access-policy {
            type enumeration {
              enum discard {
                value 1 ;
              }

              enum ignore-and-reply {
                value 2 ;
              }

            }

            ncd:revise-date 2020-05-18 ;
          }

          leaf pppoxv6-access-type {
            description 'Configure pppox IPv6 access type' ;
            type enumeration {
              enum dhcpv6 {
                value 1 ;
                description 'DHCPv6 access type' ;
              }

              enum dhcpv6-slaac {
                value 2 ;
                description 'DHCPv6 and SLAAC multiple access type' ;
              }

              enum slaac {
                value 3 ;
                description 'SLAAC access type' ;
              }

              enum pppv6 {
                value 4 ;
                description 'PPPv6 access type' ;
              }

            }

          }

          container ipoxv6-authen-type {
            description 'Configure ipv6 user authentication-type' ;
            leaf dhcp-v6 {
              description 'DHCPv6 user authentication-type' ;
              type enumeration {
                enum cir-map {
                  value 1 ;
                  description 'Circuit authentication' ;
                }

                enum option {
                  value 2 ;
                  description 'Option authentication' ;
                }

                enum web {
                  value 3 ;
                  description 'Web authentication' ;
                }

                enum option-web {
                  value 4 ;
                  description 'Option and web mixed authentication' ;
                }

              }

            }

            leaf slaac {
              description 'SLAAC authentication-type' ;
              type enumeration {
                enum cir-map {
                  value 1 ;
                  description 'Circuit authentication' ;
                }

                enum web {
                  value 3 ;
                  description 'Web authentication' ;
                }

              }

            }

          }

          leaf dhcpv6-suppress {
            description 'DHCPv6 suppress configure' ;
            type enumeration {
              enum ia-nata {
                value 1 ;
                description 'DHCPv6 suppress ia-nata' ;
              }

            }

          }

          container ipox-dual-authen {
            description 'Configure dual user authentication-type' ;
            leaf dhcp-v4 {
              description 'DHCPv4 user authentication-type' ;
              type enumeration {
                enum cir-map {
                  value 1 ;
                  description 'Circuit authentication' ;
                }

                enum option {
                  value 2 ;
                  description 'Option authentication' ;
                }

                enum web {
                  value 3 ;
                  description 'Web authentication' ;
                }

                enum option-web {
                  value 4 ;
                  description 'Option and web mixed authentication' ;
                }

              }

            }

            leaf dhcp-v6 {
              description 'DHCPv6 user authentication-type' ;
              type enumeration {
                enum cir-map {
                  value 1 ;
                  description 'Circuit authentication' ;
                }

                enum option {
                  value 2 ;
                  description 'Option authentication' ;
                }

                enum web {
                  value 3 ;
                  description 'Web authentication' ;
                }

                enum option-web {
                  value 4 ;
                  description 'Option and web mixed authentication' ;
                }

              }

            }

            leaf slaac {
              description 'SLAAC authentication-type' ;
              type enumeration {
                enum cir-map {
                  value 1 ;
                  description 'Circuit authentication' ;
                }

                enum web {
                  value 3 ;
                  description 'Web authentication' ;
                }

              }

            }

          }

          container nas-ssids {
            description 'Configure nas SSID' ;
            presence nas-ssid ;
            container ssid-qinq {
              description 'Configure nas SSID' ;
              presence ssid-qinq ;
              list ssid-qinq {
                description 'Configure nas SSID' ;
                key 'ex-vlan in-vlan' ;
                leaf ssid {
                  description 'SSID (e.g 00-15-70-91-E2-40:CFCC-EDA)' ;
                  type string {
                    length 1..51 {
                      description 'SSID (e.g 00-15-70-91-E2-40:CFCC-EDA)' ;
                    }

                  }

                  mandatory true ;
                }

                leaf ex-vlan {
                  description 'Set external vlan' ;
                  type ncd:single-range {
                    pattern "(([0-9]+-[0-9]+)|([1-9][0-9]*)){1,1}" {
                      description '(([0-9]+-[0-9]+)|([1-9][0-9]*)){1,1}' ;
                    }

                  }

                }

                leaf in-vlan {
                  description 'Set internal vlan' ;
                  type ncd:single-range {
                    pattern "(([0-9]+-[0-9]+)|([1-9][0-9]*)){1,1}" {
                      description '(([0-9]+-[0-9]+)|([1-9][0-9]*)){1,1}' ;
                    }

                  }

                }

              }

            }

            container ssid-dot1q {
              description 'Configure nas SSID' ;
              presence ssid-dot1q ;
              list ssid-dot1q {
                description 'Configure nas SSID' ;
                key ex-vlan ;
                leaf ssid {
                  description 'SSID (e.g 00-15-70-91-E2-40:CFCC-EDA)' ;
                  type string {
                    length 1..51 {
                      description 'SSID (e.g 00-15-70-91-E2-40:CFCC-EDA)' ;
                    }

                  }

                  mandatory true ;
                }

                leaf ex-vlan {
                  description 'Set external vlan' ;
                  type ncd:single-range {
                    pattern "(([0-9]+-[0-9]+)|([1-9][0-9]*)){1,1}" {
                      description '(([0-9]+-[0-9]+)|([1-9][0-9]*)){1,1}' ;
                    }

                  }

                }

              }

            }

            container ssid-no-vlan {
              description 'Configure nas SSID' ;
              presence ssid-no-vlan ;
              leaf ssid {
                description 'SSID (e.g 00-15-70-91-E2-40:CFCC-EDA)' ;
                type string {
                  length 1..51 {
                    description 'SSID (e.g 00-15-70-91-E2-40:CFCC-EDA)' ;
                  }

                }

                mandatory true ;
              }

            }

          }

          leaf nas-logic-ip {
            description 'nas logic IP address' ;
            type ncd:ipv4-address {
              pattern "(([1-9]|[1-9][0-9]|1[0-9][0-9]|2[0-4][0-9]|25[0-5])(.([0-9]|[1-9][0-9]|1[0-9][0-9]|2[0-4][0-9]|25[0-5])){3})|(([0])(.([1-9]|[1-9][0-9]|1[0-9][0-9]|2[0-4][0-9]|25[0-5]))(.([0-9]|[1-9][0-9]|1[0-9][0-9]|2[0-4][0-9]|25[0-5])){2})|(([0])(.([0]))(.([1-9]|[1-9][0-9]|1[0-9][0-9]|2[0-4][0-9]|25[0-5]))(.([0-9]|[1-9][0-9]|1[0-9][0-9]|2[0-4][0-9]|25[0-5])))|(([0])(.([0])){2}(.([1-9]|[1-9][0-9]|1[0-9][0-9]|2[0-4][0-9]|25[0-5])))" {
                description '(([1-9]|[1-9][0-9]|1[0-9][0-9]|2[0-4][0-9]|25[0-5])(.([0-9]|[1-9][0-9]|1[0-9][0-9]|2[0-4][0-9]|25[0-5])){3})|(([0])(.([1-9]|[1-9][0-9]|1[0-9][0-9]|2[0-4][0-9]|25[0-5]))(.([0-9]|[1-9][0-9]|1[0-9][0-9]|2[0-4][0-9]|25[0-5])){2})|(([0])(.([0]))(.([1-9]|[1-9][0-9]|1[0-9][0-9]|2[0-4][0-9]|25[0-5]))(.([0-9]|[1-9][0-9]|1[0-9][0-9]|2[0-4][0-9]|25[0-5])))|(([0])(.([0])){2}(.([1-9]|[1-9][0-9]|1[0-9][0-9]|2[0-4][0-9]|25[0-5])))' ;
              }

            }

          }

          leaf nas-logic-sysname {
            description 'nas logic system name' ;
            type string {
              length 1..31 ;

            }

          }

          container nas-logic-interface {
            description 'nas logic interface' ;
            presence nas-logic-interface ;
            leaf nas-logic-porttype {
              description 'nas logic interface type' ;
              type enumeration {
                enum atm {
                  value 1 ;
                  description 'ATM' ;
                }

                enum ethernet {
                  value 2 ;
                  description 'Ethernet' ;
                }

                enum smartgroup {
                  value 3 ;
                  description 'Smartgroup' ;
                }

              }

            }

            leaf nas_logic-slot {
              description 'nas logic interface slot' ;
              type uint16 {
                range 0..255 ;

              }

              mandatory true ;
            }

            leaf nas-logic-subslot {
              description 'nas logic interface subslot' ;
              type uint16 {
                range 0..255 ;

              }

              mandatory true ;
            }

            leaf nas_logic-port {
              description 'nas logic interface port number' ;
              type uint16 {
                range 0..255 ;

              }

              mandatory true ;
            }

          }

          leaf eap-authentication-type {
            description 'eap authentication type for interface' ;
            type enumeration {
              enum disable {
                value 0 ;
              }

              enum enable {
                value 1 ;
              }

            }

            default disable ;
          }

          leaf eap-template-no {
            description 'bind EAP template' ;
            type uint16 {
              range 1..1000 {
                description 'EAP template number' ;
              }

            }

          }

          leaf mac-format {
            description 'Configure MAC format' ;
            type enumeration {
              enum xx:xx:xx:xx:xx:xx {
                value 2 ;
                description 'Optional format' ;
              }

              enum xx-xx-xx-xx-xx-xx {
                value 1 ;
                description 'Optional format' ;
              }

              enum xxxx:xxxx:xxxx {
                value 3 ;
                description 'Optional format' ;
              }

              enum xxxx-xxxx-xxxx {
                value 4 ;
                description 'Optional format' ;
              }

              enum xxxxxxxxxxxx {
                value 5 ;
                description 'Optional format' ;
              }

              enum xxxx.xxxx.xxxx {
                value 6 ;
                description 'Optional format' ;
              }

              enum xx.xx.xx.xx.xx.xx {
                value 7 ;
                description 'Optional format' ;
              }

              enum user-defined {
                value 8 ;
                description 'Format eg. width 4 delimeter - : xxxx-xxxx-xxxx' ;
              }

            }

            default xx-xx-xx-xx-xx-xx ;
          }

          leaf mac-format-width {
            type enumeration {
              enum 1 {
                value 1 ;
                description 'Set width of mac-fomat 1 character' ;
              }

              enum 2 {
                value 2 ;
                description 'Set width of mac-fomat 2 characters' ;
              }

              enum 3 {
                value 3 ;
                description 'Set width of mac-fomat 3 characters' ;
              }

              enum 4 {
                value 4 ;
                description 'Set width of mac-fomat 4 characters' ;
              }

              enum 6 {
                value 6 ;
                description 'Set width of mac-fomat 6 characters' ;
              }

            }

            ncd:revise-date 2020-08-04 ;
          }

          leaf mac-format-delimiter {
            description "These characters's ASCII unicode must be between 0x21-0x2F/ 0x3A-0x3E/ 0x40/ 0x47-0x60/ 0x67-0x7E." ;
            type enumeration {
              enum "!" {
                value 33 ;
              }

              enum '"' {
                value 34 ;
              }

              enum "#" {
                value 35 ;
              }

              enum "$" {
                value 36 ;
              }

              enum "%" {
                value 37 ;
              }

              enum "&" {
                value 38 ;
              }

              enum "'" {
                value 39 ;
              }

              enum "(" {
                value 40 ;
              }

              enum ")" {
                value 41 ;
              }

              enum "*" {
                value 42 ;
              }

              enum "+" {
                value 43 ;
              }

              enum "," {
                value 44 ;
              }

              enum - {
                value 45 ;
              }

              enum . {
                value 46 ;
              }

              enum "/" {
                value 47 ;
              }

              enum : {
                value 58 ;
              }

              enum ";" {
                value 59 ;
              }

              enum "<" {
                value 60 ;
              }

              enum "=" {
                value 61 ;
              }

              enum ">" {
                value 62 ;
              }

              enum @ {
                value 64 ;
              }

              enum G {
                value 71 ;
              }

              enum H {
                value 72 ;
              }

              enum I {
                value 73 ;
              }

              enum J {
                value 74 ;
              }

              enum K {
                value 75 ;
              }

              enum L {
                value 76 ;
              }

              enum M {
                value 77 ;
              }

              enum N {
                value 78 ;
              }

              enum O {
                value 79 ;
              }

              enum P {
                value 80 ;
              }

              enum Q {
                value 81 ;
              }

              enum R {
                value 82 ;
              }

              enum S {
                value 83 ;
              }

              enum T {
                value 84 ;
              }

              enum U {
                value 85 ;
              }

              enum V {
                value 86 ;
              }

              enum W {
                value 87 ;
              }

              enum X {
                value 88 ;
              }

              enum Y {
                value 89 ;
              }

              enum Z {
                value 90 ;
              }

              enum "[" {
                value 91 ;
              }

              enum '\' {
                value 92 ;
              }

              enum "]" {
                value 93 ;
              }

              enum "^" {
                value 94 ;
              }

              enum _ {
                value 95 ;
              }

              enum "`" {
                value 96 ;
              }

              enum g {
                value 103 ;
              }

              enum h {
                value 104 ;
              }

              enum i {
                value 105 ;
              }

              enum j {
                value 106 ;
              }

              enum k {
                value 107 ;
              }

              enum l {
                value 108 ;
              }

              enum m {
                value 109 ;
              }

              enum n {
                value 110 ;
              }

              enum o {
                value 111 ;
              }

              enum p {
                value 112 ;
              }

              enum q {
                value 113 ;
              }

              enum r {
                value 114 ;
              }

              enum s {
                value 115 ;
              }

              enum t {
                value 116 ;
              }

              enum u {
                value 117 ;
              }

              enum v {
                value 118 ;
              }

              enum w {
                value 119 ;
              }

              enum x {
                value 120 ;
              }

              enum y {
                value 121 ;
              }

              enum z {
                value 122 ;
              }

              enum "{" {
                value 123 ;
              }

              enum "|" {
                value 124 ;
              }

              enum "}" {
                value 125 ;
              }

              enum "~" {
                value 126 ;
              }

            }

            ncd:revise-date 2020-08-04 ;
          }

          leaf mac-match-case {
            description 'MAC format match-case' ;
            type enumeration {
              enum majuscule {
                value 1 ;
                description 'Hexadecimal characters are in upper case' ;
              }

              enum lowercase {
                value 2 ;
                description 'Hexadecimal characters are in lower case' ;
              }

            }

            default majuscule ;
          }

          leaf close-source-mac-check {
            description 'Turn off checking source MAC' ;
            type enumeration {
              enum disable {
                value 0 ;
                description 'Turn on checking source MAC' ;
              }

              enum enable {
                value 1 ;
                description 'Turn off checking source MAC' ;
              }

            }

            default disable ;
          }

          leaf unauthentic-time {
            description 'unauthentic-timeout value' ;
            type uint32 {
              range 300..864000 {
                description 'Timeout value (s)' ;
              }

            }

          }

          leaf agent-circuit-id-format {
            description 'Configure agent-circuit-id format' ;
            type enumeration {
              enum china-tel {
                value 0 ;
                description 'China Telecom format' ;
              }

              enum tr101 {
                value 1 ;
                description 'Broadband Forum TR-101 format' ;
              }

              enum class1 {
                value 2 ;
                description 'Class1 format(e.g. ani-name atm 0/1/0/8:8.35)' ;
              }

              enum compatible {
                value 3 ;
                description 'Compatible format(include china-tel and class1)' ;
              }

              enum keep {
                value 4 ;
                description 'Keep format(for any format,do not analyse)' ;
              }

            }

            default compatible ;
          }

          leaf ac-client-group {
            description 'AC client group name' ;
            type string {
              length 1..31 ;

            }

          }

          leaf bras-ac-separate {
            description 'bras-ac separate flag' ;
            type enumeration {
              enum disable {
                value 0 ;
                description 'Disable bras-ac separate' ;
              }

              enum enable {
                value 1 ;
                description 'Enable bras-ac separate' ;
              }

            }

            default disable ;
          }

          leaf arp-safeguard {
            description 'Set arp safeguard flag' ;
            type enumeration {
              enum enable {
                value 1 ;
                description 'Enable arp safeguard' ;
              }

              enum disable {
                value 0 ;
                description 'Disable arp safeguard' ;
              }

            }

          }

          leaf access-delay-mac-offset {
            description 'Configure mac offset for access delay.' ;
            type uint32 {
              range 1..47 {
                description 'mac offset bit(s)' ;
              }

            }

            ncd:revise-date 2021-02-08 ;
          }

          container access-delay {
            description 'Configure the delay timer' ;
            presence access-delay ;
            list access-delay {
              description 'Configure the delay timer' ;
              key 'modular remainder' ;
              leaf delaytime {
                description 'Configure the delay timer(ms),multiples of 50' ;
                type uint32 {
                  range 50..20000 ;

                }

                mandatory true ;
              }

              leaf modular {
                description 'Configure the modular' ;
                type enumeration {
                  enum even-mac {
                    value 1 ;
                  }

                  enum odd-mac {
                    value 2 ;
                  }

                  enum 3 {
                    value 3 ;
                  }

                  enum 4 {
                    value 4 ;
                  }

                  enum 5 {
                    value 5 ;
                  }

                  enum 6 {
                    value 6 ;
                  }

                  enum 7 {
                    value 7 ;
                  }

                  enum 8 {
                    value 8 ;
                  }

                  enum 0 {
                    value 255 ;
                  }

                }

              }

              leaf remainder {
                description 'Configure the remainder' ;
                type uint32 {
                  range 0..7 ;

                }

              }

              leaf group-name {
                type string {
                  length 1..31 {
                    description 'delay group.' ;
                  }

                }

                ncd:revise-date 2021-12-01 ;
              }

            }

          }

          container qos-mode {
            description 'Configure qos mode' ;
            leaf userQos {
              description 'Configure User mode' ;
              type enumeration {
                enum user-classify-car {
                  value 3 ;
                  description 'User-classify-car mode' ;
                  status obsolete ;

                }

                enum user-car {
                  value 2 ;
                  description 'User-car mode' ;
                }

                enum user-queue {
                  value 1 ;
                  description 'User-queue mode' ;
                }

                enum user-car-queue {
                  value 4 ;
                  description 'User-car-queue mode' ;
                }

                enum 0 {
                  value 0 ;
                }

              }

              default user-queue ;
            }

            leaf vccIfQos {
              description 'Configure If-queue mode' ;
              type enumeration {
                enum if-queue {
                  value 1 ;
                  description 'If-queue mode' ;
                }

              }

              default if-queue ;
            }

            leaf qosDirection {
              description 'Configure qos direction' ;
              type enumeration {
                enum input {
                  value 1 ;
                  description 'Input direction' ;
                }

                enum output {
                  value 2 ;
                  description 'Output direction' ;
                }

                enum 3 {
                  value 3 ;
                }

              }

            }

          }

          container dslam {
            description 'Configure VBAS' ;
            presence dslam ;
            list dslam {
              description 'Configure VBAS' ;
              key 'dslamName dslamVlan' ;
              leaf dslamName {
                description 'Configure VBAS name' ;
                type string {
                  length 1..31 ;

                }

              }

              leaf dslamVlan {
                description 'Configure VBAS vlan' ;
                type ncd:single-range ;

              }

              leaf dslamMac {
                description 'Configure mac address' ;
                type ncd:mac-address ;

                mandatory true ;
              }

              leaf ignoreSrcMac {
                description 'Ignore source mac check' ;
                type uint8 {
                  range 0..1 ;

                }

              }

            }

          }

          container share-vlan-v4 {
            description 'Configure share-vlan interface name' ;
            list vccIfName {
              description 'Configure interface name' ;
              key ifName ;
              leaf ifName {
                description 'Configure IPv4 multicast VLAN' ;
                type ncd:ifname ;

              }

            }

          }

          container share-vlan-v6 {
            description 'Configure share-vlan interface name' ;
            list vccIfName {
              description 'Configure interface name' ;
              key ifName ;
              leaf ifName {
                description 'Configure IPv6 multicast VLAN' ;
                type ncd:ifname ;

              }

            }

          }

          choice nas-port-types {
            description 'Configure BRAS device nas-port-type' ;
            default nas-port-type ;
            case nas-port-type {
              description 'BRAS device nas-port-type information' ;
              leaf nas-port-type {
                description 'BRAS device nas-port-type information' ;
                type enumeration {
                  enum async {
                    value 0 ;
                  }

                  enum sync {
                    value 1 ;
                  }

                  enum isdn-sync {
                    value 2 ;
                  }

                  enum isdn-async-v120 {
                    value 3 ;
                  }

                  enum isdn-async-v110 {
                    value 4 ;
                  }

                  enum virtual {
                    value 5 ;
                  }

                  enum piafs {
                    value 6 ;
                  }

                  enum hdlc {
                    value 7 ;
                  }

                  enum x.25 {
                    value 8 ;
                  }

                  enum x.75 {
                    value 9 ;
                  }

                  enum g.3-fax {
                    value 10 ;
                  }

                  enum sdsl {
                    value 11 ;
                  }

                  enum adsl-cap {
                    value 12 ;
                  }

                  enum adsl-dmt {
                    value 13 ;
                  }

                  enum idsl {
                    value 14 ;
                  }

                  enum ethernet {
                    value 15 ;
                  }

                  enum xdsl {
                    value 16 ;
                  }

                  enum cable {
                    value 17 ;
                  }

                  enum wireless-other {
                    value 18 ;
                  }

                  enum 802.11 {
                    value 19 ;
                  }

                }

                default ethernet ;
              }

            }

            case user-defined {
              description 'Nas-port-type is user defined value (20~255)' ;
              leaf nas-port-type-user-defined {
                description 'Nas-port-type is user defined value (20~255)' ;
                type uint32 {
                  range 20..255 ;

                }

              }

            }

          }

          container dhcpv4-authen-on-up {
            status obsolete {
              ncd:revise-date 2019-01-09 ;
            }

            description 'Configure DHCPv4 type of username,domain-name and password' ;
            choice username-type {
              description 'Configure auth-on-up username type' ;
              case option82 {
                status obsolete {
                  ncd:revise-date 2019-01-09 ;
                }

                description 'Use the option82,mac-option82 or option82-default as user name type' ;
                leaf option82-username-type {
                  type enumeration {
                    enum option82 {
                      value 4 ;
                      description 'Use the option82 context as user name' ;
                    }

                    enum mac-option82 {
                      value 2 ;
                      description 'Use the mac and option82 context as user name' ;
                    }

                    enum option82-default {
                      value 7 ;
                      description 'Use option82 first,default second as user name' ;
                    }

                  }

                }

                leaf none-space {
                  description 'Transalte space to a minus sign' ;
                  type enumeration {
                    enum enable {
                      value 1 ;
                    }

                    enum disable {
                      value 0 ;
                    }

                  }

                  default disable ;
                }

                leaf op82-domain-type {
                  type enumeration {
                    enum optionstring {
                      value 3 ;
                      description 'Use the option60 context as domain name' ;
                    }

                  }

                }

                leaf op82-password-type {
                  type enumeration {
                    enum config {
                      value 1 ;
                      description 'Configure password' ;
                    }

                    enum mac {
                      value 2 ;
                      description 'Use the mac as password' ;
                    }

                    enum optionstring {
                      value 3 ;
                      description 'Use the option60 context as password' ;
                    }

                  }

                }

                leaf op82-password {
                  description 'Password' ;
                  type string {
                    length 1..31 ;

                  }

                }

              }

              case option60 {
                status obsolete {
                  ncd:revise-date 2019-01-09 ;
                }

                description 'Use the option60,mac-option60 or default as user name type' ;
                leaf option60-username-type {
                  type enumeration {
                    enum option60 {
                      value 3 ;
                      description 'Use the option60 context as user name' ;
                    }

                    enum mac-option60 {
                      value 5 ;
                      description 'Use the mac and option60 context as user name' ;
                    }

                    enum default {
                      value 6 ;
                      description 'Use the default as user name' ;
                    }

                  }

                }

                leaf op60-domain-type {
                  type enumeration {
                    enum optionstring {
                      value 3 ;
                      description 'Use the option60 context as domain name' ;
                    }

                  }

                }

                leaf op60-password-type {
                  type enumeration {
                    enum config {
                      value 1 ;
                      description 'Configure password' ;
                    }

                    enum mac {
                      value 2 ;
                      description 'Use the mac as password' ;
                    }

                    enum optionstring {
                      value 3 ;
                      description 'Use the option60 context as password' ;
                    }

                  }

                }

                leaf op60-password {
                  description 'Password' ;
                  type string {
                    length 1..31 ;

                  }

                }

              }

              case mac {
                status obsolete {
                  ncd:revise-date 2019-01-09 ;
                }

                description 'Use the mac as user name' ;
                leaf mac-username-type {
                  description 'Use the mac as user name' ;
                  type enumeration {
                    enum mac {
                      value 1 ;
                    }

                  }

                }

                container mac-domain {
                  choice domain-type {
                    case optionparse {
                      leaf domain-type-optionparse {
                        description 'Parse option60 context as domain/password' ;
                        type enumeration {
                          enum optionparse {
                            value 1 ;
                            description 'Parse option60 context as domain/password' ;
                          }

                        }

                        default optionparse ;
                      }

                    }

                    case other {
                      leaf mac-domain-type {
                        type enumeration {
                          enum option {
                            value 2 ;
                            description 'Use the option60 as domain name' ;
                          }

                          enum optionstring {
                            value 3 ;
                            description 'Use the option60 context as domain name' ;
                          }

                        }

                      }

                      leaf mac-password-type {
                        type enumeration {
                          enum config {
                            value 1 ;
                            description 'Configure password' ;
                          }

                          enum mac {
                            value 2 ;
                            description 'Use the mac as password' ;
                          }

                          enum optionstring {
                            value 3 ;
                            description 'Use the option60 context as password' ;
                          }

                        }

                      }

                      leaf mac-password {
                        description 'Password' ;
                        type string {
                          length 1..31 ;

                        }

                      }

                    }

                  }

                }

              }

            }

          }

          container dhcpv6-authen-on-up {
            status obsolete {
              ncd:revise-date 2019-01-09 ;
            }

            description 'Configure DHCPv6 type of username,domain-name and password' ;
            choice username-type {
              status obsolete {
                ncd:revise-date 2019-01-09 ;
              }

              description 'Configure auth-on-up username type' ;
              case option16 {
                status obsolete {
                  ncd:revise-date 2019-01-09 ;
                }

                description 'Use option16 context as user name' ;
                leaf op16-username-type {
                  description 'Configure auth-on-up username type' ;
                  type enumeration {
                    enum option16 {
                      value 4 ;
                      description 'Use option16 context as user name' ;
                    }

                  }

                }

                leaf op16-domain-type {
                  description 'Configure auth-on-up domain type' ;
                  type enumeration {
                    enum optionstring {
                      value 3 ;
                      description 'Use the option17 context as domain name' ;
                    }

                  }

                }

                leaf op16-password-type {
                  description 'Password type' ;
                  type enumeration {
                    enum config {
                      value 1 ;
                      description 'Configure password' ;
                    }

                    enum mac {
                      value 2 ;
                      description 'Use the mac as password' ;
                    }

                    enum optionstring {
                      value 3 ;
                      description 'Use the option16 context as password' ;
                    }

                  }

                }

                leaf op16-password {
                  description 'Password' ;
                  type string {
                    length 1..31 ;

                  }

                }

                leaf publicity {
                  description 'Proclaimed in writing' ;
                  type enumeration {
                    enum enable {
                      value 1 ;
                    }

                    enum disable {
                      value 0 ;
                    }

                  }

                  default disable ;
                }

              }

              case option {
                status obsolete {
                  ncd:revise-date 2019-01-09 ;
                }

                description 'Configure auth-on-up username typeoption17 or option18' ;
                leaf option-username-type {
                  description 'Configure auth-on-up username type' ;
                  type enumeration {
                    enum option17 {
                      value 3 ;
                      description 'Use option17 context as user name' ;
                    }

                    enum mac-option18 {
                      value 2 ;
                      description 'Use the mac and option18 context as user name' ;
                    }

                  }

                }

                leaf option-domain-type {
                  description 'Configure auth-on-up domain type' ;
                  type enumeration {
                    enum optionstring {
                      value 3 ;
                      description 'Use the option17 context as domain name' ;
                    }

                  }

                }

                leaf option-password-type {
                  description 'Password type' ;
                  type enumeration {
                    enum config {
                      value 1 ;
                      description 'Configure password' ;
                    }

                    enum mac {
                      value 2 ;
                      description 'Use the mac as password' ;
                    }

                    enum optionstring {
                      value 3 ;
                      description 'Use the option16 context as password' ;
                    }

                  }

                }

                leaf option-password {
                  description 'Password' ;
                  type string {
                    length 1..31 ;

                  }

                }

              }

              case mac {
                status obsolete {
                  ncd:revise-date 2019-01-09 ;
                }

                leaf mac-username-type {
                  description 'Configure auth-on-up username type mac' ;
                  type enumeration {
                    enum mac {
                      value 1 ;
                    }

                  }

                }

                container mac-domain {
                  description 'Configure auth-on-up domain type' ;
                  choice domain-type {
                    description 'Configure auth-on-up domain type' ;
                    case optionparse {
                      description 'Parse option17 context as domain/password' ;
                      leaf domain-type-optionparse {
                        description 'Parse option17 context as domain/password' ;
                        type enumeration {
                          enum optionparse {
                            value 1 ;
                            description 'Parse option17 context as domain/password' ;
                          }

                        }

                        default optionparse ;
                      }

                    }

                    case other {
                      description 'Configure auth-on-up domain type' ;
                      leaf mac-domain-type {
                        description 'Configure auth-on-up domain type' ;
                        type enumeration {
                          enum option {
                            value 2 ;
                            description 'Use the option17 as domain name' ;
                          }

                          enum optionstring {
                            value 3 ;
                            description 'Use the option17 context as domain name' ;
                          }

                        }

                      }

                      leaf mac-password-type {
                        description 'Password type' ;
                        type enumeration {
                          enum config {
                            value 1 ;
                            description 'Configure password' ;
                          }

                          enum mac {
                            value 2 ;
                            description 'Use the mac as password' ;
                          }

                          enum optionstring {
                            value 3 ;
                            description 'Use the option16 context as password' ;
                          }

                        }

                      }

                      leaf mac-password {
                        description 'Password' ;
                        type string {
                          length 1..31 ;

                        }

                      }

                    }

                  }

                }

              }

            }

          }

          container dhcp-v4-authen-on-up-new {
            choice username-types {
              description 'Configure auth-on-up username type' ;
              default username-type ;
              case optionparse {
                leaf optionparse {
                  type enumeration {
                    enum optionparse {
                      value 9 ;
                    }

                  }

                }

              }

              case username-type {
                description 'Use the default, fieldvalue, mac or option61 as user name type' ;
                leaf name-type {
                  description 'default, fieldvalue, mac or option61' ;
                  type enumeration {
                    enum option61 {
                      value 8 ;
                      description 'case option61' ;
                    }

                    enum default {
                      value 6 ;
                      description 'case default' ;
                    }

                    enum mac {
                      value 1 ;
                      description 'case mac' ;
                    }

                    enum fieldvalue {
                      value 10 ;
                      description 'case fieldvalue' ;
                    }

                  }

                  default mac ;
                }

                container domain-types {
                  choice domain-types {
                    default optionparse ;
                    case domain-config {
                      leaf domainconfig {
                        type enumeration {
                          enum config {
                            value 7 ;
                          }

                        }

                      }

                      leaf domain-name {
                        type string {
                          length 1..31 ;

                        }

                      }

                      container domain-config-password {
                        choice password-types {
                          case password-type {
                            leaf passwordtype {
                              type enumeration {
                                enum mac {
                                  value 2 ;
                                }

                                enum optionstring {
                                  value 3 ;
                                }

                                enum fieldvalue {
                                  value 5 ;
                                }

                              }

                            }

                          }

                          case password-config {
                            leaf password-config {
                              type enumeration {
                                enum config {
                                  value 1 ;
                                }

                              }

                            }

                            container passwd-or-encrypasswd {
                              choice choose-password {
                                case passwd {
                                  leaf password-ex {
                                    type string {
                                      length 1..31 ;

                                    }

                                  }

                                  leaf showclear {
                                    status obsolete {
                                      ncd:revise-date 2020-12-16 ;
                                    }

                                    type uint8 {
                                      range 0..3 ;

                                    }

                                  }

                                }

                                case encry-passwd {
                                  leaf encrypted_passwd {
                                    type string {
                                      length 0..84 ;

                                    }

                                  }

                                }

                              }

                            }

                          }

                        }

                      }

                    }

                    case domain-type {
                      leaf domain-type {
                        type enumeration {
                          enum fieldvalue {
                            value 8 ;
                          }

                          enum option {
                            value 2 ;
                          }

                          enum optionstring {
                            value 3 ;
                          }

                        }

                      }

                      container password-types {
                        choice password-types {
                          case password-type {
                            leaf passwordtype {
                              type enumeration {
                                enum mac {
                                  value 2 ;
                                }

                                enum optionstring {
                                  value 3 ;
                                }

                                enum fieldvalue {
                                  value 5 ;
                                }

                              }

                            }

                          }

                          case password-config {
                            leaf password-config {
                              type enumeration {
                                enum config {
                                  value 1 ;
                                }

                              }

                            }

                            container passwd-or-encrypasswd {
                              choice choose-password {
                                case passwd {
                                  leaf password-ex {
                                    type string {
                                      length 1..31 ;

                                    }

                                  }

                                  leaf showclear {
                                    status obsolete {
                                      ncd:revise-date 2020-12-16 ;
                                    }

                                    type uint8 {
                                      range 0..3 ;

                                    }

                                  }

                                }

                                case encry-passwd {
                                  leaf encrypted_passwd {
                                    type string {
                                      length 0..84 ;

                                    }

                                  }

                                }

                              }

                            }

                          }

                        }

                      }

                    }

                    case optionparse {
                      leaf optionparse {
                        type enumeration {
                          enum optionparse {
                            value 1 ;
                          }

                        }

                      }

                    }

                  }

                }

              }

              case mac-option60-type {
                leaf mac-option60-type {
                  type enumeration {
                    enum mac-option60 {
                      value 5 ;
                    }

                  }

                }

                leaf encrypted {
                  type enumeration {
                    enum enable {
                      value 1 ;
                    }

                    enum disable {
                      value 0 ;
                    }

                  }

                  default disable ;
                }

                leaf delimiter {
                  type enumeration {
                    enum @ {
                      value 64 ;
                    }

                    enum "#" {
                      value 35 ;
                    }

                    enum "%" {
                      value 37 ;
                    }

                    enum "/" {
                      value 47 ;
                    }

                    enum null {
                      value 0 ;
                    }

                  }

                }

                leaf default-option60 {
                  description "These characters's ASCII unicode must be between 0x21-0x3E / 0x40-0x7E." ;
                  type string {
                    length 1..31 ;

                  }

                }

                container mac-optin60-domain {
                  choice domain-types {
                    default optionparse ;
                    case domain-config {
                      leaf domainconfig {
                        type enumeration {
                          enum config {
                            value 7 ;
                          }

                        }

                      }

                      leaf domain-name {
                        type string {
                          length 1..31 ;

                        }

                      }

                      container domain-config-password {
                        choice password-types {
                          case password-type {
                            leaf passwordtype {
                              type enumeration {
                                enum mac {
                                  value 2 ;
                                }

                                enum optionstring {
                                  value 3 ;
                                }

                                enum fieldvalue {
                                  value 5 ;
                                }

                              }

                            }

                          }

                          case password-config {
                            leaf password-config {
                              type enumeration {
                                enum config {
                                  value 1 ;
                                }

                              }

                            }

                            container passwd-or-encrypasswd {
                              choice choose-password {
                                case passwd {
                                  leaf password-ex {
                                    type string {
                                      length 1..31 ;

                                    }

                                  }

                                  leaf showclear {
                                    status obsolete {
                                      ncd:revise-date 2020-12-16 ;
                                    }

                                    type uint8 {
                                      range 0..3 ;

                                    }

                                  }

                                }

                                case encry-passwd {
                                  leaf encrypted_passwd {
                                    type string {
                                      length 0..84 ;

                                    }

                                  }

                                }

                              }

                            }

                          }

                        }

                      }

                    }

                    case domain-type {
                      leaf domain-type {
                        type enumeration {
                          enum fieldvalue {
                            value 8 ;
                          }

                          enum option {
                            value 2 ;
                          }

                          enum optionstring {
                            value 3 ;
                          }

                        }

                      }

                      container password-types {
                        choice password-types {
                          case password-type {
                            leaf passwordtype {
                              type enumeration {
                                enum mac {
                                  value 2 ;
                                }

                                enum optionstring {
                                  value 3 ;
                                }

                                enum fieldvalue {
                                  value 5 ;
                                }

                              }

                            }

                          }

                          case password-config {
                            leaf password-config {
                              type enumeration {
                                enum config {
                                  value 1 ;
                                }

                              }

                            }

                            container passwd-or-encrypasswd {
                              choice choose-password {
                                case passwd {
                                  leaf password-ex {
                                    type string {
                                      length 1..31 ;

                                    }

                                  }

                                  leaf showclear {
                                    status obsolete {
                                      ncd:revise-date 2020-12-16 ;
                                    }

                                    type uint8 {
                                      range 0..3 ;

                                    }

                                  }

                                }

                                case encry-passwd {
                                  leaf encrypted_passwd {
                                    type string {
                                      length 0..84 ;

                                    }

                                  }

                                }

                              }

                            }

                          }

                        }

                      }

                    }

                    case optionparse {
                      leaf optionparse {
                        type enumeration {
                          enum optionparse {
                            value 1 ;
                          }

                        }

                      }

                    }

                  }

                }

              }

              case option82-type {
                leaf option82-type {
                  type enumeration {
                    enum option82 {
                      value 4 ;
                    }

                    enum mac-option82 {
                      value 2 ;
                    }

                    enum option82-default {
                      value 7 ;
                    }

                  }

                }

                leaf none-space {
                  type enumeration {
                    enum enable {
                      value 1 ;
                    }

                    enum disable {
                      value 0 ;
                    }

                  }

                  default disable ;
                }

                container option82-domain {
                  choice domain-types {
                    case optionparse {
                      leaf optionparse {
                        type enumeration {
                          enum optionparse {
                            value 1 ;
                          }

                        }

                      }

                    }

                    case domain-type {
                      leaf domain-type {
                        type enumeration {
                          enum fieldvalue {
                            value 8 ;
                          }

                          enum option {
                            value 2 ;
                          }

                          enum optionstring {
                            value 3 ;
                          }

                        }

                      }

                      container password-types {
                        choice password-types {
                          case password-type {
                            leaf passwordtype {
                              type enumeration {
                                enum mac {
                                  value 2 ;
                                }

                                enum optionstring {
                                  value 3 ;
                                }

                                enum fieldvalue {
                                  value 5 ;
                                }

                              }

                            }

                          }

                          case password-config {
                            leaf password-config {
                              type enumeration {
                                enum config {
                                  value 1 ;
                                }

                              }

                            }

                            container passwd-or-encrypasswd {
                              choice choose-password {
                                case passwd {
                                  leaf password-ex {
                                    type string {
                                      length 1..31 ;

                                    }

                                  }

                                  leaf showclear {
                                    status obsolete {
                                      ncd:revise-date 2020-12-16 ;
                                    }

                                    type uint8 {
                                      range 0..3 ;

                                    }

                                  }

                                }

                                case encry-passwd {
                                  leaf encrypted_passwd {
                                    type string {
                                      length 0..84 ;

                                    }

                                  }

                                }

                              }

                            }

                          }

                        }

                      }

                    }

                    case domain-config {
                      leaf domain-config {
                        type enumeration {
                          enum config {
                            value 7 ;
                          }

                        }

                      }

                      leaf domain-name {
                        type string {
                          length 1..31 ;

                        }

                      }

                      container domain-config-password {
                        choice password-types {
                          case password-type {
                            leaf passwordtype {
                              type enumeration {
                                enum mac {
                                  value 2 ;
                                }

                                enum optionstring {
                                  value 3 ;
                                }

                                enum fieldvalue {
                                  value 5 ;
                                }

                              }

                            }

                          }

                          case password-config {
                            leaf password-config {
                              type enumeration {
                                enum config {
                                  value 1 ;
                                }

                              }

                            }

                            container passwd-or-encrypasswd {
                              choice choose-password {
                                case passwd {
                                  leaf password-ex {
                                    type string {
                                      length 1..31 ;

                                    }

                                  }

                                  leaf showclear {
                                    status obsolete {
                                      ncd:revise-date 2020-12-16 ;
                                    }

                                    type uint8 {
                                      range 0..3 ;

                                    }

                                  }

                                }

                                case encry-passwd {
                                  leaf encrypted_passwd {
                                    type string {
                                      length 0..84 ;

                                    }

                                  }

                                }

                              }

                            }

                          }

                        }

                      }

                    }

                  }

                }

              }

              case option60-type {
                leaf option60-type {
                  type enumeration {
                    enum option60 {
                      value 3 ;
                    }

                  }

                }

                leaf option60-encrypted {
                  type enumeration {
                    enum enable {
                      value 1 ;
                    }

                    enum disable {
                      value 0 ;
                    }

                  }

                  default disable ;
                }

                container optin60-domain {
                  choice domain-types {
                    case optionparse {
                      leaf optionparse {
                        type enumeration {
                          enum optionparse {
                            value 1 ;
                          }

                        }

                      }

                    }

                    case domain-type {
                      leaf domain-type {
                        type enumeration {
                          enum fieldvalue {
                            value 8 ;
                          }

                          enum option {
                            value 2 ;
                          }

                          enum optionstring {
                            value 3 ;
                          }

                        }

                      }

                      container password-types {
                        choice password-types {
                          case password-type {
                            leaf passwordtype {
                              type enumeration {
                                enum mac {
                                  value 2 ;
                                }

                                enum optionstring {
                                  value 3 ;
                                }

                                enum fieldvalue {
                                  value 5 ;
                                }

                              }

                            }

                          }

                          case password-config {
                            leaf password-config {
                              type enumeration {
                                enum config {
                                  value 1 ;
                                }

                              }

                            }

                            container passwd-or-encrypasswd {
                              choice choose-password {
                                case passwd {
                                  leaf password-ex {
                                    type string {
                                      length 1..31 ;

                                    }

                                  }

                                  leaf showclear {
                                    status obsolete {
                                      ncd:revise-date 2020-12-16 ;
                                    }

                                    type uint8 {
                                      range 0..3 ;

                                    }

                                  }

                                }

                                case encry-passwd {
                                  leaf encrypted_passwd {
                                    type string {
                                      length 0..84 ;

                                    }

                                  }

                                }

                              }

                            }

                          }

                        }

                      }

                    }

                    case domain-config {
                      leaf domain-config {
                        type enumeration {
                          enum config {
                            value 7 ;
                          }

                        }

                      }

                      leaf domain-name {
                        type string {
                          length 1..31 ;

                        }

                      }

                      container domain-config-password {
                        choice password-types {
                          case password-type {
                            leaf passwordtype {
                              type enumeration {
                                enum mac {
                                  value 2 ;
                                }

                                enum optionstring {
                                  value 3 ;
                                }

                                enum fieldvalue {
                                  value 5 ;
                                }

                              }

                            }

                          }

                          case password-config {
                            leaf password-config {
                              type enumeration {
                                enum config {
                                  value 1 ;
                                }

                              }

                            }

                            container passwd-or-encrypasswd {
                              choice choose-password {
                                case passwd {
                                  leaf password-ex {
                                    type string {
                                      length 1..31 ;

                                    }

                                  }

                                  leaf showclear {
                                    status obsolete {
                                      ncd:revise-date 2020-12-16 ;
                                    }

                                    type uint8 {
                                      range 0..3 ;

                                    }

                                  }

                                }

                                case encry-passwd {
                                  leaf encrypted_passwd {
                                    type string {
                                      length 0..84 ;

                                    }

                                  }

                                }

                              }

                            }

                          }

                        }

                      }

                    }

                  }

                }

              }

            }

            ncd:revise-date 2019-01-09 ;
          }

          container dhcp-v6-authen-on-up-new {
            choice username-types {
              default username-type ;
              case username-type {
                leaf name-type {
                  type enumeration {
                    enum option17 {
                      value 3 ;
                    }

                    enum mac {
                      value 1 ;
                    }

                    enum mac-option18 {
                      value 2 ;
                    }

                    enum option18 {
                      value 7 ;
                    }

                    enum multi-option {
                      value 9 ;

                    }

                  }

                  default mac ;
                }

                container domain-types {
                  choice domain-types {
                    default domain-optionparse ;
                    case domain-option {
                      leaf domain-option {
                        type enumeration {
                          enum option16 {
                            value 5 ;
                          }

                          enum option16string {
                            value 6 ;
                          }

                          enum optionstring {
                            value 3 ;
                          }

                          enum option {
                            value 2 ;
                          }

                        }

                      }

                      container password-types {
                        choice password-types {
                          case password-type {
                            leaf passwordtype {
                              type enumeration {
                                enum mac {
                                  value 2 ;
                                }

                                enum optionstring {
                                  value 3 ;
                                }

                                enum option16string {
                                  value 4 ;
                                }

                              }

                            }

                          }

                          case password-config {
                            leaf password-config {
                              type enumeration {
                                enum config {
                                  value 1 ;
                                }

                              }

                            }

                            container passwd-or-encrypasswd {
                              choice choose-password {
                                case passwd {
                                  leaf password-ex {
                                    type string {
                                      length 1..31 ;

                                    }

                                  }

                                  leaf showclear {
                                    status obsolete {
                                      ncd:revise-date 2020-12-16 ;
                                    }

                                    type uint8 {
                                      range 0..3 ;

                                    }

                                  }

                                }

                                case encry-passwd {
                                  leaf encrypted_passwd {
                                    type string {
                                      length 0..84 ;

                                    }

                                  }

                                }

                              }

                            }

                          }

                        }

                      }

                    }

                    case domain-optionparse {
                      leaf domain-optionparse {
                        type enumeration {
                          enum option16parse {
                            value 4 ;
                          }

                          enum optionparse {
                            value 1 ;
                          }

                        }

                      }

                    }

                    case domain-config {
                      leaf domain-config {
                        type enumeration {
                          enum config {
                            value 7 ;
                          }

                        }

                      }

                      leaf domain-name {
                        type string {
                          length 1..31 ;

                        }

                      }

                      container domain-config-password {
                        choice password-types {
                          case password-type {
                            leaf passwordtype {
                              type enumeration {
                                enum mac {
                                  value 2 ;
                                }

                                enum optionstring {
                                  value 3 ;
                                }

                                enum option16string {
                                  value 4 ;
                                }

                              }

                            }

                          }

                          case password-config {
                            leaf password-config {
                              type enumeration {
                                enum config {
                                  value 1 ;
                                }

                              }

                            }

                            container passwd-or-encrypasswd {
                              choice choose-password {
                                case passwd {
                                  leaf password-ex {
                                    type string {
                                      length 1..31 ;

                                    }

                                  }

                                  leaf showclear {
                                    status obsolete {
                                      ncd:revise-date 2020-12-16 ;
                                    }

                                    type uint8 {
                                      range 0..3 ;

                                    }

                                  }

                                }

                                case encry-passwd {
                                  leaf encrypted_passwd {
                                    type string {
                                      length 0..84 ;

                                    }

                                  }

                                }

                              }

                            }

                          }

                        }

                      }

                    }

                  }

                }

              }

              case option-parse {
                leaf option-parse-type {
                  type enumeration {
                    enum option16parse {
                      value 5 ;
                    }

                    enum option17parse {
                      value 6 ;
                    }

                  }

                }

              }

              case mac-option16-type {
                leaf mac-option16-type {
                  type enumeration {
                    enum mac-option16 {
                      value 8 ;
                    }

                  }

                }

                leaf encrypted {
                  type enumeration {
                    enum enable {
                      value 1 ;
                    }

                    enum disable {
                      value 0 ;
                    }

                  }

                  default disable ;
                }

                leaf delimiter {
                  type enumeration {
                    enum @ {
                      value 64 ;
                    }

                    enum "#" {
                      value 35 ;
                    }

                    enum "%" {
                      value 37 ;
                    }

                    enum "/" {
                      value 47 ;
                    }

                    enum null {
                      value 0 ;
                    }

                  }

                }

                leaf default-option16 {
                  description "These characters's ASCII unicode must be between 0x21-0x3E / 0x40-0x7E." ;
                  type string {
                    length 1..31 ;

                  }

                }

                container mac-option16-domain {
                  choice domain-types {
                    default domain-optionparse ;
                    case domain-option {
                      leaf domain-option {
                        type enumeration {
                          enum option16 {
                            value 5 ;
                          }

                          enum option16string {
                            value 6 ;
                          }

                          enum optionstring {
                            value 3 ;
                          }

                          enum option {
                            value 2 ;
                          }

                        }

                      }

                      container password-types {
                        choice password-types {
                          case password-type {
                            leaf passwordtype {
                              type enumeration {
                                enum mac {
                                  value 2 ;
                                }

                                enum optionstring {
                                  value 3 ;
                                }

                                enum option16string {
                                  value 4 ;
                                }

                              }

                            }

                          }

                          case password-config {
                            leaf password-config {
                              type enumeration {
                                enum config {
                                  value 1 ;
                                }

                              }

                            }

                            container passwd-or-encrypasswd {
                              choice choose-password {
                                case passwd {
                                  leaf password-ex {
                                    type string {
                                      length 1..31 ;

                                    }

                                  }

                                  leaf showclear {
                                    status obsolete {
                                      ncd:revise-date 2020-12-16 ;
                                    }

                                    type uint8 {
                                      range 0..3 ;

                                    }

                                  }

                                }

                                case encry-passwd {
                                  leaf encrypted_passwd {
                                    type string {
                                      length 0..84 ;

                                    }

                                  }

                                }

                              }

                            }

                          }

                        }

                      }

                    }

                    case domain-optionparse {
                      leaf domain-optionparse {
                        type enumeration {
                          enum option16parse {
                            value 4 ;
                          }

                          enum optionparse {
                            value 1 ;
                          }

                        }

                      }

                    }

                    case domain-config {
                      leaf domain-config {
                        type enumeration {
                          enum config {
                            value 7 ;
                          }

                        }

                      }

                      leaf domain-name {
                        type string {
                          length 1..31 ;

                        }

                      }

                      container domain-config-password {
                        choice password-types {
                          case password-type {
                            leaf passwordtype {
                              type enumeration {
                                enum mac {
                                  value 2 ;
                                }

                                enum optionstring {
                                  value 3 ;
                                }

                                enum option16string {
                                  value 4 ;
                                }

                              }

                            }

                          }

                          case password-config {
                            leaf password-config {
                              type enumeration {
                                enum config {
                                  value 1 ;
                                }

                              }

                            }

                            container passwd-or-encrypasswd {
                              choice choose-password {
                                case passwd {
                                  leaf password-ex {
                                    type string {
                                      length 1..31 ;

                                    }

                                  }

                                  leaf showclear {
                                    status obsolete {
                                      ncd:revise-date 2020-12-16 ;
                                    }

                                    type uint8 {
                                      range 0..3 ;

                                    }

                                  }

                                }

                                case encry-passwd {
                                  leaf encrypted_passwd {
                                    type string {
                                      length 0..84 ;

                                    }

                                  }

                                }

                              }

                            }

                          }

                        }

                      }

                    }

                  }

                }

                ncd:revise-date 2019-08-14 ;
              }

              case option16-type {
                leaf option16-type {
                  type enumeration {
                    enum option16 {
                      value 4 ;
                    }

                  }

                }

                leaf option16-encrypted {
                  type enumeration {
                    enum enable {
                      value 1 ;
                    }

                    enum disable {
                      value 0 ;
                    }

                  }

                  default disable ;
                }

                container option16-domain-type {
                  choice domain-types {
                    default domain-optionparse ;
                    case domain-option {
                      leaf domain-option {
                        type enumeration {
                          enum option16 {
                            value 5 ;
                          }

                          enum option16string {
                            value 6 ;
                          }

                          enum optionstring {
                            value 3 ;
                          }

                          enum option {
                            value 2 ;
                          }

                        }

                      }

                      container password-types {
                        choice password-types {
                          case password-type {
                            leaf passwordtype {
                              type enumeration {
                                enum mac {
                                  value 2 ;
                                }

                                enum optionstring {
                                  value 3 ;
                                }

                                enum option16string {
                                  value 4 ;
                                }

                              }

                            }

                          }

                          case password-config {
                            leaf password-config {
                              type enumeration {
                                enum config {
                                  value 1 ;
                                }

                              }

                            }

                            container passwd-or-encrypasswd {
                              choice choose-password {
                                case passwd {
                                  leaf password-ex {
                                    type string {
                                      length 1..31 ;

                                    }

                                  }

                                  leaf showclear {
                                    status obsolete {
                                      ncd:revise-date 2020-12-16 ;
                                    }

                                    type uint8 {
                                      range 0..3 ;

                                    }

                                  }

                                }

                                case encry-passwd {
                                  leaf encrypted_passwd {
                                    type string {
                                      length 0..84 ;

                                    }

                                  }

                                }

                              }

                            }

                          }

                        }

                      }

                    }

                    case domain-optionparse {
                      leaf domain-optionparse {
                        type enumeration {
                          enum option16parse {
                            value 4 ;
                          }

                          enum optionparse {
                            value 1 ;
                          }

                        }

                      }

                    }

                    case domain-config {
                      leaf domain-config {
                        type enumeration {
                          enum config {
                            value 7 ;
                          }

                        }

                      }

                      leaf domain-name {
                        type string {
                          length 1..31 ;

                        }

                      }

                      container domain-config-password {
                        choice password-types {
                          case password-type {
                            leaf passwordtype {
                              type enumeration {
                                enum mac {
                                  value 2 ;
                                }

                                enum optionstring {
                                  value 3 ;
                                }

                                enum option16string {
                                  value 4 ;
                                }

                              }

                            }

                          }

                          case password-config {
                            leaf password-config {
                              type enumeration {
                                enum config {
                                  value 1 ;
                                }

                              }

                            }

                            container passwd-or-encrypasswd {
                              choice choose-password {
                                case passwd {
                                  leaf password-ex {
                                    type string {
                                      length 1..31 ;

                                    }

                                  }

                                  leaf showclear {
                                    status obsolete {
                                      ncd:revise-date 2020-12-16 ;
                                    }

                                    type uint8 {
                                      range 0..3 ;

                                    }

                                  }

                                }

                                case encry-passwd {
                                  leaf encrypted_passwd {
                                    type string {
                                      length 0..84 ;

                                    }

                                  }

                                }

                              }

                            }

                          }

                        }

                      }

                    }

                  }

                }

                ncd:revise-date 2019-08-14 ;
              }

            }

            ncd:revise-date 2019-01-09 ;
          }

          container dhcp-v4-username-type-option {
            presence username ;
            list username {
              key username-type ;
              leaf username-type {
                description 'Configure option parse parameters of username' ;
                type enumeration {
                  enum username-type {
                    value 3 ;
                  }

                }

              }

              leaf option {
                description 'Configure option code of parse' ;
                type uint8 {
                  range 1..255 {
                    description 'Options code(60,82)' ;
                  }
 
                }

                mandatory true ;
              }

              leaf offset {
                description 'Configure offset of option' ;
                type uint8 {
                  range 0..254 {
                    description 'Bytes of option offset' ;
                  }

                }

              }

              choice optionparse {
                case length {
                  leaf length {
                    description 'Configure length of option context' ;
                    type uint8 {
                      range 1..254 {
                        description 'Bytes of option context length' ;
                      }

                    }

                  }

                }

                case sub-option {
                  leaf sub-option-code {
                    description 'Configure sub option code of parse' ;
                    type uint8 {
                      range 1..255 {
                        description 'Sub options code' ;
                      }

                    }

                    mandatory true ;
                  }

                  container option-container {
                    choice optionparse2 {
                      case sub-offset {
                        leaf sub-offset {
                          description 'Configure offset of sub option value' ;
                          type uint8 {
                            range 0..254 {
                              description 'Bytes of sub option value offset' ;
                            }

                          }

                        }

                        leaf sub-length {
                          description 'Configure length of sub option context' ;
                          type uint8 {
                            range 0..254 {
                              description 'Bytes of sub option context length' ;
                            }

                          }

                        }

                      }

                      case sub-option2 {
                        leaf sub-option-code2 {
                          type uint8 {
                            range 1..255 {
                              description 'Sub options code' ;
                            }

                          }

                          description 'Configure sub option code of parse' ;
                        }

                      }

                    }

                    ncd:revise-date 2025-04-21 ;
                  }

                }

              }

            }

            ncd:revise-date 2019-07-10 ;
          }

          container dhcp-v4-domain-type-option {
            description 'Configure option parse parameters of domain' ;
            presence domain ;
            list domain {
              key domain-type ;
              leaf domain-type {
                description 'Configure option parse parameters of domain' ;
                type enumeration {
                  enum domain-type {
                    value 1 ;
                  }

                }

              }

              leaf option {
                description 'Configure option code of parse' ;
                type uint8 {
                  range 1..255 {
                    description 'Options code(60.82)' ;
                  }

                }

                mandatory true ;
              }

              leaf offset {
                description 'Configure offset of option' ;
                type uint8 {
                  range 0..254 {
                    description 'Bytes of option offset' ;
                  }

                }

              }

              choice optionparse {
                case length {
                  leaf length {
                    description 'Configure length of option context' ;
                    type uint8 {
                      range 1..254 {
                        description 'Bytes of option context length' ;
                      }

                    }

                  }

                }

                case sub-option {
                  leaf sub-option-code {
                    description 'Configure sub option code of parse' ;
                    type uint8 {
                      range 1..255 {
                        description 'Sub options code' ;
                      }

                    }

                    mandatory true ;
                  }

                  leaf sub-offset {
                    description 'Configure offset of sub option value' ;
                    type uint8 {
                      range 0..254 {
                        description 'Bytes of sub option value offset' ;
                      }

                    }

                  }

                  leaf sub-length {
                    description 'Configure length of sub option context' ;
                    type uint8 {
                      range 0..254 {
                        description 'Bytes of sub option context length' ;
                      }

                    }

                  }

                }

              }

            }

            ncd:revise-date 2019-07-10 ;
          }

          container dhcp-v4-password-type-option {
            description 'Configure option parse parameters of passowrd' ;
            presence password ;
            list password {
              key password-type ;
              leaf password-type {
                description 'Configure option parse parameters of domain' ;
                type enumeration {
                  enum password-type {
                    value 2 ;
                  }

                }

              }

              leaf option {
                description 'Configure option code of parse' ;
                type uint8 {
                  range 1..255 {
                    description 'Options code(60.82)' ;
                  }

                }

                mandatory true ;
              }

              leaf offset {
                description 'Configure offset of option' ;
                type uint8 {
                  range 0..254 {
                    description 'Bytes of option offset' ;
                  }

                }

              }

              choice optionparse {
                case length {
                  leaf length {
                    description 'Configure length of option context' ;
                    type uint8 {
                      range 1..254 {
                        description 'Bytes of option context length' ;
                      }

                    }

                  }

                }

                case sub-option {
                  leaf sub-option-code {
                    description 'Configure sub option code of parse' ;
                    type uint8 {
                      range 1..255 {
                        description 'Sub options code' ;
                      }

                    }

                    mandatory true ;
                  }

                  leaf sub-offset {
                    description 'Configure offset of sub option value' ;
                    type uint8 {
                      range 0..254 {
                        description 'Bytes of sub option value offset' ;
                      }

                    }

                  }

                  leaf sub-length {
                    description 'Configure length of sub option context' ;
                    type uint8 {
                      range 0..254 {
                        description 'Bytes of sub option context length' ;
                      }

                    }

                  }

                }

              }

            }

            ncd:revise-date 2019-07-10 ;
          }

          container dhcp-v6-domain-type-option {
            list domain {
              key domain-type ;
              leaf domain-type {
                description 'Configure option parse parameters of username' ;
                type enumeration {
                  enum domain-type {
                    value 1 ;
                  }

                }

              }

              leaf option {
                description 'Configure option code of parse' ;
                type uint16 {
                  range 1..255 {
                    description 'Option code(16,17)' ;
                  }

                }

                mandatory true ;
              }

              leaf offset {
                description 'Configure offset of option' ;
                type uint16 {
                  range 0..254 {
                    description 'Bytes of option offset' ;
                  }

                }

              }

              choice optionparse {
                case length {
                  leaf length {
                    description 'Configure length of option context' ;
                    type uint16 {
                      range 1..254 {
                        description 'Bytes of option context length' ;
                      }

                    }

                  }

                }

                case sub-option {
                  leaf sub-option-code {
                    description 'Configure sub option code of parse' ;
                    type uint16 {
                      range 1..255 {
                        description 'Sub options code' ;
                      }

                    }

                    mandatory true ;
                  }

                  leaf sub-offset {
                    description 'Configure offset of sub option value' ;
                    type uint16 {
                      range 0..254 {
                        description 'Bytes of sub option value offset' ;
                      }

                    }

                  }

                  leaf sub-length {
                    description 'Configure length of sub option context' ;
                    type uint16 {
                      range 0..254 {
                        description 'Bytes of sub option context length' ;
                      }

                    }

                  }

                }

              }

            }

            ncd:revise-date 2020-12-16 ;
          }

          container dhcp-v6-password-type-option {
            list password {
              key password-type ;
              leaf password-type {
                description 'Configure option parse parameters of username' ;
                type enumeration {
                  enum password-type {
                    value 2 ;
                  }

                }

              }

              leaf option {
                description 'Configure option code of parse' ;
                type uint16 {
                  range 1..255 {
                    description 'Option code(16,17)' ;
                  }

                }

                mandatory true ;
              }

              leaf offset {
                description 'Configure offset of option' ;
                type uint16 {
                  range 0..254 {
                    description 'Bytes of option offset' ;
                  }

                }

              }

              choice optionparse {
                case length {
                  leaf length {
                    description 'Configure length of option context' ;
                    type uint16 {
                      range 1..254 {
                        description 'Bytes of option context length' ;
                      }

                    }

                  }

                }

                case sub-option {
                  leaf sub-option-code {
                    description 'Configure sub option code of parse' ;
                    type uint16 {
                      range 1..255 {
                        description 'Sub options code' ;
                      }

                    }

                    mandatory true ;
                  }

                  leaf sub-offset {
                    description 'Configure offset of sub option value' ;
                    type uint16 {
                      range 0..254 {
                        description 'Bytes of sub option value offset' ;
                      }

                    }

                  }

                  leaf sub-length {
                    description 'Configure length of sub option context' ;
                    type uint16 {
                      range 0..254 {
                        description 'Bytes of sub option context length' ;
                      }

                    }

                  }

                }

              }

            }

            ncd:revise-date 2020-12-16 ;
          }

          container dhcp-v6-username-type-option {
            list username {
              key username-type ;
              leaf username-type {
                description 'Configure option parse parameters of username' ;
                type enumeration {
                  enum username-type {
                    value 3 ;
                  }

                }

              }

              leaf option {
                description 'Configure option code of parse' ;
                type uint16 {
                  range 1..255 {
                    description 'Option code(16,17,18)' ;
                  }

                }

                mandatory true ;
              }

              leaf offset {
                description 'Configure offset of option' ;
                type uint16 {
                  range 0..254 {
                    description 'Bytes of option offset' ;
                  }

                }

              }

              choice optionparse {
                case length {
                  leaf length {
                    description 'Configure length of option context' ;
                    type uint16 {
                      range 1..254 {
                        description 'Bytes of option context length' ;
                      }

                    }

                  }

                }

                case sub-option {
                  leaf sub-option-code {
                    description 'Configure sub option code of parse' ;
                    type uint16 {
                      range 1..255 {
                        description 'Sub options code' ;
                      }

                    }

                    mandatory true ;
                  }

                  leaf sub-offset {
                    description 'Configure offset of sub option value' ;
                    type uint16 {
                      range 0..254 {
                        description 'Bytes of sub option value offset' ;
                      }

                    }

                  }

                  leaf sub-length {
                    description 'Configure length of sub option context' ;
                    type uint16 {
                      range 0..254 {
                        description 'Bytes of sub option context length' ;
                      }

                    }

                  }

                }

              }

            }

            ncd:revise-date 2019-08-14 ;
          }

          container access-circuit-insert {
            container circuit-source {
              leaf option82 {
                type enumeration {
                  enum option82 {
                    value 1 ;
                  }

                }

              }

              leaf option18 {
                type enumeration {
                  enum option18 {
                    value 2 ;
                  }

                }

              }

              leaf pppoe_plus {
                type enumeration {
                  enum pppoe-plus {
                    value 4 ;
                  }

                }

              }

              leaf vbas {
                type enumeration {
                  enum vbas {
                    value 8 ;
                  }

                }

              }

              choice nas-info {
                default nas-info-basic ;
                case nas-info-basic {
                  leaf nas-basic {
                    type uint8 {
                      range 0..1 ;

                    }

                    default 0 ;
                  }

                }

                case nas-info-user-def-text {
                  leaf nas-user-def-text {
                    type ncd:string-with-blank {
                      length 1..31 ;

                    }

                  }

                }

              }

              choice ani-info {
                default ani-info-basic ;
                case ani-info-basic {
                  leaf ani-basic {
                    type uint8 {
                      range 0..1 ;

                    }

                    default 0 ;
                  }

                }

                case ani-info-user-def-text {
                  leaf ani-user-def-text {
                    type ncd:string-with-blank {
                      length 1..31 ;

                    }

                  }

                }

              }

            }

            leaf force {
              type uint8 {
                range 0..1 ;

              }

            }

            leaf none-info {
              type enumeration {
                enum class8 {
                  value 1 ;
                }

              }

              ncd:revise-date 2021-04-14 ;
            }

            ncd:revise-date 2019-11-20 ;
          }

          container iphostv4-auth-on-up {
            presence iphostv4-auth-on-up ;
            leaf user-name-type {
              type enumeration {
                enum mac {
                  value 1 ;
                }

                enum ip-address {
                  value 2 ;
                }

              }

              mandatory true ;
            }

            leaf domain-name {
              type string {
                length 1..31 ;

              }

              mandatory true ;
            }

            choice password-type {
              mandatory true ;
              case config {
                choice choose-password {
                  case password {
                    leaf passwd {
                      type string {
                        length 1..31 ;

                      }

                    }

                  }

                  case encrypted-password {
                    leaf encryted-passwd {
                      type string {
                        length 64..84 ;

                      }

                    }

                  }

                }

              }

              case types {
                leaf type {
                  type enumeration {
                    enum mac {
                      value 1 ;
                    }

                    enum ip-address {
                      value 2 ;
                    }

                  }

                }

              }

            }

            ncd:revise-date 2020-12-16 ;
          }

          container iphostv6-auth-on-up {
            presence iphostv6-auth-on-up ;
            leaf user-name-type {
              type enumeration {
                enum mac {
                  value 1 ;
                }

                enum ip-address {
                  value 2 ;
                }

              }

              mandatory true ;
            }

            leaf domain-name {
              type string {
                length 1..31 ;

              }

              mandatory true ;
            }

            choice password-type {
              mandatory true ;
              case config {
                choice choose-password {
                  case password {
                    leaf passwd {
                      type string {
                        length 1..31 ;

                      }

                    }

                  }

                  case encrypted-password {
                    leaf encryted-passwd {
                      type string {
                        length 64..84 ;

                      }

                    }

                  }

                }

              }

              case types {
                leaf type {
                  type enumeration {
                    enum mac {
                      value 1 ;
                    }

                  }

                }

              }

            }

            ncd:revise-date 2020-12-16 ;
          }

          leaf ipox-basic-service {
            description 'Configure IPoX basic-service type.' ;
            type enumeration {
              enum ipv4 {
                value 1 ;
                description 'Basic-service IPv4' ;
              }

              enum ipv6 {
                value 2 ;
                description 'Basic-service IPv6' ;
              }

            }

            ncd:revise-date 2021-02-20 ;
          }

          leaf agent-circuit-id-format-ignore-ipox {
            description 'Ipox ignore agent-circuit-id format configuration.' ;
            type enumeration {
              enum ignore-ipox {
                value 1 ;
                description 'Ipox ignore config,use China Telecom format.' ;
              }

              enum no-ignore-ipox {
                value 0 ;
                description 'Ipox use agent-circuit-id format configuration.' ;
              }

            }

            default no-ignore-ipox ;
            ncd:revise-date 2021-04-16 ;
          }

          leaf iphost-vrfname {
            type string {
              length 1..32 ;

            }

            description 'VPN Routing/Forwarding parameters on the interface' ;
            ncd:revise-date 2025-04-18 ;
          }

        }

      }

      container vbuis {
        description 'Configure VBUI parameters.' ;
        list vbui {
          description 'The port configure VBUI info.' ;
          key vbui-name ;
          leaf vbui-name {
            description 'The interface name of VBUI.' ;
            type ncd:ifname {
              length 1..31 ;

            }

          }

          container iphost-detect {
            description 'Configure iphost user detect in VBUI' ;
            presence iphost-detect ;
            leaf count {
              description 'Set iphost user detect counts' ;
              type uint32 {
                range 1..10 ;

              }

              mandatory true ;
            }

            leaf timer {
              description 'Set iphost user detect interval' ;
              type uint32 {
                range 60..864000 ;

              }

              default 180 ;
            }

            leaf no-flowcheck {
              description 'Set iphost user-detect no flow check' ;
              type enumeration {
                enum enable {
                  value 1 ;
                  description 'Send iphost detect packets with no-flowcheck.' ;
                }

                enum disable {
                  value 0 ;
                  description 'Send iphost detect packets with flowcheck.' ;
                }

              }

              ncd:revise-date 2020-01-07 ;
            }

          }

          container ipoxv6-detect {
            description 'Configure IPOXV6 user detect in VBUI' ;
            presence ipoxv6-detect ;
            leaf count {
              description 'Set ipoxv6 user detect counts' ;
              type uint32 {
                range 1..10 ;

              }

              mandatory true ;
            }

            leaf timer {
              description 'Set ipoxv6 user detect interval' ;
              type uint32 {
                range 60..864000 ;

              }

              default 180 ;
            }

            leaf no-flowcheck {
              description 'Set ipoxv6 user-detect no flow check' ;
              type enumeration {
                enum enable {
                  value 1 ;
                  description 'Send IPOXV6 detect packets with no-flowcheck.' ;
                }

                enum disable {
                  value 0 ;
                  description 'Send IPOXV6 detect packets with flowcheck.' ;
                }

              }

              ncd:revise-date 2020-01-07 ;
            }

          }

          leaf multicast-fast-leave-v4 {
            description 'Configure IPv4 multicast leave mode' ;
            type enumeration {
              enum enable {
                value 0 ;
              }

              enum disable {
                value 1 ;
              }

            }

            default enable ;
          }

          leaf multicast-fast-leave-v6 {
            description 'Configure IPv6 multicast leave mode' ;
            type enumeration {
              enum enable {
                value 0 ;
              }

              enum disable {
                value 1 ;
              }

            }

            default enable ;
          }

          leaf redirect-web-acl {
            description 'Configure redirect web acl' ;
            type string {
              length 1..31 {
                description 'acl-name' ;
              }

            }

          }

          leaf redirect-web-acl-ipv6 {
            description 'Configure ipv6 redirect web acl' ;
            type string {
              length 1..31 {
                description 'ipv6-acl-name' ;
              }

            }

          }

          leaf special-acl {
            description 'Config special acl' ;
            type string {
              length 1..31 ;

            }

          }

          leaf special-acl-ipv6 {
            description 'Config ipv6 special acl' ;
            type string {
              length 1..31 {
                description 'ipv6-acl-name' ;
              }

            }

          }

          leaf web-acl {
            description 'Configure web acl' ;
            type string {
              length 1..31 {
                description 'acl-name' ;
              }

            }

          }

          leaf web-acl-ipv6 {
            description 'Configure ipv6 web acl' ;
            type string {
              length 1..31 ;

            }

          }

          leaf web-address-renew {
            description 'Configure web address renew process' ;
            type enumeration {
              enum enable {
                value 1 ;
              }

              enum disable {
                value 0 ;
              }

              enum bas-notify {
                value 2 ;
              }

            }

            default disable ;
          }

          leaf web-force {
            description 'Configure web authentication' ;
            type enumeration {
              enum no_authentication {
                value 1 ;
              }

              enum authentication {
                value 2 ;
                description 'Set web force authentication' ;
              }

              enum disable {
                value 0 ;
                description 'Set web force disable' ;
              }

            }

            default disable ;
          }

          leaf web-offline-address-release {
            description 'Configure web offline address release process' ;
            type enumeration {
              enum enable {
                value 1 ;
                description 'Enable web offline address release process' ;
              }

              enum disable {
                value 0 ;
                description 'Disable web offline address release process' ;
              }

            }

            default disable ;
          }

          leaf web-offline-ipv6-address-release {
            description 'Configure web offline ipv6 address release process' ;
            type enumeration {
              enum enable {
                value 1 ;
                description 'Enable web offline address release process' ;
              }

              enum disable {
                value 0 ;
                description 'Disable web offline address release process' ;
              }

            }

            default disable ;
          }

          container dhcp-user-detect {
            description 'Configure DHCP user detect in VBUI' ;
            presence dhcp-user-detect ;
            leaf count {
              description 'Set DHCP user detect counts' ;
              type uint32 {
                range 1..10 ;

              }

              mandatory true ;
            }

            leaf timer {
              description 'Set DHCP user detect interval' ;
              type uint32 {
                range 60..864000 ;

              }

              default 180 ;
            }

            leaf no-flowcheck {
              description 'Set DHCP no flow check' ;
              type enumeration {
                enum enable {
                  value 1 ;
                  description 'Send dhcp detect packets with no-flowcheck.' ;
                }

                enum disable {
                  value 0 ;
                  description 'Send dhcp detect packets with flowcheck.' ;
                }

              }

              ncd:revise-date 2019-01-15 ;
            }

          }

          choice web-ipv6-servergroup {
            description 'Bind IPv6 web server or server group with the VBUI interface' ;
            case web-ipv6-server {
              description 'Bind web ipv6 server with the VBUI interface' ;
              list web-ipv6-server {
                description 'Bind web ipv6 server with the VBUI interface' ;
                key server-number ;
                leaf server-number {
                  description 'web-ipv6-sever-number' ;
                  type uint8 {
                    range 1..128 ;

                  }

                }

                leaf second {
                  description 'web-ipv6-sever-number-second' ;
                  type enumeration {
                    enum no-second {
                      value 1 ;
                    }

                    enum second {
                      value 2 ;
                    }

                  }

                }

              }

            }

            case web-ipv6-server-group {
              description 'Bind web ipv6 server group with the VBUI interface' ;
              list web-ipv6-server-group {
                description 'Bind web ipv6 server group with the VBUI interface' ;
                key grpid ;
                leaf grpid {
                  description 'web-ipv6-server-group-number' ;
                  type uint8 {
                    range 1..24 ;

                  }

                }

              }

            }

          }

          choice web-servergroup {
            description 'Bind web server or server group with the VBUI interface' ;
            case web-server {
              description 'Bind web server with the VBUI interface' ;
              list web-server {
                description 'Bind web server with the VBUI interface' ;
                key server-number ;
                leaf server-number {
                  description 'web-sever-number' ;
                  type uint8 {
                    range 1..128 ;

                  }

                }

                leaf second {
                  description 'web-sever-number-second' ;
                  type enumeration {
                    enum no-second {
                      value 1 ;
                    }

                    enum second {
                      value 2 ;
                    }

                  }

                }

              }

            }

            case web-server-group {
              description 'Bind web server group with the VBUI interface' ;
              list web-server-group {
                description 'Bind web server group with the VBUI interface' ;
                key grpid ;
                leaf grpid {
                  description 'web-server-group-number' ;
                  type uint8 {
                    range 1..24 ;

                  }

                }

              }

            }

          }

        }

      }

      container l3-accesss {
        description 'Configure L3-accesss parameters.' ;
        list l3-access {
          description 'Configure L3-accesss parameters' ;
          key if-name ;
          leaf if-name {
            description 'Interface name' ;
            type ncd:ifname {
              length 1..31 ;

            }

          }

          leaf bind-sal {
            description 'sal name' ;
            type string {
              length 1..32 ;

            }

          }

          leaf ipoxv4-authe-type {
            description 'authentication type of dhcpv4' ;
            type enumeration {
              enum cir-map {
                value 1 ;
              }

              enum option {
                value 2 ;
              }

              enum web {
                value 3 ;
              }

              enum option-web {
                value 4 ;
              }

            }

          }

          leaf mac-format {
            description "mac's format" ;
            type enumeration {
              enum xx:xx:xx:xx:xx:xx {
                value 2 ;
                description 'Optional format' ;
              }

              enum xx-xx-xx-xx-xx-xx {
                value 1 ;
                description 'Optional format' ;
              }

              enum xxxx:xxxx:xxxx {
                value 3 ;
                description 'Optional format' ;
              }

              enum xxxx-xxxx-xxxx {
                value 4 ;
                description 'Optional format' ;
              }

              enum xxxxxxxxxxxx {
                value 5 ;
                description 'Optional format' ;
              }

              enum xxxx.xxxx.xxxx {
                value 6 ;
                description 'Optional format' ;
              }

              enum xx.xx.xx.xx.xx.xx {
                value 7 ;
                description 'Optional format' ;
              }

              enum user-defined {
                value 8 ;
                description 'Format eg. width 4 delimeter - : xxxx-xxxx-xxxx' ;
              }

            }

            default xx-xx-xx-xx-xx-xx ;
          }

          leaf mac-format-width {
            type enumeration {
              enum 1 {
                value 1 ;
                description 'Set width of mac-fomat 1 character' ;
              }

              enum 2 {
                value 2 ;
                description 'Set width of mac-fomat 2 characters' ;
              }

              enum 3 {
                value 3 ;
                description 'Set width of mac-fomat 3 characters' ;
              }

              enum 4 {
                value 4 ;
                description 'Set width of mac-fomat 4 characters' ;
              }

              enum 6 {
                value 6 ;
                description 'Set width of mac-fomat 6 characters' ;
              }

            }

            ncd:revise-date 2020-08-04 ;
          }

          leaf mac-format-delimiter {
            description "These characters's ASCII unicode must be between 0x21-0x2F/ 0x3A-0x3E/ 0x40/ 0x47-0x60/ 0x67-0x7E." ;
            type enumeration {
              enum "!" {
                value 33 ;
              }

              enum '"' {
                value 34 ;
              }

              enum "#" {
                value 35 ;
              }

              enum "$" {
                value 36 ;
              }

              enum "%" {
                value 37 ;
              }

              enum "&" {
                value 38 ;
              }

              enum "'" {
                value 39 ;
              }

              enum "(" {
                value 40 ;
              }

              enum ")" {
                value 41 ;
              }

              enum "*" {
                value 42 ;
              }

              enum "+" {
                value 43 ;
              }

              enum "," {
                value 44 ;
              }

              enum - {
                value 45 ;
              }

              enum . {
                value 46 ;
              }

              enum "/" {
                value 47 ;
              }

              enum : {
                value 58 ;
              }

              enum ";" {
                value 59 ;
              }

              enum "<" {
                value 60 ;
              }

              enum "=" {
                value 61 ;
              }

              enum ">" {
                value 62 ;
              }

              enum @ {
                value 64 ;
              }

              enum G {
                value 71 ;
              }

              enum H {
                value 72 ;
              }

              enum I {
                value 73 ;
              }

              enum J {
                value 74 ;
              }

              enum K {
                value 75 ;
              }

              enum L {
                value 76 ;
              }

              enum M {
                value 77 ;
              }

              enum N {
                value 78 ;
              }

              enum O {
                value 79 ;
              }

              enum P {
                value 80 ;
              }

              enum Q {
                value 81 ;
              }

              enum R {
                value 82 ;
              }

              enum S {
                value 83 ;
              }

              enum T {
                value 84 ;
              }

              enum U {
                value 85 ;
              }

              enum V {
                value 86 ;
              }

              enum W {
                value 87 ;
              }

              enum X {
                value 88 ;
              }

              enum Y {
                value 89 ;
              }

              enum Z {
                value 90 ;
              }

              enum "[" {
                value 91 ;
              }

              enum '\' {
                value 92 ;
              }

              enum "]" {
                value 93 ;
              }

              enum "^" {
                value 94 ;
              }

              enum _ {
                value 95 ;
              }

              enum "`" {
                value 96 ;
              }

              enum g {
                value 103 ;
              }

              enum h {
                value 104 ;
              }

              enum i {
                value 105 ;
              }

              enum j {
                value 106 ;
              }

              enum k {
                value 107 ;
              }

              enum l {
                value 108 ;
              }

              enum m {
                value 109 ;
              }

              enum n {
                value 110 ;
              }

              enum o {
                value 111 ;
              }

              enum p {
                value 112 ;
              }

              enum q {
                value 113 ;
              }

              enum r {
                value 114 ;
              }

              enum s {
                value 115 ;
              }

              enum t {
                value 116 ;
              }

              enum u {
                value 117 ;
              }

              enum v {
                value 118 ;
              }

              enum w {
                value 119 ;
              }

              enum x {
                value 120 ;
              }

              enum y {
                value 121 ;
              }

              enum z {
                value 122 ;
              }

              enum "{" {
                value 123 ;
              }

              enum "|" {
                value 124 ;
              }

              enum "}" {
                value 125 ;
              }

              enum "~" {
                value 126 ;
              }

            }

            ncd:revise-date 2020-08-04 ;
          }

          leaf mac-match-case {
            description 'majuscule or lowercase of mac' ;
            type enumeration {
              enum majuscule {
                value 1 ;
              }

              enum lowercase {
                value 2 ;
              }

            }

            default majuscule ;
          }

          leaf portrange-poolname {
            description 'the pool name of nat configuration' ;
            type string {
              length 1..31 ;

            }

          }

          leaf pre-domain {
            description 'default domain before authentication' ;
            type string {
              length 1..31 ;

            }

          }

          leaf radius-proxy {
            description 'The switch of radius proxy function' ;
            type enumeration {
              enum disable {
                value 0 ;
              }

              enum protocol-mode {
                value 2 ;
              }

              enum account-mode {
                value 1 ;
              }

            }

            default disable ;
          }

          leaf redirect-web-acl {
            description 'acl of redirect web' ;
            type string {
              length 1..31 ;

            }

          }

          leaf special-acl {
            description 'The name of special acl' ;
            type string {
              length 1..31 ;

            }

          }

          leaf unauthentic-timeout {
            description 'idle time before authentication' ;
            type uint32 {
              range 300..864000 ;

            }

          }

          leaf web-acl {
            description 'The name of web acl' ;
            type string {
              length 1..31 ;

            }

          }

          leaf web-force {
            description 'The switch of force-redirect' ;
            type enumeration {
              enum web-force {
                value 1 ;
              }

              enum authentication {
                value 2 ;
              }

            }

          }

          leaf web-server-group {
            description 'The id of web server' ;
            type uint8 {
              range 1..24 ;

            }

          }

          list access-option60 {
            description 'the information of option60' ;
            key access-option60 ;
            leaf access-option60 {
              description 'the information of option60' ;
              type string {
                length 1..31 ;

              }

            }

          }

          container dhcpv4-authen-on-up {
            status obsolete {
              ncd:revise-date 2019-01-09 ;
            }

            description 'Configure DHCPv4 type of username,domain-name and password' ;
            choice username-type {
              status obsolete {
                ncd:revise-date 2019-01-09 ;
              }

              description 'Configure auth-on-up username type' ;
              case option82 {
                status obsolete {
                  ncd:revise-date 2019-01-09 ;
                }

                description 'Use the option82,mac-option82 or option82-default as user name type' ;
                leaf option82-username-type {
                  description "The type of user's name" ;
                  type enumeration {
                    enum option82 {
                      value 3 ;
                    }

                    enum mac-option82 {
                      value 1 ;
                    }

                    enum option82-default {
                      value 6 ;
                    }

                  }

                }

                leaf none-space {
                  description 'translate space of option82 to "_"' ;
                  type enumeration {
                    enum enable {
                      value 1 ;
                    }

                    enum disable {
                      value 0 ;
                    }

                  }

                  default disable ;
                }

                leaf op82-domain-type {
                  description "domain's type" ;
                  type enumeration {
                    enum optionstring {
                      value 2 ;
                    }

                  }

                }

                leaf op82-password-type {
                  description 'The type of password' ;
                  type enumeration {
                    enum config {
                      value 1 ;
                    }

                    enum mac {
                      value 2 ;
                    }

                    enum optionstring {
                      value 3 ;
                    }

                  }

                }

                leaf op82-password {
                  description 'password' ;
                  type string {
                    length 1..31 ;

                  }

                }

              }

              case option60 {
                status obsolete {
                  ncd:revise-date 2019-01-09 ;
                }

                description 'Use the option60,mac-option60 or default as user name type' ;
                leaf option60-username-type {
                  description "The type of user's name" ;
                  type enumeration {
                    enum option60 {
                      value 2 ;
                    }

                    enum mac-option60 {
                      value 4 ;
                    }

                    enum default {
                      value 5 ;
                    }

                  }

                }

                leaf op60-domain-type {
                  description "domain's type" ;
                  type enumeration {
                    enum optionstring {
                      value 2 ;
                    }

                  }

                }

                leaf op60-password-type {
                  description 'The type of password' ;
                  type enumeration {
                    enum config {
                      value 1 ;
                    }

                    enum mac {
                      value 2 ;
                    }

                    enum optionstring {
                      value 3 ;
                    }

                  }

                }

                leaf op60-password {
                  description 'password' ;
                  type string {
                    length 1..31 ;

                  }

                }

              }

              case mac {
                status obsolete {
                  ncd:revise-date 2019-01-09 ;
                }

                description 'Use the mac as user name' ;
                leaf mac-username-type {
                  description "The type of user's name" ;
                  type enumeration {
                    enum mac {
                      value 0 ;
                    }

                  }

                }

                container mac-domain {
                  description 'Configure auth-on-up domain type' ;
                  choice domain-type {
                    description 'Configure auth-on-up domain type' ;
                    case optionparse {
                      leaf domain-type-optionparse {
                        description "domain's type optionparse" ;
                        type enumeration {
                          enum optionparse {
                            value 0 ;
                          }

                        }

                        default optionparse ;
                      }

                    }

                    case other {
                      leaf mac-domain-type {
                        description "domain's type" ;
                        type enumeration {
                          enum option {
                            value 1 ;
                          }

                          enum optionstring {
                            value 2 ;
                          }

                        }

                      }

                      leaf mac-password-type {
                        description 'The type of password' ;
                        type enumeration {
                          enum config {
                            value 1 ;
                          }

                          enum mac {
                            value 2 ;
                          }

                          enum optionstring {
                            value 3 ;
                          }

                        }

                      }

                      leaf mac-password {
                        description 'password' ;
                        type string {
                          length 1..31 ;

                        }

                      }

                    }

                  }

                }

              }

            }

          }

          container dhcp-v4-authen-on-up-new {
            choice username-types {
              default username-type ;
              case optionparse {
                leaf optionparse {
                  type enumeration {
                    enum optionparse {
                      value 7 ;
                    }

                  }

                }

              }

              case username-type {
                leaf name-type {
                  type enumeration {
                    enum default {
                      value 5 ;
                    }

                    enum fieldvalue {
                      value 8 ;
                    }

                    enum mac {
                      value 0 ;
                    }

                    enum option61 {
                      value 9 ;
                    }

                  }

                  default mac ;
                }

                container domain-types {
                  choice domain-types {
                    default domain-optionparse ;
                    case domain-optionparse {
                      leaf optionparse {
                        type enumeration {
                          enum optionparse {
                            value 0 ;
                          }

                        }

                      }

                    }

                    case domain-config {
                      leaf domain-config {
                        type enumeration {
                          enum config {
                            value 4 ;
                          }

                        }

                      }

                      leaf domain-name {
                        type string {
                          length 1..31 ;

                        }

                      }

                      container password-types {
                        choice password-types {
                          case password-type {
                            leaf passwordtype {
                              type enumeration {
                                enum fieldvalue {
                                  value 4 ;
                                }

                                enum mac {
                                  value 2 ;
                                }

                                enum optionstring {
                                  value 3 ;
                                }

                              }

                            }

                          }

                          case password-config {
                            leaf passwordconfig {
                              type enumeration {
                                enum config {
                                  value 1 ;
                                }

                              }

                            }

                            container passwd-or-encrypasswd {
                              choice choose-password {
                                case passwd {
                                  leaf password-ex {
                                    type string {
                                      length 1..31 ;

                                    }

                                  }

                                  leaf showclear {
                                    status obsolete {
                                      ncd:revise-date 2020-12-16 ;
                                    }

                                    type uint8 {
                                      range 0..3 ;

                                    }

                                  }

                                }

                                case encry-passwd {
                                  leaf encrypted_passwd {
                                    type string {
                                      length 0..84 ;

                                    }

                                  }

                                }

                              }

                            }

                          }

                        }

                      }

                    }

                    case domain-type {
                      leaf domain-type {
                        type enumeration {
                          enum fieldvalue {
                            value 3 ;
                          }

                          enum option {
                            value 1 ;
                          }

                          enum optionstring {
                            value 2 ;
                          }

                        }

                      }

                      container domain-password-types {
                        choice password-types {
                          case password-type {
                            leaf passwordtype {
                              type enumeration {
                                enum fieldvalue {
                                  value 4 ;
                                }

                                enum mac {
                                  value 2 ;
                                }

                                enum optionstring {
                                  value 3 ;
                                }

                              }

                            }

                          }

                          case password-config {
                            leaf passwordconfig {
                              type enumeration {
                                enum config {
                                  value 1 ;
                                }

                              }

                            }

                            container passwd-or-encrypasswd {
                              choice choose-password {
                                case passwd {
                                  leaf password-ex {
                                    type string {
                                      length 1..31 ;

                                    }

                                  }

                                  leaf showclear {
                                    status obsolete {
                                      ncd:revise-date 2020-12-16 ;
                                    }

                                    type uint8 {
                                      range 0..3 ;

                                    }

                                  }

                                }

                                case encry-passwd {
                                  leaf encrypted_passwd {
                                    type string {
                                      length 0..84 ;

                                    }

                                  }

                                }

                              }

                            }

                          }

                        }

                      }

                    }

                  }

                }

              }

              case mac-option60-type {
                leaf mac-option60-type {
                  type enumeration {
                    enum mac-option60 {
                      value 4 ;
                    }

                  }

                }

                leaf encrypted {
                  type enumeration {
                    enum enable {
                      value 1 ;
                    }

                    enum disable {
                      value 0 ;
                    }

                  }

                  default disable ;
                }

                leaf delimiter {
                  type enumeration {
                    enum @ {
                      value 64 ;
                    }

                    enum "#" {
                      value 35 ;
                    }

                    enum "%" {
                      value 37 ;
                    }

                    enum "/" {
                      value 47 ;
                    }

                    enum null {
                      value 0 ;
                    }

                  }

                }

                leaf default-option60 {
                  type string {
                    length 1..31 ;

                  }

                }

                container mac-option60-domain-types {
                  choice domain-types {
                    case domain-optionparse {
                      leaf optionparse {
                        type enumeration {
                          enum optionparse {
                            value 0 ;
                          }

                        }

                      }

                    }

                    case domain-config {
                      leaf domain-config {
                        type enumeration {
                          enum config {
                            value 4 ;
                          }

                        }

                      }

                      leaf domain-name {
                        type string {
                          length 1..31 ;

                        }

                      }

                      container password-types {
                        choice password-types {
                          case password-type {
                            leaf passwordtype {
                              type enumeration {
                                enum fieldvalue {
                                  value 4 ;
                                }

                                enum mac {
                                  value 2 ;
                                }

                                enum optionstring {
                                  value 3 ;
                                }

                              }

                            }

                          }

                          case password-config {
                            leaf passwordconfig {
                              type enumeration {
                                enum config {
                                  value 1 ;
                                }

                              }

                            }

                            container passwd-or-encrypasswd {
                              choice choose-password {
                                case passwd {
                                  leaf password-ex {
                                    type string {
                                      length 1..31 ;

                                    }

                                  }

                                  leaf showclear {
                                    status obsolete {
                                      ncd:revise-date 2020-12-16 ;
                                    }

                                    type uint8 {
                                      range 0..3 ;

                                    }

                                  }

                                }

                                case encry-passwd {
                                  leaf encrypted_passwd {
                                    type string {
                                      length 0..84 ;

                                    }

                                  }

                                }

                              }

                            }

                          }

                        }

                      }

                    }

                    case domain-type {
                      leaf domain-type {
                        type enumeration {
                          enum fieldvalue {
                            value 3 ;
                          }

                          enum option {
                            value 1 ;
                          }

                          enum optionstring {
                            value 2 ;
                          }

                        }

                      }

                      container domain-password-types {
                        choice password-types {
                          case password-type {
                            leaf passwordtype {
                              type enumeration {
                                enum fieldvalue {
                                  value 4 ;
                                }

                                enum mac {
                                  value 2 ;
                                }

                                enum optionstring {
                                  value 3 ;
                                }

                              }

                            }

                          }

                          case password-config {
                            leaf passwordconfig {
                              type enumeration {
                                enum config {
                                  value 1 ;
                                }

                              }

                            }

                            container passwd-or-encrypasswd {
                              choice choose-password {
                                case passwd {
                                  leaf password-ex {
                                    type string {
                                      length 1..31 ;

                                    }

                                  }

                                  leaf showclear {
                                    status obsolete {
                                      ncd:revise-date 2020-12-16 ;
                                    }

                                    type uint8 {
                                      range 0..3 ;

                                    }

                                  }

                                }

                                case encry-passwd {
                                  leaf encrypted_passwd {
                                    type string {
                                      length 0..84 ;

                                    }

                                  }

                                }

                              }

                            }

                          }

                        }

                      }

                    }

                  }

                }

              }

              case option82-type {
                leaf option82-type {
                  type enumeration {
                    enum mac-option82 {
                      value 1 ;
                    }

                    enum option82 {
                      value 3 ;
                    }

                    enum option82-default {
                      value 6 ;
                    }

                  }

                }

                leaf none-space {
                  type enumeration {
                    enum enable {
                      value 1 ;
                    }

                    enum disable {
                      value 0 ;
                    }

                  }

                }

                container option82-domain-types {
                  choice domain-types {
                    case domain-optionparse {
                      leaf optionparse {
                        type enumeration {
                          enum optionparse {
                            value 0 ;
                          }

                        }

                      }

                    }

                    case domain-config {
                      leaf domain-config {
                        type enumeration {
                          enum config {
                            value 4 ;
                          }

                        }

                      }

                      leaf domain-name {
                        type string {
                          length 1..31 ;

                        }

                      }

                      container password-types {
                        choice password-types {
                          case password-type {
                            leaf passwordtype {
                              type enumeration {
                                enum fieldvalue {
                                  value 4 ;
                                }

                                enum mac {
                                  value 2 ;
                                }

                                enum optionstring {
                                  value 3 ;
                                }

                              }

                            }

                          }

                          case password-config {
                            leaf passwordconfig {
                              type enumeration {
                                enum config {
                                  value 1 ;
                                }

                              }

                            }

                            container passwd-or-encrypasswd {
                              choice choose-password {
                                case passwd {
                                  leaf password-ex {
                                    type string {
                                      length 1..31 ;

                                    }

                                  }

                                  leaf showclear {
                                    status obsolete {
                                      ncd:revise-date 2020-12-16 ;
                                    }

                                    type uint8 {
                                      range 0..3 ;

                                    }

                                  }

                                }

                                case encry-passwd {
                                  leaf encrypted_passwd {
                                    type string {
                                      length 0..84 ;

                                    }

                                  }

                                }

                              }

                            }

                          }

                        }

                      }

                    }

                    case domain-type {
                      leaf domain-type {
                        type enumeration {
                          enum fieldvalue {
                            value 3 ;
                          }

                          enum option {
                            value 1 ;
                          }

                          enum optionstring {
                            value 2 ;
                          }

                        }

                      }

                      container domain-password-types {
                        choice password-types {
                          case password-type {
                            leaf passwordtype {
                              type enumeration {
                                enum fieldvalue {
                                  value 4 ;
                                }

                                enum mac {
                                  value 2 ;
                                }

                                enum optionstring {
                                  value 3 ;
                                }

                              }

                            }

                          }

                          case password-config {
                            leaf passwordconfig {
                              type enumeration {
                                enum config {
                                  value 1 ;
                                }

                              }

                            }

                            container passwd-or-encrypasswd {
                              choice choose-password {
                                case passwd {
                                  leaf password-ex {
                                    type string {
                                      length 1..31 ;

                                    }

                                  }

                                  leaf showclear {
                                    status obsolete {
                                      ncd:revise-date 2020-12-16 ;
                                    }

                                    type uint8 {
                                      range 0..3 ;

                                    }

                                  }

                                }

                                case encry-passwd {
                                  leaf encrypted_passwd {
                                    type string {
                                      length 0..84 ;

                                    }

                                  }

                                }

                              }

                            }

                          }

                        }

                      }

                    }

                  }

                }

              }

              case option60-type {
                leaf option60-type {
                  type enumeration {
                    enum option60 {
                      value 2 ;
                    }

                  }

                }

                leaf option60-encrypted {
                  type enumeration {
                    enum enable {
                      value 1 ;
                    }

                    enum disable {
                      value 0 ;
                    }

                  }

                }

                container option60-domain-types {
                  choice domain-types {
                    case domain-optionparse {
                      leaf optionparse {
                        type enumeration {
                          enum optionparse {
                            value 0 ;
                          }

                        }

                      }

                    }

                    case domain-config {
                      leaf domain-config {
                        type enumeration {
                          enum config {
                            value 4 ;
                          }

                        }

                      }

                      leaf domain-name {
                        type string {
                          length 1..31 ;

                        }

                      }

                      container password-types {
                        choice password-types {
                          case password-type {
                            leaf passwordtype {
                              type enumeration {
                                enum fieldvalue {
                                  value 4 ;
                                }

                                enum mac {
                                  value 2 ;
                                }

                                enum optionstring {
                                  value 3 ;
                                }

                              }

                            }

                          }

                          case password-config {
                            leaf passwordconfig {
                              type enumeration {
                                enum config {
                                  value 1 ;
                                }

                              }

                            }

                            container passwd-or-encrypasswd {
                              choice choose-password {
                                case passwd {
                                  leaf password-ex {
                                    type string {
                                      length 1..31 ;

                                    }

                                  }

                                  leaf showclear {
                                    status obsolete {
                                      ncd:revise-date 2020-12-16 ;
                                    }

                                    type uint8 {
                                      range 0..3 ;

                                    }

                                  }

                                }

                                case encry-passwd {
                                  leaf encrypted_passwd {
                                    type string {
                                      length 0..84 ;

                                    }

                                  }

                                }

                              }

                            }

                          }

                        }

                      }

                    }

                    case domain-type {
                      leaf domain-type {
                        type enumeration {
                          enum fieldvalue {
                            value 3 ;
                          }

                          enum option {
                            value 1 ;
                          }

                          enum optionstring {
                            value 2 ;
                          }

                        }

                      }

                      container domain-password-types {
                        choice password-types {
                          case password-type {
                            leaf passwordtype {
                              type enumeration {
                                enum fieldvalue {
                                  value 4 ;
                                }

                                enum mac {
                                  value 2 ;
                                }

                                enum optionstring {
                                  value 3 ;
                                }

                              }

                            }

                          }

                          case password-config {
                            leaf passwordconfig {
                              type enumeration {
                                enum config {
                                  value 1 ;
                                }

                              }

                            }

                            container passwd-or-encrypasswd {
                              choice choose-password {
                                case passwd {
                                  leaf password-ex {
                                    type string {
                                      length 1..31 ;

                                    }

                                  }

                                  leaf showclear {
                                    status obsolete {
                                      ncd:revise-date 2020-12-16 ;
                                    }

                                    type uint8 {
                                      range 0..3 ;

                                    }

                                  }

                                }

                                case encry-passwd {
                                  leaf encrypted_passwd {
                                    type string {
                                      length 0..84 ;

                                    }

                                  }

                                }

                              }

                            }

                          }

                        }

                      }

                    }

                  }

                }

              }

            }

            ncd:revise-date 2019-01-09 ;
          }

          container dhcpv4-username-type-option {
            presence l3username ;
            list l3username {
              key username-type ;
              leaf username-type {
                description 'Configure option parse parameters of username' ;
                type enumeration {
                  enum username-type {
                    value 3 ;
                  }

                }

              }

              leaf option {
                description 'Configure option code of parse' ;
                type uint8 {
                  range 1..255 {
                    description 'Options code(60.82)' ;
                  }

                }

                mandatory true ;
              }

              leaf offset {
                description 'Configure offset of option' ;
                type uint8 {
                  range 0..254 {
                    description 'Bytes of option offset' ;
                  }

                }

              }

              choice optionparse {
                case length {
                  leaf length {
                    description 'Configure length of option context' ;
                    type uint8 {
                      range 1..254 {
                        description 'Bytes of option context length' ;
                      }

                    }

                  }

                }

                case sub-option {
                  leaf sub-option-code {
                    description 'Configure sub option code of parse' ;
                    type uint8 {
                      range 1..255 {
                        description 'Sub options code' ;
                      }

                    }

                    mandatory true ;
                  }

                  leaf sub-offset {
                    description 'Configure offset of sub option value' ;
                    type uint8 {
                      range 0..254 {
                        description 'Bytes of sub option value offset' ;
                      }

                    }

                  }

                  leaf sub-length {
                    description 'Configure length of sub option context' ;
                    type uint8 {
                      range 0..254 {
                        description 'Bytes of sub option context length' ;
                      }

                    }

                  }

                }

              }

            }

            ncd:revise-date 2019-07-10 ;
          }

          container dhcp-v4-domain-type-option {
            description 'Configure option parse parameters of domain' ;
            presence l3domain ;
            list l3domain {
              key domain-type ;
              leaf domain-type {
                description 'Configure option parse parameters of domain' ;
                type enumeration {
                  enum domain-type {
                    value 1 ;
                  }

                }

              }

              leaf option {
                description 'Configure option code of parse' ;
                type uint8 {
                  range 1..255 {
                    description 'Options code(60.82)' ;
                  }

                }

                mandatory true ;
              }

              leaf offset {
                description 'Configure offset of option' ;
                type uint8 {
                  range 0..254 {
                    description 'Bytes of option offset' ;
                  }

                }

              }

              choice optionparse {
                case length {
                  leaf length {
                    description 'Configure length of option context' ;
                    type uint8 {
                      range 1..254 {
                        description 'Bytes of option context length' ;
                      }

                    }

                  }

                }

                case sub-option {
                  leaf sub-option-code {
                    description 'Configure sub option code of parse' ;
                    type uint8 {
                      range 1..255 {
                        description 'Sub options code' ;
                      }

                    }

                    mandatory true ;
                  }

                  leaf sub-offset {
                    description 'Configure offset of sub option value' ;
                    type uint8 {
                      range 0..254 {
                        description 'Bytes of sub option value offset' ;
                      }

                    }

                  }

                  leaf sub-length {
                    description 'Configure length of sub option context' ;
                    type uint8 {
                      range 0..254 {
                        description 'Bytes of sub option context length' ;
                      }

                    }

                  }

                }

              }

            }

            ncd:revise-date 2019-07-10 ;
          }

          container dhcp-v4-password-type-option {
            description 'Configure option parse parameters of passowrd' ;
            presence l3password ;
            list l3password {
              key password-type ;
              leaf password-type {
                description 'Configure option parse parameters of domain' ;
                type enumeration {
                  enum password-type {
                    value 2 ;
                  }

                }

              }

              leaf option {
                description 'Configure option code of parse' ;
                type uint8 {
                  range 1..255 {
                    description 'Options code(60.82)' ;
                  }

                }

                mandatory true ;
              }

              leaf offset {
                description 'Configure offset of option' ;
                type uint8 {
                  range 0..254 {
                    description 'Bytes of option offset' ;
                  }

                }

              }

              choice optionparse {
                case length {
                  leaf length {
                    description 'Configure length of option context' ;
                    type uint8 {
                      range 1..254 {
                        description 'Bytes of option context length' ;
                      }

                    }

                  }

                }

                case sub-option {
                  leaf sub-option-code {
                    description 'Configure sub option code of parse' ;
                    type uint8 {
                      range 1..255 {
                        description 'Sub options code' ;
                      }

                    }

                    mandatory true ;
                  }

                  leaf sub-offset {
                    description 'Configure offset of sub option value' ;
                    type uint8 {
                      range 0..254 {
                        description 'Bytes of sub option value offset' ;
                      }

                    }

                  }

                  leaf sub-length {
                    description 'Configure length of sub option context' ;
                    type uint8 {
                      range 0..254 {
                        description 'Bytes of sub option context length' ;
                      }

                    }

                  }

                }

              }

            }

            ncd:revise-date 2019-07-10 ;
          }

          container access-circuit-insert {
            container circuit-source {
              leaf option82 {
                type enumeration {
                  enum option82 {
                    value 1 ;
                  }

                }

              }

              choice nas-info {
                case nas-info-basic {
                  leaf nas-basic {
                    type uint8 {
                      range 0..1 ;

                    }

                  }

                }

                case nas-info-user-def-text {
                  leaf nas-user-def-text {
                    type ncd:string-with-blank {
                      length 1..31 ;

                    }

                  }

                }

              }

              choice ani-info {
                case ani-info-basic {
                  leaf ani-basic {
                    type uint8 {
                      range 0..1 ;

                    }

                  }

                }

                case ani-info-user-def-text {
                  leaf ani-user-def-text {
                    type ncd:string-with-blank {
                      length 1..31 ;

                    }

                  }

                }

              }

            }

            leaf force {
              type uint8 {
                range 0..1 ;

              }

            }

            leaf none-info {
              type enumeration {
                enum class8 {
                  value 1 ;
                }

              }

              ncd:revise-date 2021-04-14 ;
            }

            ncd:revise-date 2019-11-20 ;
          }

          leaf dhcpv6-suppress {
            description 'DHCPv6 suppress configure' ;
            type enumeration {
              enum ia-nata {
                value 1 ;
                description 'DHCPv6 suppress ia-nata' ;
              }

            }

            ncd:revise-date 2021-02-03 ;
          }

          container ipoxv6-authen-type {
            description 'Configure ipv6 user authentication-type' ;
            leaf dhcp-v6 {
              description 'DHCPv6 user authentication-type' ;
              type enumeration {
                enum cir-map {
                  value 1 ;
                  description 'Circuit authentication' ;
                }

                enum option {
                  value 2 ;
                  description 'Option authentication' ;
                }

              }

            }

            ncd:revise-date 2021-02-26 ;
          }

          container dhcp-v6-authen-on-up {
            choice username-types {
              default username-type ;
              case username-type {
                leaf name-type {
                  type enumeration {
                    enum mac {
                      value 1 ;
                    }

                    enum mac-option18 {
                      value 2 ;
                    }

                    enum option18 {
                      value 7 ;
                    }

                  }

                  default mac ;
                }

                container domain-types {
                  choice domain-types {
                    default domain-optionparse ;
                    case domain-option {
                      leaf domain-option {
                        type enumeration {
                          enum option16 {
                            value 5 ;
                          }

                          enum option16string {
                            value 6 ;
                          }

                        }

                      }

                      container password-types {
                        choice password-types {
                          case password-type {
                            leaf passwordtype {
                              type enumeration {
                                enum mac {
                                  value 2 ;
                                }

                                enum option16string {
                                  value 4 ;
                                }

                              }

                            }

                          }

                          case password-config {
                            leaf password-config {
                              type enumeration {
                                enum config {
                                  value 1 ;
                                }

                              }

                            }

                            container passwd-or-encrypasswd {
                              choice choose-password {
                                case passwd {
                                  leaf password {
                                    type string {
                                      length 1..31 ;

                                    }

                                  }

                                }

                                case encry-passwd {
                                  leaf encrypted_passwd {
                                    type string {
                                      length 64..84 ;

                                    }

                                  }

                                }

                              }

                            }

                          }

                        }

                      }

                    }

                    case domain-optionparse {
                      leaf domain-optionparse {
                        type enumeration {
                          enum option16parse {
                            value 4 ;
                          }

                        }

                      }

                    }

                    case domain-config {
                      leaf domain-config {
                        type enumeration {
                          enum config {
                            value 7 ;
                          }

                        }

                      }

                      leaf domain-name {
                        type string {
                          length 1..31 ;

                        }

                      }

                      container domain-config-password {
                        choice password-types {
                          case password-type {
                            leaf passwordtype {
                              type enumeration {
                                enum mac {
                                  value 2 ;
                                }

                                enum option16string {
                                  value 4 ;
                                }

                              }

                            }

                          }

                          case password-config {
                            leaf password-config {
                              type enumeration {
                                enum config {
                                  value 1 ;
                                }

                              }

                            }

                            container passwd-or-encrypasswd {
                              choice choose-password {
                                case passwd {
                                  leaf password {
                                    type string {
                                      length 1..31 ;

                                    }

                                  }

                                }

                                case encry-passwd {
                                  leaf encrypted_passwd {
                                    type string {
                                      length 64..84 ;

                                    }

                                  }

                                }

                              }

                            }

                          }

                        }

                      }

                    }

                  }

                }

              }

              case option-parse {
                leaf option-parse-type {
                  type enumeration {
                    enum option16parse {
                      value 5 ;
                    }

                  }

                }

              }

              case mac-option16-type {
                leaf mac-option16-type {
                  type enumeration {
                    enum mac-option16 {
                      value 8 ;
                    }

                  }

                }

                leaf encrypted {
                  type enumeration {
                    enum enable {
                      value 1 ;
                    }

                    enum disable {
                      value 0 ;
                    }

                  }

                  default disable ;
                }

                leaf delimiter {
                  type enumeration {
                    enum @ {
                      value 64 ;
                    }

                    enum "#" {
                      value 35 ;
                    }

                    enum "%" {
                      value 37 ;
                    }

                    enum "/" {
                      value 47 ;
                    }

                    enum null {
                      value 0 ;
                    }

                  }

                }

                leaf default-option16 {
                  description "These characters's ASCII unicode must be between 0x21-0x3E / 0x40-0x7E." ;
                  type string {
                    length 1..31 ;

                  }

                }

                container mac-option16-domain {
                  choice domain-types {
                    default domain-optionparse ;
                    case domain-option {
                      leaf domain-option {
                        type enumeration {
                          enum option16 {
                            value 5 ;
                          }

                          enum option16string {
                            value 6 ;
                          }

                        }

                      }

                      container password-types {
                        choice password-types {
                          case password-type {
                            leaf passwordtype {
                              type enumeration {
                                enum mac {
                                  value 2 ;
                                }

                                enum option16string {
                                  value 4 ;
                                }

                              }

                            }

                          }

                          case password-config {
                            leaf password-config {
                              type enumeration {
                                enum config {
                                  value 1 ;
                                }

                              }

                            }

                            container passwd-or-encrypasswd {
                              choice choose-password {
                                case passwd {
                                  leaf password {
                                    type string {
                                      length 1..31 ;

                                    }

                                  }

                                }

                                case encry-passwd {
                                  leaf encrypted_passwd {
                                    type string {
                                      length 64..84 ;

                                    }

                                  }

                                }

                              }

                            }

                          }

                        }

                      }

                    }

                    case domain-optionparse {
                      leaf domain-optionparse {
                        type enumeration {
                          enum option16parse {
                            value 4 ;
                          }

                        }

                      }

                    }

                    case domain-config {
                      leaf domain-config {
                        type enumeration {
                          enum config {
                            value 7 ;
                          }

                        }

                      }

                      leaf domain-name {
                        type string {
                          length 1..31 ;

                        }

                      }

                      container domain-config-password {
                        choice password-types {
                          case password-type {
                            leaf passwordtype {
                              type enumeration {
                                enum mac {
                                  value 2 ;
                                }

                                enum option16string {
                                  value 4 ;
                                }

                              }

                            }

                          }

                          case password-config {
                            leaf password-config {
                              type enumeration {
                                enum config {
                                  value 1 ;
                                }

                              }

                            }

                            container passwd-or-encrypasswd {
                              choice choose-password {
                                case passwd {
                                  leaf password {
                                    type string {
                                      length 1..31 ;

                                    }

                                  }

                                }

                                case encry-passwd {
                                  leaf encrypted_passwd {
                                    type string {
                                      length 64..84 ;

                                    }

                                  }

                                }

                              }

                            }

                          }

                        }

                      }

                    }

                  }

                }

              }

              case option16-type {
                leaf option16-type {
                  type enumeration {
                    enum option16 {
                      value 4 ;
                    }

                  }

                }

                leaf option16-encrypted {
                  type enumeration {
                    enum enable {
                      value 1 ;
                    }

                    enum disable {
                      value 0 ;
                    }

                  }

                  default disable ;
                }

                container option16-domain-type {
                  choice domain-types {
                    default domain-optionparse ;
                    case domain-option {
                      leaf domain-option {
                        type enumeration {
                          enum option16 {
                            value 5 ;
                          }

                          enum option16string {
                            value 6 ;
                          }

                        }

                      }

                      container password-types {
                        choice password-types {
                          case password-type {
                            leaf passwordtype {
                              type enumeration {
                                enum mac {
                                  value 2 ;
                                }

                                enum option16string {
                                  value 4 ;
                                }

                              }

                            }

                          }

                          case password-config {
                            leaf password-config {
                              type enumeration {
                                enum config {
                                  value 1 ;
                                }

                              }

                            }

                            container passwd-or-encrypasswd {
                              choice choose-password {
                                case passwd {
                                  leaf password {
                                    type string {
                                      length 1..31 ;

                                    }

                                  }

                                }

                                case encry-passwd {
                                  leaf encrypted_passwd {
                                    type string {
                                      length 64..84 ;

                                    }

                                  }

                                }

                              }

                            }

                          }

                        }

                      }

                    }

                    case domain-optionparse {
                      leaf domain-optionparse {
                        type enumeration {
                          enum option16parse {
                            value 4 ;
                          }

                        }

                      }

                    }

                    case domain-config {
                      leaf domain-config {
                        type enumeration {
                          enum config {
                            value 7 ;
                          }

                        }

                      }

                      leaf domain-name {
                        type string {
                          length 1..31 ;

                        }

                      }

                      container domain-config-password {
                        choice password-types {
                          case password-type {
                            leaf passwordtype {
                              type enumeration {
                                enum mac {
                                  value 2 ;
                                }

                                enum option16string {
                                  value 4 ;
                                }

                              }

                            }

                          }

                          case password-config {
                            leaf password-config {
                              type enumeration {
                                enum config {
                                  value 1 ;
                                }

                              }

                            }

                            container passwd-or-encrypasswd {
                              choice choose-password {
                                case passwd {
                                  leaf password {
                                    type string {
                                      length 1..31 ;

                                    }

                                  }

                                }

                                case encry-passwd {
                                  leaf encrypted_passwd {
                                    type string {
                                      length 64..84 ;

                                    }

                                  }

                                }

                              }

                            }

                          }

                        }

                      }

                    }

                  }

                }

              }

            }

            ncd:revise-date 2021-02-26 ;
          }

          container dhcp-v6-username-type-option {
            list username {
              key username-type ;
              leaf username-type {
                description 'Configure option parse parameters of username' ;
                type enumeration {
                  enum username-type {
                    value 3 ;
                  }

                }

              }

              leaf option {
                description 'Configure option code of parse' ;
                type uint16 {
                  range 1..255 {
                    description 'Option code(16,18)' ;
                  }

                }

                mandatory true ;
              }

              leaf offset {
                description 'Configure offset of option' ;
                type uint16 {
                  range 0..254 {
                    description 'Bytes of option offset' ;
                  }

                }

              }

              choice optionparse {
                case length {
                  leaf length {
                    description 'Configure length of option context' ;
                    type uint16 {
                      range 1..254 {
                        description 'Bytes of option context length' ;
                      }

                    }

                  }

                }

                case sub-option {
                  leaf sub-option-code {
                    description 'Configure sub option code of parse' ;
                    type uint16 {
                      range 1..255 {
                        description 'Sub options code' ;
                      }

                    }

                    mandatory true ;
                  }

                  leaf sub-offset {
                    description 'Configure offset of sub option value' ;
                    type uint16 {
                      range 0..254 {
                        description 'Bytes of sub option value offset' ;
                      }

                    }

                  }

                  leaf sub-length {
                    description 'Configure length of sub option context' ;
                    type uint16 {
                      range 0..254 {
                        description 'Bytes of sub option context length' ;
                      }

                    }

                  }

                }

              }

            }

            ncd:revise-date 2021-02-26 ;
          }

          container dhcp-v6-domain-type-option {
            list domain {
              key domain-type ;
              leaf domain-type {
                description 'Configure option parse parameters of username' ;
                type enumeration {
                  enum domain-type {
                    value 1 ;
                  }

                }

              }

              leaf option {
                description 'Configure option code of parse' ;
                type uint16 {
                  range 1..255 {
                    description 'Option code(16)' ;
                  }

                }

                mandatory true ;
              }

              leaf offset {
                description 'Configure offset of option' ;
                type uint16 {
                  range 0..254 {
                    description 'Bytes of option offset' ;
                  }

                }

              }

              choice optionparse {
                case length {
                  leaf length {
                    description 'Configure length of option context' ;
                    type uint16 {
                      range 1..254 {
                        description 'Bytes of option context length' ;
                      }

                    }

                  }

                }

                case sub-option {
                  leaf sub-option-code {
                    description 'Configure sub option code of parse' ;
                    type uint16 {
                      range 1..255 {
                        description 'Sub options code' ;
                      }

                    }

                    mandatory true ;
                  }

                  leaf sub-offset {
                    description 'Configure offset of sub option value' ;
                    type uint16 {
                      range 0..254 {
                        description 'Bytes of sub option value offset' ;
                      }

                    }

                  }

                  leaf sub-length {
                    description 'Configure length of sub option context' ;
                    type uint16 {
                      range 0..254 {
                        description 'Bytes of sub option context length' ;
                      }

                    }

                  }

                }

              }

            }

            ncd:revise-date 2021-02-26 ;
          }

          container dhcp-v6-password-type-option {
            list password {
              key password-type ;
              leaf password-type {
                description 'Configure option parse parameters of username' ;
                type enumeration {
                  enum password-type {
                    value 2 ;
                  }

                }

              }

              leaf option {
                description 'Configure option code of parse' ;
                type uint16 {
                  range 1..255 {
                    description 'Option code(16)' ;
                  }

                }

                mandatory true ;
              }

              leaf offset {
                description 'Configure offset of option' ;
                type uint16 {
                  range 0..254 {
                    description 'Bytes of option offset' ;
                  }

                }

              }

              choice optionparse {
                case length {
                  leaf length {
                    description 'Configure length of option context' ;
                    type uint16 {
                      range 1..254 {
                        description 'Bytes of option context length' ;
                      }

                    }

                  }

                }

                case sub-option {
                  leaf sub-option-code {
                    description 'Configure sub option code of parse' ;
                    type uint16 {
                      range 1..255 {
                        description 'Sub options code' ;
                      }

                    }

                    mandatory true ;
                  }

                  leaf sub-offset {
                    description 'Configure offset of sub option value' ;
                    type uint16 {
                      range 0..254 {
                        description 'Bytes of sub option value offset' ;
                      }

                    }

                  }

                  leaf sub-length {
                    description 'Configure length of sub option context' ;
                    type uint16 {
                      range 0..254 {
                        description 'Bytes of sub option context length' ;
                      }

                    }

                  }

                }

              }

            }

            ncd:revise-date 2021-02-26 ;
          }

        }

      }

      container track {
        list trackName {
          key ifName ;
          leaf ifName {
            type ncd:ifname ;

          }

          leaf afnodeName {
            type ncd:af-name ;

            mandatory true ;
          }

          leaf name {
            description 'track name' ;
            type string {
              length 0..31 ;

            }

            mandatory true ;
          }

          leaf afnodeIndex {
            description 'af-node ID' ;
            type uint32 ;

            mandatory true ;
          }

          leaf ifIndex {
            type uint32 ;

            mandatory true ;
          }

        }

        ncd:revise-date 2018-05-14 ;
      }

      container vxlans {
        description 'Configure VXLAN parameters.' ;
        list vxlan {
          description 'Configure VXLAN parameters' ;
          key 'if-name start-id end-id' ;
          leaf if-name {
            description 'Interface name' ;
            type ncd:ifname ;

          }

          leaf start-id {
            description 'vni start id' ;
            type uint32 {
              range 1..16777215 ;

            }

          }

          leaf end-id {
            description 'vni end id' ;
            type uint32 {
              range 0..16777215 ;

            }

          }

        }

        ncd:revise-date 2018-05-14 ;
      }

      container smartgroup-master {
        presence master-interface ;
        list master {
          description 'Configure the master member port of smartgroup.' ;
          key smartgroup-id ;
          leaf smartgroup-id {
            description 'The group id bound by master port, its maximum value depends on the performance parameters.' ;
            type uint32 {
              range 1..65535 {
                description 'The maximum value depends on the performance parameters.' ;
              }

            }

          }

          leaf master-interface {
            description 'The interface name of master member port.' ;
            type ncd:ifname ;

            mandatory true ;
          }

        }

        ncd:revise-date 2019-02-23 ;
      }

      container access-delay-groups {
        description 'Configure access delay groups.' ;
        presence access-delay-group ;
        list access-delay-group {
          description 'Configure access delay group.' ;
          max-elements 32 ;
          key group-name ;
          leaf group-name {
            description 'Configure group name.' ;
            type string {
              length 1..31 {
                description 'delay group name' ;
              }

            }

          }

          leaf delay-time {
            description 'Configure group delay time.' ;
            type uint32 {
              range 0..20000 {
                description 'group delay time' ;
              }

            }

            mandatory true ;
          }

          choice algorithms {
            description 'Configure group algorithm.' ;
            mandatory true ;
            case hash {
              description 'Configure algorithm hash.' ;
              leaf algorithm-hash {
                type enumeration {
                  enum enable {
                    value 1 ;
                    description 'Configure algorithms hash enable.' ;
                  }

                }

              }

            }

            case user-balance {
              description 'Configure algorithm user-balance.' ;
              leaf algorithm-user-balance {
                type enumeration {
                  enum enable {
                    value 2 ;
                    description 'Configure algorithm user-balance enable.' ;
                  }

                }

              }

              leaf all-response {
                description 'Configure all interface response.' ;
                type enumeration {
                  enum enable {
                    value 1 ;
                  }

                  enum disable {
                    value 0 ;
                  }

                }

                mandatory true ;
              }

            }

          }

        }

        ncd:revise-date 2021-12-01 ;
      }

      container global-arp-safeguard {
        leaf arp-safeguard {
          description 'Configure global arp safeguard flag.' ;
          type enumeration {
            enum disable {
              value 0 ;
              description 'Disable global arp safeguard.' ;
            }

            enum enable {
              value 1 ;
              description 'Enable global arp safeguard.' ;
            }

          }

          default disable ;
        }

        ncd:revise-date 2022-10-21 ;
      }

    }

  }

}
