module zxr10-mac-dev-upn {
  namespace 'http://www.zte.com.cn/zxr10/netconf/schema/rosng/zxr10-mac-dev-upn'
            ;
  prefix mac-dev-upn ;
  yang-version 1 ;
  import zxr10-mac {
    prefix mac ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  revision 2022-11-23 {
    description '1.Delete deviation aging-time.'
                ;
  }
  revision 2017-11-15 {
    description '1.Delete deviation mac-vxlan-tables-expand, mac-permanent-vxla'
              + 'n-mac-address-no-vlan, delete-vxlan-no-config-mac.'
                ;
  }
  revision 2016-08-16 {
    description '1.Delete configuration/mac/permanent-mac-address/mac-permanent'
              + '-vxlan-mac-address-vlan.'
                ;
  }
  revision 2016-06-07 {
    description '1.Add /mac:configuration/mac:mac/mac:port-config/mac:mac-port-'
              + 'config/mac:dampening-policy, /mac:configuration/mac:mac/mac:po'
              + 'rt-config/mac:mac-port-config/mac:dampening-timeout;'+"\n"
              + '  2.Add /operation/mac/learn-priority-policies'
                ;
  }
  revision 2016-02-23 {
    description 'Add mac:configuration/mac:mac/mac:port-config/mac:mac-port-con'
              + 'fig/mac:exceed-limit-action.'
                ;
  }
  revision 2016-01-28 {
    description '1.Obsolete state/mac/mac-vxlan-tables.'+"\n"
              + '2.Obsolete configuration/mac/permanent-mac-address/mac-permane'
              + 'nt-vxlan-mac-address.'+"\n"
              + '3.Add state/mac/vxlan-tables-expand.'+"\n"
              + '4.Add configuration/mac/permanent-mac-address/mac-permanent-vx'
              + 'lan-mac-address-no-vlan.'+"\n"
              + '5.Add configuration/mac/permanent-mac-address/mac-permanent-vx'
              + 'lan-mac-address-vlan.'
                ;
  }
  revision 2016-01-15 {
    description '1.15K support dot1x and udld protocol,so delete the deviation '
              + 'of dot1x and udld.'
                ;
  }
  revision 2015-11-09 {
    description '1.Obsolete the l2protocol-control-policy container,so delete t'
              + 'he deviation of zdp-ztp,dot1x,lldp,all-bridge-multicast and la'
              + 'cp.'+"\n"
              + '2.Add deviation of dot1x udld,mstp,rstp,pbb-te,mac-in-mac and '
              + 'y1731 node which depend l2protocol-control-policy-expand conta'
              + 'iner.'
                ;
  }
  revision 2015-03-03 {
    description '1.Add deviation aging-time;'
                ;
  }
  revision 2015-01-19 {
    description '1.Add deviation forbidden-mac,forbidden-bind-port,learn-disabl'
              + 'e-action,learn-enable,safe-mode-policy,to-permanent-enable,lea'
              + 'rn-disable-action,mac-update-notify'+"\n"
              + 'vxlan mac,nickname,mac-vxlan-tables,to-statics,delete-vxlan-no'
              + '-config-mac;'+"\n"
              + '2.Delete deviation max-mac-num,exceed-limit-action;'
                ;
  }
  revision 2014-12-03 {
    description '1.Delete deviation default-priority-movable,higher-priority-mo'
              + 'vable;'+"\n"
              + '2.Add deviation learn-priority;'
                ;
  }
  revision 2014-05-16 {
    description 'Change "_" to "-".'
                ;
  }
  revision 2014-03-06 {
    description 'Add deviation remote-no-learning,learn-enable,max-mac-num,higi'
              + 'g-learn,default-priority-movable,lower-priority-movable,normal'
              + '-priority-movable,higher-priority-movable,exceed-limit-action,'
              + 'safe-mode-policy,auto-write-topermanent,auto-write-topermanent'
              + '-interval,forbidden-mac-reaction,learn-disable-action,mac-upda'
              + 'te-notify,mac-notify-interval,nofity-max-mac-num,learn-priorit'
              + 'y,zdp-ztp,dot1x,lldp,all-bridge-multicast,lacp.'
                ;
  }
  deviation '/mac:configuration/mac:mac/mac:vpls-instance-config/mac:vpls-confi'
          + 'g/mac:mac-learning/mac:remote-no-learning'
            {
    deviate not-supported ;
  }
  deviation /mac:configuration/mac:mac/mac:global-config/mac:learn-enable {
    deviate not-supported ;
  }
  deviation /mac:configuration/mac:mac/mac:global-config/mac:higig-learn {
    deviate not-supported ;
  }
  deviation '/mac:configuration/mac:mac/mac:global-config/mac:lower-priority-mo'
          + 'vable'
            {
    deviate not-supported ;
  }
  deviation '/mac:configuration/mac:mac/mac:global-config/mac:normal-priority-m'
          + 'ovable'
            {
    deviate not-supported ;
  }
  deviation /mac:configuration/mac:mac/mac:global-config/mac:safe-mode-policy {
    deviate not-supported ;
  }
  deviation '/mac:configuration/mac:mac/mac:global-config/mac:auto-write-toperm'
          + 'anent'
            {
    deviate not-supported ;
  }
  deviation '/mac:configuration/mac:mac/mac:global-config/mac:auto-write-toperm'
          + 'anent-interval'
            {
    deviate not-supported ;
  }
  deviation '/mac:configuration/mac:mac/mac:global-config/mac:forbidden-mac-rea'
          + 'ction'
            {
    deviate not-supported ;
  }
  deviation '/mac:configuration/mac:mac/mac:global-config/mac:learn-disable-act'
          + 'ion'
            {
    deviate not-supported ;
  }
  deviation /mac:configuration/mac:mac/mac:global-config/mac:mac-update-notify {
    deviate not-supported ;
  }
  deviation '/mac:configuration/mac:mac/mac:global-config/mac:mac-notify-interv'
          + 'al'
            {
    deviate not-supported ;
  }
  deviation /mac:configuration/mac:mac/mac:global-config/mac:notify-max-mac-num {
    deviate not-supported ;
  }
  deviation '/mac:configuration/mac:mac/mac:vpls-port-config/mac:mac-vfi-port-c'
          + 'onfig/mac:learn-priority'
            {
    deviate not-supported ;
  }
  deviation '/mac:configuration/mac:mac/mac:port-config/mac:mac-port-config/mac'
          + ':learn-priority'
            {
    deviate replace {
      type enumeration {
        enum default {
          value 0 ;
          description 'Default priority.'
                      ;
        }
        enum higher {
          value 3 ;
          description 'Higher priority.'
                      ;
        }
      }
    }
  }
  deviation /mac:configuration/mac:mac/mac:forbidden-mac {
    deviate not-supported ;
  }
  deviation /mac:configuration/mac:mac/mac:forbidden-bind-port {
    deviate not-supported ;
  }
  deviation '/mac:configuration/mac:mac/mac:vlan-config/mac:mac-vlan-config/mac'
          + ':learn-disable-action'
            {
    deviate not-supported ;
  }
  deviation '/mac:configuration/mac:mac/mac:port-config/mac:mac-port-config/mac'
          + ':learn-enable'
            {
    deviate not-supported ;
  }
  deviation '/mac:configuration/mac:mac/mac:port-config/mac:mac-port-config/mac'
          + ':safe-mode-policy'
            {
    deviate not-supported ;
  }
  deviation '/mac:configuration/mac:mac/mac:port-config/mac:mac-port-config/mac'
          + ':to-permanent-enable'
            {
    deviate not-supported ;
  }
  deviation '/mac:configuration/mac:mac/mac:port-config/mac:mac-port-config/mac'
          + ':learn-disable-action'
            {
    deviate not-supported ;
  }
  deviation '/mac:configuration/mac:mac/mac:port-config/mac:mac-port-config/mac'
          + ':mac-update-notify'
            {
    deviate not-supported ;
  }
  deviation '/mac:configuration/mac:mac/mac:permanent-mac-address/mac:mac-perma'
          + 'nent-address-no-vpn/mac:permanent-mac-address-no-vpn/mac:mac-type/'
          + 'mac:permanent/mac:outgoing/mac:ifornickname/mac:nickname'
            {
    deviate not-supported ;
  }
  deviation /mac:operation/mac:mac/mac:to-statics {
    deviate not-supported ;
  }
  deviation '/mac:configuration/mac:mac/mac:vlan-config/mac:mac-vlan-config/mac'
          + ':learn-enable'
            {
    deviate not-supported ;
  }
  deviation '/mac:configuration/mac:mac/mac:vpls-instance-config/mac:vpls-confi'
          + 'g/mac:l2protocol-control-policy-expand/mac:mstp'
            {
    deviate not-supported ;
  }
  deviation '/mac:configuration/mac:mac/mac:vpls-instance-config/mac:vpls-confi'
          + 'g/mac:l2protocol-control-policy-expand/mac:rstp'
            {
    deviate not-supported ;
  }
  deviation '/mac:configuration/mac:mac/mac:vpls-instance-config/mac:vpls-confi'
          + 'g/mac:l2protocol-control-policy-expand/mac:pbb-te'
            {
    deviate not-supported ;
  }
  deviation '/mac:configuration/mac:mac/mac:vpls-instance-config/mac:vpls-confi'
          + 'g/mac:l2protocol-control-policy-expand/mac:mac-in-mac'
            {
    deviate not-supported ;
  }
  deviation '/mac:configuration/mac:mac/mac:vpls-instance-config/mac:vpls-confi'
          + 'g/mac:l2protocol-control-policy-expand/mac:y1731'
            {
    deviate not-supported ;
  }
  deviation '/mac:configuration/mac:mac/mac:port-config/mac:mac-port-config/mac'
          + ':exceed-limit-action'
            {
    deviate replace {
      default forward ;
      type enumeration {
        enum forward {
          value 0 ;
          description Forward. ;
        }
        enum drop {
          value 1 ;
          description Drop. ;
        }
      }
    }
  }
  deviation '/mac:configuration/mac:mac/mac:port-config/mac:mac-port-config/mac'
          + ':dampening-policy'
            {
    deviate not-supported ;
  }
  deviation '/mac:configuration/mac:mac/mac:port-config/mac:mac-port-config/mac'
          + ':dampening-timeout'
            {
    deviate not-supported ;
  }
  deviation /mac:operation/mac:mac/mac:learn-priority-policy {
    deviate not-supported ;
  }
}
