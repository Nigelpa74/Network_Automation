module zxr10-dhcp-snooping {
  namespace "http://www.zte.com.cn/zxr10/netconf/schema/rosng/dhcp-snooping" ;
  prefix dhcps ;
  yang-version 1 ;
  import zxr10-netconf-defs {
    prefix ncd ;
  }

  organization "ZTE Corporation" ;
  contact "ZTE Corporation
  Nanjing Institute of ZTE Corporation
  No.68 Zijinghua Rd. Yuhuatai District, Nanjing, China
  Tel: +86-25-52870000" ;
  description 'The netconf module to describe DHCP snooping.' ;
  revision 2024-06-17 {
    description 'Add node:/dhcps:configuration/dhcps:dhcp-snooping/dhcps:interfaces/dhcps:interface/dhcps:if-enable
Add feature:if-enable' ;
  }

  revision 2024-01-29 {
    description 'Add node:/dhcps:configuration/dhcps:dhcp-snooping/dhcps:global/dhcps:binding-auto-clear
' ;
  }

  revision 2022-07-26 {
    description 'Add option82 format port-hex-tuple.' ;
  }

  revision 2021-07-23 {
    description 'Add server-type sftp.' ;
  }

  revision 2021-06-25 {
    description 'Add path:/dhcps:configuration/dhcps:dhcp-snooping/dhcps:ip-global/dhcps:update
Add feature:ip-global-update' ;
  }

  revision 2021-03-16 {
    description 'Add node:/dhcps:operation/dhcps:dhcp-snooping/dhcps:clear/dhcps:bindings/dhcps:release' ;
  }

  revision 2020-06-28 {
    description 'Modify the length of FTP/TFTP server password.' ;
  }

  revision 2019-10-31 {
    description 'Remove version-date and rely on the lastest netconf version
Add node:/dhcps:state/dhcps:dhcp-snooping/dhcps:database/dhcps:option82-chinese
Add node:/dhcps:state/dhcps:dhcp-snooping/dhcps:database-vxlan/dhcps:option82-chinese' ;
  }

  revision 2019-10-08 {
    description 'Remove the project tag of 99 from the vxlan feature.' ;
  }

  revision 2019-07-01 {
    description 'Modify the length of FTP/TFTP server user-name and password' ;
  }

  revision 2019-05-16 {
    description 'Add nodes:/dhcps:configuration/dhcps:dhcp-snooping/dhcps:evpn-vplses
Add nodes:/dhcps:configuration/dhcps:dhcp-snooping/dhcps:global/dhcps:auto-discovered-vxlan-tunnels
Add nodes:/dhcps:operation/dhcps:dhcp-snooping/dhcps:clear/dhcps:bindings/dhcps:instance/dhcps:evpn-vpls-name
Add nodes:/dhcps:state/dhcps:dhcp-snooping/dhcps:database-evpn-vpls
Add feature:evpn-vpls,auto-discovered-vxlan-tunnels,multi-ip-binding' ;
  }

  revision 2019-05-07 {
    description 'Modify node /dhcps:configuration/dhcps:dhcp-snooping/dhcps:global/dhcps:file/dhcps:server/dhcps:url to /dhcps:configuration/dhcps:dhcp-snooping/dhcps:global/dhcps:file/dhcps:server/dhcps:address/dhcps:url-type/dhcps:url
Add case:/dhcps:configuration/dhcps:dhcp-snooping/dhcps:global/dhcps:file/dhcps:server/dhcps:address/dhcps:path-type' ;
  }

  revision 2019-01-08 {
    description 'Add nodes:/dhcps:operation/dhcps:dhcp-snooping/dhcps:clear/dhcps:bindings/dhcps:type/dhcps:interface/dhcps:mac-address;
/dhcps:operation/dhcps:dhcp-snooping/dhcps:clear/dhcps:bindings/dhcps:type/dhcps:interface/dhcps:ip-address;
/dhcps:operation/dhcps:dhcp-snooping/dhcps:clear/dhcps:bindings/dhcps:type/dhcps:interface/dhcps:instance/dhcps:type/dhcps:vlan/dhcps:vlanid
/dhcps:operation/dhcps:dhcp-snooping/dhcps:clear/dhcps:bindings/dhcps:type/dhcps:interface/dhcps:instance/dhcps:type/dhcps:vpls/dhcps:vpls-name;' ;
  }

  revision 2018-12-12 {
    description 'Add nodes:/dhcps:configuration/dhcps:dhcp-snooping/dhcps:interfaces/dhcps:interface/dhcps:information/dhcps:policy,/dhcps:configuration/dhcps:dhcp-snooping/dhcps:vlans/dhcps:vlan/dhcps:information/dhcps:policy,/dhcps:configuration/dhcps:dhcp-snooping/dhcps:vlans/dhcps:vlan/dhcps:information/dhcps:interfaces/dhcps:interface/dhcps:policy;
Add feature:option82-policy.' ;
  }

  revision 2017-12-26 {
    description "Modify leaf nodes 'auto-circuit-id' and 'circuit-id' to two case branches." ;
  }

  revision 2017-10-26 {
    description 'Add path:/dhcps:configuration/dhcps:dhcp-snooping/dhcps:global/dhcps:information/dhcps:user-configuration; /dhcps:configuration/dhcps:dhcp-snooping/dhcps:vlans/dhcps:vlan/dhcps:information;
/dhcps:configuration/dhcps:dhcp-snooping/dhcps:interfaces/dhcps:interface/dhcps:information;
Add feature:user-configuration,option82-information;
Add enumeration:auto-circuit-id-type,user-configuration-policy.' ;
  }

  revision 2017-08-16 {
    description 'Add path:/dhcps:configuration/dhcps:dhcp-snooping/dhcps:vxlans,path:/dhcps:state/dhcps:dhcp-snooping/dhcps:database-vxlan
Add feature:vpls,vlan,vxlan,ip-global,database' ;
  }

  revision 2015-03-08 {
    description 'Modify the rang of global max user.' ;
  }

  revision 2015-01-19 {
    description 'Add optional parameters listen-port and output interface for file server command' ;
  }

  revision 2015-01-16 {
    description 'Add telenor format for option82' ;
  }

  revision 2015-01-12 {
    description 'Modify type of option82 in database from string to string-all' ;
  }

  revision 2014-07-02 {
    description 'Add string length of configuration/dhcp-snooping/global/file/server/url.' ;
  }

  revision 2014-05-22 {
    description 'Add enum item in typedef boot-type.' ;
  }

  revision 2014-04-09 {
    description 'Initial version.' ;
  }

  feature vxlan {
    description 'Support VXLAN instance.' ;
  }

  feature vpls {
    description 'Support VPLS instance.' ;
  }

  feature ip-global {
    description 'Support ip-global instance.' ;
  }

  feature vlan {
    description 'Support VLAN instance.' ;
  }

  feature database {
    description 'Support to get database state.' ;
  }

  feature user-configuration {
    description 'Support user-configuration of option82' ;
  }

  feature option82-information {
    description 'Support relay agent information option.' ;
  }

  feature option82-policy {
    description 'Support Option82 policy.' ;
  }

  feature evpn-vpls {
    description 'Support EVPN-VPLS instance.' ;
  }

  feature auto-discovered-vxlan-tunnel {
    description 'Support to auto-discover vxlan-tunnels.' ;
  }

  feature multi-ip-binding {
    description 'Support multicast IP bindings.' ;
  }

  feature ip-global-update {
    description 'Support to update ARP entry of DHCP snooping binding.' ;
  }

  feature if-enable {
    description 'Support enable of interfaces' ;
    ncd:revise-date 2024-06-17 ;
  }

  typedef option-82 {
    type enumeration {
      enum china-tel {
        value 1 ;
        description 'China telecom' ;
      }

      enum dsl-forum {
        value 2 ;
        description 'DSL forum' ;
      }

      enum telenor {
        value 3 ;
        description 'Telenor' ;
      }

      enum user-configuration {
        value 4 ;
        description 'User configuration' ;
      }

      enum cisco {
        value 5 ;
        description 'Cisco' ;
      }

      enum china-uni {
        value 6 ;
        description 'China UNI' ;
      }

      enum port-hex-tuple {
        value 7 ;
        description 'Port-hex-tuple' ;
      }

    }

    description 'Option82 format.1:china-tel,2:dsl-forum,3:telenor,4:user-configuration,5:cisco,6:china-uni,7:port-hex-tuple.' ;
  }

  typedef option-policy {
    type enumeration {
      enum keep {
        value 2 ;
        description 'keep original 82 option' ;
      }

      enum replace {
        value 3 ;
        description 'replace 82 option' ;
      }

      enum stripping {
        value 4 ;
        description 'strip off 82 option' ;
      }

    }

    description 'Option policy. 2:keep, 3:replace,4:stripping.' ;
  }

  typedef switch {
    type enumeration {
      enum off {
        value 0 ;
        description 'log switch off' ;
      }

      enum on {
        value 1 ;
        description 'log switch on' ;
      }

    }

    description 'Log switch.0:off,1:on.' ;
  }

  typedef boot-type {
    type enumeration {
      enum none {
        value 0 ;
        description 'no recover' ;
      }

      enum localload {
        value 1 ;
        description 'recover from local' ;
      }

      enum download {
        value 2 ;
        description 'recover from remote server' ;
      }

    }

    description 'Boot type.0:none,1:localload,2:download.' ;
  }

  typedef server-type {
    type enumeration {
      enum tftp {
        value 2 ;
        description 'trivial file transfer protocal' ;
      }

      enum ftp {
        value 3 ;
        description 'file transfer protocal' ;
      }

      enum sftp {
        value 4 ;
        description 'secure file transfer protocal' ;
      }

    }

    description 'Server name.2:tftp,3:ftp,4:sftp.' ;
  }

  typedef database-type {
    type enumeration {
      enum dynamic {
        value 0 ;
      }

      enum static {
        value 1 ;
      }

    }

    description 'database client type.0:dynamic,1:static.' ;
  }

  typedef switch-type {
    type enumeration {
      enum disable {
        value 0 ;
      }

      enum enable {
        value 1 ;
      }

    }

    description 'Switch type.0:disable,1:enable.' ;
  }

  typedef auto-circuit-id-type {
    type enumeration {
      enum port {
        value 1 ;
        description 'Generate port string automatically.' ;
      }

      enum port-and-vlan {
        value 2 ;
        description 'Generate port and VLAN string automatically.' ;
      }

    }

    description 'Generate circuit ID automatically,1:port, 2:port and VLAN' ;
  }

  typedef user-configuration-policy {
    type enumeration {
      enum interface {
        value 1 ;
        description 'Use user-configuration of the interface.' ;
      }

      enum global {
        value 2 ;
        description 'Use user-configuration of global.' ;
      }

      enum vlan {
        value 3 ;
        description 'Use user-configuration of the VLAN.' ;
      }

    }

    description 'Policy of user configuration.1:interface; 2:global; 3:vlan.' ;
  }

  container configuration {
    description 'Configuration model.' ;
    container dhcp-snooping {
      description 'Configure dhcp snooping parameters.' ;
      container global {
        description 'Dhcp snooping global configure.' ;
        leaf enable {
          description 'Enable/disable DHCP snooping globally.' ;
          type switch-type ;

          default disable ;
        }

        leaf max-user {
          description 'Configure max user number.' ;
          type uint32 {
            range 1..256000 ;

          }

          default 2048 ;
        }

        leaf ramble {
          description 'Enable/disable DHCP snooping user ramble.' ;
          type switch-type ;

          default disable ;
        }

        leaf verify-mac {
          description 'Enable DHCP snooping mac-verifying.' ;
          type switch-type ;

          default disable ;
        }

        container information {
          if-feature option82-information ;

          description 'Configure relay agent information option.' ;
          leaf option {
            description 'Insert relay information in BOOTREQUEST.' ;
            type switch-type ;

            default disable ;
          }

          leaf format {
            description 'Relay information format style.' ;
            type option-82 ;

            default china-tel ;
          }

          leaf policy {
            description 'Define reforwarding policy.' ;
            type option-policy ;

            default keep ;
          }

          container user-configuration {
            if-feature user-configuration ;

            description 'Configure global relay agent information through user-configuration.' ;
            leaf remote-id {
              description 'Configure remote ID.' ;
              type string ;

            }

            leaf policy {
              description 'Configure user-configuration policy,base on interface,global or VLAN.' ;
              type user-configuration-policy ;

              default interface ;
            }

            container circuit-id-configuration {
              description 'Configure circuit ID suboption.' ;
              choice circuit-id-suboption {
                description 'Configure circuit ID suboption.' ;
                case auto-circuit-id {
                  description 'Generate circuit-id automatically.' ;
                  leaf auto-circuit-id {
                    description 'Generate circuit-id automatically.' ;
                    type auto-circuit-id-type ;

                  }

                }

                case circuit-id {
                  description 'Configure circuit ID.' ;
                  leaf circuit-id {
                    description 'Configure circuit ID.' ;
                    type string ;

                  }

                }

              }

              ncd:revise-date 2017-12-26 ;
            }

            ncd:revise-date 2017-10-26 ;
          }

        }

        leaf logging {
          description 'Modify message logging facilities.' ;
          type switch ;

          default off ;
        }

        container file {
          description 'Configure DHCP snooping file.' ;
          leaf timeout {
            description 'The DHCP snooping database timeout.' ;
            type uint32 {
              range 0..2147483647 ;

            }

            units second ;
            default 0 ;
          }

          leaf upload-time {
            description 'The DHCP snooping database upload time (minutes).' ;
            type uint32 {
              range 0..2147483647 ;

            }

            units minute ;
            default 0 ;
          }

          leaf localdir {
            description 'The DHCP snooping database local directory.' ;
            type string {
              length 1..32 ;

            }

          }

          container server {
            description 'Configure DHCP Snooping database server address.' ;
            presence server ;
            leaf server-type {
              description 'tftp, ftp and sftp.' ;
              type server-type ;

              mandatory true ;
            }

            leaf ipv6 {
              description 'Copy file using ipv6.' ;
              type uint32 {
                range 0..1 ;

              }

              default 0 ;
            }

            choice vrf {
              description 'VPN routing/forwarding instance (VRF) name.' ;
              default mng ;
              case mng {
                description 'Management interface routes.' ;
                leaf mng {
                  description 'Management interface routes.' ;
                  type uint32 {
                    range 0..1 ;

                  }

                  default 0 ;
                }

              }

              case vrf-name {
                description 'Vrf name.' ;
                leaf vrf-name {
                  description 'Vrf name.' ;
                  type string {
                    length 1..35 ;

                  }

                }

              }

            }

            choice address {
              description 'Server address.' ;
              mandatory true ;
              case url-type {
                description 'File server address.' ;
                leaf url {
                  description 'The DHCP snooping database server address://HOST/filepath[@username:password].' ;
                  type string {
                    length 1..145 ;

                  }

                  mandatory true ;
                }

              }

              case path-type {
                description 'File server address.' ;
                container path-account {
                  description 'Configure path and account.' ;
                  leaf path {
                    description 'The DHCP snooping database server address://HOST/filepath.' ;
                    type string {
                      length 1..80 ;

                    }

                    mandatory true ;
                  }

                  container account {
                    description 'Account.' ;
                    presence account ;
                    leaf user-name {
                      description 'User name.' ;
                      type string {
                        length 1..65 ;

                      }

                      mandatory true ;
                    }

                    choice password {
                      description 'Password.' ;
                      mandatory true ;
                      case clear {
                        description 'Clear password.' ;
                        leaf clear-password {
                          description 'Clear password.' ;
                          type string {
                            length 1..64 ;

                          }

                          mandatory true ;
                        }

                      }

                      case encrypted {
                        description 'Encrypted password.' ;
                        leaf encrypted-password {
                          description 'Encrypted password.' ;
                          type string {
                            length "64 | 128 | 148" ;

                          }

                          mandatory true ;
                        }

                      }

                    }

                  }

                }

                ncd:revise-date 2019-05-07 ;
              }

            }

            leaf listen-port {
              description 'Listen port.' ;
              type uint32 {
                range 1..65535 ;

              }

            }

            leaf if-name {
              description 'Interface name.' ;
              type ncd:ifname ;

            }

          }

          container onboot {
            description 'The DHCP snooping database recover after device booting.' ;
            presence onboot ;
            leaf onboot-type {
              description 'Configure DHCP snooping on-boot recovery mode.' ;
              type boot-type ;

              mandatory true ;
            }

            leaf retry-times {
              description 'Retry times of recovering database when failed.' ;
              type uint32 {
                range 0..10 ;

              }

              default 0 ;
            }

            leaf retry-interval {
              description 'Retry interval of recovering database when failed.' ;
              type uint32 {
                range 60..600 ;

              }

              units second ;
              default 60 ;
            }

          }

        }

        leaf binding-auto-clear {
          type switch-type ;

          description 'Configure DHCP snooping binding auto-clear.' ;
          default disable ;
          ncd:revise-date 2024-01-29 ;
        }

      }

      container vplses {
        if-feature vpls ;

        description "DHCP snooping vpls configure.Can't config DHCP snooping in vpls if the vpls instance not exist.If DHCP snooping configuration exist in vpls,the vpls instance can't be deleted." ;
        list vpls {
          description 'The config of instance VPLS.' ;
          key vpls-name ;
          leaf vpls-name {
            description 'Submode instance Name of VPLS.' ;
            type string {
              length 1..32 ;

            }

          }

          leaf enable {
            description 'Enable/disable DHCP snooping in this instance.' ;
            type switch-type ;

            default disable ;
          }

          container bindings {
            description 'Add a configurable binding to the DHCP snooping database.' ;
            list binding {
              description 'Binding item.' ;
              key 'mac-address vlanid' ;
              leaf mac-address {
                description 'Client hardware MAC address.' ;
                type ncd:mac-address ;

              }

              leaf vlanid {
                description 'Client VLAN ID.' ;
                type uint16 {
                  range 0..4094 ;

                }

              }

              leaf ip-address {
                description 'Client IP address assigned from the DHCP server.' ;
                type ncd:ipv4-address ;

                mandatory true ;
              }

              leaf if-name {
                description 'Interface name.' ;
                type ncd:ifname ;

                mandatory true ;
              }

            }

          }

        }

      }

      container vlans {
        if-feature vlan ;

        description "DHCP snooping vlan configure.Can't config DHCP snooping in vlan if the vlan instance not exist." ;
        list vlan {
          description 'The config of instance VLAN.' ;
          key vlanid ;
          leaf vlanid {
            description 'VLAN ID.' ;
            type uint16 {
              range 1..4094 ;

            }

          }

          leaf enable {
            description 'Enable/disable DHCP snooping in this instance.' ;
            type switch-type ;

            default disable ;
          }

          container bindings {
            description 'Add a configurable binding to the DHCP snooping database.' ;
            list binding {
              description 'Binding item.' ;
              key mac-address ;
              leaf mac-address {
                description 'Client hardware MAC address.' ;
                type ncd:mac-address ;

              }

              leaf ip-address {
                description 'Client IP address assigned from the DHCP server.' ;
                type ncd:ipv4-address ;

                mandatory true ;
              }

              leaf gateway-address {
                description 'Gateway IP address.' ;
                type ncd:ipv4-address ;

                default 0.0.0.0 ;
              }

              leaf if-name {
                description 'Interface name.' ;
                type ncd:ifname ;

                mandatory true ;
              }

            }

          }

          container information {
            if-feature option82-information ;

            description 'Configure relay agent information option in VLAN.' ;
            container user-configuration {
              if-feature user-configuration ;

              description 'Configure relay agent information in VLAN,through user-configuration.' ;
              leaf remote-id {
                description 'Configure remote ID.' ;
                type string ;

              }

              container circuit-id-configuration {
                description 'Configure circuit ID suboption.' ;
                choice circuit-id-suboption {
                  description 'Configure circuit ID suboption.' ;
                  case auto-circuit-id {
                    description 'Generate circuit-id automatically.' ;
                    leaf auto-circuit-id {
                      description 'Generate circuit-id automatically.' ;
                      type auto-circuit-id-type ;

                    }

                  }

                  case circuit-id {
                    description 'Configure circuit ID.' ;
                    leaf circuit-id {
                      description 'Configure circuit ID.' ;
                      type string ;

                    }

                  }

                }

                ncd:revise-date 2017-12-26 ;
              }

            }

            container interfaces {
              description 'Select an interface to configure.' ;
              list interface {
                description 'Select an interface to configure.' ;
                key if-name ;
                leaf if-name {
                  type ncd:ifname ;

                }

                container user-configuration {
                  if-feature user-configuration ;

                  description 'Configure relay agent information in VLAN and port,through user-configuration.' ;
                  leaf remote-id {
                    description 'Configure remote ID.' ;
                    type string ;

                  }

                  container circuit-id-configuration {
                    description 'Configure circuit ID suboption.' ;
                    choice circuit-id-suboption {
                      description 'Configure circuit ID suboption.' ;
                      case auto-circuit-id {
                        description 'Generate circuit-id automatically.' ;
                        leaf auto-circuit-id {
                          description 'Generate circuit-id automatically.' ;
                          type auto-circuit-id-type ;

                        }

                      }

                      case circuit-id {
                        description 'Configure circuit ID.' ;
                        leaf circuit-id {
                          description 'Configure circuit ID.' ;
                          type string ;

                        }

                      }

                    }

                    ncd:revise-date 2017-12-26 ;
                  }

                }

                leaf policy {
                  if-feature option82-policy ;

                  description 'Define reforwarding policy.' ;
                  type option-policy ;

                  ncd:revise-date 2018-12-12 ;
                }

              }

            }

            leaf policy {
              if-feature option82-policy ;

              description 'Define reforwarding policy.' ;
              type option-policy ;

              ncd:revise-date 2018-12-12 ;
            }

            ncd:revise-date 2017-10-26 ;
          }

        }

      }

      container ip-global {
        if-feature ip-global ;

        description 'DHCP snooping ip global configure.' ;
        container bindings {
          description 'Add a configurable binding to the DHCP snooping database.' ;
          list binding {
            description 'Binding item.' ;
            key mac-address ;
            leaf mac-address {
              description 'Client hardware MAC address.' ;
              type ncd:mac-address ;

            }

            leaf ip-address {
              description 'Client IP address assigned from the DHCP server.' ;
              type ncd:ipv4-address ;

              mandatory true ;
            }

            leaf if-name {
              description 'Interface name.' ;
              type ncd:ifname ;

              mandatory true ;
            }

            leaf vrf-name {
              description 'Client VRF instance name.' ;
              type string {
                length 1..32 ;

              }

            }

            container vlan {
              description 'Client VLAN ID.' ;
              presence "the leaf vlanid of this container should be mandatory, and other leafs are not." ;
              leaf vlanid {
                description 'Client external-VLAN ID.' ;
                type uint16 {
                  range 0..4094 ;

                }

                mandatory true ;
              }

              leaf internal-vlanid {
                description 'Client internal-VLAN ID.' ;
                type uint16 {
                  range 0..4094 ;

                }

                default 0 ;
              }

            }

          }

        }

        container interfaces {
          description 'Select an interface to configure.' ;
          list interface {
            description 'Select an interface to configure.' ;
            key if-name ;
            leaf if-name {
              description 'Interface name.' ;
              type ncd:ifname ;

            }

            leaf enable {
              description 'Enable/disable DHCP snooping in this interface.' ;
              type switch-type ;

              default disable ;
            }

            leaf option-enable {
              description 'Enable/disable insert relay information in BOOTREQUEST in this interface.' ;
              type switch-type ;

              default disable ;
            }

            leaf send-release-enable {
              description 'Enable/disable Sending release packet in this interface.' ;
              type switch-type ;

              default disable ;
            }

          }

        }

        container vlans {
          description 'The config of DHCP snooping on this VLAN.' ;
          list vlan {
            description 'The config of DHCP snooping on this VLAN.' ;
            key 'vlanid internal-vlanid' ;
            leaf vlanid {
              description 'Client external-VLAN ID.' ;
              type uint16 {
                range 1..4094 ;

              }

            }

            leaf internal-vlanid {
              description 'Client internal-VLAN ID.' ;
              type uint16 {
                range 0..4094 ;

              }

            }

            leaf max-user {
              description 'The max user of DHCP snooping on this VLAN.' ;
              type uint32 {
                range 1..32000 ;

              }

              default 2048 ;
            }

          }

        }

        container update {
          if-feature ip-global-update ;

          description 'Update ARP entry of DHCP snooping binding.' ;
          leaf arp {
            description 'Update ARP entry of DHCP snooping binding.' ;
            type switch-type ;

            default disable ;
          }

          ncd:revise-date 2021-06-25 ;
        }

      }

      container interfaces {
        description 'Select an interface to configure.' ;
        list interface {
          description 'Select an interface to configure.' ;
          key if-name ;
          leaf if-name {
            description 'Interface name.' ;
            type ncd:ifname ;

          }

          leaf max-user {
            description 'The max user of DHCP snooping on this interface.' ;
            type uint32 {
              range 1..32000 ;

            }

            default 2048 ;
          }

          leaf trust-enable {
            description 'Configure an interface as trusted.' ;
            type switch-type ;

            default disable ;
          }

          leaf verify-mac-enable {
            description 'Configure DHCP snooping mac-verifying for this interface.' ;
            type switch-type ;

            default enable ;
          }

          leaf if-enable {
            description 'Enable DHCP snooping.' ;
            if-feature if-enable ;

            type enumeration {
              enum enable {
                value 1 ;
              }

            }

            ncd:revise-date 2024-06-17 ;
          }

          container information {
            if-feature option82-information ;

            description 'Configure relay agent information option in port.' ;
            container user-configuration {
              if-feature user-configuration ;

              description 'Configure relay agent information in port,through user-configuration.' ;
              leaf remote-id {
                description 'Configure remote ID.' ;
                type string ;

              }

              container circuit-id-configuration {
                description 'Configure circuit ID suboption.' ;
                choice circuit-id-suboption {
                  description 'Configure circuit ID suboption.' ;
                  case auto-circuit-id {
                    description 'Generate circuit-id automatically.' ;
                    leaf auto-circuit-id {
                      description 'Generate circuit-id automatically.' ;
                      type auto-circuit-id-type ;

                    }

                  }

                  case circuit-id {
                    description 'Configure circuit ID.' ;
                    leaf circuit-id {
                      description 'Configure circuit ID.' ;
                      type string ;

                    }

                  }

                }

                ncd:revise-date 2017-12-26 ;
              }

            }

            leaf policy {
              if-feature option82-policy ;

              description 'Define reforwarding policy.' ;
              type option-policy ;

              ncd:revise-date 2018-12-12 ;
            }

            ncd:revise-date 2017-10-26 ;
          }

        }

      }

      container vxlans {
        if-feature vxlan ;

        description "DHCP snooping vxlan configure.Can't config DHCP snooping in vxlan if the vxlan instance not exist." ;
        list vxlan {
          description 'The config of instance VXLAN.' ;
          key vxlanid ;
          leaf vxlanid {
            description 'VXLAN ID.' ;
            type uint32 {
              range 1..16777215 ;

            }

          }

          leaf enable {
            description 'Enable/disable DHCP snooping in this instance.' ;
            type switch-type ;

            default disable ;
          }

          container bindings {
            description 'Add a configurable binding to the DHCP snooping database.' ;
            list binding {
              description 'Binding item.' ;
              key mac-address ;
              leaf mac-address {
                description 'Client hardware MAC address.' ;
                type ncd:mac-address ;

              }

              leaf ip-address {
                description 'Client IP address assigned from the DHCP server.' ;
                type ncd:ipv4-address ;

                mandatory true ;
              }

              leaf if-name {
                description 'Interface name.' ;
                type ncd:ifname ;

                mandatory true ;
              }

            }

          }

        }

        ncd:revise-date 2017-08-16 ;
      }

      container evpn-vplses {
        if-feature evpn-vpls ;

        description "DHCP snooping EVPN-VPLS configuration.Can't config DHCP snooping in the EVPN-VPLS instance if it does not exist.The EVPN-VPLS instance can't be deleted if it has some configuration." ;
        list evpn-vpls {
          description 'Configuration of the EVPN-VPLS instance.' ;
          key evpn-vpls-name ;
          leaf evpn-vpls-name {
            description 'Name of the EVPN-VPLS instance.' ;
            type string {
              length 1..32 ;

            }

          }

          leaf enable {
            description 'Enable/disable DHCP snooping in this instance.' ;
            type switch-type ;

            default disable ;
          }

          container multi-ip-bindings {
            if-feature multi-ip-binding ;

            description 'Add a configurable multi-IP bindings to the DHCP snooping database.' ;
            list multi-ip-binding {
              description 'Binding item.' ;
              key 'mac-address ip-address' ;
              leaf mac-address {
                description 'Client hardware MAC address.' ;
                type ncd:mac-address ;

              }

              leaf ip-address {
                description 'Client IP address assigned from the DHCP server.' ;
                type ncd:ipv4-address ;

              }

              choice interface {
                description 'VLAN interface , VXLAN tunnel or other interface.' ;
                mandatory true ;
                case if {
                  description 'Interface name.' ;
                  leaf if-name {
                    description 'Interface name.' ;
                    type ncd:ifname ;

                    mandatory true ;
                  }

                }

                case vlanif {
                  description 'VLAN interface.' ;
                  leaf vlanif {
                    description 'Interface name.' ;
                    type ncd:ifname ;

                    mandatory true ;
                  }

                  leaf phy-if-name {
                    description 'Physical interface name.' ;
                    type ncd:ifname ;

                    mandatory true ;
                  }

                }

                case vxlan-tunnel {
                  description 'VXLAN tunnel.' ;
                  leaf vni {
                    description 'VNI.' ;
                    type uint32 {
                      range 1..16777215 ;

                    }

                    mandatory true ;
                  }

                  leaf vxlan-tunnel-name {
                    description 'VXLAN tunnel name.' ;
                    type ncd:ifname ;

                    mandatory true ;
                  }

                }

              }

            }

          }

        }

        ncd:revise-date 2019-05-16 ;
      }

      container auto-discovered-vxlan-tunnels {
        if-feature auto-discovered-vxlan-tunnel ;

        description 'Configure dynamic vxlan-tunnels.' ;
        container ipv4-vxlan-tunnels {
          description 'Add IPv4 vxlan-tunnels.' ;
          list ipv4-vxlan-tunnel {
            description 'Vxlan-tunnel.' ;
            key 'source destination' ;
            leaf source {
              description 'Source IPv4 address.' ;
              type ncd:ipv4-address ;

            }

            leaf destination {
              description 'Destination IPv4 address.' ;
              type ncd:ipv4-address ;

            }

            leaf trust-enable {
              description 'Configure an interface as trusted.' ;
              type switch-type ;

              default disable ;
            }

          }

        }

        container ipv6-vxlan-tunnels {
          description 'Add IPv6 vxlan-tunnels.' ;
          list ipv6-vxlan-tunnel {
            description 'Vxlan-tunnel.' ;
            key 'source destination' ;
            leaf source {
              description 'Source IPv6 address.' ;
              type ncd:ipv6-address ;

            }

            leaf destination {
              description 'Destination IPv6 address.' ;
              type ncd:ipv6-address ;

            }

            leaf trust-enable {
              description 'Configure an interface as trusted.' ;
              type switch-type ;

              default disable ;
            }

          }

        }

        ncd:revise-date 2019-05-16 ;
      }

    }

  }

  container operation {
    config false ;
    description 'Operation model.' ;
    container dhcp-snooping {
      description 'Operation of DHCP snooping.' ;
      container clear {
        description 'Clear Operation.' ;
        container bindings {
          description 'Clear the dynamic DHCP snooping database.' ;
          choice type {
            case all {
              description 'Clear all DHCP snooping database.' ;
              leaf all-bindings {
                description 'All items.' ;
                type empty ;

              }

            }

            case interface {
              description 'Clear the DHCP snooping database by interface,and other optional parameters.' ;
              leaf if-name {
                description 'Interface name.' ;
                type ncd:ifname ;

              }

              leaf mac-address {
                description 'Client hardware MAC address.' ;
                type ncd:mac-address ;

                ncd:revise-date 2019-01-08 ;
              }

              leaf ip-address {
                description 'Client IP address assigned from the DHCP server.' ;
                type ncd:ipv4-address ;

                ncd:revise-date 2019-01-08 ;
              }

              container instance {
                description 'Clear the DHCP snooping database of the instance.' ;
                choice type {
                  case vlan {
                    description 'Clear the DHCP snooping database of VLAN instance.' ;
                    leaf vlanid {
                      description 'VLAN ID.' ;
                      type uint16 {
                        range 1..4094 ;

                      }

                    }

                  }

                  case vpls {
                    description 'Clear the DHCP snooping database of VPLS instance.' ;
                    leaf vpls-name {
                      description 'VPLS name.' ;
                      type string {
                        length 1..32 ;

                      }

                    }

                  }

                  case evpn-vpls {
                    description 'Clear the DHCP snooping database of EVPN-VPLS instance.' ;
                    leaf evpn-vpls-name {
                      description 'EVPN-VPLS name.' ;
                      type string ;

                    }

                    ncd:revise-date 2019-05-16 ;
                  }

                }

                ncd:revise-date 2019-01-08 ;
              }

            }

          }

          leaf release {
            description 'Send DHCP release packet when clearing database.' ;
            type empty ;

            ncd:revise-date 2021-03-16 ;
          }

        }

      }

      container file {
        description 'Operation of file.' ;
        choice type {
          case download {
            description 'The DHCP snooping database download.' ;
            leaf download {
              description 'The DHCP snooping database download.' ;
              type empty ;

            }

          }

          case localload {
            description 'The DHCP snooping database local download.' ;
            leaf localload {
              description 'The DHCP snooping database local download.' ;
              type empty ;

            }

          }

          case localwrite {
            description 'The DHCP snooping database local write.' ;
            leaf localwrite {
              description 'The DHCP snooping database local write.' ;
              type empty ;

            }

          }

          case upload {
            description 'The DHCP snooping database upload.' ;
            leaf upload {
              description 'The DHCP snooping database upload.' ;
              type empty ;

            }

          }

        }

      }

    }

  }

  container state {
    config false ;
    description 'State model.' ;
    container dhcp-snooping {
      description 'DHCP snooping state parameters.' ;
      list database {
        if-feature database ;

        description 'DHCP snooping binding database.' ;
        key 'mac-address vlanid vpls-name' ;
        leaf mac-address {
          description 'Client hardware MAC address.' ;
          type ncd:mac-address ;

        }

        leaf vlanid {
          description 'Client VLAN ID.' ;
          type uint16 {
            range 0..4094 ;

          }

        }

        leaf vpls-name {
          description 'Client instance Name of VPLS.' ;
          type string {
            length 0..32 ;

          }

        }

        leaf layer {
          description 'Client layer.' ;
          type uint8 ;

        }

        leaf external-vlanid {
          description 'Client external-VLAN ID.' ;
          type uint16 {
            range 0..4094 ;

          }

        }

        leaf internal-vlanid {
          description 'Client external-VLAN ID.' ;
          type uint16 {
            range 0..4094 ;

          }

        }

        leaf type {
          description 'Client type.' ;
          type database-type ;

        }

        leaf if-name {
          description 'Interface name.' ;
          type ncd:ifname ;

        }

        leaf ip-address {
          description 'Client IP address assigned from the DHCP server.' ;
          type ncd:ipv4-address ;

        }

        leaf expiration {
          description 'Client expiration.' ;
          type string ;

        }

        leaf option82 {
          description 'Client option82. This option82 is available for ASCII characters.' ;
          type ncd:string-all {
            length 0..255 ;

          }

        }

        leaf option82-all-chars {
          description 'Client option82. This option82 is available for all kinds of characters.' ;
          type string {
            length 0..255 ;

          }

          ncd:revise-date 2019-10-31 ;
        }

        leaf gateway-address {
          description 'Gateway IP address.' ;
          type ncd:ipv4-address ;

        }

        leaf vrf-name {
          description 'Client VRF instance name.' ;
          type string {
            length 0..32 ;

          }

        }

        ncd:select if-name ;
      }

      list database-vxlan {
        if-feature vxlan ;

        description 'DHCP snooping binding database.' ;
        key 'mac-address ip-address vxlanid' ;
        leaf vxlanid {
          description 'VXLAN ID.' ;
          type uint32 {
            range 0..16777215 ;

          }

        }

        leaf mac-address {
          description 'Client hardware MAC address.' ;
          type ncd:mac-address ;

        }

        leaf ip-address {
          description 'Client IP address assigned from the DHCP server.' ;
          type ncd:ipv4-address ;

        }

        leaf layer {
          description 'Client layer.' ;
          type uint8 ;

        }

        leaf external-vlanid {
          description 'Client external-VLAN ID.' ;
          type uint16 {
            range 0..4094 ;

          }

        }

        leaf internal-vlanid {
          description 'Client external-VLAN ID.' ;
          type uint16 {
            range 0..4094 ;

          }

        }

        leaf type {
          description 'Client type.' ;
          type database-type ;

        }

        leaf if-name {
          description 'Interface name.' ;
          type ncd:ifname ;

        }

        leaf expiration {
          description 'Client expiration.' ;
          type string ;

        }

        leaf option82 {
          description 'Client option82. This option82 is available for ASCII characters.' ;
          type ncd:string-all {
            length 0..255 ;

          }

        }

        leaf option82-all-chars {
          description 'Client option82. This option82 is available for all kinds of characters.' ;
          type string {
            length 0..255 ;

          }

          ncd:revise-date 2019-10-31 ;
        }

        leaf gateway-address {
          description 'Gateway IP address.' ;
          type ncd:ipv4-address ;

        }

        ncd:revise-date 2017-08-16 ;
        ncd:select if-name ;
      }

      list database-evpn-vpls {
        if-feature evpn-vpls ;

        description 'DHCP snooping binding database.' ;
        key 'evpn-vpls-name mac-address ip-address' ;
        leaf evpn-vpls-name {
          description 'Client instance Name of EVPN VPLS.' ;
          type string {
            length 0..32 ;

          }

        }

        leaf mac-address {
          description 'Client hardware MAC address.' ;
          type ncd:mac-address ;

        }

        leaf ip-address {
          description 'Client IP address assigned from the DHCP server.' ;
          type ncd:ipv4-address ;

        }

        leaf layer {
          description 'Client layer.' ;
          type uint8 ;

        }

        leaf type {
          description 'Client type.' ;
          type database-type ;

        }

        leaf vni {
          description 'Client VNI ID.' ;
          type uint32 ;

        }

        leaf phy-if-name {
          description 'Interface name.' ;
          type ncd:ifname ;

        }

        leaf if-name {
          description 'Interface name.' ;
          type ncd:ifname ;

        }

        leaf expiration {
          description 'Client expiration.' ;
          type string ;

        }

        leaf gateway-address {
          description 'Gateway IP address.' ;
          type ncd:ipv4-address ;

        }

        ncd:revise-date 2019-05-16 ;
        ncd:select if-name ;
      }

    }

  }

}
