module zxr10-inband-oam {
  namespace "http://www.zte.com.cn/zxr10/netconf/schema/rosng/inband-oam" ;
  prefix inband-oam ;
  yang-version 1 ;
  import zxr10-netconf-defs {
    prefix ncd ;
  }

  organization "ZTE Corporation" ;
  contact "ZTE Corporation
  Nanjing Institute of ZTE Corporation
  No.68 Zijinghua Rd. Yuhuatai District, Nanjing, China
  Tel: +86-25-52870000" ;
  revision 2025-02-13 {
    description 'Add node of state/inband-oam/flow-informations.' ;
  }

  revision 2024-08-05 {
    description '1. Add leaf of binding-device-mode to configuration/inband-oam-ex/global.
2. Add leaf of binding-device-mode to configuration/inband-oam-ex/instances/instance.
3. Add leaf of addr-family to configuration/inband-oam-ex/instances/instance/flow-info/peer-locator.' ;
  }

  revision 2024-07-30 {
    description '1. Add leaf of age-period-mult to configuration/inband-oam-ex/global.' ;
  }

  revision 2024-04-16 {
    description '1. Add leaf of transit-point-oam-status to configuration/inband-oam-ex/global.' ;
  }

  revision 2024-03-23 {
    description '1. Add container of configuration/interfaces.' ;
  }

  revision 2023-12-28 {
    description 'Add choice node of vpn-type on configuration/inband-oam-ex/instances/instance/flow-info/peer-locator with cases as follow:
1. Case of vrf with leaf node vrf-name;
2. Case of vpws with leaf node vpws-name;
3. Case of evpn-vpws with leaf node evpn-vpws-name;
4. Case of vpls with leaf node vpls-name.' ;
  }

  revision 2023-07-11 {
    description '1. Add container of configuration/inband-oam-ex/instances/instance/flow-info/sr-policy.
2. Add leaf of configuration/inband-oam-ex/global/trace-packet-parse.
3. Add a new enumeration value of doh-post to configuration/inband-oam-ex/global/trace-encap-mode.
4.Add feature of sr-policy.
5.Add feature of trace-packet-parse.' ;
  }

  revision 2022-10-13 {
    description '1. Add leaf of device-ip to configuration/inband-oam-ex/global.
2. Add leaf of mode to configuration/inband-oam-ex/instances/instance.' ;
  }

  revision 2022-06-13 {
    description '1. Add state/flow-mappings.
2. Add operation/flow-mappings.
3. Add feature of flow-mappings.
4. Add feature of peer-locator.' ;
  }

  revision 2022-04-25 {
    description '1. Add container of configuration/inband-oam-ex/instances/instance/flow-info/peer-locator.' ;
  }

  revision 2022-03-29 {
    description '1. Add container of configuration/inband-oam-ex/instances/instance/flow-info/eth.' ;
  }

  revision 2022-02-07 {
    description '1.Add leaf of configuration/inband-oam/global/period.
2.Add leaf of configuration/inband-oam/global/decapsulation-status.
3.Add feature of global-period.
4.Add feature of global-decapsulation.' ;
  }

  revision 2021-10-08 {
    description '1. Reconstructed configuration/inband-oam-ex/instances/instance.' ;
  }

  revision 2021-08-24 {
    description '1.Change all ipv6 address type form "ipv6-address" to "ipv6-address-none-zero".' ;
  }

  revision 2021-08-05 {
    description '1. Add configuration/inband-oam-ex.' ;
  }

  revision 2021-07-27 {
    description '1. Add feature access-if-list.
2. Add feature access-vrf.' ;
  }

  revision 2021-04-27 {
    description '1.Add leaf of configuration/inband-oam/relations/relation/hop-by-hop-status.' ;
  }

  revision 2021-04-01 {
    description '1. Add leaf of configuration/inband-oam/flows/flow/flow-type/ip/ipv4-or-ipv6/ipv4/source-mask-length.
2. Add leaf of configuration/inband-oam/flows/flow/flow-type/ip/ipv4-or-ipv6/ipv4/dest-mask-length.
3. Add leaf of configuration/inband-oam/flows/flow/flow-type/ip/ipv4-or-ipv6/ipv6/source-mask-length.
4. Add leaf of configuration/inband-oam/flows/flow/flow-type/ip/ipv4-or-ipv6/ipv6/dest-mask-length.
5. Add container of configuration/inband-oam/flows/flow/flow-type/ip/interface-list.
6. Add container of configuration/inband-oam/flows/flow/flow-type/ip/vrf.
7. Add container of configuration/inband-oam/interface-lists.' ;
  }

  revision 2021-03-17 {
    description '1. Add leaf of configuration/inband-oam/flows/flow/flow-type/ip/vpn-type.' ;
  }

  revision 2021-02-24 {
    description '1. Add presence to configuration/inband-oam/flows/flow/flow-type/ip/eth.' ;
  }

  revision 2021-02-01 {
    description '1.Add leaf of configuration/inband-oam/flows/flow/per-packet-dm-status.
2.Add leaf of configuration/inband-oam/relations/relation/per-packet-dm-status.
3.Add feature of per-packet-dm.' ;
  }

  revision 2021-01-20 {
    description '1. Add vpls case of configuration/relations/relation/vpn-type.' ;
  }

  revision 2021-01-08 {
    description '1. Add evpn-vpws case of configuration/relations/relation/vpn-type.' ;
  }

  revision 2020-06-05 {
    description '1. Add feature eth-flow.
2. Add feature tunnel-flow.
3. Add feature vpws-name.
4. Add container of configuration/inband-oam/flows/flow/flow-type/ip/eth.
5. Add container of configuration/relations/relation/vpn-type,which include the case of vrf and the case of vpws.
6. Add leaf of configuration/relations/relation/vpws-name.' ;
  }

  revision 2020-05-22 {
    description '1. Add leaf node configuration/inband-oam/flows/flow/flow-type/ip/member-port.' ;
  }

  revision 2019-10-30 {
    description '1 Modify configuration/relations/relation/vrf-name,change its mandatory status from false to true.' ;
  }

  revision 2019-09-09 {
    description '1 Add configuration/inband-oam/flows/flow/hop-by-hop-status.
2 Add configuration/relations/relation/period.
3 Add configuration/relations/relation/interfaces.' ;
  }

  revision 2019-01-31 {
    description '1. Add feature relation.
2. Add configuration/global.
3. Add configuration/relations.
4. Modify the range of configuration/inband-oam/flows/flow/flow-id.
5. Modify the range of configuration/inband-oam/decapsulation/decapsulation-no-ifname/flow-id.
6. Modify the range of configuration/inband-oam/decapsulation/decapsulation-with-ifname/flow-id.
7. Add configuration/inband-oam/flows/flow/dm-dscp.
8. Add configuration/inband-oam/flows/flow/dm-exp.
9. Add configuration/inband-oam/flows/flow/flow-type/ip/protocol.
10. Add configuration/inband-oam/flows/flow/flow-type/ip/source-port.
11. Add configuration/inband-oam/flows/flow/flow-type/ip/dest-port.
12. Add configuration/inband-oam/flows/flow/flow-type/ip/dscp.
13. Add an enumeration value 1s for typedef of alternate-marking-period and modify the default value to 30s. 
13. Modify the default value of configuration/inband-oam/flows/flow/period.
14. Remove the mandatory feature of source-addr-ipv4 and dest-addr-ipv4 in configuration/inband-oam/flows/flow/flow-type/ip/ipv4-or-ipv6/ipv4.
15. Remove the mandatory feature of source-addr-ipv6 and dest-addr-ipv6 in configuration/inband-oam/flows/flow/flow-type/ip/ipv4-or-ipv6/ipv6.' ;
  }

  revision 2018-10-30 {
    description 'Initial version.' ;
  }

  feature relation {
    description 'Configure the relation between Flowid and VRF.' ;
  }

  feature eth-flow {
    description 'Support the flow of eth.' ;
  }

  feature tunnel-flow {
    description 'Support the flow of tunnel.' ;
  }

  feature dm {
    description 'Support the operation of DM.' ;
  }

  feature vpws-name {
    description 'Support the configuration of vpws-name.' ;
  }

  feature evpn-vpnws {
    description 'Support the configuration of evpn-vpws.' ;
  }

  feature l2vpn-vpls {
    description 'Support the configuration of vpls.' ;
  }

  feature per-packet-dm {
    description 'Support the configuration of per-packet-dm.' ;
  }

  feature vpn-type {
    description 'Support the configuration of vpn-type.' ;
  }

  feature mask-length {
    description 'Support the configuration of mask-length.' ;
  }

  feature relation-hop-by-hop ;

  feature access-if-list {
    description 'Support interface list access.' ;
  }

  feature access-vrf {
    description 'Support vrf access.' ;
  }

  feature inband-oam-ex {
    description 'In-suit OAM support.' ;
  }

  feature global-period {
    description 'Support the configuration of global period.' ;
    ncd:revise-date 2022-02-07 ;
  }

  feature global-decapsulation {
    description 'Support the configuration of global decapsulation.' ;
    ncd:revise-date 2022-02-07 ;
  }

  feature peer-locator {
    description 'Peer locator support.' ;
    ncd:revise-date 2022-06-13 ;
  }

  feature flow-mapping {
    description 'Flow mapping support.' ;
    ncd:revise-date 2022-06-13 ;
  }

  feature native-ip {
    description 'Native-ip network support.' ;
    ncd:revise-date 2022-10-13 ;
  }

  feature sr-policy {
    description 'SR policy support.' ;
    ncd:revise-date 2023-07-11 ;
  }

  feature trace-packet-parse {
    description 'Trace packet parsing support.' ;
    ncd:revise-date 2023-07-11 ;
  }

  feature interface-ioam-data-processing-mode {
    description 'Interface ioam data processing mode.' ;
    ncd:revise-date 2024-03-23 ;
  }

  feature transit-point-oam {
    description 'IOAM function support for SRv6 transit point.' ;
    ncd:revise-date 2024-04-16 ;
  }

  feature binding-device-mode {
    description 'IOAM flow ID supports device-level allocation.' ;
    ncd:revise-date 2024-08-05 ;
  }

  feature age-period-multiple {
    description 'The multiple of dynamic flow aging time.' ;
    ncd:revise-date 2024-07-30 ;
  }

  feature addr-family {
    description 'IP address family support.' ;
    ncd:revise-date 2024-08-05 ;
  }

  typedef alternate-marking-period {
    type enumeration {
      enum 5s {
        value 1 ;
        description 'Alternate marking period is 5s.' ;
      }

      enum 10s {
        value 2 ;
        description 'Alternate marking period is 10s.' ;
      }

      enum 30s {
        value 3 ;
        description 'Alternate marking period is 30s.' ;
      }

      enum 60s {
        value 4 ;
        description 'Alternate marking period is 60s.' ;
      }

      enum 5min {
        value 5 ;
        description 'Alternate marking period is 5min.' ;
      }

      enum 15min {
        value 6 ;
        description 'Alternate marking period is 15min.' ;
      }

      enum 1s {
        value 7 ;
        description 'Alternate marking period is 1s.' ;
      }

    }

    default 30s ;
    description 'Alternate marking period,including 1s,5s,10s,30s,60s,5min and 15min(default:30s).' ;
  }

  container configuration {
    description 'Configuration of inband OAM model Info.' ;
    container interfaces {
      list interface {
        leaf ifName {
          description 'Interface name.' ;
          type ncd:ifname {
            length 1..31 ;

          }

        }

        leaf ioam-data-processing-mode {
          description 'Interface ioam data processing mode.' ;
          mandatory true ;
          type enumeration {
            enum decapsulation {
              value 1 ;
              description 'Decapsulation mode' ;
            }

            enum inheritance {
              description 'Inheritance mode' ;
              value 2 ;
            }

          }

        }

        description 'Inband OAM interface configuration.' ;
        key ifName ;
      }

      if-feature interface-ioam-data-processing-mode ;

      description 'Inband OAM interfaces configuration.' ;
      ncd:revise-date 2024-03-23 ;
    }

    container inband-oam {
      description 'Inband OAM flow alternate marking configuration.' ;
      container global {
        description 'Global configuration.' ;
        leaf label {
          description 'The label ranges from 4 to 6 and 8 to 12(default:12).' ;
          type uint32 {
            range "4..6 | 8..12" {
              description 'The range of the label.' ;
            }

          }

          default 12 ;
        }

        leaf period {
          if-feature global-period ;

          description 'The global period of flow coloring,range form 1 to 256(default 10).' ;
          type uint16 {
            range 1..256 ;

          }

          units s ;
          default 10 ;
          ncd:revise-date 2022-02-07 ;
        }

        leaf decapsulation-status {
          if-feature global-decapsulation ;

          description 'Inband OAM flow global decapsulation configuration.' ;
          type enumeration {
            enum disable {
              value 0 ;
            }

            enum enable {
              value 1 ;
            }

          }

          default disable ;
          ncd:revise-date 2022-02-07 ;
        }

        ncd:revise-date 2019-01-31 ;
      }

      container interface-lists {
        if-feature access-if-list ;

        description 'Configure inband OAM interface list.' ;
        list interface-list {
          description 'Configure inband OAM interface list.' ;
          key if-list-name ;
          leaf if-list-name {
            description 'The interface list name.' ;
            type string {
              length 1..31 {
                description 'The range of interface list name length.' ;
              }

            }

          }

          container interfaces {
            description 'Configure interfaces of interface-list.' ;
            list interface {
              description 'Configure interfaces of interface-list.' ;
              key ifname ;
              leaf ifname {
                description 'The interface name of interface-list.' ;
                type ncd:ifname {
                  length 1..31 {
                    description 'The range of interface name length.' ;
                  }

                }

              }

            }

          }

        }

        ncd:revise-date 2021-04-01 ;
      }

      container flows {
        description 'Configure inband OAM flow coloring.' ;
        list flow {
          description 'Configure inband OAM flow coloring.' ;
          key flow-id ;
          leaf flow-id {
            description 'The flow id to identify a specific flow,ranges from 1 to 1048575.' ;
            type uint32 {
              range 1..1048575 {
                description 'The range of flow id.' ;
              }

            }

          }

          leaf alternate-status {
            description 'The status of flow alternate marking,including enable and disable(default:enable).' ;
            type enumeration {
              enum disable {
                value 0 ;
                description 'The status of flow alternate marking is disable.' ;
              }

              enum enable {
                value 1 ;
                description 'The status of flow alternate marking is enable.' ;
              }

            }

            default enable ;
          }

          leaf period {
            description 'The period of flow coloring,including 1s,5s,10s,30s,60s,5min and 15min(default:30s).' ;
            type alternate-marking-period ;

            default 30s ;
          }

          leaf dm-dscp {
            if-feature dm ;

            description 'The DSCP value in delay measurement of IP flow,ranges from 0 to 63.' ;
            type uint8 {
              range 0..63 {
                description 'The range of DSCP.' ;
              }

            }

            ncd:revise-date 2019-01-31 ;
          }

          leaf dm-exp {
            if-feature dm ;

            description 'The EXP value in delay measurement of TE tunnel,ranges from 0 to 7.' ;
            type uint8 {
              range 0..7 {
                description 'The range of EXP.' ;
              }

            }

            ncd:revise-date 2019-01-31 ;
          }

          leaf hop-by-hop-status {
            description 'The status of hop-by-hop coloring,including enable and disable(default:enable).' ;
            type enumeration {
              enum disable {
                value 0 ;
                description 'Disable hop-by-hop coloring.' ;
              }

              enum enable {
                value 1 ;
                description 'Enable hop-by-hop coloring.' ;
              }

            }

            default disable ;
            ncd:revise-date 2019-09-09 ;
          }

          leaf per-packet-dm-status {
            if-feature per-packet-dm ;

            description 'The status of per-packet delay measurement,including enable and disable(default:enable).' ;
            type enumeration {
              enum disable {
                value 0 ;
                description 'Disable per-packet DM.' ;
              }

              enum enable {
                value 1 ;
                description 'Enable per-packet DM.' ;
              }

            }

            default disable ;
            ncd:revise-date 2021-02-01 ;
          }

          container flow-type {
            description 'Choose one flow type from ip and TE tunnel.' ;
            choice flow-type {
              description 'Choose one flow type from ip and TE tunnel.' ;
              mandatory true ;
              case ip {
                description 'The coloring flow type is ip.' ;
                container ip {
                  description 'The coloring flow type is ip.' ;
                  choice access-type {
                    description 'Choose access type from interface, interface list and VRF.' ;
                    case interface {
                      description 'The access type is interface.' ;
                      leaf ifname {
                        description 'The UNI interface name of ip flow.' ;
                        type ncd:ifname {
                          length 1..31 {
                            description 'The range of interface name length.' ;
                          }

                        }

                        mandatory true ;
                      }

                    }

                    case interface-list {
                      if-feature access-if-list ;

                      description 'The access type is interface list.' ;
                      container interface-list {
                        description 'The access type is interface list.' ;
                        leaf if-list-name {
                          description 'The access interface list name of ip flow.' ;
                          type string {
                            length 1..31 {
                              description 'The range of interface list name length.' ;
                            }

                          }

                          mandatory true ;
                        }

                      }

                    }

                    case vrf {
                      if-feature access-vrf ;

                      description 'The access type is VRF.' ;
                      container vrf {
                        description 'The access type is VRF.' ;
                        leaf vrf-name {
                          description 'The access VRF name of ip flow.' ;
                          type string {
                            length 1..35 {
                              description 'The range of VRF name length.' ;
                            }

                          }

                          mandatory true ;
                        }

                        leaf if-list-name {
                          description 'The access interface list name of ip flow.' ;
                          type string {
                            length 1..31 {
                              description 'The range of interface list name length.' ;
                            }

                          }

                        }

                      }

                    }

                    ncd:revise-date 2021-04-01 ;
                  }

                  leaf member-port {
                    description 'The member port of the UNI interface.' ;
                    type ncd:ifname {
                      length 1..31 {
                        description 'The range of interface name length.' ;
                      }

                    }

                    ncd:revise-date 2020-06-05 ;
                  }

                  container ipv4-or-ipv6 {
                    description 'Choose one from ipv4 and ipv6.' ;
                    choice ipv4-or-ipv6 {
                      description 'Choose one from ipv4 and ipv6.' ;
                      case ipv4 {
                        description 'Type is ipv4.' ;
                        container ipv4 {
                          description 'Type is ipv4.' ;
                          leaf source-addr-ipv4 {
                            description 'The source ipv4 address.' ;
                            type ncd:ipv4-address-none-zero ;

                          }

                          leaf dest-addr-ipv4 {
                            description 'The destination ipv4 address.' ;
                            type ncd:ipv4-address-none-zero ;

                          }

                          leaf source-mask-length {
                            if-feature mask-length ;

                            description 'The source IP mask length.' ;
                            type uint8 {
                              range 1..32 {
                                description 'The source IP mask length.' ;
                              }

                            }

                            ncd:revise-date 2021-04-01 ;
                          }

                          leaf dest-mask-length {
                            if-feature mask-length ;

                            description 'The destination IP mask length.' ;
                            type uint8 {
                              range 1..32 {
                                description 'The source IP mask length.' ;
                              }

                            }

                            ncd:revise-date 2021-04-01 ;
                          }

                        }

                      }

                      case ipv6 {
                        description 'Type is ipv6.' ;
                        container ipv6 {
                          description 'Type is ipv6.' ;
                          leaf source-addr-ipv6 {
                            description 'The source ipv6 address.' ;
                            type ncd:ipv6-address-none-zero ;

                          }

                          leaf dest-addr-ipv6 {
                            description 'The destination ipv6 address.' ;
                            type ncd:ipv6-address-none-zero ;

                          }

                          leaf source-mask-length {
                            if-feature mask-length ;

                            description 'The source IP mask length.' ;
                            type uint8 {
                              range 1..128 {
                                description 'The destination IP mask length.' ;
                              }

                            }

                            ncd:revise-date 2021-04-01 ;
                          }

                          leaf dest-mask-length {
                            if-feature mask-length ;

                            description 'The destination IP mask length.' ;
                            type uint8 {
                              range 1..128 {
                                description 'The destination IP mask length.' ;
                              }

                            }

                            ncd:revise-date 2021-04-01 ;
                          }

                        }

                      }

                    }

                  }

                  leaf protocol {
                    description 'The protocol number,ranges from 1 to 255.' ;
                    type uint8 {
                      range 1..255 {
                        description 'The range of protocol.' ;
                      }

                    }

                    ncd:revise-date 2019-01-31 ;
                  }

                  leaf source-port {
                    description 'The source port,ranges from 1 to 65535.' ;
                    type uint16 {
                      range 1..65535 {
                        description 'The range of port number.' ;
                      }

                    }

                    ncd:revise-date 2019-01-31 ;
                  }

                  leaf dest-port {
                    description 'The destination port,ranges from 1 to 65535.' ;
                    type uint16 {
                      range 1..65535 {
                        description 'The range of port number.' ;
                      }

                    }

                    ncd:revise-date 2019-01-31 ;
                  }

                  leaf dscp {
                    description 'The value of DSCP,ranges from 0 to 63.' ;
                    type uint8 {
                      range 0..63 {
                        description 'The range of DSCP.' ;
                      }

                    }

                    ncd:revise-date 2019-01-31 ;
                  }

                  container eth {
                    if-feature eth-flow ;

                    description 'The coloring flow type is eth.' ;
                    presence eth ;
                    leaf source-mac {
                      description 'The source MAC address.' ;
                      type ncd:mac-address-none-zero ;

                    }

                    leaf dest-mac {
                      description 'The destination MAC address.' ;
                      type ncd:mac-address-none-zero ;

                    }

                    leaf vlan-id {
                      description 'The value of vlan ID,ranges from 1 to 4094.' ;
                      type uint16 {
                        range 1..4094 {
                          description 'The range of VLAN ID.' ;
                        }

                      }

                    }

                    leaf internal-vlan-id {
                      description 'The value of internal vlan ID,ranges from 1 to 4094.' ;
                      type uint16 {
                        range 1..4094 {
                          description 'The range of internal VLAN ID.' ;
                        }

                      }

                    }

                    leaf priority-8021p {
                      description 'The value of priority-8021p,ranges from 0 to 7.' ;
                      type uint8 {
                        range 0..7 {
                          description 'The range of priority-8021p.' ;
                        }

                      }

                    }

                    ncd:revise-date 2020-06-05 ;
                  }

                  leaf vpn-type {
                    if-feature vpn-type ;

                    description 'The VPN type of the UNI interface.' ;
                    type enumeration {
                      enum l2 {
                        value 1 ;
                        description 'The L2 VPN type of the UNI interface.' ;
                      }

                      enum l3 {
                        value 0 ;
                        description 'The L3 VPN type of the UNI interface.' ;
                      }

                    }

                    ncd:revise-date 2021-03-17 ;
                  }

                }

              }

              case tunnel {
                description 'The coloring flow type is TE tunnel.' ;
                container tunnel {
                  if-feature tunnel-flow ;

                  description 'The coloring flow type is TE tunnel.' ;
                  leaf tunnel-id {
                    description 'Tunnel ID,the upper limit of this parameter depend on the device.' ;
                    type uint32 {
                      range 1..131072 {
                        description 'The range of tunnel id.' ;
                      }

                    }

                    mandatory true ;
                  }

                }

              }

            }

          }

        }

      }

      container decapsulation {
        description 'Inband OAM flow decapsulation configuration.' ;
        list decapsulation-no-ifname {
          description 'Configure flow decapsulation function.' ;
          key flow-id ;
          leaf flow-id {
            description 'The flow id to identify a specific flow,ranges from 1 to 1048575.' ;
            type uint32 {
              range 1..1048575 {
                description 'The range of flow id,ranges from 1 to 1048575.' ;
              }

            }

          }

        }

        list decapsulation-with-ifname {
          description 'Configure flow decapsulation function.' ;
          key 'flow-id ifname' ;
          leaf flow-id {
            description 'The flow id to identify a specific flow,ranges from 1 to 1048575.' ;
            type uint32 {
              range 1..1048575 {
                description 'The range of flow id,ranges from 1 to 1048575.' ;
              }

            }

          }

          leaf ifname {
            description 'The physical interface name passed through by the flow.' ;
            type ncd:ifname {
              length 1..31 {
                description 'The range of interface name length.' ;
              }

            }

          }

        }

      }

      container relations {
        if-feature relation ;

        description 'Configure the relation between Flowid and VRF.' ;
        list relation {
          description 'Configure the relation between Flowid and VRF.' ;
          key flow-id ;
          leaf flow-id {
            description 'The flow id to identify a specific flow,ranges from 1 to 1048575.' ;
            type uint32 {
              range 1..1048575 {
                description 'The range of flow-id.' ;
              }

            }

          }

          choice vpn-type {
            description 'Choose one from vrf and vpws.' ;
            case vrf {
              description 'Type is VRF.' ;
              leaf vrf-name {
                description 'The name of VRF,this string length ranges from 1 to 32.' ;
                type string {
                  length 1..32 {
                    description 'This string length ranges from 1 to 32.' ;
                  }

                }

                mandatory true ;
              }

            }

            case vpws {
              description 'Type is vpws.' ;
              leaf vpws-name {
                if-feature vpws-name ;

                description 'The name of VPWS,this string length ranges from 1 to 32.' ;
                type string {
                  length 1..32 {
                    description 'This string length ranges from 1 to 32.' ;
                  }

                }

                mandatory true ;
              }

            }

            case evpn-vpws {
              if-feature evpn-vpnws ;

              description 'Type is EVPN VPWS.' ;
              leaf evpn-vpws-name {
                description 'EVPN VPWS name,this string length ranges from 1 to 32.' ;
                type string {
                  length 1..32 {
                    description 'This string length ranges from 1 to 32.' ;
                  }

                }

                mandatory true ;
              }

              leaf ifname {
                description 'Access point bound to the EVPN.' ;
                type ncd:ifname {
                  length 1..31 {
                    description 'The range of interface name length.' ;
                  }

                }

                mandatory true ;
              }

              ncd:revise-date 2021-01-08 ;
            }

            case vpls {
              if-feature l2vpn-vpls ;

              description 'Type is VPLS.' ;
              leaf vpls-name {
                description 'The name of VPLS,this string length ranges from 1 to 32.' ;
                type string {
                  length 1..32 {
                    description 'This string length ranges from 1 to 32.' ;
                  }

                }

              }

              ncd:revise-date 2021-01-20 ;
            }

            ncd:revise-date 2020-06-05 ;
          }

          leaf period {
            description 'The flip period of relation,range form 1000 to 900000(default 30000).' ;
            type uint32 {
              range 1000..900000 {
                description 'The value of this parameter ranges from 1000ms to 900000ms(default:30000ms).' ;
              }

            }

            units ms ;
            default 30000 ;
            ncd:revise-date 2019-09-09 ;
          }

          leaf per-packet-dm-status {
            if-feature per-packet-dm ;

            description 'The status of per-packet delay measurement,including enable and disable(default:enable).' ;
            type enumeration {
              enum disable {
                value 0 ;
                description 'Disable per-packet DM.' ;
              }

              enum enable {
                value 1 ;
                description 'Enable per-packet DM.' ;
              }

            }

            default disable ;
            ncd:revise-date 2021-02-01 ;
          }

          leaf hop-by-hop-status {
            if-feature relation-hop-by-hop ;

            description 'The status of hop-by-hop,including enable and disable(default:enable).' ;
            type enumeration {
              enum disable {
                value 0 ;
                description 'Disable hop-by-hop coloring.' ;
              }

              enum enable {
                value 1 ;
                description 'Enable hop-by-hop coloring.' ;
              }

            }

            default disable ;
            ncd:revise-date 2021-04-27 ;
          }

          container interfaces {
            description 'Configure interfaces of relation.' ;
            list interface {
              description 'Configure interface of relation.' ;
              key ifname ;
              leaf ifname {
                description 'The UNI interface name of relation.' ;
                type ncd:ifname {
                  length 1..31 {
                    description 'The range of interface name length.' ;
                  }

                }

              }

            }

            ncd:revise-date 2019-09-09 ;
          }

        }

        ncd:revise-date 2019-01-31 ;
      }

    }

    container inband-oam-ex {
      if-feature inband-oam-ex ;

      description 'In-suit OAM configuration.' ;
      container global {
        description 'Global configuration.' ;
        leaf oam-status {
          description 'The status of global OAM function.' ;
          type enumeration {
            enum disable {
              value 0 ;
              description 'Disable OAM.' ;
            }

            enum enable {
              value 1 ;
              description 'Enable OAM.' ;
            }

          }

          default disable ;
        }

        leaf device-id {
          description 'Device ID.' ;
          type uint32 {
            range 1..1048575 ;

          }

        }

        leaf trace-encap-mode {
          description 'The packet encapsulation mode for hop-by-hop measurement.' ;
          type enumeration {
            enum doh {
              value 0 ;
              description 'DOH encapsulation mode.' ;
            }

            enum srh-tlv {
              value 1 ;
              description 'SRH tlv encapsulation mode.' ;
            }

            enum doh-post {
              value 2 ;
              description 'DOH postposition encapsulation mode.' ;
            }

          }

          default doh ;
          ncd:revise-date 2022-03-29 ;
        }

        leaf device-ip {
          if-feature native-ip ;

          description 'Device IP address.' ;
          status obsolete {
            ncd:revise-date 2024-08-05 ;
          }

          type ncd:ipv4-address-none-zero ;

          ncd:revise-date 2022-10-13 ;
        }

        leaf trace-packet-parse {
          type enumeration {
            enum disable {
              value 0 ;
              description 'Disable trace packet parsing.' ;
            }

            enum enable {
              description 'Enable trace packet parsing.' ;
              value 1 ;
            }

          }

          default disable ;
          description 'The status of intermediate node packet parsing in hop-by-hop measurement.' ;
          if-feature trace-packet-parse ;

          ncd:revise-date 2023-07-11 ;
        }

        leaf transit-point-oam-status {
          if-feature transit-point-oam ;

          type enumeration {
            enum disable {
              description 'Disable oam function for SRv6 transit point.' ;
              value 0 ;
            }

            enum enable {
              description 'Enable oam function for SRv6 transit point.' ;
              value 1 ;
            }

          }

          description 'Inband OAM status configuration for SRv6 transit point.' ;
          default disable ;
          ncd:revise-date 2024-04-16 ;
        }

        leaf age-period-mult {
          type uint16 {
            range 1..200 ;

          }

          description 'The multiple of dynamic flow aging time, the aging time is equal to the period multiplied by the multiple.' ;
          default 3 ;
          if-feature age-period-multiple ;

          ncd:revise-date 2024-07-30 ;
        }

        leaf binding-device-mode {
          type enumeration {
            enum interface-based {
              value 0 ;
              description 'Interface-based mode' ;
            }

            enum device-based {
              value 1 ;
              description 'Device-based mode' ;
            }

          }

          description 'The device mode of IOAM egress node.' ;
          default interface-based ;
          if-feature binding-device-mode ;

          ncd:revise-date 2024-08-05 ;
        }

      }

      container instances {
        description 'In-suit OAM instances configuration.' ;
        list instance {
          description 'Instance configuration.' ;
          key instance-name ;
          leaf instance-name {
            description 'Instance name.' ;
            type string {
              length 1..31 ;

            }

          }

          leaf oam-status {
            description 'The status of in-suit OAM,including enable and disable(default:enable).' ;
            type enumeration {
              enum disable {
                value 0 ;
                description 'The status of flow alternate marking is disable.' ;
              }

              enum enable {
                value 1 ;
                description 'The status of flow alternate marking is enable.' ;
              }

            }

            default enable ;
          }

          leaf measure-type {
            description 'The measure type of in-suit OAM,including e2e and trace(default:e2e).' ;
            type enumeration {
              enum e2e {
                value 0 ;
                description 'End to end.' ;
              }

              enum trace {
                value 1 ;
                description 'Trace.' ;
              }

            }

            default e2e ;
          }

          leaf period {
            description 'The period of flow coloring,including 1s,5s,10s,30s,60s,5min and 15min(default:30s).' ;
            type alternate-marking-period ;

            default 30s ;
          }

          leaf dm-status {
            description 'Delay measurement status,including enable and disable(default:disable).' ;
            type enumeration {
              enum disable {
                value 0 ;
                description 'Disable DM.' ;
              }

              enum enable {
                value 1 ;
                description 'Enable DM.' ;
              }

            }

            default disable ;
          }

          leaf mode {
            if-feature native-ip ;

            description 'Network mode.' ;
            type enumeration {
              enum srv6 {
                value 0 ;
                description 'Srv6 mode.' ;
              }

              enum native-ip {
                value 1 ;
                description 'Native-ip mode.' ;
              }

            }

            default srv6 ;
            ncd:revise-date 2022-10-13 ;
          }

          leaf binding-device-mode {
            description 'Device-level IOAM switch, including enable and disable (default:disable).' ;
            type enumeration {
              enum disable {
                value 0 ;
                description 'Disable' ;
              }

              enum enable {
                value 1 ;
                description 'Enable' ;
              }

            }

            default disable ;
            if-feature binding-device-mode ;

            ncd:revise-date 2024-08-05 ;
          }

          container flow-info {
            description 'Flow Information configuration.' ;
            container ip {
              description 'The flow type is ip.' ;
              choice ip-addr-family {
                description 'Choose one from ipv4 and ipv6.' ;
                case ipv4 {
                  description 'Type is ipv4.' ;
                  container ipv4 {
                    description 'Type is ipv4.' ;
                    leaf source-addr-ipv4 {
                      description 'The source ipv4 address.' ;
                      type ncd:ipv4-address-none-zero ;

                    }

                    leaf dest-addr-ipv4 {
                      description 'The destination ipv4 address.' ;
                      type ncd:ipv4-address-none-zero ;

                    }

                    leaf source-mask-length {
                      if-feature mask-length ;

                      description 'The source IP mask length.' ;
                      type uint8 {
                        range 1..32 {
                          description 'The source IP mask length.' ;
                        }

                      }

                    }

                    leaf dest-mask-length {
                      if-feature mask-length ;

                      description 'The destination IP mask length.' ;
                      type uint8 {
                        range 1..32 {
                          description 'The source IP mask length.' ;
                        }

                      }

                    }

                  }

                }

                case ipv6 {
                  description 'Type is ipv6.' ;
                  container ipv6 {
                    description 'Type is ipv6.' ;
                    leaf source-addr-ipv6 {
                      description 'The source ipv6 address.' ;
                      type ncd:ipv6-address-none-zero ;

                    }

                    leaf dest-addr-ipv6 {
                      description 'The destination ipv6 address.' ;
                      type ncd:ipv6-address-none-zero ;

                    }

                    leaf source-mask-length {
                      if-feature mask-length ;

                      description 'The source IP mask length.' ;
                      type uint8 {
                        range 1..128 {
                          description 'The destination IP mask length.' ;
                        }

                      }

                    }

                    leaf dest-mask-length {
                      if-feature mask-length ;

                      description 'The destination IP mask length.' ;
                      type uint8 {
                        range 1..128 {
                          description 'The destination IP mask length.' ;
                        }

                      }

                    }

                  }

                }

              }

              leaf protocol {
                description 'The protocol number,ranges from 1 to 255.' ;
                type uint8 {
                  range 1..255 {
                    description 'The range of protocol.' ;
                  }

                }

              }

              leaf source-port {
                description 'The source port,ranges from 1 to 65535.' ;
                type uint16 {
                  range 1..65535 {
                    description 'The range of port number.' ;
                  }

                }

              }

              leaf dest-port {
                description 'The destination port,ranges from 1 to 65535.' ;
                type uint16 {
                  range 1..65535 {
                    description 'The range of port number.' ;
                  }

                }

              }

              leaf dscp {
                description 'The value of DSCP,ranges from 0 to 63.' ;
                type uint8 {
                  range 0..63 {
                    description 'The range of DSCP.' ;
                  }

                }

              }

              leaf vrf-name {
                description 'VRF name.' ;
                type string {
                  length 1..32 {
                    description 'This string length ranges from 1 to 32.' ;
                  }

                }

                ncd:revise-date 2021-10-08 ;
              }

            }

            container eth {
              description 'The coloring flow type is eth.' ;
              leaf source-mac {
                description 'The source MAC address.' ;
                type ncd:mac-address-none-zero ;

              }

              leaf dest-mac {
                description 'The destination MAC address.' ;
                type ncd:mac-address-none-zero ;

              }

              leaf vlan-id {
                description 'The value of vlan ID,ranges from 1 to 4094.' ;
                type uint16 {
                  range 1..4094 {
                    description 'The range of VLAN ID.' ;
                  }

                }

              }

              leaf internal-vlan-id {
                description 'The value of internal vlan ID,ranges from 1 to 4094.' ;
                type uint16 {
                  range 1..4094 {
                    description 'The range of internal VLAN ID.' ;
                  }

                }

              }

              leaf priority-8021p {
                description 'The value of priority-8021p,ranges from 0 to 7.' ;
                type uint8 {
                  range 0..7 {
                    description 'The range of priority-8021p.' ;
                  }

                }

              }

              choice l2vpn-type {
                case vpws {
                  leaf vpws-name {
                    type string {
                      length 1..32 {
                        description 'This string length ranges from 1 to 32.' ;
                      }

                    }

                    description 'The name of VPWS,this string length ranges from 1 to 32.' ;
                  }

                  description 'Type is VPWS.' ;
                }

                case evpn-vpws {
                  leaf evpn-vpws-name {
                    type string {
                      length 1..32 {
                        description 'This string length ranges from 1 to 32.' ;
                      }

                    }

                    description 'The name of EVPN VPWS,this string length ranges from 1 to 32.' ;
                  }

                  description 'Type is EVPN VPWS.' ;
                }

                case vpls {
                  leaf vpls-name {
                    type string {
                      length 1..32 {
                        description 'This string length ranges from 1 to 32.' ;
                      }

                    }

                    description 'The name of VPLS,this string length ranges from 1 to 32.' ;
                  }

                  description 'Type is VPLS.' ;
                }

                description 'Choose one L2VPN type.' ;
                ncd:revise-date 2023-12-28 ;
              }

              ncd:revise-date 2022-03-29 ;
            }

            container peer-locator {
              if-feature peer-locator {
                ncd:revise-date 2022-06-13 ;
              }

              description 'Flow coloring based on peer locator.' ;
              presence peer-locator ;
              leaf addr-family {
                type enumeration {
                  enum any {
                    value 0 ;
                    description 'Any address family.' ;
                  }

                  enum ipv4 {
                    description 'IPv4 address family.' ;
                    value 1 ;
                  }

                  enum ipv6 {
                    description 'IPv6 address family.' ;
                    value 2 ;
                  }

                }

                description 'IP address family.' ;
                if-feature addr-family ;

                ncd:revise-date 2024-08-05 ;
              }

              leaf peer-locator {
                description 'Peer locator.' ;
                type ncd:ipv6-address-none-zero ;

                mandatory true ;
              }

              leaf prefix-length {
                description 'Prefix length of peer locator.' ;
                type uint8 {
                  range 1..128 ;

                }

                mandatory true ;
              }

              choice vpn-type {
                description 'Choose one VPN type.' ;
                case vrf {
                  description 'Type is VRF.' ;
                  leaf vrf-name {
                    type string {
                      length 1..32 {
                        description 'This string length ranges from 1 to 32.' ;
                      }

                    }

                    description 'The name of VRF,this string length ranges from 1 to 32.' ;
                  }

                }

                case vpws {
                  leaf vpws-name {
                    type string {
                      length 1..32 {
                        description 'This string length ranges from 1 to 32.' ;
                      }

                    }

                    description 'The name of VPWS,this string length ranges from 1 to 32.' ;
                  }

                  description 'Type is vpws.' ;
                }

                case evpn-vpws {
                  leaf evpn-vpws-name {
                    type string {
                      length 1..32 {
                        description 'This string length ranges from 1 to 32.' ;
                      }

                    }

                    description 'The name of EVPN VPWS,this string length ranges from 1 to 32.' ;
                  }

                  description 'Type is EVPN VPWS.' ;
                }

                case vpls {
                  leaf vpls-name {
                    type string {
                      length 1..32 {
                        description 'This string length ranges from 1 to 32.' ;
                      }

                    }

                    description 'The name of VPLS,this string length ranges from 1 to 32.' ;
                  }

                  description 'Type is VPLS.' ;
                }

                ncd:revise-date 2023-12-28 ;
              }

              ncd:revise-date 2022-04-25 ;
            }

            container sr-policy {
              leaf color {
                mandatory true ;
                description 'Color.' ;
                type uint32 {
                  range 1..4294967295 ;

                }

              }

              container end-point {
                choice ip-addr-family {
                  case ipv4 {
                    leaf end-point-v4 {
                      mandatory true ;
                      description 'The IPv4 address of end-point.' ;
                      type ncd:ipv4-address-none-zero ;

                    }

                    description 'Type is IPv4.' ;
                  }

                  case ipv6 {
                    leaf end-point-v6 {
                      mandatory true ;
                      description 'The IPv6 address of end-point.' ;
                      type ncd:ipv6-address-none-zero ;

                    }

                    description 'Type is IPv6.' ;
                  }

                  description 'IP address family.' ;
                  mandatory true ;
                }

                presence end-point ;
                description 'End point.' ;
              }

              presence sr-policy ;
              description 'Flow coloring based on SR policy.' ;
              if-feature sr-policy ;

              ncd:revise-date 2023-07-11 ;
            }

          }

          container interface-list {
            description 'Flow interface list configuration.' ;
            list interface {
              description 'Configure interfaces of interface-list.' ;
              key ifname ;
              leaf ifname {
                description 'The interface name of interface-list.' ;
                type ncd:ifname {
                  length 1..31 {
                    description 'The range of interface name length.' ;
                  }

                }

              }

            }

            ncd:revise-date 2021-10-08 ;
          }

        }

      }

      ncd:revise-date 2021-08-05 ;
    }

  }

  container state {
    description 'State model info of inband OAM.' ;
    config false ;
    container inband-oam {
      container flow-mappings {
        description 'Inband OAM flow mapping configuration.' ;
        list flow-mapping {
          description 'Inband OAM flow mapping configuration.' ;
          key 'node-id inner-flow-id' ;
          leaf node-id {
            description 'Device ID.' ;
            type uint32 {
              range 1..1048575 ;

            }

          }

          leaf inner-flow-id {
            description 'Inner flow id.' ;
            type uint32 {
              range 1..1048575 ;

            }

          }

          leaf outer-flow-id {
            description 'Outer flow ID.' ;
            type uint32 {
              range 1..1048575 ;

            }

          }

        }

      }

      container flow-informations {
        list flow-information {
          leaf instance-name {
            type string {
              length 1..31 {
                description 'The length of the instance name.' ;
              }

            }

            description 'Flow instance name.' ;
          }

          description 'The flow information.' ;
          key instance-name ;
          leaf node-id {
            type uint32 {
              range 0..1048575 ;

            }

            description 'Device ID.' ;
          }

          leaf binding-device-mode {
            type enumeration {
              enum disable {
                value 0 ;
                description 'The device mode disabled.' ;
              }

              enum enable {
                value 1 ;
                description 'The device mode enabled.' ;
              }

            }

            description 'Device-level IOAM switch.' ;
            default disable ;
          }

          container ip {
            leaf addr-family {
              type enumeration {
                enum IPv4 {
                  description 'IPv4 type.' ;
                  value 0 ;
                }

                enum IPv6 {
                  description 'IPv6 type.' ;
                  value 1 ;
                }

              }

              description 'The address family.' ;
            }

            leaf source-addr {
              type string {
                length 0..45 {
                  description 'The length of the source IP address.' ;
                }

              }

              description 'The source IP address.' ;
            }

            leaf source-mask-length {
              type uint8 {
                range 1..128 {
                  description 'The source IP mask length.' ;
                }

              }

              description 'The source IP mask length.' ;
            }

            leaf dest-addr {
              type string {
                length 0..45 {
                  description 'The length of the destination IP address.' ;
                }

              }

              description 'The destination IP address.' ;
            }

            leaf dest-mask-length {
              type uint8 {
                range 1..128 {
                  description 'The source IP mask length.' ;
                }

              }

              description 'The destination IP mask length.' ;
            }

            leaf source-port {
              type uint16 {
                range 1..65535 {
                  description 'The range of port number.' ;
                }

              }

              description 'The source port.' ;
            }

            leaf dest-port {
              type uint16 {
                range 1..65535 {
                  description 'The range of port number.' ;
                }

              }

              description 'The destination port.' ;
            }

            leaf protocol {
              type uint8 {
                range 1..255 {
                  description 'The range of protocol.' ;
                }

              }

              description 'The protocol number.' ;
            }

            leaf vrf-name {
              type string {
                length 0..32 {
                  description 'This string length of the VRF name.' ;
                }

              }

              description 'VRF name.' ;
            }

            leaf dscp {
              type uint8 {
                range 0..63 {
                  description 'The range of DSCP.' ;
                }

              }

              description 'The value of DSCP.' ;
            }

            description 'Flow coloring based on L3.' ;
          }

          container eth {
            leaf source-mac {
              type string {
                length 0..15 {
                  description 'This string length of the source MAC.' ;
                }

              }

              description 'The source MAC address.' ;
            }

            leaf dest-mac {
              type string {
                length 0..15 {
                  description 'This string length of the destination MAC.' ;
                }

              }

              description 'The destination MAC address.' ;
            }

            leaf vlan {
              type uint16 {
                range 1..4094 {
                  description 'The range of vlan id.' ;
                }

              }

              description 'The value of vlan id.' ;
            }

            leaf internal-vlan {
              type uint16 {
                range 1..4094 {
                  description 'The range of internal VLAN ID.' ;
                }

              }

              description 'The value of internal vlan id.' ;
            }

            leaf priority-8021p {
              type uint8 {
                range 0..7 {
                  description 'The range of priority-8021p.' ;
                }

              }

              description 'The value of priority-8021p.' ;
            }

            choice l2vpn-type {
              case vpws {
                leaf vpws-name {
                  type string {
                    length 0..32 {
                      description 'This string length of the VPWS name.' ;
                    }

                  }

                  description 'The name of VPWS.' ;
                }

                description 'Type is VPWS.' ;
              }

              case evpn-vpws {
                leaf evpn-vpws-name {
                  type string {
                    length 0..32 {
                      description 'This string length of the EVPN VPWS name.' ;
                    }

                  }

                  description 'The name of EVPN VPWS.' ;
                }

                description 'Type is EVPN VPWS.' ;
              }

              case vpls {
                leaf vpls-name {
                  type string {
                    length 0..32 {
                      description 'This string length of the VPLS name.' ;
                    }

                  }

                  description 'The name of VPLS.' ;
                }

                description 'Type is VPLS.' ;
              }

              description 'Choose one L2VPN type.' ;
            }

            description 'Flow coloring based on L2.' ;
          }

          container peer-locator {
            leaf addr-family {
              type enumeration {
                enum UnSpecific {
                  value 0 ;
                  description 'Any address family.' ;
                }

                enum IPv4 {
                  value 1 ;
                  description 'IPv4 address family.' ;
                }

                enum IPv6 {
                  value 2 ;
                  description 'IPv6 address family.' ;
                }

              }

              description 'IP address family.' ;
            }

            leaf peer-locator {
              type string {
                length 0..45 {
                  description 'The length of the peer locator.' ;
                }

              }

              description 'Peer locator.' ;
            }

            leaf prefix-length {
              type uint8 {
                range 1..128 {
                  description 'The range of the prefix length.' ;
                }

              }

              description 'Prefix length of peer locator.' ;
            }

            choice vpn-type {
              case vrf {
                leaf vrf-name {
                  type string {
                    length 0..32 {
                      description 'This string length of the VRF name.' ;
                    }

                  }

                  description 'The name of VRF.' ;
                }

                description 'Type is VRF.' ;
              }

              case vpws {
                leaf vpws-name {
                  type string {
                    length 0..32 {
                      description 'This string length of the VPWS name.' ;
                    }

                  }

                  description 'The name of VPWS.' ;
                }

                description 'Type is VPWS.' ;
              }

              case evpn-vpws {
                leaf evpn-vpws-name {
                  type string {
                    length 0..32 {
                      description 'This string length of the EVPN VPWS name.' ;
                    }

                  }

                  description 'The name of EVPN VPWS.' ;
                }

                description 'Type is EVPN VPWS.' ;
              }

              case vpls {
                leaf vpls-name {
                  type string {
                    length 0..32 {
                      description 'This string length of the VPLS name.' ;
                    }

                  }

                  description 'The name of VPLS.' ;
                }

                description 'Type is VPLS.' ;
              }

              description 'Choose one VPN type.' ;
            }

            description 'Flow coloring based on peer locator.' ;
          }

          container sr-policy {
            leaf color {
              type uint32 {
                range 1..4294967295 {
                  description 'The range of the color.' ;
                }

              }

              description 'Color.' ;
            }

            leaf end-point {
              type string {
                length 0..45 {
                  description 'The string length of the end point.' ;
                }

              }

              description 'The IP address of end-point.' ;
            }

            description 'Flow coloring based on SR policy.' ;
          }

          container flow-id-list {
            list flow-id-info {
              leaf flow-id {
                type uint32 {
                  range 1..1048575 {
                    description 'The range of flow id.' ;
                  }

                }

                description 'The flow id to identify a specific flow.' ;
              }

              description 'The flow id information.' ;
              key flow-id ;
              leaf interface-name {
                type string {
                  length 0..31 {
                    description 'The length of the interface name.' ;
                  }

                }

                description 'The interface name.' ;
              }

              leaf trunk-interface-name {
                type string {
                  length 0..31 {
                    description 'The length of the trunk interface name.' ;
                  }

                }

                description 'The trunk interface name.' ;
              }

              leaf sl-index {
                type uint32 {
                  range 0..4294967295 {
                    description 'The range of the SL index.' ;
                  }

                }

                description 'The segment-list index.' ;
              }

              leaf as-num {
                type uint32 {
                  range 0..4294967295 {
                    description 'The range of the AS number.' ;
                  }

                }

                description 'The as number of SR policy originator.' ;
              }

              leaf originator-address {
                type string {
                  length 0..45 {
                    description 'The length of the originator address.' ;
                  }

                }

                description 'The originator address of SR policy.' ;
              }

              leaf discriminator {
                type uint32 {
                  range 0..4294967295 {
                    description 'The range of the discriminator.' ;
                  }

                }

                description 'The discriminator of SR policy.' ;
              }

              leaf protocol-origin {
                type enumeration {
                  enum bgp {
                    value 20 ;
                    description 'Protocol BGP.' ;
                  }

                  enum configuration {
                    value 30 ;
                    description 'Protocol configuration.' ;
                  }

                  enum pcep {
                    value 10 ;
                    description 'Protocol PCEP.' ;
                  }

                }

                description 'The protocol origin of SR policy.' ;
              }

            }

            description 'The flow id information.' ;
          }

        }

        description 'The flow information.' ;
        ncd:revise-date 2025-02-13 ;
      }

      description 'Inband OAM state parameters.' ;
    }

    ncd:revise-date 2022-06-13 ;
  }

  container operation {
    if-feature flow-mapping ;

    config false ;
    container inband-oam {
      container flow-mappings {
        description 'Inband OAM flow mapping configuration.' ;
        list flow-mapping {
          description 'Inband OAM flow mapping configuration.' ;
          key 'node-id inner-flow-id' ;
          leaf node-id {
            description 'Device ID.' ;
            type uint32 {
              range 1..1048575 ;

            }

          }

          leaf inner-flow-id {
            description 'Inner flow id.' ;
            type uint32 {
              range 1..1048575 ;

            }

          }

          choice status {
            mandatory true ;
            case enable {
              description 'Enable the flow mapping.' ;
              leaf outer-flow-id {
                description 'Outer flow ID.' ;
                type uint32 {
                  range 1..1048575 ;

                }

                mandatory true ;
              }

            }

            case disable {
              description 'Disable the flow mapping.' ;
              leaf disable {
                description 'Disable.' ;
                type empty ;

                mandatory true ;
              }

            }

          }

        }

      }

    }

    ncd:revise-date 2022-06-13 ;
  }

}
