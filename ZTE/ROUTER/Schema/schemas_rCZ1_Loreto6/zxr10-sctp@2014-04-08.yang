module zxr10-sctp {
  namespace 'http://www.zte.com.cn/zxr10/netconf/schema/rosng/sctp' ;
  prefix sctp ;
  organization 'ZTE Corporation' ;
  contact "ZTE Corporation  
\n"
        + "   Nanjing Institute of ZTE Corporation 
\n"
        + "   No.68 Zijinghua Rd. Yuhuatai District, Nanjing, China 
\n"
        + '   Tel: +86-25-52870000'
          ;
  description 'NETCONF of SCTP module' ;
  revision 2014-04-08 {
    description 'Second version. Modify one field of the commad of show sctp br'
              + 'ief. The state field length from 1-12 strings to 1-20 strings.'
                ;
  }
  revision 2014-02-20 {
    description 'Initail version' ;
  }
  container state {
    description 'Command of sctp show' ;
    config false ;
    container sctp {
      description 'Command of sctp show' ;
      container statistics {
        description 'Show the statistics of sctp' ;
        container received {
          description 'Information of received' ;
          presence 'information of receiving' ;
          leaf recv-bytes {
            description 'Total receive bytes' ;
            type uint32 {
              range 0..4294967295 ;
            }
            units bytes ;
          }
          leaf recv-chunks {
            description 'Total receive chunks' ;
            type uint32 {
              range 0..4294967295 ;
            }
          }
          leaf sctp2ulp-bytes {
            description 'ULP receive bytes' ;
            type uint32 {
              range 0..4294967295 ;
            }
            units bytes ;
          }
          leaf sctptoulp {
            description 'Number of SCTP send data to UDP' ;
            type uint32 {
              range 0..4294967295 ;
            }
          }
          leaf retrans-chunks {
            description 'Retransmitted chunk counts' ;
            type uint32 {
              range 0..4294967295 ;
            }
          }
          leaf tmout-resend-chk {
            description 'Send chunks for retransmitted timer out' ;
            type uint32 {
              range 0..4294967295 ;
            }
          }
          leaf recv-sack {
            description 'Total receive SACK packets' ;
            type uint32 {
              range 0..4294967295 ;
            }
          }
          leaf retran-break {
            description 'Break counts' ;
            type uint32 {
              range 0..4294967295 ;
            }
          }
          leaf rcv-dup-chk {
            description 'Total receive duplicate chunk counts' ;
            type uint32 {
              range 0..4294967295 ;
            }
          }
          leaf rcv-frag-msg {
            description 'Reveive fragment message counts' ;
            type uint32 {
              range 0..4294967295 ;
            }
          }
          leaf rcv-frag-chk {
            description 'Reveive fragment chunk counts' ;
            type uint32 {
              range 0..4294967295 ;
            }
          }
          leaf unorder-recv-msg {
            description 'Receive unorder messages' ;
            type uint32 {
              range 0..4294967295 ;
            }
          }
          leaf unorder-recv-chk {
            description 'Receive unorder chunks' ;
            type uint32 {
              range 0..4294967295 ;
            }
          }
          leaf passive-assoc {
            description 'Passive open counts' ;
            type uint32 {
              range 0..4294967295 ;
            }
          }
          leaf shutdown-assoc {
            description 'Close association counts' ;
            type uint32 {
              range 0..4294967295 ;
            }
          }
        }
        container sent {
          description 'Information of send' ;
          leaf sent-bytes {
            description 'Total send bytes' ;
            type uint32 {
              range 0..4294967295 ;
            }
            units bytes ;
          }
          leaf sent-chunks {
            description 'Total send chunks' ;
            type uint32 {
              range 0..4294967295 ;
            }
          }
          leaf ulp2sctp-bytes {
            description 'ULP send to SCTP bytes' ;
            type uint32 {
              range 0..4294967295 ;
            }
            units bytes ;
          }
          leaf ulptosctp {
            description 'Number of ULP send data to SCTP' ;
            type uint32 {
              range 0..4294967295 ;
            }
          }
          leaf creat-chks {
            description 'Create data chunk counts' ;
            type uint32 {
              range 0..4294967295 ;
            }
          }
          leaf fast-resend-chk {
            description 'Fast retransmitted chunk counts' ;
            type uint32 {
              range 0..4294967295 ;
            }
          }
          leaf sent-sack {
            description 'Total send SACK packets' ;
            type uint32 {
              range 0..4294967295 ;
            }
          }
          leaf curr-assoc {
            description 'Current associations' ;
            type uint32 {
              range 0..4294967295 ;
            }
          }
          leaf rcv-disord-chk {
            description 'Number of received chunks of TSN out of order' ;
            type uint32 {
              range 0..4294967295 ;
            }
          }
          leaf snd-frag-msg {
            description 'Send fragment message counts' ;
            type uint32 {
              range 0..4294967295 ;
            }
          }
          leaf snd-frag-chk {
            description 'Send fragment chunk counts' ;
            type uint32 {
              range 0..4294967295 ;
            }
          }
          leaf unorder-sent-msg {
            description 'Send unorder messages' ;
            type uint32 {
              range 0..4294967295 ;
            }
          }
          leaf unorder-sent-chk {
            description 'Send unorder chunks' ;
            type uint32 {
              range 0..4294967295 ;
            }
          }
          leaf active-assoc {
            description 'Active open counts' ;
            type uint32 {
              range 0..4294967295 ;
            }
          }
          leaf abort-assoc {
            description 'Abort closed association counts' ;
            type uint32 {
              range 0..4294967295 ;
            }
          }
        }
        container common-info {
          description 'Total information of sctp' ;
          leaf total-sent {
            description 'Total send packets' ;
            type uint32 {
              range 0..4294967295 ;
            }
          }
          leaf total-recv {
            description 'Total receive packets' ;
            type uint32 {
              range 0..4294967295 ;
            }
          }
          leaf sent-heart-beat {
            description 'Send heart beat counts' ;
            type uint32 {
              range 0..4294967295 ;
            }
          }
          leaf recv-heart-beat {
            description 'Receive heart beat counts' ;
            type uint32 {
              range 0..4294967295 ;
            }
          }
          leaf sent-heart-beat-ack {
            description 'Send heart-beat-ack counts' ;
            type uint32 {
              range 0..4294967295 ;
            }
          }
          leaf recv-heart-beat-ack {
            description 'Receive heart-beat-ack counts' ;
            type uint32 {
              range 0..4294967295 ;
            }
          }
          leaf sent-heart-beat-probe {
            description 'Send heart-beat-probe counts' ;
            type uint32 {
              range 0..4294967295 ;
            }
          }
          leaf recv-heart-beat-probe {
            description 'Receive heart-beat-probe counts' ;
            type uint32 {
              range 0..4294967295 ;
            }
          }
          leaf sent-heart-beat-probe-ack {
            description 'Send heart-beat-probe-ack counts' ;
            type uint32 {
              range 0..4294967295 ;
            }
          }
          leaf recv-heart-beat-probe-ack {
            description 'Receive heart-beat-probe-ack counts' ;
            type uint32 {
              range 0..4294967295 ;
            }
          }
          leaf sent-init {
            description 'Total send INIT packets' ;
            type uint32 {
              range 0..4294967295 ;
            }
          }
          leaf recv-init {
            description 'Total receive INIT packets' ;
            type uint32 {
              range 0..4294967295 ;
            }
          }
          leaf sent-init-ack {
            description 'Total send INIT-ACK packets' ;
            type uint32 {
              range 0..4294967295 ;
            }
          }
          leaf recv-init-ack {
            description 'Total receive INIT-ACK packets' ;
            type uint32 {
              range 0..4294967295 ;
            }
          }
          leaf sent-cookie-echo {
            description 'Total send COOKIE-ECHO packets' ;
            type uint32 {
              range 0..4294967295 ;
            }
          }
          leaf recv-cookie-echo {
            description 'Total receive COOKIE-ECHO packets' ;
            type uint32 {
              range 0..4294967295 ;
            }
          }
          leaf sent-cookie-ack {
            description 'Total send COOKIE-ACK packets' ;
            type uint32 {
              range 0..4294967295 ;
            }
          }
          leaf recv-cookie-ack {
            description 'Total receive COOKIE-ACK packets' ;
            type uint32 {
              range 0..4294967295 ;
            }
          }
          leaf sent-shutdown {
            description 'Total send SHUT-DOWN packets' ;
            type uint32 {
              range 0..4294967295 ;
            }
          }
          leaf recv-shutdown {
            description 'Total receive SHUT-DOWN packets' ;
            type uint32 {
              range 0..4294967295 ;
            }
          }
          leaf sent-shutdown-ack {
            description 'Total send SHUT-DOWN-ACK packets' ;
            type uint32 {
              range 0..4294967295 ;
            }
          }
          leaf recv-shutdown-ack {
            description 'Total receive SHUT-DOWN-ACK packets' ;
            type uint32 {
              range 0..4294967295 ;
            }
          }
          leaf sent-shutdown-complete {
            description 'Total send SHUT-DOWN-COMPLETE packets' ;
            type uint32 {
              range 0..4294967295 ;
            }
          }
          leaf recv-shutdown-complete {
            description 'Total receive SHUT-DOWN-COMPLETE packets' ;
            type uint32 {
              range 0..4294967295 ;
            }
          }
          leaf sent-abort {
            description 'Total send ABORT packets' ;
            type uint32 {
              range 0..4294967295 ;
            }
          }
          leaf recv-abort {
            description 'Total receive ABORT packets' ;
            type uint32 {
              range 0..4294967295 ;
            }
          }
          leaf sent-error {
            description 'Total send ERROR packets' ;
            type uint32 {
              range 0..4294967295 ;
            }
          }
          leaf recv-error {
            description 'Total receive ERROR packets' ;
            type uint32 {
              range 0..4294967295 ;
            }
          }
          leaf numof-ootb {
            description 'Number of OOTB packets' ;
            type uint32 {
              range 0..4294967295 ;
            }
          }
          leaf unreco-chunk {
            description 'Number of unrecognized chunks' ;
            type uint32 {
              range 0..4294967295 ;
            }
          }
        }
      }
      container briefs {
        description 'Show the brief information of sctp connections' ;
        presence 'Show sctp brief' ;
        list brief {
          description 'Show brief information of sctp connections' ;
          key association-id ;
          leaf association-id {
            description 'Index of association id' ;
            type uint32 {
              range 0..4294967295 ;
            }
          }
          leaf local-address {
            description 'Local ip address and port' ;
            type string {
              length 1..50 ;
            }
          }
          leaf remote-address {
            description 'Remote ip address and port' ;
            type string {
              length 1..50 ;
            }
          }
          leaf state {
            description 'State of a SCTP connection' ;
            type string {
              length 1..20 ;
            }
          }
        }
      }
      container tcps {
        description 'Show tcb information of all sctp connections' ;
        list tcp {
          description 'Show the detail information of all sctp connections or a'
                    + ' specific sctp connection'
                      ;
          key association-id ;
          leaf association-id {
            description 'Index of association id' ;
            type uint32 {
              range 0..4294967295 ;
            }
          }
          leaf state {
            description 'State of association' ;
            type string {
              length 1..20 ;
            }
          }
          leaf check-sum {
            description 'Type of checksum' ;
            type uint8 {
              range 0..255 ;
            }
          }
          leaf local-address {
            description 'Local ip address,port and vpnid' ;
            type string {
              length 1..50 ;
            }
          }
          leaf remote-address {
            description 'Remote ip address,port and vpnid' ;
            type string {
              length 1..50 ;
            }
          }
          leaf primary-dest-ip {
            description 'Primary destination address' ;
            type string {
              length 1..50 ;
            }
          }
          leaf cul-tsn-acked {
            description 'Last ACK TSN number being received' ;
            type uint32 {
              range 0..4294967295 ;
            }
          }
          leaf next-tsn-assign {
            description 'Next TSN number that will assign' ;
            type uint32 {
              range 0..4294967295 ;
            }
          }
          leaf last-recv-tsn {
            description 'The last TSN received; cumulative TSN point' ;
            type uint32 {
              range 0..4294967295 ;
            }
          }
          leaf out-standing-size {
            description 'Size of unacked data' ;
            type uint32 {
              range 0..4294967295 ;
            }
          }
          leaf pending-chk-num {
            description 'Size of remained space' ;
            type uint32 {
              range 0..4294967295 ;
            }
          }
          leaf mtu-size {
            description 'Minmum mtu of all path' ;
            type uint16 {
              range 0..65535 ;
            }
          }
          leaf tx-rechk-num {
            description 'Number of waiting for retransmitting packets' ;
            type uint32 {
              range 0..4294967295 ;
            }
          }
          leaf tx-strm-num {
            description 'Number of send stream' ;
            type uint16 {
              range 0..65535 ;
            }
          }
          leaf rx-strm-num {
            description 'Number of receive stream' ;
            type uint16 {
              range 0..65535 ;
            }
          }
          leaf anti-break-time {
            description 'Pesist time for breaking of bear network' ;
            type uint32 {
              range 0..4294967295 ;
            }
          }
          leaf forecast-flux {
            description 'Estimate size of stream' ;
            type uint32 {
              range 0..4294967295 ;
            }
          }
          leaf max-tx-que-cell-use {
            description 'Maximum memory size of association' ;
            type uint32 {
              range 0..4294967295 ;
            }
          }
          leaf peer-verif-tag {
            description 'TAG of verified by peer' ;
            type uint32 {
              range 0..4294967295 ;
            }
          }
          leaf my-verif-tag {
            description 'TAG of local send' ;
            type uint32 {
              range 0..4294967295 ;
            }
          }
          leaf cwnd-min {
            description 'Minmum of congestion window' ;
            type uint32 {
              range 0..4294967295 ;
            }
          }
        }
      }
    }
  }
  container operation {
    description 'Command of sctp clear' ;
    config false ;
    container sctp {
      description 'Command of sctp clear' ;
      container clear {
        description 'Closed a sctp connection or clear the statistics of all sc'
                  + 'tp connections'
                    ;
        container connects {
          description 'Closed a sctp connection based on the index of associati'
                    + 'on id'
                      ;
          leaf association-id {
            description 'Closed a sctp connetion based on the index of associat'
                      + 'ion id'
                        ;
            type uint32 {
              range 0..4294967295 ;
            }
          }
        }
        container statistics {
          description 'Clear statistics of SCTP' ;
          leaf statistic {
            description 'Clear statistics data of sctp' ;
            type empty ;
          }
        }
      }
    }
  }
}
