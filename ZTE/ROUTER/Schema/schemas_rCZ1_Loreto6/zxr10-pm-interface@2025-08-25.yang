module zxr10-pm-interface {
  namespace "http://www.zte.com.cn/zxr10/netconf/schema/rosng/pm-interface" ;
  prefix pm-interface ;
  yang-version 1 ;
  import zxr10-netconf-defs {
    prefix ncd ;
  }

  organization "ZTE Corporation" ;
  contact "ZTE Corporation
  Nanjing Institute of ZTE Corporation
  No.68 Zijinghua Rd. Yuhuatai District, Nanjing, China
  Tel: +86-25-52870000" ;
  revision 2025-08-25 {
    description 'increase wavelength config range from 191.15THz, add optical module channel for wavelength state node. ' ;
  }

  revision 2025-07-18 {
    description 'Increase wavelength decimal to 5.' ;
  }

  revision 2025-05-13 {
    description 'Add 99x to optical-module-config.' ;
  }

  revision 2025-04-29 {
    description 'add 59E 99X 5960X 5960M 59X-ES to interface feature flow-control-threshold' ;
  }

  revision 2025-01-02 {
    description 'Add second container in control-flap container.' ;
  }

  revision 2024-11-12 {
    description 'Add sat holdtime.' ;
  }

  revision 2024-11-04 {
    description 'obsolete wavelength-capability.' ;
  }

  revision 2024-10-29 {
    description 'add 59M to interface feature optical-module-config.' ;
  }

  revision 2024-10-16 {
    description 'Add port-alarm mgmt ' ;
  }

  revision 2024-09-20 {
    description 'add enum speed-800G in leaf speed.' ;
  }

  revision 2024-08-15 {
    description 'add pc-test feature, add to wavelength-capability' ;
  }

  revision 2024-06-10 {
    description 'Add wan-config container in eth list and increase interface name filter in wans list.' ;
  }

  revision 2024-06-04 {
    description 'Change the type string of if-name to ncd:ifname in eths, dampings, link-delays and threshold-sd-fers configuration container.' ;
  }

  revision 2024-02-06 {
    description 'Add query port config speed.' ;
  }

  revision 2024-01-23 {
    description 'Add optical-power-detect container.' ;
  }

  revision 2024-01-20 {
    description 'Add split type cgei in split container.' ;
  }

  revision 2023-12-12 {
    description 'Modify the range of 
threshold-error-packet in eth and wan container to 0-65535 and add perfcode in default value.' ;
  }

  revision 2023-11-13 {
    description 'Add split type ccgei in split container.' ;
  }

  revision 2023-10-25 {
    description 'Add wavelength-capability container.' ;
  }

  revision 2023-07-22 {
    description 'Add lan-wan-switch container.' ;
  }

  revision 2023-07-13 {
    description 'Add sdhs container.' ;
  }

  revision 2023-05-19 {
    description 'Add split type lgei in split container.' ;
  }

  revision 2023-01-30 {
    description 'Change the range of recovery-time and interval-time to 86400 of control-flap.' ;
  }

  revision 2022-11-03 {
    description 'Change accuracy of the configuration center frequency.' ;
  }

  revision 2022-10-13 {
    description 'Add leaf fec-enable-para in eth list.' ;
  }

  revision 2022-09-09 {
    description 'Add T8000 to feature optical-module-config,support configuration/pm-if/eths/eth/wavelength.' ;
  }

  revision 2022-08-31 {
    description 'Add flowcontrol off-threshold node to support configure flowcontrol off-threshold.' ;
  }

  revision 2022-08-11 {
    description 'change als status.
change 3,4,dele 5,add 6,7,8,254.' ;
  }

  revision 2022-07-16 {
    description 'Adjust the range of center frequency to 191.3-196.1' ;
  }

  revision 2022-06-05 {
    description 'add eth speed mode "speed-2.5G".' ;
  }

  revision 2022-06-01 {
    description 'add leaf af-node and shelf in list port-status.' ;
  }

  revision 2022-02-09 {
    description 'add 5960M.' ;
  }

  revision 2022-01-21 {
    description 'add port-alarm if-down.' ;
  }

  revision 2021-09-29 {
    description 'add work-mode mtn-fg.' ;
  }

  revision 2021-07-30 {
    description 'add enum line-extend and internal-extend in loopback leaf on eth list and eth-status container.' ;
  }

  revision 2021-07-03 {
    description 'add port-alarm sd-insert.' ;
  }

  revision 2021-05-29 {
    description 'add enum 16-trace-mode-null and 64-trace-mode-null in container flag j0,j0ex,j1,j1ex of wan port.' ;
  }

  revision 2021-04-19 {
    description 'add flexe dcn overhead.' ;
  }

  revision 2021-01-28 {
    description 'Modify the range of holdtime value.' ;
  }

  revision 2021-01-11 {
    description 'add laser-status invalid mode.' ;
  }

  revision 2021-01-05 {
    description 'add flow control on threshold' ;
  }

  revision 2020-09-21 {
    description 'add MTN leaf' ;
  }

  revision 2020-09-14 {
    description 'add single-fiber and link-force' ;
  }

  revision 2020-06-12 {
    description 'add eth speed mode "speed-auto"' ;
  }

  revision 2020-04-28 {
    description 'Add create-vsgs.' ;
  }

  revision 2020-04-01 {
    description 'add enum speed-25G, speed-40G, speed-50G and speed-100G in leaf ulei speed.' ;
  }

  revision 2020-02-25 {
    description 'Add container eee-statisticss,clear-eee-statisticss,control-flap,control-flap-clears,eee-config and optical-inform-monitor.' ;
  }

  revision 2020-02-15 {
    description 'Add contain split.' ;
  }

  revision 2019-06-25 {
    description 'add fec-eth and fec-bypass add center-frequency and obsolete center-freq.' ;
  }

  revision 2019-05-10 {
    description 'add leaf loopback.' ;
  }

  revision 2019-03-05 {
    description 'add optical module config.' ;
  }

  revision 2018-12-12 {
    description 'jumbo add.' ;
  }

  revision 2018-11-14 {
    description 'add work-mode' ;
  }

  revision 2018-09-17 {
    description 'ipg add perfcode.' ;
  }

  revision 2018-09-08 {
    description 'add ipg container delete2reset and modify default value.' ;
  }

  revision 2018-09-06 {
    description 'add port-speed.' ;
  }

  revision 2018-09-03 {
    description 'add enum speed-25G and speed-50G in leaf speed.' ;
  }

  revision 2018-08-16 {
    description 'add port-status.' ;
  }

  revision 2018-07-25 {
    description 'add laser off-reason and modify current-status.' ;
  }

  revision 2018-07-01 {
    description 'add gfp-mplss.' ;
  }

  revision 2018-06-28 {
    description 'add laser-status and loopback-auto-cancel.' ;
  }

  revision 2018-05-28 {
    description 'add ifhaslos.' ;
  }

  revision 2018-05-24 {
    description 'add loopback time.' ;
  }

  revision 2018-03-09 {
    description 'add rf2sf and ipg.' ;
  }

  revision 2017-10-16 {
    description 'add laser-status.' ;
  }

  revision 2017-08-01 {
    description 'add alarm insert sd.' ;
  }

  revision 2017-06-02 {
    description 'add leaf trace-64-value to pos j0 and j0ex' ;
  }

  revision 2016-11-18 {
    description 'add loopback-external' ;
  }

  revision 2016-09-26 {
    description 'leaf loopback modify type for eths wans poss and atms.' ;
  }

  revision 2016-09-10 {
    description 'list port-mode add leaf xgei-gei, leaf lan-wan add parameter pos3 and pos12, leaf pos3-pos12 add parameter lan, wan and gei.' ;
  }

  revision 2016-08-10 {
    description 'add alarm-insert-hp and alarm-insert-ms for atms and poss' ;
  }

  revision 2016-04-15 {
    description 'modify the range of link-delay-up and link-delay-down from 0 to 600000.' ;
  }

  revision 2016-03-15 {
    description 'add b2-sd-ber b2-sf-ber to sdh-threshold, only for atm' ;
  }

  revision 2016-02-29 {
    description 'modify contain threshold-sd-fers leaf occur-exponent and clear-exponent range 1 to 9' ;
  }

  revision 2016-01-20 {
    description 'Add leaf speed-100G and modify the value of speed-40G.' ;
  }

  revision 2015-12-31 {
    description 'modify atm flag c2/c2ex default value
modify pos clock-mode default value' ;
  }

  revision 2015-12-17 {
    description 'leaf recovery-mode add parameter laser-on add laser-off.' ;
  }

  revision 2015-09-06 {
    description 'add contain sdh-thresholds' ;
  }

  feature optical-module-config ;

  feature flow-control-threshold {
    ncd:revise-date 2025-04-29 ;
  }

  feature port-alarm-ifdown {
    description 'add port-alarm-ifdown feature.' ;
    ncd:revise-date 2022-01-21 ;
  }

  feature optical-power-detect {
    description 'Add optical-power-detect feature.' ;
    ncd:revise-date 2024-01-23 ;
  }

  feature pc-test {
    description 'add feature for pc test only.' ;
    ncd:revise-date 2024-08-15 ;
  }

  container configuration {
    container pm-if {
      container eths {
        list eth {
          description 'Ethernet interface mode.' ;
          key if-name ;
          leaf if-name {
            description 'Interface name.' ;
            type ncd:ifname ;

          }

          leaf holdtime {
            description 'Configures the port hold-time.' ;
            type uint16 {
              range 0..3600 {
                description 'Range: 0-3600.' ;
              }

            }

            units second ;
            default 120 ;
          }

          leaf negotiation {
            description 'Configures the port negotiation mode.' ;
            type enumeration {
              enum negotiation-force {
                value 1 ;
                description 'Force negotiation mode.' ;
              }

              enum negotiation-auto {
                value 2 ;
                description 'Auto negotiation mode.' ;
              }

            }

            default negotiation-auto ;
          }

          leaf speed {
            description 'Configures the rate of a port.' ;
            type enumeration {
              enum speed-10M {
                value 1 ;
                description 'Port speed is 10M.' ;
              }

              enum speed-100M {
                value 2 ;
                description 'Port speed is 100M.' ;
              }

              enum speed-1G {
                value 3 ;
                description 'Port speed is 1G.' ;
              }

              enum speed-10G {
                value 4 ;
                description 'Port speed is 10G.' ;
              }

              enum speed-25G {
                value 10 ;
                description 'Port speed is 25G.' ;
              }

              enum speed-40G {
                value 5 ;
                description 'Port speed is 40G.' ;
              }

              enum speed-50G {
                value 11 ;
                description 'Port speed is 50G.' ;
              }

              enum speed-100G {
                value 6 ;
                description 'Port speed is 100G.' ;
              }

              enum speed-200G {
                value 12 ;
                description 'Port speed is 200G.' ;
              }

              enum speed-400G {
                value 13 ;
                description 'Port speed is 400G.' ;
              }

              enum speed-auto {
                value 15 ;
                description 'Port speed is configured to auto, the real speed depend on optical module.' ;
              }

              enum speed-2.5G {
                value 14 ;
                description 'Port speed is 2.5G.' ;
              }
	      
              enum speed-800G {
                value 16 ;
                description 'Port speed is 800G.'
                            ;
              }

            }

            default speed-1G ;
          }

          leaf duplex {
            description 'Configures the Ethernet working mode.' ;
            type enumeration {
              enum duplex-full {
                value 1 ;
                description 'Full duplex mode.' ;
              }

              enum duplex-half {
                value 2 ;
                description 'Half duplex mode.' ;
              }

            }

            default duplex-full ;
          }

          leaf loopback {
            description 'Configures the loopback method of a port.' ;
            type enumeration {
              enum cancel {
                value 0 ;
                description 'Cancel loopback mode.' ;
              }

              enum outer {
                value 1 ;
                description 'Line loopback mode.' ;
              }

              enum inner {
                value 2 ;
                description 'Inner loopback mode.' ;
              }

              enum external {
                value 3 ;
                description 'External loopback mode.' ;
              }

              enum line-extend {
                value 4 ;
                description 'Line loopback mode extension.' ;
              }

              enum internal-extend {
                value 5 ;
                description 'Internal loopback mode extension.' ;
              }

            }

            default cancel ;
          }

          leaf mdimode {
            description 'Configures the MDI/MDI-X function, the XGEI port does not support this configuration when it is in WAN mode.' ;
            type enumeration {
              enum mdimode-mdix {
                value 1 ;
                description 'Switch port to straight-through mode.' ;
              }

              enum mdimode-mdi {
                value 2 ;
                description 'Switch port to crossover mode.' ;
              }

              enum mdimode-auto {
                value 3 ;
                description 'Switch port to auto-cross mode.' ;
              }

            }

            default mdimode-auto ;
          }

          leaf pemode {
            description 'Configures the copper-fiber attribute of a port, the XGEI port does not support this configuration when it is in WAN mode.' ;
            type enumeration {
              enum media-copper {
                value 1 ;
                description 'The PEMode of the port is electric.' ;
              }

              enum media-fiber {
                value 2 ;
                description 'The PEMode of the port is optical.' ;
              }

            }

            default media-fiber ;
          }

          leaf threshold-error-packet {
            description 'Sets the alarm threshold for port errors.' ;
            type uint16 {
              range 0..65535 {
                description 'The number of error packets.' ;
              }

            }

            default 3 ;
          }

          leaf unidirection {
            description 'Configures an unframing channel.' ;
            type enumeration {
              enum disable {
                value 1 ;
                description 'Unidirection disable.' ;
              }

              enum enable {
                value 2 ;
                description 'Unidirection enable' ;
              }

            }

            default disable ;
          }

          leaf rf2sf {
            description 'Configures rf2sf, the XGEI port does not support this configuration when it is in WAN mode.' ;
            type enumeration {
              enum enable {
                value 1 ;
                description 'rf2sf enable' ;
              }

              enum disable {
                value 0 ;
                description 'rf2sf diable' ;
              }

            }

            default enable ;
            ncd:revise-date 2018-03-09 ;
          }

          container laser-status {
            leaf status {
              description 'Open/close laser or set recover mode of ALS status.' ;
              type enumeration {
                enum on {
                  value 1 ;
                  description 'Open laser.' ;
                }

                enum off {
                  value 2 ;
                  description 'Close laser.' ;
                }

                enum auto-recovery {
                  value 3 ;
                  description 'Set recover mode is auto-recovery.' ;
                }

                enum manual-recovery {
                  value 4 ;
                  description 'Set recover mode is manual-recovery.' ;
                }

                enum invalid {
                  value 0 ;
                  description 'The invalid value of laser-status mode.' ;
                }

              }

              default on ;
            }

            leaf period {
              description 'Start period of automatic.' ;
              type uint16 {
                range 20..600 {
                  description 'Range: 20-600.' ;
                }

              }

              units second ;
              default 100 ;
            }

            leaf pulsewidth {
              description 'Start pulse wide of automatic.' ;
              type uint8 {
                range 1..20 {
                  description 'Range: 1-20.' ;
                }

              }

              units second ;
              default 2 ;
            }

            leaf testpulsewidth {
              description 'Start pulse wide of testing.' ;
              type uint8 {
                range 50..200 {
                  description 'Range: 50-200.' ;
                }

              }

              units second ;
              default 90 ;
            }

            leaf offtime {
              description 'Time of laser reopen, unit is second' ;
              type uint32 {
                range 0..65535 {
                  description 'laser status off times (s)' ;
                }

              }

              units second ;
              default 0 ;
            }

          }

          leaf flow-ctr-receive {
            description 'Flow control receive, the XGEI port does not support this configuration when it is in WAN mode.' ;
            type enumeration {
              enum disable {
                value 1 ;
                description 'Disable receive flow control.' ;
              }

              enum enable {
                value 2 ;
                description 'Enable receive flow control.' ;
              }

            }

            default disable ;
          }

          leaf flow-ctrl-send {
            description 'Flow control send, the XGEI port does not support this configuration when it is in WAN mode.' ;
            type enumeration {
              enum disable {
                value 1 ;
                description 'Disable send flow control.' ;
              }

              enum enable {
                value 2 ;
                description 'Enable send flow control.' ;
              }

            }

            default disable ;
          }

          leaf jumbo {
            description 'Configures jumbo, the XGEI port does not support this configuration when it is in WAN mode.' ;
            type enumeration {
              enum disable {
                value 1 ;
                description 'Jumbo disable.' ;
              }

              enum enable {
                value 2 ;
                description 'Jumbo enable.' ;
              }

            }

            default enable ;
            ncd:revise-date 2018-12-12 ;
          }

          leaf jumbo-size {
            description 'Configures jumbo size, the XGEI port does not support this configuration when it is in WAN mode.' ;
            type uint32 ;

            default 9216 ;
            ncd:revise-date 2018-12-12 ;
          }

          leaf master-slave-mode {
            description 'Set clock negotiation mode of interface, the XGEI port does not support this configuration when it is in WAN mode.' ;
            type enumeration {
              enum master {
                value 1 ;
                description 'Master mode.' ;
              }

              enum slave {
                value 2 ;
                description 'Slave mode.' ;
              }

              enum auto {
                value 3 ;
                description 'Auto mode.' ;
              }

            }

            default auto ;
          }

          leaf fec-eth {
            description 'Configures fec of a port, the XGEI port does not support this configuration when it is in WAN mode.' ;
            type enumeration {
              enum enable {
                value 1 ;
                description 'enable.' ;
              }

              enum disable {
                value 2 ;
                description 'disable.' ;
              }

              enum auto {
                value 3 ;
                description 'auto.' ;
              }

              enum invalid {
                value 0 ;
                description 'invalid' ;
              }

            }

            default invalid ;
            ncd:revise-date 2019-06-25 ;
          }

          container alarm-insert {
            description 'Configure alarm insert, the XGEI port does not support this configuration when it is in WAN mode.' ;
            leaf alarm-insert-sd {
              description 'Alarm insert SD.' ;
              type empty ;

            }

            ncd:revise-date 2017-08-01 ;
          }

          container ipg-config {
            description 'Configure ipg.' ;
            leaf ipg {
              description 'ipg' ;
              type uint16 {
                range 0..255 {
                  description 'ipg rang value and default value configured by perfcode.' ;
                }

              }

              default 12 ;
            }

            ncd:revise-date 2018-03-09 ;
          }

          container loopback-time {
            description 'Configure loopback time.' ;
            choice effective-time {
              case timeliness {
                leaf permanent {
                  description 'Loopback config permanent effective' ;
                  type empty ;

                }

              }

              case date-time {
                leaf begin-date {
                  description 'Begin date from 1-1-2001 to 12-31-2037' ;
                  type ncd:date ;

                  mandatory true ;
                }

                leaf begin-time {
                  description 'Begin time' ;
                  type ncd:time ;

                  mandatory true ;
                }

                leaf end-date {
                  description 'End date from 1-1-2001 to 12-31-2037' ;
                  type ncd:date ;

                  mandatory true ;
                }

                leaf end-time {
                  description 'End time' ;
                  type ncd:time ;

                  mandatory true ;
                }

              }

            }

          }

          container work-mode-config {
            description 'Configure work mode, the XGEI port does not support this configuration when it is in WAN mode.' ;
            leaf work-mode {
              description 'Ethernet working mode.' ;
              type enumeration {
                enum eth {
                  value 1 ;
                  description 'Work mode is eth' ;
                }

                enum flexe {
                  value 2 ;
                  description 'Work mode is flexe' ;
                }

                enum mtn-fg {
                  value 3 ;
                  description 'Work mode is mtn-fg' ;
                }

              }

              default eth ;
            }

            ncd:revise-date 2018-11-14 ;
          }

          container optical-module-config {
            if-feature optical-module-config ;

            description 'Configure optical module, the XGEI port does not support this configuration when it is in WAN mode.' ;
            leaf fec-mode {
              if-feature optical-module-config ;

              description 'Configure fec mode for interface' ;
              type enumeration {
                enum GFEC {
                  value 12 ;
                  description 'OTU-4 G.709 FEC' ;
                }

                enum OTNnoFEC {
                  value 18 ;
                  description 'OTU-4 Transparent mode' ;
                }

                enum HD-FEC1 {
                  value 48 ;
                  description 'OTU-4 7% Staircase HD-FEC' ;
                }

                enum SD-FECy-DIFF-15 {
                  value 53 ;
                  description '15% SD-FEC Everest Compatible' ;
                }

                enum SD-FECy-NONDIFF-15 {
                  value 85 ;
                  description '15% SD-FEC Denali Compatible' ;
                }

              }

            }

            leaf optical-power-adjust {
              if-feature optical-module-config ;

              description 'Configure optical power for interface' ;
              type int32 {
                range -2000..1000 {
                  description 'Optical power(0.01dbm, must be a multiple of 10)' ;
                }

              }

            }

            container wavelength {
              if-feature optical-module-config ;

              description 'Configure wavelength for interface' ;
              presence wavelength ;
              leaf translation-mode {
                if-feature optical-module-config ;

                description 'Configure translation mode for interface' ;
                type enumeration {
                  enum dwdm {
                    value 1 ;
                  }

                  enum cwdm {
                    value 3 ;
                  }

                }

                mandatory true ;
              }

              leaf center-frequency {
                if-feature optical-module-config ;

                description 'Configure center frequency for interface.The range is 191.15000-196.10000.' ;
                type decimal64 {
                  fraction-digits 5 ;
                  range 191.15000..196.10000 ;

                }

                mandatory true ;
                ncd:revise-date 2019-06-25 ;
              }

              leaf center-freq {
                if-feature optical-module-config ;

                status obsolete {
                  ncd:revise-date 2019-06-25 ;
                }

                description 'Configure center frequency for interface.The range is 191.3-196.1.' ;
                type string ;

                mandatory true ;
              }

            }

            container wavelength-capability {
              leaf spacing {
                if-feature pc-test {
                  ncd:revise-date 2023-10-25 ;
                }

                mandatory true ;
                type enumeration {
                  enum 50G-Spacing {
                    value 1 ;
                  }

                  enum 6.25G-Spacing {
                    value 2 ;
                  }

                }

                description 'Configurable frequency spacing, such as 50GHz, 6.25GHz.' ;
                status obsolete ;

              }

              choice configtype {
                if-feature pc-test {
                  ncd:revise-date 2023-10-25 ;
                }

                case center-frequency {
                  if-feature pc-test {
                    ncd:revise-date 2023-10-25 ;
                  }

                  leaf center-freq {
                    type empty ;

                    mandatory true ;
                    description 'Configure with frequency.' ;
                    if-feature pc-test {
                      ncd:revise-date 2023-10-25 ;
                    }

                  }

                  leaf freq-value {
                    mandatory true ;
                    if-feature pc-test {
                      ncd:revise-date 2023-10-25 ;
                    }

                    type int32 {
                      range 191150000..196100000 ;

                    }

                    description 'Integer frequency value, in range of 191150000 to 196100000, such as 191320000 representing 191.32THz.
For details, Please execute the show wavelength-capability command to view more configurable frequencies.' ;
                  }

                }

                case wavelength {
                  if-feature pc-test {
                    ncd:revise-date 2023-10-25 ;
                  }

                  leaf wavelength {
                    if-feature pc-test {
                      ncd:revise-date 2023-10-25 ;
                    }

                    mandatory true ;
                    description 'Configure with wavelength.' ;
                    type empty ;

                  }

                  leaf wavelength-value {
                    if-feature pc-test {
                      ncd:revise-date 2023-10-25 ;
                    }

                    type uint32 {
                      range 152877300..156836200 ;

                    }

                    mandatory true ;
                    description 'Integer wavelength value, in range of 152877300 to 156836200, such as 152877300 representing 1528.773nm.
For details, Please execute the show wavelength-capability command to view more configurable wavelengths.' ;
                  }

                }

                case channel {
                  if-feature pc-test {
                    ncd:revise-date 2023-10-25 ;
                  }

                  leaf channel-index {
                    type empty ;

                    if-feature pc-test {
                      ncd:revise-date 2023-10-25 ;
                    }

                    mandatory true ;
                    description 'Configure with channel number index.' ;
                  }

                  leaf channel-value {
                    if-feature pc-test {
                      ncd:revise-date 2023-10-25 ;
                    }

                    type uint32 {
                      range 1..793 ;

                    }

                    mandatory true ;
                    description 'It is the channel number index displayed in the show wavelength-capability command, with one frequency (wavelength) corresponding to one channel number. 
The range of 50GHz spacing is 1-100, and the range of 6.25GHz spacing is 1-793.' ;
                  }

                }

                mandatory true ;
              }

              presence wavelength-capability ;
              description 'Configure wavelength for interface by frequency,wavelength,channel index.' ;
              status obsolete {
                ncd:revise-date 2024-11-04 ;
              }

              if-feature pc-test {
                ncd:revise-date 2024-08-15 ;
              }

              ncd:revise-date 2023-10-25 ;
            }

            ncd:revise-date 2019-03-05 ;
          }

          container split {
            leaf split-name {
              description 'Split name' ;
              type enumeration {
                enum xgei {
                  value 132 ;
                  description 'Port xgei.' ;
                }

                enum xxvgei {
                  value 145 ;
                  description 'Port xxvgei.' ;
                }

                enum lgei {
                  value 158 ;
                  description 'Port lgei.' ;
                }

                enum ccgei {
                  value 159 ;
                  description 'Port ccgei.' ;
                }

                enum cgei {
                  value 139 ;
                  description 'Port cgei.' ;
                }

              }

            }

            leaf split-num {
              description 'Split number' ;
              type uint8 {
                range 1..255 {
                  description 'Split number range' ;
                }

              }

            }

            description 'Configure port split, the XGEI port does not support this configuration when it is in WAN mode.' ;
            ncd:revise-date 2020-02-15 ;
          }

          container eee-config {
            description 'Configure ethernet energy efficient function, the XGEI port does not support this configuration when it is in WAN mode.' ;
            leaf status {
              description 'Enable or disable eee function.' ;
              type enumeration {
                enum disable {
                  value 0 ;
                  description 'Disable eee function.' ;
                }

                enum enable {
                  value 1 ;
                  description 'Enable eee function.' ;
                }

              }

              default disable ;
            }

            leaf txidletime {
              description 'Duration to the low power idle state.' ;
              type uint8 {
                range 0..100 ;

              }

              default 0 ;
            }

            leaf txwaketime {
              description 'Duration to the active state.' ;
              type uint8 {
                range 0..100 ;

              }

              default 0 ;
            }

            ncd:revise-date 2020-02-25 ;
          }

          container optical-inform-monitor {
            description 'Optical information monitor switch.' ;
            leaf status {
              description 'Enable or disable optical information monitor.' ;
              type enumeration {
                enum disable {
                  value 0 ;
                  description 'Disable optical information monitor.' ;
                }

                enum enable {
                  value 1 ;
                  description 'Enable optical information monitor.' ;
                }

              }

              default disable ;
            }

            ncd:revise-date 2020-02-25 ;
          }

          container control-flap {
            description 'Interface control flap auto or manual recovery, the XGEI port does not support this configuration when it is in WAN mode.' ;
            presence control-flap ;
            choice recovery-mode {
              description 'Configure recovery mode.' ;
              mandatory true ;
              case automode {
                leaf auto {
                  description 'Configure interface auto recovery of control flap.' ;
                  type empty ;

                  mandatory true ;
                }

                leaf recovery-time {
                  description 'Configure interface recovery time of control flap.' ;
                  type uint32 {
                    range 1..86400 ;

                  }

                  mandatory true ;
                }

              }

              case forcemode {
                leaf force {
                  description 'Configure interface manual recovery of control flap.' ;
                  type empty ;

                  mandatory true ;
                }

              }

            }

            leaf interval-unit {
              description 'Configure the unit to second or millisecond.' ;
              type enumeration {
                enum s {
                  value 0 ;
                  description 'The control flap unit of time is second.' ;
                }

                enum ms {
                  value 1 ;
                  description 'The control flap unit of time is millisecond.' ;
                }

              }

              mandatory true ;
            }

            leaf threshold-times {
              description 'The threshold times of interface.' ;
              type uint16 {
                range 1..20000 ;

              }

              mandatory true ;
            }

            leaf interval-time {
              description 'The interval time of interface.' ;
              type uint32 {
                range 1..86400 ;

              }

              mandatory true ;
            }

            container second {
              description 'Second threshold-times and interval-time.' ;
              presence second ;
              leaf threshold-times {
                type uint16 {
                  range 1..20000 ;

                }

                description 'The second threshold times of interface.' ;
                mandatory true ;
              }

              leaf interval-time {
                type uint32 {
                  range 1..86400 ;

                }

                description 'The second interval time of interface.' ;
                mandatory true ;
              }

              ncd:revise-date 2025-01-02 ;
            }

            ncd:revise-date 2020-02-25 ;
          }

          container single-fiber {
            description 'Config single-fiber tx/rx disable/enable, the XGEI port does not support this configuration when it is in WAN mode.' ;
            leaf tx {
              description 'Singel fiber tx disable/enable' ;
              type enumeration {
                enum disable {
                  value 0 ;
                  description 'Singel fiber tx disable' ;
                }

                enum enable {
                  value 1 ;
                  description 'Singel fiber tx enable' ;
                }

              }

              default disable ;
            }

            leaf rx {
              description 'Singel fiber rx disable/enable' ;
              type enumeration {
                enum disable {
                  value 0 ;
                  description 'Singel fiber rx disable' ;
                }

                enum enable {
                  value 1 ;
                  description 'Singel fiber rx enable' ;
                }

              }

              default disable ;
            }

            ncd:revise-date 2020-09-14 ;
          }

          leaf link-force {
            description 'Config port link-force, the XGEI port does not support this configuration when it is in WAN mode.' ;
            type uint8 {
              range 0..1 {
                description 'The range of link-force' ;
              }

            }

            default 0 ;
            ncd:revise-date 2020-09-14 ;
          }

          container link-delays {
            description 'Configure port link delay.' ;
            leaf link-delay-down {
              description 'Delay the processing of hardware link down notifications.' ;
              type uint32 {
                range 0..600000 {
                  description 'The time to delay link down notifications(ms).' ;
                }

              }

              units millisecond ;
              default 0 ;
            }

            leaf link-delay-up {
              description 'Delay the processing of hardware link up notifications.' ;
              type uint32 {
                range 0..600000 {
                  description 'The time to delay link up notifications(ms).' ;
                }

              }

              units millisecond ;
              default 0 ;
            }

            ncd:revise-date 2020-09-21 ;
          }

          leaf flow-ctrl-onthreshold {
            if-feature flow-control-threshold ;

            description 'Configures flow control on threshold, 0-15000, the XGEI port does not support this configuration when it is in WAN mode.' ;
            type uint32 {
              range 0..15000 ;

            }

            ncd:revise-date 2022-09-09 ;
          }

          leaf flow-ctrl-offthreshold {
            if-feature flow-control-threshold ;

            description 'Configures flow control off threshold, 0-15000, the XGEI port does not support this configuration when it is in WAN mode.' ;
            type uint32 {
              range 0..15000 ;

            }

            default 0 ;
            ncd:revise-date 2022-08-31 ;
          }

          container port-alarm {
            if-feature port-alarm-ifdown ;

            container if-down {
              leaf crc-error {
                type uint8 {
                  range 0..1 ;

                }

                default 0 ;
              }

              leaf symbol-error {
                type uint8 {
                  range 0..1 ;

                }

                default 0 ;
              }

              leaf bip8-sd {
                type uint8 {
                  range 0..1 ;

                }

                default 0 ;
              }

            }

            ncd:revise-date 2022-08-31 ;
          }

          leaf fec-enable-para {
            description 'Configures fec enable para of a port, the XGEI port does not support this configuration when it is in WAN mode.' ;
            type enumeration {
              enum rs {
                value 1 ;
                description 'RS FEC mode.' ;
              }

              enum base-r {
                value 2 ;
                description 'Base-R FEC mode.' ;
              }

              enum invalid {
                value 0 ;
                description 'Invalid enable para.' ;
              }

            }

            default invalid ;
            ncd:revise-date 2022-10-13 ;
          }

          container optical-power-detect {
            if-feature optical-power-detect {
              ncd:revise-date 2024-01-23 ;
            }

            leaf switch {
              type enumeration {
                enum enable {
                  value 1 ;
                  description 'Enable optical power detect.' ;
                }

                enum disable {
                  value 2 ;
                  description 'Disable optical power detect.' ;
                }

              }

              description 'Enable or disable optical power detect.' ;
              default disable ;
            }

            leaf mode {
              type enumeration {
                enum period {
                  description 'Auto recovery of port status (up) after optical module alarm.' ;
                  value 1 ;
                }

                enum permanent-shut {
                  description 'The port will be permanently shutdown after an optical power alarm.' ;
                  value 2 ;
                }

              }

              description 'Configure the mode of optical-power-detect.' ;
              default permanent-shut ;
            }

            leaf period-time {
              description 'The period time for automatic restoration of port status (up) after optical module alarm.' ;
              default 10 ;
              type uint16 {
                range 10..65535 ;

              }

            }

            description 'Configures optical power detect, the XGEI port does not support this configuration when it is in WAN mode.' ;
            ncd:revise-date 2024-01-23 ;
          }

          container wan-config {
            leaf clock-mode {
              type enumeration {
                enum internal {
                  value 1 ;
                  description 'Select clock from local.' ;
                }

                enum line {
                  value 2 ;
                  description 'Select clock from line.' ;
                }

              }

              description 'Configures the clock mode.' ;
              default internal ;
            }

            leaf framing {
              type enumeration {
                enum sdh {
                  value 1 ;
                  description 'Select sdh framing.' ;
                }

                enum sonet {
                  value 2 ;
                  description 'Select sonet framing.' ;
                }

              }

              description 'Configures the framing format on port.' ;
              default sdh ;
            }

            leaf threshold-sd-ber {
              type uint8 {
                range 5..8 {
                  description 'Sd-ber value.' ;
                }

              }

              description 'Configure the degrade threshold of signal for interface.' ;
              default 6 ;
            }

            leaf threshold-sf-ber {
              type uint8 {
                range 4..8 {
                  description 'Sf-ber value.' ;
                }

              }

              description 'Configure the failure threshold of signal for interface' ;
              default 4 ;
            }

            container flag {
              leaf c2 {
                type uint16 {
                  range "0..5 | 18..28 | 32 | 207 | 254" ;

                }

                description 'Configures signaling path flag of a interface.' ;
                default 22 ;
              }

              leaf c2ex {
                type uint16 {
                  range "0..5 | 18..28 | 32 | 207 | 254" ;

                }

                description 'Configures the channel signal flag of the expected peer on interface.' ;
                default 22 ;
              }

              container j0 {
                leaf trace-mode {
                  type enumeration {
                    enum trace-1 {
                      value 1 ;
                    }

                    enum trace-16 {
                      value 2 ;
                    }

                    enum trace-64 {
                      value 3 ;
                    }

                    enum trace-16-null {
                      value 5 ;
                    }

                    enum trace-64-null {
                      value 6 ;
                    }

                  }

                  description 'Trace mode.' ;
                }

                leaf trace-1-value {
                  type ncd:hex {
                    length 0..255 ;

                  }

                  description 'J0 description.' ;
                }

                leaf trace-16-value {
                  type ncd:string-with-blank {
                    length 1..15 {
                      description 'Range: 1-15.' ;
                    }

                  }

                  description 'J0 description.' ;
                }

                leaf trace-64-value {
                  type ncd:string-with-blank {
                    length 1..62 {
                      description 'Range: 1-62.' ;
                    }

                  }

                  description 'J0 description.' ;
                }

              }

              container j0ex {
                leaf trace-mode {
                  type enumeration {
                    enum trace-1 {
                      value 1 ;
                    }

                    enum trace-16 {
                      value 2 ;
                    }

                    enum trace-64 {
                      value 3 ;
                    }

                    enum trace-16-null {
                      value 5 ;
                    }

                    enum trace-64-null {
                      value 6 ;
                    }

                  }

                  description 'Trace mode.' ;
                }

                leaf trace-1-value {
                  type ncd:hex {
                    length 0..255 ;

                  }

                  description 'J0ex description.' ;
                }

                leaf trace-16-value {
                  type ncd:string-with-blank {
                    length 1..15 {
                      description 'Range: 1-15.' ;
                    }

                  }

                  description 'J0ex description.' ;
                }

                leaf trace-64-value {
                  type ncd:string-with-blank {
                    length 1..62 {
                      description 'Range: 1-62.' ;
                    }

                  }

                  description 'J0ex description.' ;
                }

              }

              container j1 {
                leaf trace-mode {
                  type enumeration {
                    enum trace-1 {
                      value 1 ;
                    }

                    enum trace-16 {
                      value 2 ;
                    }

                    enum trace-64 {
                      value 3 ;
                    }

                    enum trace-16-null {
                      value 5 ;
                    }

                    enum trace-64-null {
                      value 6 ;
                    }

                  }

                  description 'Trace mode.' ;
                }

                leaf trace-1-value {
                  type ncd:hex {
                    length 0..255 ;

                  }

                  description 'J1 description.' ;
                }

                leaf trace-16-64-value {
                  type ncd:string-with-blank {
                    length 1..62 {
                      description 'Range: 1-62.' ;
                    }

                  }

                  description 'J1 description.' ;
                }

              }

              container j1ex {
                leaf trace-mode {
                  type enumeration {
                    enum trace-1 {
                      value 1 ;
                    }

                    enum trace-16 {
                      value 2 ;
                    }

                    enum trace-64 {
                      value 3 ;
                    }

                    enum trace-16-null {
                      value 5 ;
                    }

                    enum trace-64-null {
                      value 6 ;
                    }

                  }

                  description 'Trace mode.' ;
                }

                leaf trace-1-value {
                  type ncd:hex {
                    length 0..255 ;

                  }

                  description 'J1ex description.' ;
                }

                leaf trace-16-64-value {
                  type ncd:string-with-blank {
                    length 1..62 {
                      description 'Range: 1-62.' ;
                    }

                  }

                  description 'J1ex description.' ;
                }

              }

            }

            container port-down-sdh-alarm {
              leaf rdi-l {
                type uint8 {
                  range 0..1 {
                    description 'Range: 0-1.' ;
                  }

                }

                description 'RDI-L alarm.' ;
                default 0 ;
              }

              leaf rdi-p {
                type uint8 {
                  range 0..1 {
                    description 'Range: 0-1.' ;
                  }

                }

                description 'RDI-P alarm.' ;
                default 0 ;
              }

              leaf sd {
                type uint8 {
                  range 0..1 {
                    description 'Range: 0-1.' ;
                  }

                }

                description 'SD alarm.' ;
                default 0 ;
              }

              leaf sf {
                type uint8 {
                  range 0..1 {
                    description 'Range: 0-1.' ;
                  }

                }

                description 'SF alarm.' ;
                default 0 ;
              }

            }

            description 'Configurations for the XGigabit Ethernet port in WAN mode.' ;
            ncd:revise-date 2024-06-10 ;
          }

          leaf sat-holdtime {
            type uint16 {
              range 0..65535 {
                description 'Range: 0-65535.' ;
              }

            }

            description 'Configures the port hold-time in satellite.' ;
            units second ;
            ncd:revise-date 2024-11-12 ;
          }

        }

      }

      container wans {
        list wan {
          key if-name ;
          leaf if-name {
            type string ;

            description 'Interface name.' ;
          }

          leaf holdtime {
            description 'Configures the port hold-time.' ;
            type uint16 {
              range 0..3600 {
                description 'Range: 0-3600.' ;
              }

            }

            units second ;
            default 120 ;
          }

          leaf negotiation {
            description 'Configures the port negotiation mode.' ;
            type enumeration {
              enum negotiation-force {
                value 1 ;
                description 'Force negotiation mode.' ;
              }

              enum negotiation-auto {
                value 2 ;
                description 'Auto negotiation mode.' ;
              }

            }

            default negotiation-force ;
          }

          leaf loopback {
            description 'Configures the loopback method of a port.' ;
            type enumeration {
              enum cancel {
                value 0 ;
                description 'Cancel loopback mode.' ;
              }

              enum outer {
                value 1 ;
                description 'Line loopback mode.' ;
              }

              enum inner {
                value 2 ;
                description 'Inner loopback mode.' ;
              }

              enum external {
                value 3 ;
                description 'External loopback mode.' ;
              }

            }

            default cancel ;
          }

          leaf clock-mode {
            description 'Configures the clock mode.' ;
            type enumeration {
              enum internal {
                value 1 ;
                description 'Select clock from local.' ;
              }

              enum line {
                value 2 ;
                description 'Select clock from line.' ;
              }

            }

            default internal ;
          }

          leaf framing {
            description 'Configures the framing format on port.' ;
            type enumeration {
              enum sdh {
                value 1 ;
                description 'Select sdh framing.' ;
              }

              enum sonet {
                value 2 ;
                description 'Select sonet framing.' ;
              }

            }

            default sdh ;
          }

          leaf threshold-error-packet {
            description 'Sets the alarm threshold for port errors.' ;
            type uint16 {
              range 0..65535 {
                description 'The number of error packets.' ;
              }

            }

            default 3 ;
            ncd:revise-date 2023-12-12 ;
          }

          leaf threshold-sd-ber {
            description 'Configure the degrade threshold of signal for interface.' ;
            type uint8 {
              range 5..8 {
                description 'Sd-ber value.' ;
              }

            }

            default 6 ;
          }

          leaf threshold-sf-ber {
            description 'Configure the failure threshold of signal for interface' ;
            type uint8 {
              range 4..8 {
                description 'Sf-ber value.' ;
              }

            }

            default 4 ;
          }

          leaf unidirection {
            description 'Configures an unframing channel.' ;
            type enumeration {
              enum disable {
                value 1 ;
                description 'Unidirection disable.' ;
              }

              enum enable {
                value 2 ;
                description 'Unidirection enable.' ;
              }

            }

            default disable ;
          }

          container flag {
            leaf c2 {
              description 'Configures signaling path flag of a interface.' ;
              type uint16 {
                range "0..5 | 18..28 | 32 | 207 | 254" ;

              }

              default 22 ;
            }

            leaf c2ex {
              description 'Configures the channel signal flag of the expected peer on interface.' ;
              type uint16 {
                range "0..5 | 18..28 | 32 | 207 | 254" ;

              }

              default 22 ;
            }

            container j0 {
              leaf trace-mode {
                description 'Trace mode.' ;
                type enumeration {
                  enum trace-1 {
                    value 1 ;
                  }

                  enum trace-16 {
                    value 2 ;
                  }

                  enum trace-64 {
                    value 3 ;
                  }

                  enum trace-16-null {
                    value 5 ;
                  }

                  enum trace-64-null {
                    value 6 ;
                  }

                }

              }

              leaf trace-1-value {
                description 'J0 description.' ;
                type ncd:hex {
                  length 0..255 ;

                }

              }

              leaf trace-16-value {
                description 'J0 description.' ;
                type ncd:string-with-blank {
                  length 1..15 {
                    description 'Range: 1-15.' ;
                  }

                }

              }

              leaf trace-64-value {
                description 'J0 description.' ;
                type ncd:string-with-blank {
                  length 1..62 {
                    description 'Range: 1-62.' ;
                  }

                }

                ncd:revise-date 2021-05-29 ;
              }

            }

            container j0ex {
              leaf trace-mode {
                description 'Trace mode.' ;
                type enumeration {
                  enum trace-1 {
                    value 1 ;
                  }

                  enum trace-16 {
                    value 2 ;
                  }

                  enum trace-64 {
                    value 3 ;
                  }

                  enum trace-16-null {
                    value 5 ;
                  }

                  enum trace-64-null {
                    value 6 ;
                  }

                }

              }

              leaf trace-1-value {
                description 'J0ex description.' ;
                type ncd:hex {
                  length 0..255 ;

                }

              }

              leaf trace-16-value {
                description 'J0ex description.' ;
                type ncd:string-with-blank {
                  length 1..15 {
                    description 'Range: 1-15.' ;
                  }

                }

              }

              leaf trace-64-value {
                description 'J0ex description.' ;
                type ncd:string-with-blank {
                  length 1..62 {
                    description 'Range: 1-62.' ;
                  }

                }

                ncd:revise-date 2021-05-29 ;
              }

            }

            container j1 {
              leaf trace-mode {
                description 'Trace mode.' ;
                type enumeration {
                  enum trace-1 {
                    value 1 ;
                  }

                  enum trace-16 {
                    value 2 ;
                  }

                  enum trace-64 {
                    value 3 ;
                  }

                  enum trace-16-null {
                    value 5 ;
                  }

                  enum trace-64-null {
                    value 6 ;
                  }

                }

              }

              leaf trace-1-value {
                description 'J1 description.' ;
                type ncd:hex {
                  length 0..255 ;

                }

              }

              leaf trace-16-64-value {
                description 'J1 description.' ;
                type ncd:string-with-blank {
                  length 1..62 {
                    description 'Range: 1-62.' ;
                  }

                }

              }

            }

            container j1ex {
              leaf trace-mode {
                description 'Trace mode.' ;
                type enumeration {
                  enum trace-1 {
                    value 1 ;
                  }

                  enum trace-16 {
                    value 2 ;
                  }

                  enum trace-64 {
                    value 3 ;
                  }

                  enum trace-16-null {
                    value 5 ;
                  }

                  enum trace-64-null {
                    value 6 ;
                  }

                }

              }

              leaf trace-1-value {
                description 'J1ex description.' ;
                type ncd:hex {
                  length 0..255 ;

                }

              }

              leaf trace-16-64-value {
                description 'J1ex description.' ;
                type ncd:string-with-blank {
                  length 1..62 {
                    description 'Range: 1-62.' ;
                  }

                }

              }

            }

          }

          container port-down-sdh-alarm {
            leaf rdi-l {
              description 'RDI-L alarm.' ;
              type uint8 {
                range 0..1 {
                  description 'Range: 0-1.' ;
                }

              }

              default 0 ;
            }

            leaf rdi-p {
              description 'RDI-P alarm.' ;
              type uint8 {
                range 0..1 {
                  description 'Range: 0-1.' ;
                }

              }

              default 0 ;
            }

            leaf sd {
              description 'SD alarm.' ;
              type uint8 {
                range 0..1 {
                  description 'Range: 0-1.' ;
                }

              }

              default 0 ;
            }

            leaf sf {
              description 'SF alarm.' ;
              type uint8 {
                range 0..1 {
                  description 'Range: 0-1.' ;
                }

              }

              default 0 ;
            }

          }

          container laser-status {
            leaf status {
              description 'Open/close laser or set recover mode of ALS status.' ;
              type enumeration {
                enum on {
                  value 1 ;
                  description 'Open laser.' ;
                }

                enum off {
                  value 2 ;
                  description 'Close laser.' ;
                }

                enum auto-recovery {
                  value 3 ;
                  description 'Set recover mode is auto-recovery.' ;
                }

                enum manual-recovery {
                  value 4 ;
                  description 'Set recover mode is manual-recovery.' ;
                }

              }

              default on ;
            }

            leaf period {
              description 'Start period of automatic.' ;
              type uint16 {
                range 20..600 {
                  description 'Range: 20-600.' ;
                }

              }

              units second ;
              default 100 ;
            }

            leaf pulsewidth {
              description 'Start pulse wide of automatic.' ;
              type uint8 {
                range 1..20 {
                  description 'Range: 1-20.' ;
                }

              }

              units second ;
              default 2 ;
            }

            leaf testpulsewidth {
              description 'Start pulse wide of testing.' ;
              type uint8 {
                range 50..200 {
                  description 'Range: 50-200.' ;
                }

              }

              units second ;
              default 90 ;
            }

          }

        }

        description 'Configurations for the XGigabit WAN Ethernet port.' ;
      }

      container atms {
        list atm {
          description 'ATM interface mode.' ;
          key if-name ;
          leaf if-name {
            description 'Interface name.' ;
            type string ;

          }

          leaf holdtime {
            description 'Configures the port hold-time.' ;
            type uint16 {
              range 0..3600 {
                description 'Range: 0-3600.' ;
              }

            }

            units second ;
            default 120 ;
          }

          leaf loopback {
            description 'Configures the loopback method of a port.' ;
            type enumeration {
              enum cancel {
                value 0 ;
                description 'Cancel loopback mode.' ;
              }

              enum outer {
                value 1 ;
                description 'Line loopback mode.' ;
              }

              enum inner {
                value 2 ;
                description 'Inner loopback mode.' ;
              }

            }

            default cancel ;
          }

          leaf scramble {
            description 'Configures the scrambling code of a port.' ;
            type enumeration {
              enum scramble-disable {
                value 1 ;
                description 'Disable scramble payload.' ;
              }

              enum scramble-enable {
                value 2 ;
                description 'Enable scramble payload.' ;
              }

            }

            default scramble-enable ;
          }

          leaf clock-mode {
            description 'Configures the clock mode.' ;
            type enumeration {
              enum internal {
                value 1 ;
                description 'Select clock from local.' ;
              }

              enum line {
                value 2 ;
                description 'Select clock from line.' ;
              }

            }

            default internal ;
          }

          leaf framing {
            description 'Configures the framing format on port.' ;
            type enumeration {
              enum sdh {
                value 1 ;
                description 'Select sdh framing.' ;
              }

              enum sonet {
                value 2 ;
                description 'Select sonet framing.' ;
              }

            }

            default sdh ;
          }

          leaf threshold-error-packet {
            description 'Sets the alarm threshold for port errors.' ;
            type uint16 {
              range 1..65535 {
                description 'The number of error packets.' ;
              }

            }

            default 3 ;
          }

          container flag {
            leaf c2 {
              description 'Configures signaling path flag of a interface.' ;
              type uint16 {
                range "0..5 | 18..28 | 32 | 207 | 254" ;

              }

              default 19 ;
            }

            leaf c2ex {
              description 'Configures the channel signal flag of the expected peer on interface.' ;
              type uint16 {
                range "0..5 | 18..28 | 32 | 207 | 254" ;

              }

              default 19 ;
            }

            container j0 {
              leaf trace-mode {
                description 'Trace mode.' ;
                type enumeration {
                  enum trace-1 {
                    value 1 ;
                  }

                  enum trace-16 {
                    value 2 ;
                  }

                }

              }

              leaf trace-1-value {
                description 'J0 description.' ;
                type ncd:hex {
                  length 0..255 ;

                }

              }

              leaf trace-16-value {
                description 'J0 description.' ;
                type ncd:string-with-blank {
                  length 1..15 {
                    description 'Range: 1-15.' ;
                  }

                }

              }

            }

            container j0ex {
              leaf trace-mode {
                description 'Trace mode.' ;
                type enumeration {
                  enum trace-1 {
                    value 1 ;
                  }

                  enum trace-16 {
                    value 2 ;
                  }

                }

              }

              leaf trace-1-value {
                description 'J0ex description.' ;
                type ncd:hex {
                  length 0..255 ;

                }

              }

              leaf trace-16-value {
                description 'J0ex description.' ;
                type ncd:string-with-blank {
                  length 1..15 {
                    description 'Range: 1-15.' ;
                  }

                }

              }

            }

            container j1 {
              leaf trace-mode {
                description 'Trace mode.' ;
                type enumeration {
                  enum trace-1 {
                    value 1 ;
                  }

                  enum trace-16 {
                    value 2 ;
                  }

                  enum trace-64 {
                    value 3 ;
                  }

                }

              }

              leaf trace-1-value {
                description 'J1 description.' ;
                type ncd:hex {
                  length 0..255 ;

                }

              }

              leaf trace-16-64-value {
                description 'J1 description.' ;
                type ncd:string-with-blank {
                  length 1..62 {
                    description 'Range: 1-62.' ;
                  }

                }

              }

            }

            container j1ex {
              leaf trace-mode {
                description 'Trace mode.' ;
                type enumeration {
                  enum trace-1 {
                    value 1 ;
                  }

                  enum trace-16 {
                    value 2 ;
                  }

                  enum trace-64 {
                    value 3 ;
                  }

                }

              }

              leaf trace-1-value {
                description 'J1ex description.' ;
                type ncd:hex {
                  length 0..255 ;

                }

              }

              leaf trace-16-64-value {
                description 'J1ex description.' ;
                type ncd:string-with-blank {
                  length 1..62 {
                    description 'Range: 1-62.' ;
                  }

                }

              }

            }

          }

          container laser-status {
            leaf status {
              description 'Open/close laser or set recover mode of ALS status.' ;
              type enumeration {
                enum on {
                  value 1 ;
                  description 'Open laser.' ;
                }

                enum off {
                  value 2 ;
                  description 'Close laser.' ;
                }

                enum auto-recovery {
                  value 3 ;
                  description 'Set recover mode is auto-recovery.' ;
                }

                enum manual-recovery {
                  value 4 ;
                  description 'Set recover mode is manual-recovery.' ;
                }

              }

              default on ;
            }

            leaf period {
              description 'Start period of automatic.' ;
              type uint16 {
                range 20..600 {
                  description 'Range: 20-600.' ;
                }

              }

              units second ;
              default 100 ;
            }

            leaf pulsewidth {
              description 'Start pulse wide of automatic.' ;
              type uint8 {
                range 1..20 {
                  description 'Range: 1-20.' ;
                }

              }

              units second ;
              default 2 ;
            }

            leaf testpulsewidth {
              description 'Start pulse wide of testing.' ;
              type uint8 {
                range 50..200 {
                  description 'Range: 50-200.' ;
                }

              }

              units second ;
              default 90 ;
            }

          }

          container alarm-insert {
            description 'Configure alarm insert' ;
            leaf alarm-insert-hp {
              description 'High order path alarm insert' ;
              type empty ;

            }

            leaf alarm-insert-ms {
              description 'Multiplex section alarm insert' ;
              type empty ;

            }

          }

        }

      }

      container poss {
        list pos {
          description 'POS interface mode.' ;
          key if-name ;
          leaf if-name {
            description 'Interface name.' ;
            type string ;

          }

          leaf holdtime {
            description 'Configures the port hold-time.' ;
            type uint16 {
              range 0..3600 {
                description 'Range: 0-3600.' ;
              }

            }

            units second ;
            default 120 ;
          }

          leaf loopback {
            description 'Configures the loopback method of a port.' ;
            type enumeration {
              enum cancel {
                value 0 ;
                description 'Cancel loopback mode.' ;
              }

              enum outer {
                value 1 ;
                description 'Line loopback mode.' ;
              }

              enum inner {
                value 2 ;
                description 'Inner loopback mode.' ;
              }

              enum external {
                value 3 ;
                description 'External loopback mode.' ;
              }

            }

            default cancel ;
          }

          leaf crc {
            description 'Configures CRC mode of a interface.' ;
            type enumeration {
              enum crc16 {
                value 1 ;
                description 'CRC 16.' ;
              }

              enum crc32 {
                value 2 ;
                description 'CRC 32.' ;
              }

            }

            default crc32 ;
          }

          leaf scramble {
            description 'Configures the scrambling code of a port.' ;
            type enumeration {
              enum scramble-disable {
                value 1 ;
                description 'Disable scramble payload.' ;
              }

              enum scramble-enable {
                value 2 ;
                description 'Enable scramble payload.' ;
              }

            }

            default scramble-enable ;
          }

          leaf clock-mode {
            description 'Configures the clock mode.' ;
            type enumeration {
              enum internal {
                value 1 ;
                description 'Select clock from local.' ;
              }

              enum line {
                value 2 ;
                description 'Select clock from line.' ;
              }

            }

            default internal ;
          }

          leaf threshold-error-packet {
            description 'Sets the alarm threshold for port errors.' ;
            type uint16 {
              range 1..65535 {
                description 'The number of error packets.' ;
              }

            }

            default 3 ;
          }

          leaf threshold-sd-ber {
            description 'Configure the degrade threshold of signal for interface.' ;
            type uint8 {
              range 5..8 {
                description 'Sd-ber value.' ;
              }

            }

            default 6 ;
          }

          leaf threshold-sf-ber {
            description 'Configure the failure threshold of signal for interface.' ;
            type uint8 {
              range 4..8 {
                description 'Sf-ber value.' ;
              }

            }

            default 4 ;
          }

          container flag {
            leaf c2 {
              description 'Configures signaling path flag of a interface.' ;
              type uint16 {
                range "0..5 | 18..28 | 32 | 207 | 254" ;

              }

              default 22 ;
            }

            leaf c2ex {
              description 'Configures the channel signal flag of the expected peer on interface.' ;
              type uint16 {
                range "0..5 | 18..28 | 32 | 207 | 254" ;

              }

              default 22 ;
            }

            container j0 {
              leaf trace-mode {
                description 'Trace mode.' ;
                type enumeration {
                  enum trace-1 {
                    value 1 ;
                  }

                  enum trace-16 {
                    value 2 ;
                  }

                  enum trace-64 {
                    value 3 ;
                  }

                }

              }

              leaf trace-1-value {
                description 'J0 description.' ;
                type ncd:hex {
                  length 0..255 ;

                }

              }

              leaf trace-16-value {
                description 'J0 description.' ;
                type ncd:string-with-blank {
                  length 1..15 {
                    description 'Range: 1-15.' ;
                  }

                }

              }

              leaf trace-64-value {
                description 'J0 description.' ;
                type ncd:string-with-blank {
                  length 1..62 {
                    description 'Range: 1-62.' ;
                  }

                }

                ncd:revise-date 2017-06-02 ;
              }

            }

            container j0ex {
              leaf trace-mode {
                description 'Trace mode.' ;
                type enumeration {
                  enum trace-1 {
                    value 1 ;
                  }

                  enum trace-16 {
                    value 2 ;
                  }

                  enum trace-64 {
                    value 3 ;
                  }

                }

              }

              leaf trace-1-value {
                description 'J0ex description.' ;
                type ncd:hex {
                  length 0..255 ;

                }

              }

              leaf trace-16-value {
                description 'J0ex description.' ;
                type ncd:string-with-blank {
                  length 1..15 {
                    description 'Range: 1-15.' ;
                  }

                }

              }

              leaf trace-64-value {
                description 'J0ex description.' ;
                type ncd:string-with-blank {
                  length 1..63 {
                    description 'Range: 1-63.' ;
                  }

                }

                ncd:revise-date 2017-06-02 ;
              }

            }

            container j1 {
              leaf trace-mode {
                description 'Trace mode.' ;
                type enumeration {
                  enum trace-1 {
                    value 1 ;
                  }

                  enum trace-16 {
                    value 2 ;
                  }

                  enum trace-64 {
                    value 3 ;
                  }

                }

              }

              leaf trace-1-value {
                description 'J1 description.' ;
                type ncd:hex {
                  length 0..255 ;

                }

              }

              leaf trace-16-64-value {
                description 'J1 description.' ;
                type ncd:string-with-blank {
                  length 1..62 {
                    description 'Range: 1-62.' ;
                  }

                }

              }

            }

            container j1ex {
              leaf trace-mode {
                description 'Trace mode.' ;
                type enumeration {
                  enum trace-1 {
                    value 1 ;
                  }

                  enum trace-16 {
                    value 2 ;
                  }

                  enum trace-64 {
                    value 3 ;
                  }

                }

              }

              leaf trace-1-value {
                description 'J1ex description.' ;
                type ncd:hex {
                  length 0..255 ;

                }

              }

              leaf trace-16-64-value {
                description 'J1ex description.' ;
                type ncd:string-with-blank {
                  length 1..62 {
                    description 'Range: 1-62.' ;
                  }

                }

              }

            }

          }

          container laser-status {
            leaf status {
              description 'Open/close laser or set recover mode of ALS status.' ;
              type enumeration {
                enum on {
                  value 1 ;
                  description 'Open laser.' ;
                }

                enum off {
                  value 2 ;
                  description 'Close laser.' ;
                }

                enum auto-recovery {
                  value 3 ;
                  description 'Set recover mode is auto-recovery.' ;
                }

                enum manual-recovery {
                  value 4 ;
                  description 'Set recover mode is manual-recovery.' ;
                }

              }

              default on ;
            }

            leaf period {
              description 'Start period of automatic.' ;
              type uint16 {
                range 20..600 {
                  description 'Range: 20-600.' ;
                }

              }

              units second ;
              default 100 ;
            }

            leaf pulsewidth {
              description 'Start pulse wide of automatic.' ;
              type uint8 {
                range 1..20 {
                  description 'Range: 1-20.' ;
                }

              }

              units second ;
              default 2 ;
            }

            leaf testpulsewidth {
              description 'Start pulse wide of testing.' ;
              type uint8 {
                range 50..200 {
                  description 'Range: 50-200.' ;
                }

              }

              units second ;
              default 90 ;
            }

          }

          container alarm-insert {
            description 'Configure alarm insert' ;
            leaf alarm-insert-hp {
              description 'High order path alarm insert' ;
              type empty ;

            }

            leaf alarm-insert-ms {
              description 'Multiplex section alarm insert' ;
              type empty ;

            }

          }

        }

      }

      container uleis {
        list ulei {
          description 'ULEI interface mode.' ;
          key if-name ;
          leaf if-name {
            description 'Interface name.' ;
            type string ;

          }

          leaf holdtime {
            description 'Configures the port hold-time.' ;
            type uint16 {
              range 0..3600 {
                description 'Range: 0-3600.' ;
              }

            }

            units second ;
            default 120 ;
          }

          leaf speed {
            description 'Configures the rate of a port.' ;
            type enumeration {
              enum speed-10M {
                value 1 ;
                description 'Port speed is 10M.' ;
              }

              enum speed-100M {
                value 2 ;
                description 'Port speed is 100M.' ;
              }

              enum speed-1G {
                value 3 ;
                description 'Port speed is 1G.' ;
              }

              enum speed-10G {
                value 4 ;
                description 'Port speed is 10G.' ;
              }

              enum speed-25G {
                value 10 ;
                description 'Port speed is 25G.' ;
              }

              enum speed-40G {
                value 5 ;
                description 'Port speed is 40G.' ;
              }

              enum speed-50G {
                value 11 ;
                description 'Port speed is 50G.' ;
              }

              enum speed-100G {
                value 6 ;
                description 'Port speed is 100G.' ;
              }

            }

            default speed-1G ;
          }

        }

      }

      container dampings {
        list damp-status {
          key if-name ;
          leaf if-name {
            description 'Interface name.' ;
            type ncd:ifname ;

          }

          leaf status {
            description 'Port damping status.' ;
            type enumeration {
              enum disable {
                value 1 ;
                description 'Port damping disable.' ;
              }

              enum enable {
                value 2 ;
                description 'Port damping enable.' ;
              }

            }

            default enable ;
          }

        }

        list damping {
          key if-name ;
          leaf if-name {
            type ncd:ifname ;

          }

          leaf max-suppress-time {
            description 'Max suppress time(max-suppress-time > half-life).' ;
            type uint16 {
              range 2..600 {
                description 'Range: 2-600.' ;
              }

            }

            units second ;
            default 20 ;
          }

          leaf suppress-threshold {
            description 'Suppress threshold(suppress > reuse).' ;
            type uint16 {
              range 2..10000 {
                description 'Range: 2-10000.' ;
              }

            }

            default 2000 ;
          }

          leaf reuse-threshold {
            description 'Reuse threshold(suppress > reuse).' ;
            type uint16 {
              range 1..2000 {
                description 'Range: 1-2000.' ;
              }

            }

            default 1000 ;
          }

          leaf halflife {
            description 'Half life(max-suppress-time > half-life).' ;
            type uint8 {
              range 1..100 {
                description 'Range: 1-100.' ;
              }

            }

            units second ;
            default 5 ;
          }

        }

      }

      container link-delays {
        list link-delay {
          key if-name ;
          leaf if-name {
            description 'Interface name.' ;
            type ncd:ifname ;

          }

          leaf link-delay-down {
            description 'Delay the processing of hardware link down notifications.' ;
            type uint32 {
              range 0..600000 {
                description 'The time to delay link down notifications(ms).' ;
              }

            }

            units millisecond ;
            default 0 ;
          }

          leaf link-delay-up {
            description 'Delay the processing of hardware link up notifications.' ;
            type uint32 {
              range 0..600000 {
                description 'The time to delay link up notifications(ms).' ;
              }

            }

            units millisecond ;
            default 0 ;
          }

        }

      }

      container port-modes {
        list port-mode {
          key if-name ;
          leaf if-name {
            description 'Interface name.' ;
            type string ;

          }

          leaf lan-wan {
            description 'Switch port mode to LAN or WAN.' ;
            type enumeration {
              enum lan {
                value 132 ;
                description 'Switch port to LAN mode.' ;
              }

              enum wan {
                value 133 ;
                description 'Switch port to WAN mode.' ;
              }

              enum gei {
                value 131 ;
              }

              enum pos3 {
                value 260 ;
                description 'Switch port to POS3 mode.' ;
              }

              enum pos12 {
                value 261 ;
                description 'Switch port to POS12 mode.' ;
              }

              enum pos48 {
                value 262 ;
                description 'Switch port to POS48 mode.' ;
              }

            }

          }

          leaf pos3-pos12 {
            description 'Switches pos interface modes.' ;
            type enumeration {
              enum pos3 {
                value 260 ;
                description 'Switch port to POS3 mode.' ;
              }

              enum pos12 {
                value 261 ;
                description 'Switch port to POS12 mode.' ;
              }

              enum lan {
                value 132 ;
                description 'Switch port to LAN mode.' ;
              }

              enum wan {
                value 133 ;
                description 'Switch port to WAN mode.' ;
              }

              enum gei {
                value 131 ;
              }

              enum pos48 {
                value 262 ;
                description 'Switch port to POS48 mode.' ;
              }

            }

          }

          leaf xgei-gei {
            description 'Switch port mode to xgei or gei.' ;
            type enumeration {
              enum xgei {
                value 132 ;
                description 'Switch to xgei' ;
              }

              enum gei {
                value 131 ;
                description 'Switch to gei' ;
              }

              enum wan {
                value 133 ;
                description 'Switch to wan' ;
              }

              enum pos3 {
                value 260 ;
                description 'Switch to POS3' ;
              }

              enum pos12 {
                value 261 ;
                description 'Switch to POS12' ;
              }

              enum pos48 {
                value 262 ;
                description 'Switch to POS48' ;
              }

            }

            ncd:revise-date 2016-09-10 ;
          }

        }

      }

      container create-uleis {
        list create-ulei {
          key ulei-ifname ;
          leaf ulei-ifname {
            description 'Ulei interface name.' ;
            type string ;

          }

        }

      }

      container sdh-thresholds {
        list sdh-threshold {
          key if-name ;
          leaf if-name {
            description 'Interface name' ;
            type string ;

          }

          leaf b2-sf-ber {
            description 'Configure multiplex section signal failure threshold' ;
            type uint8 {
              range 4..8 {
                description 'Range: 4-8' ;
              }

            }

          }

          leaf b2-sd-ber {
            description 'Configure multiplex section signal degradation threshold' ;
            type uint8 {
              range 5..8 {
                description 'Range: 5-8' ;
              }

            }

          }

          leaf b3-sf-ber {
            description 'Configure high order channel signal failure threshold' ;
            type uint8 {
              range 4..8 {
                description 'Range: 4-8' ;
              }

            }

          }

          leaf b3-sd-ber {
            description 'Configure high order channel signal degradation threshold' ;
            type uint8 {
              range 5..8 {
                description 'Range: 5-8' ;
              }

            }

          }

          leaf b1-sf-ber {
            description 'Configure regeneration segment signal failure threshold' ;
            type uint8 {
              range 4..8 {
                description 'Range: 4-8' ;
              }

            }

          }

          leaf b1-sd-ber {
            description 'Configure regeneration segment signal degradation threshold' ;
            type uint8 {
              range 5..8 {
                description 'Range: 5-8' ;
              }

            }

          }

        }

        ncd:revise-date 2021-07-03 ;
      }

      container special-opticals {
        list special-optical {
          description 'Special optical interface mode, such as OSC, OCH, SOMS.' ;
          key if-name ;
          leaf if-name {
            description 'Interface name.' ;
            type string {
              length 1..31 ;

            }

          }

          container laser-status {
            description 'Configure laser status.' ;
            leaf status {
              description 'Open/close laser or set recover mode of ALS status.' ;
              type enumeration {
                enum on {
                  value 1 ;
                  description 'Open laser.' ;
                }

                enum off {
                  value 2 ;
                  description 'Close laser.' ;
                }

                enum auto-recovery {
                  value 3 ;
                  description 'Set recover mode is auto-recovery.' ;
                }

                enum manual-recovery {
                  value 4 ;
                  description 'Set recover mode is manual-recovery.' ;
                }

              }

              default on ;
            }

            leaf period {
              description 'Start period of automatic.' ;
              type uint16 {
                range 20..600 {
                  description 'Range: 20-600.' ;
                }

              }

              units second ;
              default 100 ;
            }

            leaf pulsewidth {
              description 'Start pulse wide of automatic.' ;
              type uint8 {
                range 1..20 {
                  description 'Range: 1-20.' ;
                }

              }

              units second ;
              default 2 ;
            }

            leaf testpulsewidth {
              description 'Start pulse wide of testing.' ;
              type uint8 {
                range 50..200 {
                  description 'Range: 50-200.' ;
                }

              }

              units second ;
              default 90 ;
            }

            leaf offtime {
              description 'Time of laser reopen, unit is second' ;
              type uint32 {
                range 0..65535 {
                  description 'laser status off times (s)' ;
                }

              }

              units second ;
              default 0 ;
            }

          }

        }

        ncd:revise-date 2021-07-03 ;
      }

      container gfp-mplss {
        list gfp-mpls {
          key if-name ;
          leaf if-name {
            description 'Interface name.' ;
            type string {
              length 1..31 ;

            }

          }

          leaf odu-if-name {
            description "The binding port's interface name." ;
            type string {
              length 1..31 ;

            }

          }

          leaf sd-enabled {
            description 'sd enabled.' ;
            type enumeration {
              enum disable {
                value 0 ;
              }

              enum enable {
                value 1 ;
              }

            }

            default disable ;
          }

          leaf rf2sf {
            description 'The Switch of rf to sf.' ;
            type enumeration {
              enum off {
                value 0 ;
              }

              enum on {
                value 1 ;
              }

            }

            default on ;
          }

        }

        ncd:revise-date 2021-07-03 ;
      }

      container create-vsgs {
        list create-vsg {
          key vsg-ifname ;
          leaf vsg-ifname {
            description 'VSG interface name. The name starts with "vsg", followed with a number. The default range of the number is 1025..1056 without customized.' ;
            type string {
              length 1..31 ;

            }

          }

        }

        ncd:revise-date 2021-07-03 ;
      }

      container threshold-sd-fers {
        list sd-status {
          key if-name ;
          leaf if-name {
            description 'Interface name.' ;
            type ncd:ifname ;

          }

          leaf status {
            description 'Enable or disable sd detection.' ;
            type enumeration {
              enum disable {
                value 0 ;
                description 'Disable sd detection.' ;
              }

              enum enable {
                value 1 ;
                description 'Enable sd detection.' ;
              }

            }

            default disable ;
          }

        }

        list threshold-sd-fer {
          key if-name ;
          leaf if-name {
            description 'Interface name.' ;
            type ncd:ifname ;

          }

          leaf occur-coefficient {
            description 'Threshold coefficient of occur alarm.' ;
            type uint8 {
              range 1..9 {
                description 'Range: 1-9.' ;
              }

            }

            default 5 ;
          }

          leaf occur-exponent {
            description 'Threshold exponent of occur alarm.' ;
            type uint8 {
              range 1..9 {
                description 'Range: 1-9.' ;
              }

            }

            default 5 ;
          }

          leaf clear-coefficient {
            description 'Threshold coefficient of clear alarm.' ;
            type uint8 {
              range 1..9 {
                description 'Range: 1-9.' ;
              }

            }

            default 5 ;
          }

          leaf clear-exponent {
            description 'Threshold exponent of clear alarm.' ;
            type uint8 {
              range 1..9 {
                description 'Range: 1-9.' ;
              }

            }

            default 6 ;
          }

          leaf period {
            description 'alarm period.' ;
            type uint16 {
              range 20..3000 {
                description 'Range: 20-3000.' ;
              }

            }

            units second ;
            default 20 ;
          }

        }

        list sd-insert-status {
          key if-name ;
          leaf if-name {
            description 'Interface name.' ;
            type ncd:ifname ;

          }

          leaf status {
            description 'Enable or disable sd insert.' ;
            type enumeration {
              enum disable {
                value 0 ;
                description 'Disable sd insert.' ;
              }

              enum enable {
                value 1 ;
                description 'Enable sd insert.' ;
              }

            }

            default disable ;
          }

          ncd:revise-date 2021-07-03 ;
        }

        list sd-insert-parameter {
          key if-name ;
          leaf if-name {
            description 'Interface name.' ;
            type ncd:ifname ;

          }

          leaf phb {
            description 'Port PHB parameter.' ;
            type enumeration {
              enum be {
                value 1 ;
              }

              enum af11 {
                value 2 ;
              }

              enum af12 {
                value 3 ;
              }

              enum af21 {
                value 4 ;
              }

              enum af22 {
                value 5 ;
              }

              enum af31 {
                value 6 ;
              }

              enum af32 {
                value 7 ;
              }

              enum af41 {
                value 8 ;
              }

              enum af42 {
                value 9 ;
              }

              enum cs6 {
                value 10 ;
              }

              enum cs7 {
                value 11 ;
              }

              enum ef {
                value 12 ;
              }

              enum invalid {
                value 0 ;
              }

            }

            default ef ;
          }

          ncd:revise-date 2021-07-03 ;
        }

      }

      container sdhs {
        list sdh {
          key if-name ;
          leaf if-name {
            description 'Interface name.' ;
            type string ;

          }

          container delay {
            leaf clear {
              description 'Configure time value for SDH alarm clear.' ;
              type uint32 {
                range "0|200..300000" ;

              }

              units ms ;
            }

            leaf trigger {
              description 'Configure time value for SDH alarm trigger.' ;
              type uint16 {
                range "0|20..10000" ;

              }

              units ms ;
            }

          }

          container threshold {
            leaf b1-tca {
              description 'Configure B1 BER threshold crossing alarm.' ;
              type uint8 {
                range 3..9 ;

              }

              default 6 ;
            }

            leaf b2-tca {
              description 'Configure B2 BER threshold crossing alarm.' ;
              type uint8 {
                range 3..9 ;

              }

              default 6 ;
            }

            leaf b3-tca {
              description 'Configure B3 BER threshold crossing alarm.' ;
              type uint8 {
                range 3..9 ;

              }

              default 6 ;
            }

          }

          container if-down {
            description 'Configure SDH alarms which will trigger port down.' ;
            leaf los {
              description 'Configure whether LOS alarm triggers interface physical down.' ;
              type uint8 {
                range 0..1 ;

              }

              default 1 ;
            }

            leaf lof {
              description 'Configure whether LOF alarm triggers interface physical down.' ;
              type uint8 {
                range 0..1 ;

              }

              default 1 ;
            }

            leaf b1-tca {
              description 'Configure whether B1-TCA alarm triggers interface physical down.' ;
              type uint8 {
                range 0..1 ;

              }

              default 0 ;
            }

            leaf b2-tca {
              description 'Configure whether B2-TCA alarm triggers interface physical down.' ;
              type uint8 {
                range 0..1 ;

              }

              default 0 ;
            }

            leaf b3-tca {
              description 'Configure whether B3-TCA alarm triggers interface physical down.' ;
              type uint8 {
                range 0..1 ;

              }

              default 0 ;
            }

            leaf lais {
              description 'Configure whether LAIS alarm triggers interface physical down.' ;
              type uint8 {
                range 0..1 ;

              }

              default 1 ;
            }

            leaf lrdi {
              description 'Configure whether LRDI alarm triggers interface physical down.' ;
              type uint8 {
                range 0..1 ;

              }

              default 0 ;
            }

            leaf sd-ber {
              description 'Configure whether SD-BER alarm triggers interface physical down.' ;
              type uint8 {
                range 0..1 ;

              }

              default 0 ;
            }

            leaf sf-ber {
              description 'Configure whether SF-BER alarm triggers interface physical down.' ;
              type uint8 {
                range 0..1 ;

              }

              default 0 ;
            }

            leaf pais {
              description 'Configure whether PAIS alarm triggers interface physical down.' ;
              type uint8 {
                range 0..1 ;

              }

              default 0 ;
            }

            leaf plop {
              description 'Configure whether PLOP alarm triggers interface physical down.' ;
              type uint8 {
                range 0..1 ;

              }

              default 0 ;
            }

            leaf prdi {
              description 'Configure whether PRDI alarm triggers interface physical down.' ;
              type uint8 {
                range 0..1 ;

              }

              default 0 ;
            }

            leaf pplm {
              description 'Configure whether PPLM alarm triggers interface physical down.' ;
              type uint8 {
                range 0..1 ;

              }

              default 0 ;
            }

            leaf puneq {
              description 'Configure whether PUNEQ alarm triggers interface physical down.' ;
              type uint8 {
                range 0..1 ;

              }

              default 0 ;
            }

          }

        }

        ncd:revise-date 2023-07-13 ;
      }

      container lan-wan-switch {
        leaf switch {
          type enumeration {
            enum off {
              value 0 ;
              description 'Name change after configuring port-mode LAN/WAN.' ;
            }

            enum on {
              value 1 ;
              description 'Name unchange after configuring port-mode LAN/WAN.' ;
            }

          }

          default off ;
        }

        ncd:revise-date 2023-07-22 ;
      }

      container mgmts {
        list mgmt {
          leaf if-name {
            type ncd:ifname ;

            description 'Interface name.' ;
          }

          leaf alarm-down {
            type enumeration {
              enum enable {
                value 1 ;
              }

              enum disable {
                value 2 ;
              }

            }

            description 'Configure whether an alarm occurs when the management port goes down.' ;
          }

          key if-name ;
        }

        ncd:revise-date 2024-10-16 ;
      }

    }

    container flexe-dcn-oh {
      leaf global-dcn-oh {
        description 'All port dcn overhead.' ;
        type enumeration {
          enum shim-to-shim {
            value 1 ;
            description 'Flexe dcn section overhead.' ;
          }

          enum section {
            value 0 ;
            description 'Flexe dcn shim-to-shim overhead.' ;
          }

        }

        default section ;
      }

      list port-dcn-oh {
        key if-name ;
        leaf if-name {
          description 'Interface name.' ;
          type ncd:ifname ;

        }

        leaf dcn-oh {
          description 'Port dcn overhead.' ;
          type enumeration {
            enum shim-to-shim {
              value 1 ;
              description 'Flexe dcn section overhead.' ;
            }

            enum section {
              value 0 ;
              description 'Flexe dcn shim-to-shim overhead.' ;
            }

          }

          default section ;
        }

      }

      ncd:revise-date 2021-04-19 ;
    }

  }

  container operation {
    config false ;
    container pm-if {
      container start-alss {
        list start-als {
          key if-name ;
          leaf if-name {
            description 'Interface name.' ;
            type string ;

          }

          leaf als {
            description 'Set recovery mode.' ;
            type enumeration {
              enum manual {
                value 0 ;
                description 'Manual impulse.' ;
              }

              enum testing {
                value 1 ;
                description 'Testing impulse.' ;
              }

            }

          }

        }

      }

      container expire-holdtimes {
        list expire-holdtime {
          key if-name ;
          leaf if-name {
            description 'Interface name.' ;
            type string ;

          }

        }

      }

      container clear-eee-statisticss {
        description 'Clear eee statistics.' ;
        list clear-eee-statistics-interface {
          description 'Clear eee statistics by ifname.' ;
          key if-name ;
          leaf if-name {
            description 'Interface name.' ;
            type string ;

          }

        }

        list clear-eee-statistics-pfu {
          description 'Clear eee statistics by pfu.' ;
          key 'shelf boardtype panel' ;
          leaf shelf {
            description 'Shelf number.' ;
            type uint8 {
              range 0..254 ;

            }

          }

          leaf boardtype {
            description 'Board type.' ;
            type enumeration {
              enum MPU {
                value 1 ;
              }

              enum PFU {
                value 3 ;
              }

              enum SFU {
                value 4 ;
              }

            }

          }

          leaf panel {
            description 'Panel number of line-card.' ;
            type string ;

          }

        }

        ncd:revise-date 2020-02-25 ;
      }

      container control-flap-clears {
        description 'Clear control flap of interface.' ;
        list control-flap-clear {
          description 'Clear control flap of interface.' ;
          key if-name ;
          leaf if-name {
            description 'Interface name.' ;
            type string ;

          }

        }

        ncd:revise-date 2020-02-25 ;
      }

    }

  }

  container state {
    config false ;
    container pm-if {
      container als-statuss {
        list als-status {
          key if-name ;
          leaf if-name {
            type string ;

          }

          leaf als-flag {
            type enumeration {
              enum on {
                value 0 ;
              }

              enum off {
                value 1 ;
              }

            }

          }

          leaf recovery-mode {
            type enumeration {
              enum automatic-recovery {
                value 0 ;
              }

              enum manual-recovery {
                value 1 ;
              }

              enum laser-on {
                value 2 ;
              }

              enum laser-off {
                value 3 ;
              }

            }

          }

          leaf current-status {
            description 'The current status of the laser' ;
            type enumeration {
              enum ALS {
                value 0 ;
              }

              enum normal {
                value 1 ;
              }

            }

          }

          leaf laser-status {
            type enumeration {
              enum unkonwn {
                value 0 ;
              }

              enum off {
                value 1 ;
              }

              enum on {
                value 2 ;
              }

            }

            ncd:revise-date 2017-10-16 ;
          }

          leaf off-reason {
            description 'The reason of the laser power off' ;
            type enumeration {
              enum power-on-laser {
                value 0 ;
              }

              enum power-off-laser {
                value 1 ;
              }

              enum power-off-als {
                value 2 ;
              }

              enum power-off-delayup {
                value 3 ;
              }

              enum power-off-shutdown {
                value 4 ;
              }

              enum power-off-cfgshutdown {
                value 6 ;
              }

              enum power-off-los {
                value 5 ;
              }

              enum power-off-loopback-interalex {
                value 8 ;
              }

              enum power-off-unknown {
                value 254 ;
              }

              enum power-off-lst {
                value 203 ;
              }

              enum power-off-hwerror {
                value 204 ;
              }

              enum power-off-los-ex {
                value 7 ;
                description 'The true reported value, converted to 5 to ensure compatibility.' ;
              }

            }

          }

        }

      }

      container damp-statuss {
        list damp-status {
          key if-name ;
          leaf if-name {
            type string ;

          }

          leaf flap-number {
            type uint32 ;

          }

          leaf damp-number {
            type uint32 ;

          }

          leaf penalty {
            type uint32 ;

          }

          leaf max-penalty {
            type uint32 ;

          }

          leaf suppress {
            type enumeration {
              enum FALSE {
                value 0 ;
              }

              enum TRUE {
                value 1 ;
              }

            }

          }

        }

      }

      container port-statuss {
        list port-status {
          key if-name ;
          leaf if-name {
            description 'Interface name.' ;
            type string ;

          }

          leaf portphystatus {
            description 'Port physical status.' ;
            type enumeration {
              enum up {
                value 0 ;
                description 'up.' ;
              }

              enum down {
                value 1 ;
                description 'down.' ;
              }

              enum offline {
                value 32 ;
                description 'offline.' ;
              }

            }

          }

          leaf af-node {
            description 'Port af-node name.' ;
            type ncd:af-name {
              length 0..32 ;

            }

            ncd:revise-date 2022-06-01 ;
          }

          leaf shelf {
            description 'Port shelf no.' ;
            type uint8 {
              range 0..255 ;

            }

            ncd:revise-date 2022-06-01 ;
          }

        }

        ncd:revise-date 2018-08-16 ;
      }

      container eth-statuss {
        list eth-status {
          key if-name ;
          leaf if-name {
            description 'Interface name.' ;
            type string ;

          }

          leaf ifhaslos {
            type enumeration {
              enum no {
                value 0 ;
                description 'no.' ;
              }

              enum yes {
                value 1 ;
                description 'yes.' ;
              }

            }

          }

          leaf loopback {
            description 'Query the loopback mode of a port.' ;
            type enumeration {
              enum cancel {
                value 0 ;
                description 'Cancel loopback mode.' ;
              }

              enum outer {
                value 1 ;
                description 'Line loopback mode.' ;
              }

              enum inner {
                value 2 ;
                description 'Inner loopback mode.' ;
              }

              enum external {
                value 3 ;
                description 'External loopback mode.' ;
              }

              enum line-extend {
                value 4 ;
                description 'Line loopback mode extension.' ;
              }

              enum internal-extend {
                value 5 ;
                description 'Internal loopback mode extension.' ;
              }

            }

          }

          ncd:revise-date 2019-05-10 ;
        }

      }

      container eee-statisticss {
        description 'Show eee statistics.' ;
        list eee-statistics-interface {
          description 'Show eee statistics of interface.' ;
          key if-name ;
          leaf if-name {
            description 'Interface name.' ;
            type string ;

          }

          leaf txevents {
            type uint32 ;

          }

          leaf txduration {
            type uint32 ;

          }

          leaf rxevents {
            type uint32 ;

          }

          leaf rxduration {
            type uint32 ;

          }

        }

        list eee-statistics-pfu {
          description 'Show eee statistics of board.' ;
          key 'shelf boardtype panel' ;
          leaf shelf {
            description 'Shelf number.' ;
            type uint8 ;

          }

          leaf boardtype {
            description 'Board type.' ;
            type enumeration {
              enum MPU {
                value 1 ;
              }

              enum PFU {
                value 3 ;
              }

              enum SFU {
                value 4 ;
              }

              enum UNKNOWN {
                value 255 ;
              }

            }

          }

          leaf panel {
            description 'Panel number.' ;
            type string ;

          }

          leaf if-name {
            description 'Interface name.' ;
            type string ;

          }

          leaf txevents {
            type uint32 ;

          }

          leaf txduration {
            type uint32 ;

          }

          leaf rxevents {
            type uint32 ;

          }

          leaf rxduration {
            type uint32 ;

          }

        }

        ncd:revise-date 2020-02-25 ;
      }

      container mtn-statuss {
        list mtn-status {
          key if-name ;
          leaf if-name {
            description 'Interface name.' ;
            type string ;

          }

          leaf portphystatus {
            description 'Port physical status.' ;
            type enumeration {
              enum up {
                value 0 ;
                description 'up.' ;
              }

              enum down {
                value 1 ;
                description 'down.' ;
              }

              enum offline {
                value 32 ;
                description 'offline.' ;
              }

            }

          }

          leaf group-id {
            type uint32 ;

          }

          leaf fec-mode {
            description 'fec of a port.' ;
            type enumeration {
              enum enable {
                value 1 ;
                description 'enable.' ;
              }

              enum disable {
                value 2 ;
                description 'disable.' ;
              }

              enum auto {
                value 3 ;
                description 'auto.' ;
              }

              enum invalid {
                value 0 ;
                description 'invalid' ;
              }

            }

          }

        }

        ncd:revise-date 2020-09-21 ;
      }



      container port-speed-infos {
        list port-speed-info {
          leaf if-name {
            type ncd:ifname {
              length 1..31 {
                description Ifname ;
              }
            }

            description 'Interface name.' ;
          }

          leaf current-speed {
            description 'Port current speed.' ;
            type uint32 ;

            units Mbs ;
          }

          leaf adjustable-speed {
            type string ;

            description 'Interface adjustable speed.' ;
          }

          key if-name ;
        }

        ncd:revise-date 2024-02-06 ;
      }
    }

  }


  rpc fec-bypass {
    description 'RPC Operation' ;
    input {
      leaf if-name {
        config false ;
        description 'Interface name.' ;
        type string ;

        mandatory true ;
      }

      leaf bypass-status {
        config false ;
        description 'Set fec bypass.' ;
        type enumeration {
          enum enable {
            value 1 ;
            description 'enable.' ;
          }

          enum disable {
            value 2 ;
            description 'disable.' ;
          }

        }

        mandatory true ;
      }

    }

  }

  notification event {
    container loopback-auto-cancel {
      config false ;
      description 'Loopback auto cancel event.' ;
      leaf ifname {
        description 'Interface name.' ;
        type string ;

      }

    }

  }

}
