module zxr10-vxlan {
  namespace "http://www.zte.com.cn/zxr10/netconf/schema/rosng/vxlan" ;
  prefix vxlan ;
  import zxr10-netconf-defs {
    prefix ncd ;
  }

  organization "ZTE Corporation" ;
  contact "ZTE Corporation
  Nanjing Institute of ZTE Corporation
  No.68 Zijinghua Rd. Yuhuatai District, Nanjing, China
  Tel: +86-25-52870000" ;
  description 'The netconf module to describe VXLAN.' ;
  revision 2025-07-03 {
    description '1.The node range is changed from 0-128 to 1-128,/vxlan:configuration/vxlan:vxlan/vxlan:micro-segment/vxlan:segment-id/vxlan:segment-id/vxlan:ipv6-configuration/vxlan:mask-len
2.The node range is changed from 0-128 to 1-128,/vxlan:configuration/vxlan:vxlan/vxlan:micro-segment/vxlan:segment-id/vxlan:segment-id/vxlan:ipv6-configuration-with-vrf/vxlan:mask-len' ;
  }

  revision 2024-09-02 {
    description '1.Obsolete a container /vxlan:configuration/vxlan:vxlan/vxlan:mac-floodings.
2.Obsolete a container /vxlan:configuration/vxlan:vxlan/vxlan:vxlan-instances.
3.Obsolete a container /vxlan:configuration/vxlan:vxlan/vxlan:vtep-instances.
4.Obsolete a container /vxlan:configuration/vxlan:vxlan/vxlan:vtep-binds.
5.Obsolete a container /vxlan:configuration/vxlan:vxlan/vxlan:static-tunnel-binds.
6.Obsolete a container /vxlan:configuration/vxlan:vxlan/vxlan:redundancy-group-binds.' ;
  }

  revision 2024-08-27 {
    description '1.The node not support IPv6 link local,/vxlan:configuration/vxlan:vxlan/vxlan:nve-instances/vxlan:nve-instance-v6/vxlan:source-vtep-ipv6.' ;
  }

  revision 2024-04-07 {
    description '1.Add a new container rule-extend on /vxlan:configuration/vxlan:vxlan/vxlan:micro-segment/vxlan:classifier/vxlan:classifier-name;' ;
  }

  revision 2023-12-14 {
    description '1.Add a new list nve-mac on zxr10-vxlan\configuration\vxlan\nve-instances;' ;
  }

  revision 2023-11-29 {
    description '1.Change the node length to 128, /vxlan:configuration/vxlan:vxlan/vxlan:micro-segment/vxlan:segment-id/vxlan:segment-id/vxlan:segment-name.
2.Change the node length to 128, /vxlan:configuration/vxlan:vxlan/vxlan:micro-segment/vxlan:classifier/vxlan:classifier-name/vxlan:name.
3.Change the node length to 128, /vxlan:configuration/vxlan:vxlan/vxlan:micro-segment/vxlan:policy/vxlan:policy-name/vxlan:name.' ;
  }

  revision 2023-06-19 {
    description '1.Add a new list icmpv6-rule-with-type on zxr10-vxlan\configuration\vxlan\micro-segment\classifier\classifier-name;' ;
  }

  revision 2023-04-24 {
    description '1.Add a new container vni-v6-multicasts on zxr10-vxlan\configuration\vxlan\vni-instances\vni-instance;
2.Add a new list nve-instances-v6 on zxr10-vxlan\configuration\vxlan\nve-instances;' ;
  }

  revision 2023-03-10 {
    description '1.Change the length of node /vxlan:configuration/vxlan:vxlan/vxlan:micro-segment/vxlan:segment-id/vxlan:segment-id/vxlan:segment-name.
2.Change the length of node /vxlan:configuration/vxlan:vxlan/vxlan:micro-segment/vxlan:classifier/vxlan:classifier-name/vxlan:name.
3.Change the length of node /vxlan:configuration/vxlan:vxlan/vxlan:micro-segment/vxlan:policy/vxlan:policy-name/vxlan:name.' ;
  }

  revision 2022-10-10 {
    description '1.Add a new containor micro-segment on zxr10-vxlan\configuration\vxlan;' ;
  }

  revision 2020-04-09 {
    description '1.Add a new select evpn-tunnel-id on zxr10-vxlan\state\vxlan\vxlan-tunnels;' ;
  }

  revision 2019-11-19 {
    description '1.Add a new container vni-instances on zxr10-vxlan\configuration\vxlan;
2.Add a new container nve-instances on zxr10-vxlan\configuration\vxlan;' ;
  }

  revision 2018-11-29 {
    description '1.Add a new list tunnel-ipv6-statistics-config on zxr10-vxlan\configuration\vxlan\tunnel-statistics-configs;
2.Add a new list tunnel-ipv6-vni-statistics-config on zxr10-vxlan\configuration\vxlan\tunnel-statistics-configs;
3.Add a new container statistics on zxr10-vxlan\state\vxlan\vxlan-tunnels\vxlan-tunnel-ipv6;
4.Add a new list vxlan-tunnel-ipv6-statistics on zxr10-vxlan\operation\vxlan\clear-vxlan-tunnel-statistics.' ;
  }

  revision 2018-11-05 {
    description '1.Add a new list vni-statistics-config on zxr10-vxlan\configuration\vxlan\tunnel-statistics-configs;
2.Add a new container vxlan-statistics on zxr10-vxlan\state\vxlan;
3.Add a new list vxlan-statistics on zxr10-vxlan\operation\vxlan\clear-vxlan-tunnel-statistics.' ;
  }

  revision 2018-02-06 {
    description '1.Add a new list node of vxlan-tunnel-ipv6 on zxr10-vxlan\state\vxlan\vxlan-tunnels.' ;
  }

  revision 2017-11-15 {
    description '1.Delete SWITCH & C600 labels in feature mac-flooding;
2.Delete SWITCH & C600 labels in feature vxlan-instance-mode;
3.Delete SWITCH & C600 labels in feature static-tunnel;
4.Delete SWITCH & C600 labels in feature redundancy-group-bind;
5.Delete SWITCH & C600 labels in feature vtep-bind;
6.Delete SWITCH & C600 labels in feature move-dampening.' ;
  }

  revision 2017-09-20 {
    description '1.Add a new container node of move-dampening-policy on zxr10-vxlan\configuration\vxlan\vxlan-instances\vxlan-instance;
2.The feature of move-dampening is defined.' ;
  }

  revision 2017-09-15 {
    description '1.The feature of vtep-bind is defined.
2.The feature of vtep-instance-mode is validated to 15K and T8K. 
3.All features in the yang of revison 2017-9-15 are validated to 89 and 89-GM.' ;
  }

  revision 2017-05-04 {
    description '1.Add a new container node of mac-policy on zxr10-vxlan\configuration\vxlan\vxlan-instances\vxlan-instance;
2.Add a leaf node of evpn-remote-mac-learning on zxr10-vxlan\configuration\vxlan\vxlan-instances\vxlan-instance\mac-policy;
3.Add a leaf node of local-mac-learning on zxr10-vxlan\configuration\vxlan\vxlan-instances\vxlan-instance\mac-policy;
4.Add a leaf node of evpn-remote-mac-receiving on zxr10-vxlan\configuration\vxlan\vxlan-instances\vxlan-instance\mac-policy;
5.Add a leaf node of evpn-local-mac-advertising on zxr10-vxlan\configuration\vxlan\vxlan-instances\vxlan-instance\mac-policy;' ;
  }

  revision 2017-03-30 {
    description '1.Add a new choice of ingress-adjust on zxr10-vxlan\configuration\vxlan\vxlan-instances\vxlan-instance\vxlan-map-tables\vxlan-map-l2interface;
2.delete a leaf node of ingress-adjust-tag-as-payload on zxr10-vxlan\configuration\vxlan\vxlan-instances\vxlan-instance\vxlan-map-tables\vxlan-map-l2interface;' ;
  }

  revision 2017-01-16 {
    description '1.Add a leaf node /vxlan:configuration/vxlan:vxlan/vxlan:vxlan-instances/vxlan:vxlan-instance/vxlan:vxlan-route-targets/vxlan:vxlan-route-target/vxlan:split-horizon-group.' ;
  }

  revision 2017-01-10 {
    description '1.Add four new leaves on vxlan:state/vxlan:vxlan/vxlan:vxlan-tunnels/vxlan:vxlan-tunnel/vxlan:statistics/vxlan:tunnel-statistics/
2.Add four new leaves on vxlan:state/vxlan:vxlan/vxlan:vxlan-tunnels/vxlan:vxlan-tunnel/vxlan:statistics/vxlan:tunnel-vni-statistics/vxlan:tunnel-vni-statistic/' ;
  }

  revision 2016-08-18 {
    description '1.Delete the container node of map-l2interace on zxr10-vxlan\configuration\vxlan\vxlan-instances\vxlan-instance\vxlan-map-tables\vxlan-map-l2interface;
2.Add a new list node of map-l2interace on zxr10-vxlan\configuration\vxlan\vxlan-instances\vxlan-instance\vxlan-map-tables\vxlan-map-l2interface;' ;
  }

  revision 2016-07-05 {
    description "(1)Add feature node mac-flooding, VXLAN-instance-mode, vtep-instance-mode, static-tunnel, redundancy-group-bind.
    (2)Add feature attribute mac-flooding on container 'configuration/vxlan/mac-floodings'.
    (3)Add feature attribute VXLAN-instance-mode on container 'configuration/vxlan/vxlan-instances'.
    (4)Add feature attribute vtep-instance-mode on container 'configuration/vxlan/vtep-instances' and 'configuration/vxlan/vtep-binds'.
    (5)Add feature attribute static-tunnel on container 'configuration/vxlan/static-tunnel-binds'.
    (6)Add feature attribute redundancy-group-bind on container 'configuration/vxlan/redundancy-group-binds'." ;
  }

  revision 2016-04-26 {
    description '1.Add range of /vxlan:state/vxlan:vxlan/vxlan:vxlan-tunnels/vxlan:vxlan-tunnel/vxlan:statistics/vxlan:tunnel-vni-statistics/vxlan:tunnel-vni-statistic/vxlan:vxlan-id.
2.Change range of /vxlan:state/vxlan:vxlan/vxlan:vxlan-tunnels/vxlan:vxlan-tunnel/vxlan:statistics/vxlan:tunnel-statistics/vxlan:in-bytes,/vxlan:state/vxlan:vxlan/vxlan:vxlan-tunnels/vxlan:vxlan-tunnel/vxlan:statistics/vxlan:tunnel-statistics/vxlan:out-bytes,/vxlan:state/vxlan:vxlan/vxlan:vxlan-tunnels/vxlan:vxlan-tunnel/vxlan:statistics/vxlan:tunnel-statistics/vxlan:in-packets and /vxlan:state/vxlan:vxlan/vxlan:vxlan-tunnels/vxlan:vxlan-tunnel/vxlan:statistics/vxlan:tunnel-statistics/vxlan:out-packets.' ;
  }

  revision 2016-04-20 {
    description '1.Add a new container on zxr10-vxlan\configuration\vxlan\static-tunnel-binds;
2.Add a new container on zxr10-vxlan\configuration\vxlan\tunnel-statistics-configs;
3.Add a new container on zxr10-vxlan\configuration\vxlan\redundancy-group-binds;
4.Add a new leaf on zxr10-vxlan\state\vxlan\vxlan-tunnels\vxlan-tunnel\static-tunnel-id;
5.Add a new container on zxr10-vxlan\state\vxlan\vxlan-tunnels\vxlan-tunnel\statistics;
6.Add a new container on zxr10-vxlan\operation.' ;
  }

  revision 2016-04-05 {
    description '1.Delete the node /vxlan:state/vxlan:vxlan/vxlan:vxlan-tunnels/vxlan:vxlan-tunnel/vxlan:tunnel-type.
2.Change the name of node /vxlan:state/vxlan:vxlan/vxlan:vxlan-tunnels/vxlan:vxlan-tunnel/vxlan:destination-ip to /vxlan:state/vxlan:vxlan/vxlan:vxlan-tunnels/vxlan:vxlan-tunnel/vxlan:remote-ipv4.
3.Change the name of node /vxlan:state/vxlan:vxlan/vxlan:vxlan-tunnels/vxlan:vxlan-tunnel/vxlan:source-ip to /vxlan:state/vxlan:vxlan/vxlan:vxlan-tunnels/vxlan:vxlan-tunnel/vxlan:local-ipv4.
4.Change the name of node /vxlan:state/vxlan:vxlan/vxlan:vxlan-tunnels/vxlan:vxlan-tunnel/vxlan:tunnel-id to /vxlan:state/vxlan:vxlan/vxlan:vxlan-tunnels/vxlan:vxlan-tunnel/vxlan:evpn-tunnel-id.' ;
  }

  revision 2016-03-16 {
    description '1.Change the name of node /vxlan:configuration/vxlan:vxlan/vxlan:vxlan-instances/vxlan:vxlan-instance/vxlan:vxlan-route-targets/vxlan:vxlan-route-target/vxlan:rd to rt-value,change the description of this node.' ;
  }

  revision 2016-01-08 {
    description '1.Add container /vxlan:configuration/vxlan:vxlan/vxlan:mac-floodings.
2.Add leaf /vxlan:configuration/vxlan:vxlan/vxlan:vxlan-instances/vxlan:vxlan-instance/vxlan:description.
3.Add leaf /vxlan:configuration/vxlan:vxlan/vxlan:vxlan-instances/vxlan:vxlan-instance/vxlan:unknow-unicast-drop.
4.Add leaf /vxlan:configuration/vxlan:vxlan/vxlan:vxlan-instances/vxlan:vxlan-instance/vxlan:filter-vrrp.
5.Add container /vxlan:configuration/vxlan:vxlan/vxlan:vxlan-instances/vxlan:vxlan-instance/vxlan:vxlan-rd.
6.Add container /vxlan:configuration/vxlan:vxlan/vxlan:vxlan-instances/vxlan:vxlan-instance/vxlan:vxlan-route-targets.
7.Add container /vxlan:state.
8.Obsolete container /vxlan:configuration/vxlan:vxlan/vxlan:vxlan-instances/vxlan:vxlan-instance/vxlan:vxlan-multicast-ip.
9.Obsolete container /vxlan:configuration/vxlan:vxlan/vxlan:vxlan-instances/vxlan:vxlan-instance/vxlan:vxlan-multicast-ipv6.' ;
  }

  revision 2015-11-25 {
    description 'Add container /vxlan:configuration/vxlan:vxlan/vxlan:vxlan-instances/vxlan:vxlan-instance/vxlan:vxlan-multicast-ipv6.' ;
  }

  revision 2014-09-16 {
    description 'Initial version.' ;
  }

  feature mac-flooding {
    description 'This node is used to distinguish whether the MAC flooding function can be enabled.' ;
  }

  feature vxlan-instance-mode {
    description 'This node is used to distinguish whether the VXLAN instance mode can be enabled.' ;
  }

  feature vtep-instance-mode {
    description 'This node is used to distinguish whether the vtep instance mode can be enabled.' ;
  }

  feature static-tunnel {
    description 'This node is used to distinguish whether static tunnel function can be enabled.' ;
  }

  feature redundancy-group-bind {
    description 'This node is used to distinguish whether redundancy group bind table function can be enabled.' ;
  }

  feature vtep-bind {
    description 'This node is used to distinguish whether the vtep bind can be enabled.' ;
  }

  feature move-dampening {
    description 'This node is used to distinguish whether the move dampening policy can be enabled.' ;
  }

  feature vxlan-micro-segment {
    description 'This node is used to distinguish whether the micro-segment function can be enabled.' ;
    ncd:revise-date 2022-10-10 ;
  }

  feature micro-segment-rule-extend {
    description 'This node is used to distinguish whether the micro-segment rule-extend function can be enabled.' ;
    ncd:revise-date 2024-04-07 ;
  }

  container configuration {
    description 'Configuration model info.' ;
    container vxlan {
      description 'Configure VXLAN parameters.' ;
      container global-config {
        description 'Global enable configuration of VXLAN.' ;
        presence global-config ;
        leaf global-enable {
          description 'VXLAN global enble.' ;
          type empty ;

          mandatory true ;
        }

      }

      container mac-floodings {
        if-feature mac-flooding ;

        description 'Configuration of MAC flooding.' ;
        status obsolete {
          ncd:revise-date 2024-09-02 ;
        }

        list mac-flooding {
          description 'Configuration of MAC flooding.' ;
          key 'mac-address vlan-id' ;
          leaf mac-address {
            description 'Specific MAC address of MAC flooding.' ;
            type ncd:mac-address ;

            status obsolete ;

          }

          leaf vlan-id {
            description 'VLAN ID of MAC flooding.' ;
            type uint16 {
              range 1..4094 {
                description 'The value of VLAN,it must be between 1 to 4094.' ;
              }

            }

            status obsolete ;

          }

          status obsolete ;

        }

        ncd:revise-date 2016-01-08 ;
      }

      container vxlan-instances {
        if-feature vxlan-instance-mode ;

        description 'Configuration of VXLAN instances.' ;
        status obsolete {
          ncd:revise-date 2024-09-02 ;
        }

        list vxlan-instance {
          description 'Configuration of VXLAN instance.' ;
          key vxlan-id ;
          leaf vxlan-id {
            description 'VXLAN ID of VXLAN instance.' ;
            type uint32 {
              range 1..16777215 {
                description 'The value of VXLAN,it must be between 1 to 16777215.' ;
              }

            }

            status obsolete ;

          }

          leaf description {
            description 'The description information of VXLAN instance.' ;
            type string {
              length 0..64 {
                description 'VXLAN instance description information.' ;
              }

            }

            default '' ;
            status obsolete ;

            ncd:revise-date 2016-01-08 ;
          }

          leaf unknow-unicast-drop {
            description 'Unknow unicast drop configuration of VXLAN instance.' ;
            type enumeration {
              enum enable {
                value 1 ;
                description 'Unknown unicast drop enable.' ;
              }

              enum disable {
                value 2 ;
                description 'Unknown unicast drop disable.' ;
              }

            }

            default enable ;
            status obsolete ;

            ncd:revise-date 2016-01-08 ;
          }

          leaf filter-vrrp {
            description 'VRRP packets filter configuration of VXLAN instance.' ;
            type enumeration {
              enum enable {
                value 1 ;
                description 'VRRP packets filter.' ;
              }

              enum disable {
                value 2 ;
                description 'VRRP packets not filter.' ;
              }

            }

            default enable ;
            status obsolete ;

            ncd:revise-date 2016-01-08 ;
          }

          container vxlan-multicast-ip {
            description 'VXLAN multicast IP address.' ;
            status obsolete {
              ncd:revise-date 2016-01-08 ;
            }

            presence vxlan-multicast-ip ;
            leaf multicast-ip {
              description 'VXLAN multicast IP address.' ;
              status obsolete {
                ncd:revise-date 2016-01-08 ;
              }

              type ncd:ipv4-address ;

              mandatory true ;
            }

          }

          container vxlan-multicast-ipv6 {
            description 'VXLAN multicast IPv6 address.' ;
            status obsolete {
              ncd:revise-date 2016-01-08 ;
            }

            presence vxlan-multicast-ipv6 ;
            leaf multicast-ipv6 {
              description 'VXLAN multicast IPv6 address.' ;
              status obsolete {
                ncd:revise-date 2016-01-08 ;
              }

              type ncd:ipv6-address ;

              mandatory true ;
            }

            ncd:revise-date 2015-11-25 ;
          }

          container vxlan-map-tables {
            description 'VXLAN map tables.' ;
            presence vxlan-map-tables ;
            choice vxlan-map-types {
              description 'VXLAN map type choice.' ;
              case vxlan-map-vlan {
                description 'VXLAN map VLAN.' ;
                leaf map-type-vlan {
                  description 'VXLAN map VLAN.' ;
                  type enumeration {
                    enum map-type-vlan1to1 {
                      value 1 ;
                      description 'Map type VLAN1:1.' ;
                    }

                    enum map-type-vlan1ton {
                      value 2 ;
                      description 'Map type VLAN1:n.' ;
                    }

                  }

                  default map-type-vlan1to1 ;
                }

                list map-vlan {
                  description 'VXLAN map VLAN.' ;
                  key vlan-id ;
                  leaf vlan-id {
                    description 'VLAN ID.' ;
                    type uint16 {
                      range 1..4094 {
                        description 'The value of VLAN,it must be between 1 to 4094.' ;
                      }

                    }

                  }

                }

              }

              case vxlan-map-mac {
                description 'VXLAN map MAC.' ;
                leaf map-type-mac {
                  description 'VXLAN map MAC.' ;
                  type empty ;

                }

                container map-mac {
                  description 'VXLAN map MAC.' ;
                  presence map-mac ;
                  leaf mac {
                    description 'MAC address.' ;
                    type ncd:mac-address ;

                    mandatory true ;
                  }

                }

              }

              case vxlan-map-l2interface {
                description 'VXLAN map L2 interface.' ;
                leaf map-type-l2interface {
                  description 'VXLAN map L2 interface.' ;
                  type empty ;

                }

                list map-l2interface {
                  description 'VXLAN map L2 interface.' ;
                  key interface-name ;
                  leaf interface-name {
                    description 'L2 interface name.' ;
                    type ncd:ifname ;

                  }

                  leaf ingress-adjust-tag-as-payload {
                    description 'The ingress tag as payload flag of the ethernet parameter.' ;
                    status obsolete {
                      ncd:revise-date 2017-03-30 ;
                    }

                    type enumeration {
                      enum default {
                        value 0 ;
                        description 'Sub-interface means pTag. The others means uTag.' ;
                      }

                      enum all {
                        value 1 ;
                        description 'The ingress tag as payload flag is from outer most.' ;
                      }

                      enum from-sublayer {
                        value 2 ;
                        description 'The ingress tag as payload flag is from sub layer.' ;
                      }

                    }

                    default default ;
                  }

                  choice ingress-adjust {
                    description 'Configure ingress-adjustment operation' ;
                    case tag-as-payload {
                      description 'The ingress tag as payload flag of the ethernet parameter.' ;
                      leaf tag-as-payload {
                        description 'The ingress tag as payload flag of the ethernet parameter.' ;
                        type enumeration {
                          enum default {
                            value 0 ;
                            description 'Sub-interface means pTag. The others means uTag.' ;
                          }

                          enum all {
                            value 1 ;
                            description 'The ingress tag as payload flag is from outer most.' ;
                          }

                          enum from-sublayer {
                            value 2 ;
                            description 'The ingress tag as payload flag is from sub layer.' ;
                          }

                        }

                        default default ;
                      }

                    }

                    ncd:revise-date 2017-03-30 ;
                  }

                  ncd:revise-date 2016-08-18 ;
                }

              }

              case vxlan-map-l3interface {
                description 'VXLAN map L3 interface.' ;
                leaf map-type-l3interface {
                  description 'VXLAN map L3 interface.' ;
                  type empty ;

                }

                list map-l3interface {
                  description 'VXLAN map L3 interface.' ;
                  key interface-name ;
                  leaf interface-name {
                    description 'L3 interface name.' ;
                    type ncd:ifname {
                      length 1..31 {
                        description 'The length of interface name must be between 1 to 31.' ;
                      }

                    }

                  }

                }

              }

            }

            status obsolete ;

          }

          container vxlan-rd {
            description 'Information of route distinguisher.' ;
            presence vxlan-rd ;
            leaf rd {
              description 'The route distinguisher parameter.' ;
              type union {
                type ncd:asn-nn ;

                type ncd:ipadd-nn ;

              }

              mandatory true ;
              status obsolete ;

            }

            status obsolete ;

            ncd:revise-date 2016-01-08 ;
          }

          container vxlan-route-targets {
            description 'The configuration of route target.' ;
            presence vxlan-route-targets ;
            list vxlan-route-target {
              description 'The configuration of route target.' ;
              key 'effect-type rt-value' ;
              leaf effect-type {
                description 'The effect type of route target.' ;
                type enumeration {
                  enum export {
                    value 2 ;
                    description 'The route target effect type is export.' ;
                  }

                  enum import {
                    value 3 ;
                    description 'The route target effect type is import.' ;
                  }

                }

                status obsolete ;

              }

              leaf rt-value {
                description 'The value of RT attribution.' ;
                type union {
                  type ncd:asn-nn ;

                  type ncd:ipadd-nn ;

                }

                status obsolete ;

                ncd:revise-date 2016-03-16 ;
              }

              leaf split-horizon-group {
                description 'Split-horizon group,the range is A-Z.' ;
                type string ;

                status obsolete ;

                ncd:revise-date 2017-01-16 ;
              }

              status obsolete ;

            }

            status obsolete ;

            ncd:revise-date 2016-01-08 ;
          }

          container mac-policy {
            description 'Information of MAC learning policy.' ;
            presence mac-policy ;
            leaf evpn-remote-mac-learning {
              description 'Remote MAC of EVPN tunnel learning enable.' ;
              type enumeration {
                enum enable {
                  value 1 ;
                  description 'Enable' ;
                }

                enum disable {
                  value 2 ;
                  description 'Disable' ;
                }

              }

              default enable ;
              status obsolete ;

            }

            leaf evpn-remote-mac-receiving {
              description 'Remote EVPN tunnel advertise MAC receiving enable.' ;
              type enumeration {
                enum enable {
                  value 1 ;
                  description 'Enable' ;
                }

                enum disable {
                  value 2 ;
                  description 'Disable' ;
                }

              }

              default enable ;
              status obsolete ;

            }

            leaf evpn-local-mac-advertising {
              description 'EVPN local MAC advertising enable.' ;
              type enumeration {
                enum enable {
                  value 1 ;
                }

                enum disable {
                  value 2 ;
                }

              }

              default enable ;
              status obsolete ;

            }

            leaf local-mac-learning {
              description 'Local MAC learning enable of VXLAN instance.' ;
              type enumeration {
                enum enable {
                  value 1 ;
                  description 'Enable' ;
                }

                enum disable {
                  value 2 ;
                  description 'Disable' ;
                }

              }

              default enable ;
              status obsolete ;

            }

            status obsolete ;

            ncd:revise-date 2017-05-04 ;
          }

          container move-dampening-policy {
            description 'The detector of MAC/IP routing drift.' ;
            leaf move-dampening {
              description 'The detector switch of MAC/IP routing drift.' ;
              type enumeration {
                enum enable {
                  value 1 ;
                  description 'The detector switch of MAC/IP routing drift is enable.' ;
                }

                enum disable {
                  value 2 ;
                  description 'The detector switch of MAC/IP routing drift is disable.' ;
                }

              }

              default enable ;
              status obsolete ;

            }

            leaf move-dampening-interval {
              description 'The detector interval of MAC/IP routing drift,unit second.' ;
              type uint16 {
                range 60..900 {
                  description 'The interval range is from 60 to 900.' ;
                }

              }

              default 180 ;
              status obsolete ;

            }

            leaf move-dampening-count {
              description 'The detector count of MAC/IP routing drift.' ;
              type uint16 {
                range 1..30 {
                  description 'The count range is from 1 to 30.' ;
                }

              }

              default 5 ;
              status obsolete ;

            }

            leaf move-dampening-timeout {
              description 'The timeout of MAC/IP routing drift,unit second.' ;
              type uint16 {
                range 30..1200 {
                  description 'The timeout range is from 30 to 1200.' ;
                }

              }

              default 180 ;
              status obsolete ;

            }

            status obsolete ;

            ncd:revise-date 2017-09-20 ;
          }

          status obsolete ;

        }

      }

      container vtep-instances {
        if-feature vtep-instance-mode ;

        description 'Configuration of VTEP instances.' ;
        status obsolete {
          ncd:revise-date 2024-09-02 ;
        }

        container vtep-source-interfaces {
          description 'Configuration of VTEP source interfaces.' ;
          list vtep-source-interface {
            description 'Configuration of VTEP source interface.' ;
            key vtep-name ;
            leaf vtep-name {
              description 'VTEP interface name.' ;
              type ncd:ifname {
                length 1..31 {
                  description 'The length of interface name must be between 1 to 31.' ;
                }

              }

              status obsolete ;

            }

            leaf source-interface {
              description 'Source interface name of VTEP instance.' ;
              type ncd:ifname {
                length 1..31 {
                  description 'The length of interface name must be between 1 to 31.' ;
                }

              }

              mandatory true ;
              status obsolete ;

            }

            status obsolete ;

          }

          status obsolete ;

        }

        container vtep-modes {
          description 'Configuration of VTEP modes.' ;
          list vtep-mode {
            description 'Configuration of VTEP mode.' ;
            key vtep-name ;
            leaf vtep-name {
              description 'VTEP interface name.' ;
              type ncd:ifname {
                length 1..31 {
                  description 'The length of interface name must be between 1 to 31.' ;
                }

              }

              status obsolete ;

            }

            leaf vtep-mode {
              description 'VTEP mode.' ;
              type enumeration {
                enum discard-inner-vlan {
                  value 1 ;
                  description 'Discard inner-VLAN.' ;
                }

                enum no-discard-inner-vlan {
                  value 2 ;
                  description 'No discard inner-VLAN.' ;
                }

              }

              default discard-inner-vlan ;
              status obsolete ;

            }

            status obsolete ;

          }

          status obsolete ;

        }

        container vtep-multicast-ips {
          description 'The multicast IP address of VTEP instance.' ;
          list vtep-multicast-ip {
            description 'The multicast IP address of VTEP instance.' ;
            key vtep-name ;
            leaf vtep-name {
              description 'VTEP interface name.' ;
              type ncd:ifname ;

              status obsolete ;

            }

            leaf multicast-ip {
              description 'Multicast IP address of VTEP instance.' ;
              type ncd:ipv4-address ;

              mandatory true ;
              status obsolete ;

            }

            status obsolete ;

          }

          status obsolete ;

          ncd:revise-date 2016-01-08 ;
        }

        container vtep-multicast-ipv6s {
          description 'The multicast IPv6 address of VTEP instance.' ;
          list vtep-multicast-ipv6 {
            description 'The multicast IPv6 address of VTEP instance.' ;
            key vtep-name ;
            leaf vtep-name {
              description 'VTEP interface name.' ;
              type ncd:ifname ;

              status obsolete ;

            }

            leaf multicast-ipv6 {
              description 'Multicast IPv6 address of VTEP instance.' ;
              type ncd:ipv6-address ;

              mandatory true ;
              status obsolete ;

            }

            status obsolete ;

          }

          status obsolete ;

          ncd:revise-date 2016-01-08 ;
        }

      }

      container vtep-binds {
        if-feature vtep-bind ;

        description 'VTEP bind table.' ;
        status obsolete {
          ncd:revise-date 2024-09-02 ;
        }

        list vtep-bind {
          description 'VTEP bind table.' ;
          key 'vtep-name vxlan-id' ;
          leaf vtep-name {
            description 'VTEP interface name.' ;
            type ncd:ifname {
              length 1..31 {
                description 'The length of interface name must be between 1 to 31.' ;
              }

            }

            status obsolete ;

          }

          leaf vxlan-id {
            description 'VXLAN ID binding by VTEP interface.' ;
            type uint32 {
              range 1..16777215 {
                description 'The value of VXLAN,it must be between 1 to 16777215.' ;
              }

            }

            status obsolete ;

          }

          status obsolete ;

        }

      }

      container static-tunnel-binds {
        if-feature static-tunnel ;

        description 'Static tunnel bind table.' ;
        status obsolete {
          ncd:revise-date 2024-09-02 ;
        }

        list static-tunnel-bind {
          description 'Static tunnel bind table.' ;
          key 'vxlan-id static-tunnel-name' ;
          leaf static-tunnel-name {
            description 'Static tunnel interface name.' ;
            type ncd:ifname {
              length 1..31 {
                description 'The length of interface name must be between 1 to 31.' ;
              }

            }

            status obsolete ;

          }

          leaf vxlan-id {
            description 'VXLAN ID binding by static tunnel interface.' ;
            type uint32 {
              range 1..16777215 {
                description 'The value of VXLAN,it must be between 1 to 16777215.' ;
              }

            }

            status obsolete ;

          }

          status obsolete ;

        }

        ncd:revise-date 2016-04-20 ;
      }

      container tunnel-statistics-configs {
        description 'Configuration of tunnel statistics.' ;
        list tunnel-statistics-config {
          description 'Configuration of tunnel statistics.' ;
          key 'local-ipv4 remote-ipv4' ;
          leaf local-ipv4 {
            description 'Local IP address.' ;
            type ncd:ipv4-address ;

          }

          leaf remote-ipv4 {
            description 'Remote IP address.' ;
            type ncd:ipv4-address ;

          }

        }

        list tunnel-vni-statistics-config {
          description 'Configuration of tunnel statistics in VXLAN.' ;
          key 'local-ipv4 remote-ipv4 vxlan-id' ;
          leaf local-ipv4 {
            description 'Local IP address.' ;
            type ncd:ipv4-address ;

          }

          leaf remote-ipv4 {
            description 'Remote IP address.' ;
            type ncd:ipv4-address ;

          }

          leaf vxlan-id {
            description 'The VXLAN in tunnel.' ;
            type uint32 {
              range 1..16777215 {
                description 'The value of VXLAN,it must be between 1 to 16777215.' ;
              }

            }

          }

        }

        list tunnel-ipv6-statistics-config {
          description 'Configuration of IPv6 tunnel statistics.' ;
          key 'local-ipv6 remote-ipv6' ;
          leaf local-ipv6 {
            description 'Local IPv6 address.' ;
            type ncd:ipv6-address ;

          }

          leaf remote-ipv6 {
            description 'Remote IPv6 address.' ;
            type ncd:ipv6-address ;

          }

          ncd:revise-date 2018-11-29 ;
        }

        list tunnel-ipv6-vni-statistics-config {
          description 'Configuration of IPv6 tunnel statistics in VXLAN.' ;
          key 'local-ipv6 remote-ipv6 vxlan-id' ;
          leaf local-ipv6 {
            description 'Local IPv6 address.' ;
            type ncd:ipv6-address ;

          }

          leaf remote-ipv6 {
            description 'Remote IPv6 address.' ;
            type ncd:ipv6-address ;

          }

          leaf vxlan-id {
            description 'The VXLAN in tunnel.' ;
            type uint32 {
              range 1..16777215 {
                description 'The value of VXLAN,it must be between 1 to 16777215.' ;
              }

            }

          }

          ncd:revise-date 2018-11-29 ;
        }

        list vni-statistics-config {
          description 'Configuration of vxlan statistics.' ;
          key vxlan-id ;
          leaf vxlan-id {
            description 'VXLAN Network Identifier.' ;
            type uint32 ;

          }

          ncd:revise-date 2018-11-05 ;
        }

        ncd:revise-date 2016-04-20 ;
      }

      container redundancy-group-binds {
        if-feature redundancy-group-bind ;

        description 'Redundancy group bind table.' ;
        status obsolete {
          ncd:revise-date 2024-09-02 ;
        }

        list redundancy-group-bind {
          description 'Redundancy group bind table.' ;
          key 'vxlan-id redundancy-group' ;
          leaf vxlan-id {
            description 'VXLAN ID binding by redundancy group.' ;
            type uint32 {
              range 1..16777215 {
                description 'The value of VXLAN,it must be between 1 to 16777215.' ;
              }

            }

            status obsolete ;

          }

          leaf redundancy-group {
            description 'Redundancy group ID.' ;
            type uint32 {
              range 1..4294967293 {
                description 'The value of redundancy group,it must be between 1 to 4294967293.' ;
              }

            }

            status obsolete ;

          }

          status obsolete ;

        }

        ncd:revise-date 2016-04-20 ;
      }

      container nve-instances {
        description 'Configuration of NVE instances.' ;
        list nve-instance {
          description 'Configuration of NVE instance.' ;
          key nve-port ;
          leaf nve-port {
            description 'Interface name.' ;
            type ncd:ifname ;

          }

          leaf source-vtep-ipv4 {
            description 'Source IP of NVE instance.' ;
            type ncd:ipv4-address ;

            mandatory true ;
          }

        }

        list nve-instance-v6 {
          description 'Configuration of NVE ipv6 instance.' ;
          key nve-port ;
          leaf nve-port {
            description 'Interface name.' ;
            type ncd:ifname ;

          }

          leaf source-vtep-ipv6 {
            description 'Source IP of NVE ipv6 instance.' ;
            type ncd:ipv6-address ;

            mandatory true ;
          }

          ncd:revise-date 2023-04-24 ;
        }

        list nve-mac {
          description 'Set MAC address of NVE.' ;
          key nve-port ;
          leaf nve-port {
            description 'Interface name.' ;
            type ncd:ifname ;

          }

          leaf mac-address {
            description 'MAC address.' ;
            type ncd:mac-address ;

            mandatory true ;
          }

          ncd:revise-date 2023-12-14 ;
        }

        ncd:revise-date 2019-11-19 ;
      }

      container vni-instances {
        description 'Configuration of VNI instances.' ;
        list vni-instance {
          description 'Configuration of VNI instance.' ;
          key vni-id ;
          leaf vni-id {
            description 'ID of VNI instance.' ;
            type uint32 ;

          }

          leaf protocol-type {
            description 'Protocol type of VNI.' ;
            type enumeration {
              enum null {
                value 0 ;
                description 'Null.' ;
              }

              enum bgp {
                value 1 ;
                description "Use bgp as vxlan's protocol." ;
              }

            }

            default null ;
          }

          container source-nve-instance {
            description 'Configuration of VNI source interfaces.' ;
            presence source-nve-instance ;
            leaf nve-port {
              description 'Source interface name of VNI instance.' ;
              type ncd:ifname ;

            }

          }

          container vni-multicasts {
            description 'VNI multicast IP address.' ;
            list vni-multicast {
              description 'VNI multicast IP address.' ;
              key multicast-ipv4 ;
              leaf multicast-ipv4 {
                description 'VNI multicast IP address.' ;
                type ncd:ipv4-address ;

                mandatory true ;
              }

              leaf pim-mode {
                description 'PIM mode.' ;
                type enumeration {
                  enum sm {
                    value 1 ;
                    description 'PIM Sparse Mode.' ;
                  }

                  enum ssm {
                    value 2 ;
                    description 'PIM Source Specific Multicast.' ;
                  }

                }

                mandatory true ;
              }

            }

          }

          container vni-v6-multicasts {
            description 'VNI multicast IPV6 address.' ;
            list vni-v6-multicast {
              description 'VNI multicast IPV6 address.' ;
              key multicast-ipv6 ;
              leaf multicast-ipv6 {
                description 'VNI multicast IPV6 address.' ;
                type ncd:ipv6-address ;

                mandatory true ;
              }

              leaf pim-mode {
                description 'PIM mode.' ;
                type enumeration {
                  enum sm {
                    value 1 ;
                    description 'PIM Sparse Mode.' ;
                  }

                  enum ssm {
                    value 2 ;
                    description 'PIM Source Specific Multicast.' ;
                  }

                }

                mandatory true ;
              }

            }

            ncd:revise-date 2023-04-24 ;
          }

        }

        ncd:revise-date 2019-11-19 ;
      }

      container micro-segment {
        if-feature vxlan-micro-segment ;

        container global-config {
          description 'Micro segment global config.' ;
          leaf micro-segment-enable {
            description 'Set micro segment enable or disable.' ;
            type enumeration {
              enum enable {
                value 1 ;
                description 'Enable micro segment function.' ;
              }

              enum disable {
                value 2 ;
                description 'Disable micro segment function.' ;
              }

            }

            default disable ;
          }

          leaf unknown-segment {
            description 'Policy between unknown segments.' ;
            type enumeration {
              enum permit {
                value 1 ;
                description 'Permit the connection between unknown segments.' ;
              }

              enum deny {
                value 2 ;
                description 'Deny the connection between unknown segments.' ;
              }

            }

            default permit ;
          }

          leaf unknown-to-known-segment {
            description 'Policy from unknown to known segments.' ;
            type enumeration {
              enum permit {
                value 1 ;
                description 'Permit the connectivity.' ;
              }

              enum deny {
                value 2 ;
                description 'Deny the connectivity.' ;
              }

            }

            default permit ;
          }

          leaf known-to-unknown-segment {
            description 'Policy from known to unknown segments.' ;
            type enumeration {
              enum permit {
                value 1 ;
                description 'Permit the connectivity.' ;
              }

              enum deny {
                value 2 ;
                description 'Deny the connectivity.' ;
              }

            }

            default permit ;
          }

          leaf segment {
            description 'Policy between known segments.' ;
            type enumeration {
              enum permit {
                value 1 ;
                description 'Permit the connectivity.' ;
              }

              enum deny {
                value 2 ;
                description 'Deny the connectivity.' ;
              }

            }

            default deny ;
          }

          leaf same-segment {
            description 'Policy within the same segment.' ;
            type enumeration {
              enum permit {
                value 1 ;
                description 'Permit the connectivity.' ;
              }

              enum deny {
                value 2 ;
                description 'Deny the connectivity.' ;
              }

            }

          }

        }

        container segment-id {
          description 'Configure a segment instance' ;
          list segment-id {
            description 'Configure a segment instance.' ;
            key id ;
            leaf id {
              description 'Segment ID.' ;
              type uint16 {
                range 1..65535 ;

              }

            }

            leaf segment-name {
              description 'Segment name.' ;
              type ncd:string-with-blank {
                length 1..128 ;

              }

              ncd:revise-date 2023-11-29 ;
            }

            list ipv4-configuration {
              description 'IPv4 configuration.' ;
              key 'ipv4-addr mask-addr' ;
              leaf ipv4-addr {
                description 'The ipv4 address of route.' ;
                type ncd:ipv4-address ;

              }

              leaf mask-addr {
                description 'The mask address.' ;
                type ncd:ipv4-address ;

              }

            }

            list ipv4-configuration-with-vrf {
              description 'IPv4 configuration.' ;
              key 'ipv4-addr mask-addr vrf-name' ;
              leaf ipv4-addr {
                description 'The ipv4 address of route.' ;
                type ncd:ipv4-address ;

              }

              leaf mask-addr {
                description 'The mask address.' ;
                type ncd:ipv4-address ;

              }

              leaf vrf-name {
                description 'The name of the private network VPN.' ;
                type string {
                  length 1..32 {
                    description 'The length of vrf name.' ;
                  }

                }

              }

            }

            list ipv6-configuration {
              description 'IPv6 configuration.' ;
              key 'ipv6-addr mask-len' ;
              leaf ipv6-addr {
                description 'The ipv6 address of route.' ;
                type ncd:ipv6-address ;

              }

              leaf mask-len {
                description 'The mask length.' ;
                type uint8 {
                  range 1..128 {
                    description 'The length of mask.' ;
                  }

                }

              }

            }

            list ipv6-configuration-with-vrf {
              description 'IPv6 configuration.' ;
              key 'ipv6-addr mask-len vrf-name' ;
              leaf ipv6-addr {
                description 'The ipv6 address of route.' ;
                type ncd:ipv6-address ;

              }

              leaf mask-len {
                description 'The mask length.' ;
                type uint8 {
                  range 1..128 {
                    description 'The length of mask.' ;
                  }

                }

              }

              leaf vrf-name {
                description 'The name of the private network VPN.' ;
                type string {
                  length 1..32 {
                    description 'The length of vrf name.' ;
                  }

                }

              }

            }

          }

        }

        container classifier {
          description 'Classifier.' ;
          list classifier-name {
            description 'Classifier name' ;
            key name ;
            leaf name {
              description 'Classifier name.' ;
              type ncd:string-with-blank {
                length 1..128 ;

              }

              ncd:revise-date 2023-11-29 ;
            }

            list common-rule {
              description 'Common rule with protocol.' ;
              key 'source-segment destination-segment protocol' ;
              leaf source-segment {
                description 'Source segment.(0 means unknown)' ;
                type uint16 {
                  range 0..65535 {
                    description 'Maximum must be in this range.Value 0 means unknow.' ;
                  }

                }

              }

              leaf destination-segment {
                description 'Destination segment.(0 means unknown)' ;
                type uint16 {
                  range 0..65535 {
                    description 'Maximum must be in this range.Value 0 means unknow.' ;
                  }

                }

              }

              leaf protocol {
                description 'Protocol value.(exclusion:1-icmp,6-tcp,17-udp)' ;
                type uint16 {
                  range "0|2..5|7..16|18..255" {
                    description 'Maximum must be in this range. 1:icmp, 6:tcp, 17:udp.' ;
                  }

                }

              }

            }

            list common-rule-without-protocol {
              description 'Common rule without protocol.' ;
              key 'source-segment destination-segment' ;
              leaf source-segment {
                description 'Source segment.(0 means unknown)' ;
                type uint16 {
                  range 0..65535 {
                    description 'Maximum must be in this range.Value 0 means unknow.' ;
                  }

                }

              }

              leaf destination-segment {
                description 'Destination segment.(0 means unknown)' ;
                type uint16 {
                  range 0..65535 {
                    description 'Maximum must be in this range.Value 0 means unknow.' ;
                  }

                }

              }

            }

            list icmp-rule {
              description 'Icmp protocol rule.' ;
              key 'source-segment destination-segment' ;
              leaf source-segment {
                description 'Source segment.(0 means unknown)' ;
                type uint16 {
                  range 0..65535 {
                    description 'Maximum must be in this range.Value 0 means unknow.' ;
                  }

                }

              }

              leaf destination-segment {
                description 'Destination segment.(0 means unknown)' ;
                type uint16 {
                  range 0..65535 {
                    description 'Maximum must be in this range.Value 0 means unknow.' ;
                  }

                }

              }

            }

            list icmp-rule-with-type {
              description 'Icmp protocol rule.' ;
              key 'source-segment destination-segment type' ;
              leaf source-segment {
                description 'Source segment.(0 means unknown)' ;
                type uint16 {
                  range 0..65535 {
                    description 'Maximum must be in this range.Value 0 means unknow.' ;
                  }

                }

              }

              leaf destination-segment {
                description 'Destination segment.(0 means unknown)' ;
                type uint16 {
                  range 0..65535 {
                    description 'Maximum must be in this range.Value 0 means unknow.' ;
                  }

                }

              }

              leaf type {
                description 'Icmp type.' ;
                type uint16 {
                  range 0..255 ;

                }

              }

            }

            list icmpv6-rule-with-type {
              description 'Icmpv6 protocol rule.' ;
              key 'source-segment destination-segment type' ;
              leaf source-segment {
                description 'Source segment.(0 means unknown)' ;
                type uint16 {
                  range 0..65535 {
                    description 'Maximum must be in this range.Value 0 means unknow.' ;
                  }

                }

              }

              leaf destination-segment {
                description 'Destination segment.(0 means unknown)' ;
                type uint16 {
                  range 0..65535 {
                    description 'Maximum must be in this range.Value 0 means unknow.' ;
                  }

                }

              }

              leaf type {
                description 'Icmpv6 type.' ;
                type uint16 {
                  range 0..255 ;

                }

              }

              ncd:revise-date 2023-06-19 ;
            }

            list tcp-rule {
              description 'Tcp protocol rule.' ;
              key 'source-segment destination-segment' ;
              leaf source-segment {
                description 'Source segment.(0 means unknown)' ;
                type uint16 {
                  range 0..65535 {
                    description 'Maximum must be in this range.Value 0 means unknow.' ;
                  }

                }

              }

              leaf destination-segment {
                description 'Destination segment.(0 means unknown)' ;
                type uint16 {
                  range 0..65535 {
                    description 'Maximum must be in this range.Value 0 means unknow.' ;
                  }

                }

              }

            }

            list tcp-rule-with-source-port {
              description 'Tcp protocol rule.' ;
              key 'source-segment destination-segment source-port' ;
              leaf source-segment {
                description 'Source segment.(0 means unknown)' ;
                type uint16 {
                  range 0..65535 {
                    description 'Maximum must be in this range.Value 0 means unknow.' ;
                  }

                }

              }

              leaf destination-segment {
                description 'Destination segment.(0 means unknown)' ;
                type uint16 {
                  range 0..65535 {
                    description 'Maximum must be in this range.Value 0 means unknow.' ;
                  }

                }

              }

              leaf source-port {
                description 'Source port value.' ;
                type uint16 {
                  range 1..65535 {
                    description 'Maximum must be in this range.(0 is invalid)' ;
                  }

                }

              }

            }

            list tcp-rule-with-destination-port {
              description 'Tcp protocol rule.' ;
              key 'source-segment destination-segment destination-port' ;
              leaf source-segment {
                description 'Source segment.(0 means unknown)' ;
                type uint16 {
                  range 0..65535 {
                    description 'Maximum must be in this range.Value 0 means unknow.' ;
                  }

                }

              }

              leaf destination-segment {
                description 'Destination segment.(0 means unknown)' ;
                type uint16 {
                  range 0..65535 {
                    description 'Maximum must be in this range.Value 0 means unknow.' ;
                  }

                }

              }

              leaf destination-port {
                description 'Source port value.' ;
                type uint16 {
                  range 1..65535 {
                    description 'Maximum must be in this range.(0 is invalid)' ;
                  }

                }

              }

            }

            list tcp-rule-with-both-port {
              description 'Tcp protocol rule.' ;
              key 'source-segment destination-segment source-port destination-port' ;
              leaf source-segment {
                description 'Source segment.(0 means unknown)' ;
                type uint16 {
                  range 0..65535 {
                    description 'Maximum must be in this range.Value 0 means unknow.' ;
                  }

                }

              }

              leaf destination-segment {
                description 'Destination segment.(0 means unknown)' ;
                type uint16 {
                  range 0..65535 {
                    description 'Maximum must be in this range.Value 0 means unknow.' ;
                  }

                }

              }

              leaf source-port {
                description 'Source port value.' ;
                type uint16 {
                  range 1..65535 {
                    description 'Maximum must be in this range.(0 is invalid)' ;
                  }

                }

              }

              leaf destination-port {
                description 'Source port value.' ;
                type uint16 {
                  range 1..65535 {
                    description 'Maximum must be in this range.(0 is invalid)' ;
                  }

                }

              }

            }

            list udp-rule {
              description 'Udp protocol rule.' ;
              key 'source-segment destination-segment' ;
              leaf source-segment {
                description 'Source segment.(0 means unknown)' ;
                type uint16 {
                  range 0..65535 {
                    description 'Maximum must be in this range.Value 0 means unknow.' ;
                  }

                }

              }

              leaf destination-segment {
                description 'Destination segment.(0 means unknown)' ;
                type uint16 {
                  range 0..65535 {
                    description 'Maximum must be in this range.Value 0 means unknow.' ;
                  }

                }

              }

            }

            list udp-rule-with-source-port {
              description 'Udp protocol rule.' ;
              key 'source-segment destination-segment source-port' ;
              leaf source-segment {
                description 'Source segment.(0 means unknown)' ;
                type uint16 {
                  range 0..65535 {
                    description 'Maximum must be in this range.Value 0 means unknow.' ;
                  }

                }

              }

              leaf destination-segment {
                description 'Destination segment.(0 means unknown)' ;
                type uint16 {
                  range 0..65535 {
                    description 'Maximum must be in this range.Value 0 means unknow.' ;
                  }

                }

              }

              leaf source-port {
                description 'Source port value.' ;
                type uint16 {
                  range 1..65535 {
                    description 'Maximum must be in this range.(0 is invalid)' ;
                  }

                }

              }

            }

            list udp-rule-with-destination-port {
              description 'Udp protocol rule.' ;
              key 'source-segment destination-segment destination-port' ;
              leaf source-segment {
                description 'Source segment.(0 means unknown)' ;
                type uint16 {
                  range 0..65535 {
                    description 'Maximum must be in this range.Value 0 means unknow.' ;
                  }

                }

              }

              leaf destination-segment {
                description 'Destination segment.(0 means unknown)' ;
                type uint16 {
                  range 0..65535 {
                    description 'Maximum must be in this range.Value 0 means unknow.' ;
                  }

                }

              }

              leaf destination-port {
                description 'Source port value.' ;
                type uint16 {
                  range 1..65535 {
                    description 'Maximum must be in this range.(0 is invalid)' ;
                  }

                }

              }

            }

            list udp-rule-with-both-port {
              description 'Udp protocol rule.' ;
              key 'source-segment destination-segment source-port destination-port' ;
              leaf source-segment {
                description 'Source segment.(0 means unknown)' ;
                type uint16 {
                  range 0..65535 {
                    description 'Maximum must be in this range.Value 0 means unknow.' ;
                  }

                }

              }

              leaf destination-segment {
                description 'Destination segment.(0 means unknown)' ;
                type uint16 {
                  range 0..65535 {
                    description 'Maximum must be in this range.Value 0 means unknow.' ;
                  }

                }

              }

              leaf source-port {
                description 'Source port value.' ;
                type uint16 {
                  range 1..65535 {
                    description 'Maximum must be in this range.(0 is invalid)' ;
                  }

                }

              }

              leaf destination-port {
                description 'Destination port value.' ;
                type uint16 {
                  range 1..65535 {
                    description 'Maximum must be in this range.(0 is invalid)' ;
                  }

                }

              }

            }

            container rule-extend {
              description 'The configuration of rule extend.' ;
              list rule-extend {
                description 'rule extend.' ;
                key rule-id ;
                leaf rule-id {
                  description 'ID of this rule.' ;
                  type uint32 {
                    range 1..65535 ;

                  }

                }

                leaf source-segment {
                  description 'Source segment.(0 means unknown)' ;
                  type uint16 {
                    range 0..65535 ;

                  }

                  mandatory true ;
                }

                leaf destination-segment {
                  description 'Destination segment.(0 means unknown)' ;
                  type uint16 {
                    range 0..65535 ;

                  }

                  mandatory true ;
                }

                choice protocol {
                  description 'protocol type.' ;
                  case common {
                    description 'Common rule.' ;
                    leaf protocol-type {
                      description 'protocol type.' ;
                      mandatory true ;
                      type uint16 {
                        range "0..5|7..16|18..131|133..255" ;

                      }

                    }

                  }

                  case icmp {
                    description 'Icmp protocol rule.' ;
                    leaf icmp-protocol {
                      type empty ;

                      description 'icmp protocol.' ;
                      mandatory true ;
                    }

                    leaf icmp-type {
                      description 'icmp type.' ;
                      mandatory true ;
                      type uint16 {
                        range 0..255 ;

                      }

                    }

                  }

                  case icmpv6 {
                    description 'Icmpv6 protocol rule.' ;
                    leaf icmpv6-protocol {
                      type empty ;

                      description 'icmpv6 protocol.' ;
                      mandatory true ;
                    }

                    leaf icmpv6-type {
                      description 'icmpv6 type.' ;
                      mandatory true ;
                      type uint16 {
                        range 0..255 ;

                      }

                    }

                  }

                  case tcp {
                    description 'Tcp protocol rule.' ;
                    leaf tcp-protocol {
                      type empty ;

                      description 'tcp protocol.' ;
                      mandatory true ;
                    }

                    container tcp-port {
                      description 'port.' ;
                      choice source-port-type {
                        case source-port {
                          leaf source-port {
                            type uint16 {
                              range 1..65535 ;

                            }

                            description 'Source port value.' ;
                            mandatory true ;
                          }

                        }

                        case source-port-range {
                          leaf source-port-range {
                            type ncd:single-range {
                              pattern "(([1-9][0-9]{1,3})|([1-9][0-9]{0,0})|([1-5][0-9]{4,4})|(6[0-4][0-9]{3,3})|(65[0-4][0-9]{2,2})|(655[0-2][0-9]{1,1})|(6553[0-4])|65535)(-(([1-9][0-9]{1,3})|([1-9][0-9]{0,0})|0|([1-5][0-9]{4,4})|(6[0-4][0-9]{3,3})|(65[0-4][0-9]{2,2})|(655[0-2][0-9]{1,1})|(6553[0-4])|65535)){0,1}" ;

                            }

                            description 'Source port range value.' ;
                            mandatory true ;
                          }

                        }

                      }

                      choice destination-port-type {
                        case destination-port {
                          leaf destination-port {
                            type uint16 {
                              range 1..65535 ;

                            }

                            description 'Destination port value.' ;
                            mandatory true ;
                          }

                        }

                        case destination-port-range {
                          leaf destination-port-range {
                            type ncd:single-range {
                              pattern "(([1-9][0-9]{1,3})|([1-9][0-9]{0,0})|([1-5][0-9]{4,4})|(6[0-4][0-9]{3,3})|(65[0-4][0-9]{2,2})|(655[0-2][0-9]{1,1})|(6553[0-4])|65535)(-(([1-9][0-9]{1,3})|([1-9][0-9]{0,0})|0|([1-5][0-9]{4,4})|(6[0-4][0-9]{3,3})|(65[0-4][0-9]{2,2})|(655[0-2][0-9]{1,1})|(6553[0-4])|65535)){0,1}" ;

                            }

                            description 'Destination port range value.' ;
                            mandatory true ;
                          }

                        }

                      }

                    }

                  }

                  case udp {
                    description 'Udp protocol rule.' ;
                    leaf udp-protocol {
                      type empty ;

                      description 'udp protocol.' ;
                      mandatory true ;
                    }

                    container udp-port {
                      description 'port.' ;
                      choice source-port-type {
                        case source-port {
                          leaf source-port {
                            type uint16 {
                              range 1..65535 ;

                            }

                            description 'Source port value.' ;
                            mandatory true ;
                          }

                        }

                        case source-port-range {
                          leaf source-port-range {
                            type ncd:single-range {
                              pattern "(([1-9][0-9]{1,3})|([1-9][0-9]{0,0})|([1-5][0-9]{4,4})|(6[0-4][0-9]{3,3})|(65[0-4][0-9]{2,2})|(655[0-2][0-9]{1,1})|(6553[0-4])|65535)(-(([1-9][0-9]{1,3})|([1-9][0-9]{0,0})|0|([1-5][0-9]{4,4})|(6[0-4][0-9]{3,3})|(65[0-4][0-9]{2,2})|(655[0-2][0-9]{1,1})|(6553[0-4])|65535)){0,1}" ;

                            }

                            description 'Source port range value.' ;
                            mandatory true ;
                          }

                        }

                      }

                      choice destination-port-type {
                        case destination-port {
                          leaf destination-port {
                            type uint16 {
                              range 1..65535 ;

                            }

                            description 'Destination port value.' ;
                            mandatory true ;
                          }

                        }

                        case destination-port-range {
                          leaf destination-port-range {
                            type ncd:single-range {
                              pattern "(([1-9][0-9]{1,3})|([1-9][0-9]{0,0})|([1-5][0-9]{4,4})|(6[0-4][0-9]{3,3})|(65[0-4][0-9]{2,2})|(655[0-2][0-9]{1,1})|(6553[0-4])|65535)(-(([1-9][0-9]{1,3})|([1-9][0-9]{0,0})|0|([1-5][0-9]{4,4})|(6[0-4][0-9]{3,3})|(65[0-4][0-9]{2,2})|(655[0-2][0-9]{1,1})|(6553[0-4])|65535)){0,1}" ;

                            }

                            description 'Destination port range value.' ;
                            mandatory true ;
                          }

                        }

                      }

                    }

                  }

                  case sctp {
                    description 'Sctp protocol rule.' ;
                    leaf sctp-protocol {
                      type empty ;

                      description 'sctp protocol.' ;
                      mandatory true ;
                    }

                    container sctp-port {
                      description 'port.' ;
                      choice source-port-type {
                        case source-port {
                          leaf source-port {
                            type uint16 {
                              range 1..65535 ;

                            }

                            description 'Source port value.' ;
                            mandatory true ;
                          }

                        }

                        case source-port-range {
                          leaf source-port-range {
                            type ncd:single-range {
                              pattern "(([1-9][0-9]{1,3})|([1-9][0-9]{0,0})|([1-5][0-9]{4,4})|(6[0-4][0-9]{3,3})|(65[0-4][0-9]{2,2})|(655[0-2][0-9]{1,1})|(6553[0-4])|65535)(-(([1-9][0-9]{1,3})|([1-9][0-9]{0,0})|0|([1-5][0-9]{4,4})|(6[0-4][0-9]{3,3})|(65[0-4][0-9]{2,2})|(655[0-2][0-9]{1,1})|(6553[0-4])|65535)){0,1}" ;

                            }

                            description 'Source port range value.' ;
                            mandatory true ;
                          }

                        }

                      }

                      choice destination-port-type {
                        case destination-port {
                          leaf destination-port {
                            type uint16 {
                              range 1..65535 ;

                            }

                            description 'Destination port value.' ;
                            mandatory true ;
                          }

                        }

                        case destination-port-range {
                          leaf destination-port-range {
                            type ncd:single-range {
                              pattern "(([1-9][0-9]{1,3})|([1-9][0-9]{0,0})|([1-5][0-9]{4,4})|(6[0-4][0-9]{3,3})|(65[0-4][0-9]{2,2})|(655[0-2][0-9]{1,1})|(6553[0-4])|65535)(-(([1-9][0-9]{1,3})|([1-9][0-9]{0,0})|0|([1-5][0-9]{4,4})|(6[0-4][0-9]{3,3})|(65[0-4][0-9]{2,2})|(655[0-2][0-9]{1,1})|(6553[0-4])|65535)){0,1}" ;

                            }

                            description 'Destination port range value.' ;
                            mandatory true ;
                          }

                        }

                      }

                    }

                  }

                }

              }

              if-feature micro-segment-rule-extend ;

              ncd:revise-date 2024-04-07 ;
            }

          }

        }

        container policy {
          description 'Configure a segment policy.' ;
          list policy-name {
            description 'Policy name.' ;
            key name ;
            leaf name {
              description 'Policy name.' ;
              type ncd:string-with-blank {
                length 1..128 ;

              }

              ncd:revise-date 2023-11-29 ;
            }

            list classifier {
              description 'Set classifier state.' ;
              key classifier-name ;
              leaf classifier-name {
                description 'Classifier name.' ;
                type ncd:string-with-blank {
                  length 1..128 ;

                }

                ncd:revise-date 2023-11-29 ;
              }

              leaf state {
                description 'State.' ;
                type enumeration {
                  enum permit {
                    value 1 ;
                    description 'Permit' ;
                  }

                  enum deny {
                    value 2 ;
                    description 'Deny' ;
                  }

                }

                mandatory true ;
              }

            }

          }

        }

        ncd:revise-date 2022-10-10 ;
      }

    }

  }

  container state {
    description 'Information of VXLAN state.' ;
    config false ;
    container vxlan {
      description 'Information of VXLAN state.' ;
      container vxlan-tunnels {
        description 'Information of VXLAN tunnel.' ;
        list vxlan-tunnel {
          description 'Information of VXLAN tunnel.' ;
          key 'remote-ipv4 local-ipv4' ;
          leaf remote-ipv4 {
            description 'Remote IPv4 address of VXLAN tunnel.' ;
            type ncd:ipv4-address ;

            ncd:revise-date 2016-04-05 ;
          }

          leaf local-ipv4 {
            description 'Local IPv4 address of VXLAN tunnel.' ;
            type ncd:ipv4-address ;

            ncd:revise-date 2016-04-05 ;
          }

          leaf static-tunnel-id {
            description 'Static tunnel ID.' ;
            type uint32 ;

            ncd:revise-date 2016-04-20 ;
          }

          leaf evpn-tunnel-id {
            description 'EVPN tunnel ID.' ;
            type uint32 ;

            ncd:revise-date 2016-04-05 ;
          }

          container statistics {
            description 'Tunnel statistics.' ;
            container tunnel-statistics {
              description 'Total tunnel statistics.' ;
              leaf in-bytes {
                description 'Total bytes received.' ;
                type string {
                  length 1..24 ;

                }

              }

              leaf out-bytes {
                description 'Total bytes sent.' ;
                type string {
                  length 1..24 ;

                }

              }

              leaf in-packets {
                description 'Total packets received.' ;
                type string {
                  length 1..24 ;

                }

              }

              leaf out-packets {
                description 'Total packets sent.' ;
                type string {
                  length 1..24 ;

                }

              }

              leaf in-rate-bps {
                description '120s-bytes-rate received.' ;
                type uint64 ;

                ncd:revise-date 2017-01-10 ;
              }

              leaf out-rate-bps {
                description '120s-bytes-rate sent.' ;
                type uint64 ;

                ncd:revise-date 2017-01-10 ;
              }

              leaf in-rate-pps {
                description '120s-packets-rate received.' ;
                type uint64 ;

                ncd:revise-date 2017-01-10 ;
              }

              leaf out-rate-pps {
                description '120s-packets-rate sent.' ;
                type uint64 ;

                ncd:revise-date 2017-01-10 ;
              }

            }

            container tunnel-vni-statistics {
              description 'Statistics in VXLAN tunnel.' ;
              list tunnel-vni-statistic {
                description 'Statistics in VXLAN tunnel.' ;
                key vxlan-id ;
                leaf vxlan-id {
                  description 'The VXLAN in tunnel.' ;
                  type uint32 {
                    range 1..16777215 {
                      description 'The value of VXLAN,it must be between 1 to 16777215.' ;
                    }

                  }

                }

                leaf in-bytes {
                  description 'Total bytes received.' ;
                  type string {
                    length 1..24 ;

                  }

                }

                leaf out-bytes {
                  description 'Total bytes sent.' ;
                  type string {
                    length 1..24 ;

                  }

                }

                leaf in-packets {
                  description 'Total packets received.' ;
                  type string {
                    length 1..24 ;

                  }

                }

                leaf out-packets {
                  description 'Total packets sent.' ;
                  type string {
                    length 1..24 ;

                  }

                }

                leaf in-rate-bps {
                  description '120s-bytes-rate received.' ;
                  type uint64 ;

                  ncd:revise-date 2017-01-10 ;
                }

                leaf out-rate-bps {
                  description '120s-bytes-rate sent.' ;
                  type uint64 ;

                  ncd:revise-date 2017-01-10 ;
                }

                leaf in-rate-pps {
                  description '120s-packets-rate received.' ;
                  type uint64 ;

                  ncd:revise-date 2017-01-10 ;
                }

                leaf out-rate-pps {
                  description '120s-packets-rate sent.' ;
                  type uint64 ;

                  ncd:revise-date 2017-01-10 ;
                }

              }

            }

            ncd:revise-date 2016-04-20 ;
          }

          ncd:select "remote-ipv4 local-ipv4" ;
          ncd:select evpn-tunnel-id ;
        }

        list vxlan-tunnel-ipv6 {
          description 'Information of VXLAN tunnel(IPv6).' ;
          key 'remote-ipv6 local-ipv6' ;
          leaf remote-ipv6 {
            description 'Remote IPv6 address of VXLAN tunnel.' ;
            type ncd:ipv6-address ;

          }

          leaf local-ipv6 {
            description 'Local IPv6 address of VXLAN tunnel.' ;
            type ncd:ipv6-address ;

          }

          leaf static-tunnel-id {
            description 'Static tunnel ID.' ;
            type uint32 ;

          }

          leaf evpn-tunnel-id {
            description 'EVPN tunnel ID.' ;
            type uint32 ;

          }

          container statistics {
            description 'Tunnel(IPv6) statistics.' ;
            container tunnel-ipv6-statistics {
              description 'Total IPv6 tunnel statistics.' ;
              leaf in-bytes {
                description 'Total bytes received.' ;
                type string {
                  length 1..24 ;

                }

              }

              leaf out-bytes {
                description 'Total bytes sent.' ;
                type string {
                  length 1..24 ;

                }

              }

              leaf in-packets {
                description 'Total packets received.' ;
                type string {
                  length 1..24 ;

                }

              }

              leaf out-packets {
                description 'Total packets sent.' ;
                type string {
                  length 1..24 ;

                }

              }

              leaf in-rate-bps {
                description '120s-bytes-rate received.' ;
                type uint64 ;

              }

              leaf out-rate-bps {
                description '120s-bytes-rate sent.' ;
                type uint64 ;

              }

              leaf in-rate-pps {
                description '120s-packets-rate received.' ;
                type uint64 ;

              }

              leaf out-rate-pps {
                description '120s-packets-rate sent.' ;
                type uint64 ;

              }

            }

            container tunnel-ipv6-vni-statistics {
              description 'Statistics in VXLAN IPv6 tunnel.' ;
              list tunnel-ipv6-vni-statistic {
                description 'Statistics in VXLAN IPv6 tunnel.' ;
                key vxlan-id ;
                leaf vxlan-id {
                  description 'The VXLAN in tunnel.' ;
                  type uint32 {
                    range 1..16777215 {
                      description 'The value of VXLAN,it must be between 1 to 16777215.' ;
                    }

                  }

                }

                leaf in-bytes {
                  description 'Total bytes received.' ;
                  type string {
                    length 1..24 ;

                  }

                }

                leaf out-bytes {
                  description 'Total bytes sent.' ;
                  type string {
                    length 1..24 ;

                  }

                }

                leaf in-packets {
                  description 'Total packets received.' ;
                  type string {
                    length 1..24 ;

                  }

                }

                leaf out-packets {
                  description 'Total packets sent.' ;
                  type string {
                    length 1..24 ;

                  }

                }

                leaf in-rate-bps {
                  description '120s-bytes-rate received.' ;
                  type uint64 ;

                }

                leaf out-rate-bps {
                  description '120s-bytes-rate sent.' ;
                  type uint64 ;

                }

                leaf in-rate-pps {
                  description '120s-packets-rate received.' ;
                  type uint64 ;

                }

                leaf out-rate-pps {
                  description '120s-packets-rate sent.' ;
                  type uint64 ;

                }

              }

            }

            ncd:revise-date 2018-11-29 ;
          }

          ncd:revise-date 2018-02-06 ;
          ncd:select "remote-ipv6 local-ipv6" ;
          ncd:select evpn-tunnel-id ;
        }

      }

      container vxlan-statistics {
        description 'Statistics in VXLAN.' ;
        list vxlan-statistic {
          description 'Statistic in VXLAN.' ;
          key vxlan-id ;
          leaf vxlan-id {
            description 'VXLAN Network Identifier' ;
            type uint32 {
              range 1..16777215 {
                description 'The value of VXLAN,it must be between 1 to 16777215.' ;
              }

            }

          }

          leaf in-bytes {
            description 'Total bytes received.' ;
            type string ;

          }

          leaf out-bytes {
            description 'Total bytes sent.' ;
            type string ;

          }

          leaf in-packets {
            description 'Total packets received.' ;
            type string ;

          }

          leaf out-packets {
            description 'Total packets sent.' ;
            type string ;

          }

          leaf in-rate-bps {
            description '120s-bytes-rate received.' ;
            type uint64 ;

          }

          leaf out-rate-bps {
            description '120s-bytes-rate sent.' ;
            type uint64 ;

          }

          leaf in-rate-pps {
            description '120s-packets-rate received.' ;
            type uint64 ;

          }

          leaf out-rate-pps {
            description '120s-packets-rate sent.' ;
            type uint64 ;

          }

        }

        ncd:revise-date 2018-11-05 ;
      }

    }

    ncd:revise-date 2016-01-08 ;
  }

  container operation {
    description 'Operation of VXLAN.' ;
    config false ;
    container vxlan {
      description 'Operation of VXLAN.' ;
      container clear-vxlan-tunnel-statistics {
        description 'Clear statistics of VXLAN tunnel.' ;
        list vxlan-tunnel-statistics {
          description 'Clear statistics of VXLAN tunnel.' ;
          key 'local-ipv4 remote-ipv4' ;
          leaf local-ipv4 {
            description 'Local IP address.' ;
            type ncd:ipv4-address ;

          }

          leaf remote-ipv4 {
            description 'Remote IP address.' ;
            type ncd:ipv4-address ;

          }

          leaf vxlan-id {
            description 'The VXLAN in tunnel.' ;
            type uint32 {
              range 1..16777215 {
                description 'Range of VXLAN ID.' ;
              }

            }

          }

        }

        list vxlan-tunnel-ipv6-statistics {
          description 'Clear statistics of VXLAN tunnel(IPv6).' ;
          key 'local-ipv6 remote-ipv6' ;
          leaf local-ipv6 {
            description 'Local IPv6 address.' ;
            type ncd:ipv6-address ;

          }

          leaf remote-ipv6 {
            description 'Remote IPv6 address.' ;
            type ncd:ipv6-address ;

          }

          leaf vxlan-id {
            description 'The VXLAN in tunnel.' ;
            type uint32 {
              range 1..16777215 {
                description 'Range of VXLAN ID.' ;
              }

            }

          }

          ncd:revise-date 2018-11-29 ;
        }

        list vxlan-statistics {
          description 'Clear statistics of VXLAN.' ;
          key vxlan-id ;
          leaf vxlan-id {
            description 'VXLAN Network Identifier' ;
            type uint32 {
              range 1..16777215 {
                description 'Range of VXLAN ID.' ;
              }

            }

          }

          ncd:revise-date 2018-11-05 ;
        }

      }

    }

    ncd:revise-date 2016-04-20 ;
  }

}
