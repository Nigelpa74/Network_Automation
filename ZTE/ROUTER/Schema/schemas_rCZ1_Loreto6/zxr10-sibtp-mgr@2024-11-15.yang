module zxr10-sibtp-mgr {
  namespace "http://www.zte.com.cn/zxr10/netconf/schema/rosng/sibtp-mgr" ;
  prefix sibtp-mgr ;
  import zxr10-netconf-defs {
    prefix ncd ;
    revision-date 2019-07-16 ;
  }

  organization "ZTE Corporation" ;
  contact "ZTE Corporation
  Nanjing Institute of ZTE Corporation
  No.68 Zijinghua Rd. Yuhuatai District, Nanjing, China
  Tel: +86-25-52870000" ;
  revision 2024-11-15 {
    description 'add leaf:
configuration\sibtp-mgr\instance-list\instance\authentication\authentication-keychain-name
configuration\sibtp-mgr\link-list\authentication-keychain-name' ;
  }

  revision 2024-08-29 {
    description 'modify description of list:
state\sibtp-mgr\link-list\link-ipv6-public
state\sibtp-mgr\link-list\link-ipv6-vrf
state\sibtp-mgr\link-list\link-ipv4-vrf' ;
  }

  revision 2023-05-09 {
    description 'add revision indicates that the obsolete is deleted from the link-list node' ;
  }

  revision 2023-03-17 {
    description 'modify container:
configuration/sibtp-mgr/link-list state obsolete to current' ;
  }

  revision 2022-10-08 {
    description 'add container:
state\sibtp-mgr\instance-link-list
configuration\sibtp-mgr-instance-list' ;
  }

  revision 2021-12-30 {
    description 'add list:
state\sibtp-mgr\l2-link\l2-link-list
Obsolete nodes:
state\sibtp-mgr\l2-link\interface-name
state\sibtp-mgr\l2-link\state' ;
  }

  revision 2021-07-22 {
    description 'Modify nodes:
state\sibtp-mgr\l2-link' ;
  }

  revision 2020-02-12 {
    description 'Initial version.' ;
  }

  container state {
    config false ;
    description 'The state of SIBTP-MGR.' ;
    container sibtp-mgr {
      description 'The SIBTP-MGR state.' ;
      container l2-link {
        description 'The L2 link.' ;
        leaf interface-name {
          status obsolete {
            ncd:revise-date 2021-12-30 ;
          }

          description 'Interface name.' ;
          type string {
            length 1..31 ;

          }

        }

        leaf state {
          status obsolete {
            ncd:revise-date 2021-12-30 ;
          }

          description 'The state.' ;
          type string {
            length 1..31 ;

          }

        }

        list l2-link-list {
          description 'The l2 link.' ;
          key interface-name ;
          leaf interface-name {
            description 'Interface name.' ;
            type string {
              length 1..31 ;

            }

          }

          leaf state {
            description 'The state.' ;
            type string {
              length 1..31 ;

            }

          }

          ncd:revise-date 2021-12-30 ;
        }

        ncd:revise-date 2021-07-22 ;
      }

      container instance-link-list {
        description 'The instance link list.' ;
        list instance-link-ipv6-public {
          description 'The ipv6 link in sibtp instance.' ;
          key 'source-ipv6 peer-ipv6 source-port peer-port instance-id' ;
          leaf source-ipv6 {
            description 'The source ipv6.' ;
            type ncd:ipv6-address-none-zero ;

          }

          leaf peer-ipv6 {
            description 'The peer ipv6.' ;
            type ncd:ipv6-address-none-zero ;

          }

          leaf source-port {
            description 'The source port.' ;
            type uint32 {
              range 1025..65535 ;

            }

          }

          leaf peer-port {
            description 'The peer port.' ;
            type uint32 {
              range 1025..65535 ;

            }

          }

          leaf instance-id {
            description 'The sibtp instance id' ;
            type uint32 {
              range 1..16 ;

            }

          }

          leaf state {
            description 'The state.' ;
            type string {
              length 1..31 ;

            }

          }

        }

        list instance-link-ipv4-vrf {
          description 'The ipv4 link with vrf in sibtp instance.' ;
          key 'source-ipv4 peer-ipv4 source-port peer-port vrf-name instance-id' ;
          leaf source-ipv4 {
            description 'The source ipv4.' ;
            type ncd:ipv4-address-none-zero ;

          }

          leaf peer-ipv4 {
            description 'The peer ipv4.' ;
            type ncd:ipv4-address-none-zero ;

          }

          leaf source-port {
            description 'The source port.' ;
            type uint32 {
              range 1025..65535 ;

            }

          }

          leaf peer-port {
            description 'The peer port.' ;
            type uint32 {
              range 1025..65535 ;

            }

          }

          leaf vrf-name {
            description 'The vrf name.' ;
            type string {
              length 1..32 ;

            }

          }

          leaf instance-id {
            description 'The sibtp instance id' ;
            type uint32 {
              range 1..16 ;

            }

          }

          leaf state {
            description 'The state.' ;
            type string {
              length 1..31 ;

            }

          }

        }

        list instance-link-ipv6-vrf {
          description 'The ipv6 link with vrf in sibtp instance.' ;
          key 'source-ipv6 peer-ipv6 source-port peer-port vrf-name instance-id' ;
          leaf source-ipv6 {
            description 'The source ipv6.' ;
            type ncd:ipv6-address-none-zero ;

          }

          leaf peer-ipv6 {
            description 'The peer ipv6.' ;
            type ncd:ipv6-address-none-zero ;

          }

          leaf source-port {
            description 'The source port.' ;
            type uint32 {
              range 1025..65535 ;

            }

          }

          leaf peer-port {
            description 'The peer port.' ;
            type uint32 {
              range 1025..65535 ;

            }

          }

          leaf vrf-name {
            description 'The vrf name.' ;
            type string {
              length 1..32 ;

            }

          }

          leaf instance-id {
            description 'The sibtp instance id' ;
            type uint32 {
              range 1..16 ;

            }

          }

          leaf state {
            description 'The state.' ;
            type string {
              length 1..31 ;

            }

          }

        }

        list instance-link-ipv4-public {
          description 'The ipv4 link in sibtp instance.' ;
          key 'source-ipv4 peer-ipv4 source-port peer-port instance-id' ;
          leaf source-ipv4 {
            description 'The source ipv4.' ;
            type ncd:ipv4-address-none-zero ;

          }

          leaf peer-ipv4 {
            description 'The peer ipv4.' ;
            type ncd:ipv4-address-none-zero ;

          }

          leaf source-port {
            description 'The source port.' ;
            type uint32 {
              range 1025..65535 ;

            }

          }

          leaf peer-port {
            description 'The peer port.' ;
            type uint32 {
              range 1025..65535 ;

            }

          }

          leaf instance-id {
            description 'The sibtp instance id' ;
            type uint32 {
              range 1..16 ;

            }

          }

          leaf state {
            description 'The state.' ;
            type string {
              length 1..31 ;

            }

          }

        }

        ncd:revise-date 2022-10-08 ;
      }

      container link-list {
        description 'The link list.' ;
        list link-ipv6-public {
          description 'The ipv6 link.' ;
          key 'source-ipv6 peer-ipv6 source-port peer-port' ;
          leaf source-ipv6 {
            description 'The source ipv6.' ;
            type ncd:ipv6-address-none-zero ;

          }

          leaf peer-ipv6 {
            description 'The peer ipv6.' ;
            type ncd:ipv6-address-none-zero ;

          }

          leaf source-port {
            description 'The source port.' ;
            type uint32 {
              range 1025..65535 ;

            }

          }

          leaf peer-port {
            description 'The peer port.' ;
            type uint32 {
              range 1025..65535 ;

            }

          }

          leaf state {
            description 'The state.' ;
            type string {
              length 1..31 ;

            }

          }

        }

        list link-ipv4-public {
          description 'The ipv4 link.' ;
          key 'source-ipv4 peer-ipv4 source-port peer-port' ;
          leaf source-ipv4 {
            description 'The source ipv4.' ;
            type ncd:ipv4-address-none-zero ;

          }

          leaf peer-ipv4 {
            description 'The peer ipv4.' ;
            type ncd:ipv4-address-none-zero ;

          }

          leaf source-port {
            description 'The source port.' ;
            type uint32 {
              range 1025..65535 ;

            }

          }

          leaf peer-port {
            description 'The peer port.' ;
            type uint32 {
              range 1025..65535 ;

            }

          }

          leaf state {
            description 'The state.' ;
            type string {
              length 1..31 ;

            }

          }

        }

        list link-ipv4-vrf {
          description 'The ipv4 vrf link.' ;
          key 'source-ipv4 peer-ipv4 source-port peer-port vrf-name' ;
          leaf source-ipv4 {
            description 'The source ipv4.' ;
            type ncd:ipv4-address-none-zero ;

          }

          leaf peer-ipv4 {
            description 'The peer ipv4.' ;
            type ncd:ipv4-address-none-zero ;

          }

          leaf source-port {
            description 'The source port.' ;
            type uint32 {
              range 1025..65535 ;

            }

          }

          leaf peer-port {
            description 'The peer port.' ;
            type uint32 {
              range 1025..65535 ;

            }

          }

          leaf vrf-name {
            description 'The vrf name.' ;
            type string {
              length 1..32 ;

            }

          }

          leaf state {
            description 'The state.' ;
            type string {
              length 1..31 ;

            }

          }

        }

        list link-ipv6-vrf {
          description 'The ipv6 vrf link.' ;
          key 'source-ipv6 peer-ipv6 source-port peer-port vrf-name' ;
          leaf source-ipv6 {
            description 'The source ipv6.' ;
            type ncd:ipv6-address-none-zero ;

          }

          leaf peer-ipv6 {
            description 'The peer ipv6.' ;
            type ncd:ipv6-address-none-zero ;

          }

          leaf source-port {
            description 'The source port.' ;
            type uint32 {
              range 1025..65535 ;

            }

          }

          leaf peer-port {
            description 'The peer port.' ;
            type uint32 {
              range 1025..65535 ;

            }

          }

          leaf vrf-name {
            description 'The vrf name.' ;
            type string {
              length 1..32 ;

            }

          }

          leaf state {
            description 'The state.' ;
            type string {
              length 1..31 ;

            }

          }

        }

      }

    }

  }

  container configuration {
    description 'The configuration of SIBTP-MGR.' ;
    container sibtp-mgr {
      description 'Configure SIBTP-MGR.' ;
      container instance-list {
        description 'The sibtp instance list.' ;
        list instance {
          description 'The sibtp instance' ;
          key instance-id ;
          leaf instance-id {
            description 'The sibtp instance id' ;
            type uint32 {
              range 1..16 ;

            }

          }

          container authentication {
            leaf authentication-keychain-name {
              type string {
                length 1..31 ;

              }

              description 'The authentication keychain name.' ;
            }

            description 'The authentication.' ;
            ncd:revise-date 2024-11-15 ;
          }

          container link-ipv4-public-list {
            description 'The link ipv4 public list.' ;
            list link-ipv4-public {
              description 'The ipv4 public link.' ;
              key 'source-ipv4 peer-ipv4 source-port peer-port' ;
              leaf source-ipv4 {
                description 'The source ipv4.' ;
                type ncd:ipv4-address-none-zero ;

              }

              leaf peer-ipv4 {
                description 'The peer ipv4.' ;
                type ncd:ipv4-address-none-zero ;

              }

              leaf source-port {
                description 'The source port.' ;
                type uint32 {
                  range 1025..65535 ;

                }

              }

              leaf peer-port {
                description 'The peer port.' ;
                type uint32 {
                  range 1025..65535 ;

                }

              }

              leaf tcp-mss {
                description 'The tcp mss.' ;
                type uint32 {
                  range 68..10000 ;

                }

                default 1400 ;
              }

            }

          }

          container link-ipv4-vrf-list {
            description 'The link ipv4 vrf list.' ;
            list link-ipv4-vrf {
              description 'The ipv4 vrf link.' ;
              key 'source-ipv4 peer-ipv4 source-port peer-port vrf-name' ;
              leaf source-ipv4 {
                description 'The source ipv4.' ;
                type ncd:ipv4-address-none-zero ;

              }

              leaf peer-ipv4 {
                description 'The peer ipv4.' ;
                type ncd:ipv4-address-none-zero ;

              }

              leaf source-port {
                description 'The source port.' ;
                type uint32 {
                  range 1025..65535 ;

                }

              }

              leaf peer-port {
                description 'The peer port.' ;
                type uint32 {
                  range 1025..65535 ;

                }

              }

              leaf tcp-mss {
                description 'The tcp mss.' ;
                type uint32 {
                  range 68..10000 ;

                }

                default 1400 ;
              }

              leaf vrf-name {
                description 'The vrf name.' ;
                type string {
                  length 1..32 ;

                }

              }

            }

          }

          container link-ipv6-public-list {
            description 'The link ipv6 public list.' ;
            list link-ipv6-public {
              description 'The ipv6 public link.' ;
              key 'source-ipv6 peer-ipv6 source-port peer-port' ;
              leaf source-ipv6 {
                description 'The source ipv6.' ;
                type ncd:ipv6-address-none-zero ;

              }

              leaf peer-ipv6 {
                description 'The peer ipv6.' ;
                type ncd:ipv6-address-none-zero ;

              }

              leaf source-port {
                description 'The source port.' ;
                type uint32 {
                  range 1025..65535 ;

                }

              }

              leaf peer-port {
                description 'The peer port.' ;
                type uint32 {
                  range 1025..65535 ;

                }

              }

            }

          }

          container link-ipv6-vrf-list {
            description 'The link ipv6 vrf list.' ;
            list link-ipv6-vrf {
              description 'The ipv6 vrf link.' ;
              key 'source-ipv6 peer-ipv6 source-port peer-port vrf-name' ;
              leaf source-ipv6 {
                description 'The source ipv6.' ;
                type ncd:ipv6-address-none-zero ;

              }

              leaf peer-ipv6 {
                description 'The peer ipv6.' ;
                type ncd:ipv6-address-none-zero ;

              }

              leaf source-port {
                description 'The source port.' ;
                type uint32 {
                  range 1025..65535 ;

                }

              }

              leaf peer-port {
                description 'The peer port.' ;
                type uint32 {
                  range 1025..65535 ;

                }

              }

              leaf vrf-name {
                description 'The vrf name.' ;
                type string {
                  length 1..32 ;

                }

              }

            }

          }

        }

        ncd:revise-date 2022-10-08 ;
      }

      container link-list {
        description 'The link list.' ;
        leaf authentication-keychain-name {
          type string {
            length 1..31 ;

          }

          description 'The authentication keychain name.' ;
          ncd:revise-date 2024-11-15 ;
        }

        container link-ipv4-public-list {
          description 'The link ipv4 public list.' ;
          list link-ipv4-public {
            description 'The ipv4 public link.' ;
            key 'source-ipv4 peer-ipv4 source-port peer-port' ;
            leaf source-ipv4 {
              description 'The source ipv4.' ;
              type ncd:ipv4-address-none-zero ;

            }

            leaf peer-ipv4 {
              description 'The peer ipv4.' ;
              type ncd:ipv4-address-none-zero ;

            }

            leaf source-port {
              description 'The source port.' ;
              type uint32 {
                range 1025..65535 ;

              }

            }

            leaf peer-port {
              description 'The peer port.' ;
              type uint32 {
                range 1025..65535 ;

              }

            }

            leaf tcp-mss {
              description 'The tcp mss.' ;
              type uint32 {
                range 68..10000 ;

              }

              default 1400 ;
            }

          }

        }

        container link-ipv4-vrf-list {
          description 'The link ipv4 vrf list.' ;
          list link-ipv4-vrf {
            description 'The ipv4 vrf link.' ;
            key 'source-ipv4 peer-ipv4 source-port peer-port vrf-name' ;
            leaf source-ipv4 {
              description 'The source ipv4.' ;
              type ncd:ipv4-address-none-zero ;

            }

            leaf peer-ipv4 {
              description 'The peer ipv4.' ;
              type ncd:ipv4-address-none-zero ;

            }

            leaf source-port {
              description 'The source port.' ;
              type uint32 {
                range 1025..65535 ;

              }

            }

            leaf peer-port {
              description 'The peer port.' ;
              type uint32 {
                range 1025..65535 ;

              }

            }

            leaf tcp-mss {
              description 'The tcp mss.' ;
              type uint32 {
                range 68..10000 ;

              }

              default 1400 ;
            }

            leaf vrf-name {
              description 'The vrf name.' ;
              type string {
                length 1..32 ;

              }

            }

          }

        }

        container link-ipv6-public-list {
          description 'The link ipv6 public list.' ;
          list link-ipv6-public {
            description 'The ipv6 public link.' ;
            key 'source-ipv6 peer-ipv6 source-port peer-port' ;
            leaf source-ipv6 {
              description 'The source ipv6.' ;
              type ncd:ipv6-address-none-zero ;

            }

            leaf peer-ipv6 {
              description 'The peer ipv6.' ;
              type ncd:ipv6-address-none-zero ;

            }

            leaf source-port {
              description 'The source port.' ;
              type uint32 {
                range 1025..65535 ;

              }

            }

            leaf peer-port {
              description 'The peer port.' ;
              type uint32 {
                range 1025..65535 ;

              }

            }

          }

        }

        container link-ipv6-vrf-list {
          description 'The link ipv6 vrf list.' ;
          list link-ipv6-vrf {
            description 'The ipv6 vrf link.' ;
            key 'source-ipv6 peer-ipv6 source-port peer-port vrf-name' ;
            leaf source-ipv6 {
              description 'The source ipv6.' ;
              type ncd:ipv6-address-none-zero ;

            }

            leaf peer-ipv6 {
              description 'The peer ipv6.' ;
              type ncd:ipv6-address-none-zero ;

            }

            leaf source-port {
              description 'The source port.' ;
              type uint32 {
                range 1025..65535 ;

              }

            }

            leaf peer-port {
              description 'The peer port.' ;
              type uint32 {
                range 1025..65535 ;

              }

            }

            leaf vrf-name {
              description 'The vrf name.' ;
              type string {
                length 1..32 ;

              }

            }

          }

        }

        ncd:revise-date 2023-05-09 ;
      }

    }

  }

}
