module zxr10-snetconf {
  namespace 'http://www.zte.com.cn/zxr10/netconf/schema/rosng/snetconf' ;
  prefix snetc ;
  organization 'ZTE Corporation' ;
  contact "ZTE Corporation 
\n"
        + "         Nanjing Institute of ZTE Corporation
\n"
        + "         
\n"
        + "         No.68 Zijinghua Rd. Yuhuatai District, Nanjing, China
\n"
        + "         
\n"
        + '         Tel: +86-25-52870000'
          ;
  description 'ZXR10 ROSNG:the netconf model for snetconf' ;
  revision 2015-01-12 {
    description 'modify the listenning port of snetconf' ;
  }
  revision 2013-11-25 {
    description 'add description to some nodes; modify range for port node;' ;
  }
  revision 2013-01-31 {
    description 'initial version' ;
  }
  container configuration {
    description 'configuration model' ;
    container snetconf {
      description 'Configure SNETCONF parameters' ;
      container server {
        description 'Configure snetconf server parameters' ;
        choice status {
          description 'The status of snetconf server,the default state is disab'
                    + 'le'
                      ;
          default disable ;
          case disable {
            leaf disable {
              description 'disable snetconf server' ;
              type empty ;
            }
          }
          case enable {
            leaf enable {
              description 'enable snetconf server' ;
              type empty ;
            }
          }
        }
        leaf port {
          description 'The listenning port of snetconf. the default value is 83'
                    + '0'
                      ;
          type uint16 {
            range '22 | 830 | 1025..20000' ;
          }
          default 830 ;
        }
      }
    }
  }
}
