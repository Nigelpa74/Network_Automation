module zxr10-sqa {
  namespace "http://www.zte.com.cn/zxr10/netconf/schema/rosng/sqa" ;
  prefix sqa ;
  yang-version 1 ;
  import zxr10-netconf-defs {
    prefix ncd ;
  }

  organization "ZTE Corporation" ;
  contact "ZTE Corporation
  Nanjing Institute of ZTE Corporation
  No.68 Zijinghua Rd. Yuhuatai District, Nanjing, China
  Tel: +86-25-52870000" ;
  description 'The netconf module to describe SQA' ;
  revision 2025-05-12 {
    description '1.Modify range from 64-9600 to 64-10000 of leaf:/sqa:configuration/sqa:sqa/sqa:tests/sqa:test/sqa:generalflow/sqa:packet-size/sqa:size;
2.Modify range from 2-10000000 to 2-400000000 of leaf: leaf:/sqa:configuration/sqa:sqa/sqa:tests/sqa:test/sqa:generalflow/sqa:throughput/sqa:one-rate/sqa:rate;
3.Modify range from 1-10000000 to 1-400000000 of leaf: leaf:/sqa:configuration/sqa:sqa/sqa:tests/sqa:test/sqa:generalflow/sqa:throughput/sqa:two-rate/sqa:low-rate;
4.Modify range from 1-10000000 to 1-400000000 of leaf: leaf:/sqa:configuration/sqa:sqa/sqa:tests/sqa:test/sqa:generalflow/sqa:throughput/sqa:two-rate/sqa:high-rate;
5.Modify range from 1-10000000 to 1-400000000 of leaf: leaf:/sqa:configuration/sqa:sqa/sqa:tests/sqa:test/sqa:generalflow/sqa:loss/sqa:rate;
6.Modify range from 0-10000000 to 0-400000000 of leaf: leaf:/sqa:configuration/sqa:sqa/sqa:tests/sqa:test/sqa:generalflow/sqa:delay/sqa:rate;
7.Modify range from 1-10000000 to 1-400000000 of leaf: leaf:/sqa:state/sqa:sqa/sqa:generalflow-loss-results/sqa:generalflow-loss-result/sqa:rate;
8.Modify range from 0-10000000 to 0-400000000 of leaf: leaf:/sqa:state/sqa:sqa/sqa:generalflow-delay-results/sqa:generalflow-delay-result/sqa:rate;
9.Modify range from 1-10000000 to 1-400000000 of leaf: leaf:/sqa:loss-event/sqa:loss-result/sqa:loss-rate;
10.Modify range from 0-10000000 to 0-400000000 of leaf: leaf:/sqa:delay-event/sqa:delay-result/sqa:delay-rate;
11.Modify the range description of test-number.' ;
  }

  revision 2025-02-26 {
    description '1.Add leaf:/sqa:configuration/sqa:sqa/sqa:tests/sqa:test/sqa:icmp/sqa:timeout
2.Add leaf:/sqa:configuration/sqa:sqa/sqa:tests/sqa:test/sqa:icmpjitter/sqa:timeout' ;
  }

  revision 2025-02-25 {
    description '1. Add enum value pcep of node /sqa:state/sqa:sqa/sqa:light-twamp-results/sqa:light-twamp-result/sqa:protocol-origin.' ;
  }

  revision 2025-01-21 {
    description '1、add case configuration/sqa/tests/test/light-twamp/interval-unit/unit-minute
2、add  case configuration/sqa/sqa-templates/sqa-template/light-twamp/interval/unit-min' ;
  }

  revision 2024-12-27 {
    description '1、Modify the range of configuration/sqa/tests/test/result-policy/result-number from 5-10 to 5-20;
2、Modify the range of configuration/sqa/tests/test/result-policy/success-count/success-count-low from 2-8 to 2-18;
3、Modify the range of configuration/sqa/tests/test/result-policy/success-count/success-count-high from 3-9 to 3-19.' ;
  }

  revision 2024-11-11 {
    description 'Add leaf:/sqa:configuration/sqa:sqa/sqa:global/sqa:twamp-hqos-sensitive' ;
  }

  revision 2024-10-16 {
    description '1.Add container of configuration/sqa/ethernet-loopbacks.' ;
  }

  revision 2024-07-01 {
    description 'Modify the description of following nodes(including some spelling errors in the description information):
1. configuration/sqa/tests/test/light-twamp/client-mode;
2. configuration/sqa/reflectors/reflector/reflector-mode;
3. state/sqa/reflector-informations/reflector-information/reflector-mode;
4. state/sqa/reflector-informations/reflector-information/disnontest-8021p;
5. state/sqa/reflector-informations/reflector-information/disnontest-dscp;
6. state/sqa/reflector-informations/reflector-information/vlan-id;
7. state/sqa/reflector-informations/reflector-information/internal-vlan-id;
8. state/sqa/reflector-informations/reflector-information/external-vlan-id;
9. state/sqa/reflector-informations/reflector-information/priority-8021p;
10. state/sqa/reflector-informations/reflector-information/dscp;
11. state/sqa/reflector-informations/reflector-information/free-arp-vlan-id;
12. state/sqa/reflector-informations/reflector-information/free-arp-internal-id;
13. state/sqa/reflector-informations/reflector-information/free-arp-external-id;
14. state/sqa/twamp-reflector-informations/twamp-reflector-information;
15. state/sqa/twamp-reflector-informations/twamp-reflector-information/source-port;
16. state/sqa/twamp-reflector-informations/twamp-reflector-information/destination-port;
17. state/sqa/twamp-reflector-informations/twamp-reflector-information/vlan-id;
18. state/sqa/twamp-reflector-informations/twamp-reflector-information/internal-vlan-id;
19. state/sqa/twamp-reflector-informations/twamp-reflector-information/external-vlan-id;
20. state/sqa/twamp-reflector-informations/twamp-reflector-information/priority-8021p;
21. state/sqa/twamp-reflector-informations/twamp-reflector-information/dscp;
22. state/sqa/twamp-reflector-informations/twamp-reflector-information/free-arp-vlan-id;
23. state/sqa/twamp-reflector-informations/twamp-reflector-information/free-arp-internal-id;
24. state/sqa/twamp-reflector-informations/twamp-reflector-information/free-arp-external-id;
25. state/sqa/light-twamp-results;
26. state/sqa/light-twamp-results/light-twamp-result;
27. state/sqa/light-twamp-results/light-twamp-result/client-mode;
28. state/sqa/light-twamp-results/light-twamp-result/originator-as-num;
29. state/sqa/light-twamp-results/light-twamp-result/originator-address;
30. state/sqa/generalflow-throughput-results/generalflow-throughput-result;
31. state/sqa/generalflow-loss-results/generalflow-loss-result;
32. state/sqa/generalflow-delay-results/generalflow-delay-result;
33. state/sqa/y1564-results;
34. state/sqa/y1564-results/y1564-result.' ;
  }

  revision 2024-06-15 {
    description 'Modify the description of delay-statistics-mode of following nodes(as discard the performance code 36241424):
1. configuration/sqa/tests/test/light-twamp/delay-statistics-mode;
2. configuration/sqa/sqa-templates/sqa-template/light-twamp/delay-statistics-mode.' ;
  }

  revision 2024-04-25 {
    description 'Modify the default value from both to bidirection of following nodes:
1. configuration/sqa/tests/test/light-twamp/delay-statistics-mode;
2. configuration/sqa/sqa-templates/sqa-template/light-twamp/delay-statistics-mode.' ;
  }

  revision 2024-04-08 {
    description '1.The leaf of configuration/sqa/sqa-templates/delay-statistics-mode associates to performance code.' ;
  }

  revision 2024-01-31 {
    description 'Changes the description of the test instance and reflector from 31 characters to 127 characters.' ;
  }

  revision 2023-10-30 {
    description 'Support flow policy of light twamp test, add nodes as follows:
1. Add leaf of configuration/sqa/tests/test/light-twamp/flow-policy;
2. Add leaf of configuration/sqa/twamp-reflectors/twamp-reflector/flow-policy.' ;
  }

  revision 2023-10-19 {
    description '1.Add send-trap-interval leaf of configuration/sqa/tests/test/test-type/proactiveping' ;
  }

  revision 2023-08-30 {
    description '1. Add container of configuration/sqa/tests/test/result-policy.' ;
  }

  revision 2023-06-27 {
    description '1. Add nexthop and out-interface leafs of configuration/sqa/tests/test/icmp' ;
  }

  revision 2023-06-20 {
    description '1.Add leaf of configuration/sqa/tests/test/light-twamp/template-name.
2.Add container of configuration/sqa/sqa-templates.' ;
  }

  revision 2023-06-12 {
    description '1. change leaf max value，such as test-number,packet-size .' ;
  }

  revision 2022-09-27 {
    description '1.Add pcep type to configuration/sqa/tests/test/light-twamp/light-twamp/sr-policy/end-point;
2.Add leaf of originator-as-num to state/sqa/light-twamp-results/light-twamp-result;
3.Add leaf of originator-address to state/sqa/light-twamp-results/light-twamp-result.' ;
  }

  revision 2022-09-19 {
    description '1.Change the range of delay-event/delay-result/delay-rate from 1-10000000 to 0-10000000.
2.Change the range of /state/generalflow-delay-results/generalflow-delay-result/rate from 1-10000000 to 0-10000000.' ;
  }

  revision 2022-07-27 {
    description '1.Add sqa:state/sqa/generalflow-throughput-results/generalflow-throughput-result.
2.Add sqa:state/sqa/generalflow-loss-results/generalflow-loss-result.
3.Add sqa:state/sqa/generalflow-delay-results/generalflow-delay-result.
4.Add sqa:state/sqa/y1564-results/y1564-result.' ;
  }

  revision 2022-07-04 {
    description '1.Add leaf of report-mode to configuration/sqa/tests/test/light-twamp/.' ;
  }

  revision 2022-04-25 {
    description '1.Change the leaf name of lighttwamp-event/lighttwamp-result/out-interface from out-interface to member-interface.' ;
  }

  revision 2022-04-21 {
    description '1.Change the range of throughput-event/throughput-result/packet-size from 64-9216 to 64-65535;
2.Change the range of loss-event/loss-result/packet-size from 64-9216 to 64-65535;
3.Change the range of delay-event/delay-result/packet-size from 64-9216 to 64-65535;
4.Change the range of y1564-event/y1564-result/packet-size from 64-9216 to 64-65535.' ;
  }

  revision 2022-03-28 {
    description '1 Add leaf of configuration/sqa/tests/test/test-type/generalflow/priority-ignore
2 Add leaf of configuration/sqa/tests/test/test-type/light-twamp/priority-ignore' ;
  }

  revision 2022-03-08 {
    description '1.Add leaf of reflector-mode to state/sqa/twamp-reflector-informations/twamp-reflector-information/
2.Add leaf of on-lag to state/sqa/twamp-reflector-informations/twamp-reflector-information/
3.Add leaf of out-interface to lighttwamp-event/lighttwamp-result/' ;
  }

  revision 2022-02-14 {
    description '1.Add leaf of bind-lag-interface to configuration/sqa/tests/test/light-twamp/.
2.Add leaf of on-lag to configuration/sqa/twamp-reflectors/twamp-reflector/.
3.Add a enumeration value of configuration/sqa/tests/test/light-twamp/light-twamp/client-mode.
4.Add feature of lag-mode.
5.Add leaf of source-port to state/sqa/light-twamp-results/light-twamp-result/
6.Add leaf of destination-port to state/sqa/light-twamp-results/light-twamp-result/
7.Add leaf of out-interface to state/sqa/light-twamp-results/light-twamp-result/' ;
  }

  revision 2022-01-17 {
    description '1.Add leaf of flex-algo-id to configuration/sqa/tests/test/light-twamp/.
2.Add leaf of flex-algo-id to state/sqa/light-twamp-results/light-twamp-result/
3.Add feature of flex-algo.' ;
  }

  revision 2021-12-31 {
    description '1.Add leaf of source-ip to configuration/sqa/tests/test/udp/.
2.Add leaf of source-ipv6 to configuration/sqa/tests/test/udp/.
3.Add leaf of source-port to configuration/sqa/tests/test/udp/.
4.Add leaf of ttl to configuration/sqa/tests/test/udp/.
5.Add leaf of source-ip to configuration/sqa/tests/test/udpjitter/.
6.Add leaf of source-ipv6 to configuration/sqa/tests/test/udpjitter/.
7.Add leaf of source-port to configuration/sqa/tests/test/udpjitter/.
8.Add leaf of ttl to configuration/sqa/tests/test/udpjitter/.' ;
  }

  revision 2021-12-28 {
    description '1.Add leaf of vrf-name to state/sqa/icmpjitter-results/icmpjitter-result/' ;
  }

  revision 2021-12-06 {
    description '1.Add leaf of configuration/sqa/twamp-reflectors/twamp-reflector/reflector-mode.' ;
  }

  revision 2021-11-30 {
    description '1.Add leaf of description to state/sqa/light-twamp-results/light-twamp-result/' ;
  }

  revision 2021-11-17 {
    description '1.Add leaf of configuration/sqa/tests/test/description.
2.Add leaf of configuration/sqa/reflectors/reflector/description.
3.Add leaf of configuration/sqa/twamp-reflectors/twamp-reflector/description.' ;
  }

  revision 2021-11-12 {
    description 'Support source address and source port of tcp test, add nodes as follows:
1. configuration/sqa/tests/test/tcp/ipv4/source-ip;
2. configuration/sqa/tests/test/tcp/ipv6/source-ipv6;
3. configuration/sqa/tests/test/tcp/source-port.' ;
  }

  revision 2021-11-10 {
    description '1.Change the range of configuration/sqa/tests/test/light-twamp/light-twamp/statistics-interval from 5-300 to 5-900.' ;
  }

  revision 2021-10-28 {
    description '1.Add leaf of configuration/sqa/reflectors/reflector/ignore-udp-port.' ;
  }

  revision 2021-07-15 {
    description '1.Change the range of configuration/sqa/tests/test/test-type/light-twamp/statistics-interval from 5-60 to 5-300.' ;
  }

  revision 2021-06-03 {
    description '1 Add container of configuration/sqa/tests/test/jitter-threshold.
2 Add leaf of configuration/sqa/tests/test/jitter-threshold/jitter-threshold-value.' ;
  }

  revision 2021-05-25 {
    description '1. Del leaf of nexthop-address-ipv6 form choice case of configuration/sqa/tests/test/proactive-ping/ip-addr-family/ipv6.
2. Del leaf of nexthop-address form choice case of configuration/sqa/tests/test/proactive-ping/ip-addr-family/ipv4.
3. Add choice of NextHop to configuration/sqa/tests/test/proactive-ping.' ;
  }

  revision 2021-04-23 {
    description 'The key length of FTP username can be up to 128 characters.' ;
  }

  revision 2021-04-20 {
    description '1.Add choice case of ip to state/sqa/light-twamp-results/light-twamp-result/path.
2. Add leaf of client-mode to state/sqa/light-twamp-results/light-twamp-result/' ;
  }

  revision 2021-03-31 {
    description '1.Add the sr-mpls-policy-sl enumeration type to configuration/sqa/tests/test/light-twamp/light-twamp/client-mode.
2.Add the te-tunnel enumeration type to configuration/sqa/tests/test/light-twamp/light-twamp/client-mode.
3.Add leaf of tunnel-id to configuration/sqa/tests/test/light-twamp/light-twamp/.
4.Add feature of te-tunnel.
5.Add end-point-v4 to configuration/sqa/tests/test/light-twamp/light-twamp/sr-policy/end-point.
6.Add path to state/sqa/light-twamp-results/light-twamp-result.' ;
  }

  revision 2021-03-09 {
    description '1.Modify description of delay-statistics-mode at configuration/sqa/tests/test/light-twamp.' ;
  }

  revision 2021-02-18 {
    description '1.Add configuration/sqa/tests/test/generalflow/y1564/ses-measure.
2.Add configuration/sqa/tests/test/generalflow/y1564/ses-threshold.
3.Add y1564-event/y1564-result/ses-count.
4.Add y1564-event/y1564-result/total-count.
5.Add y1564-event/y1564-result/sesr.' ;
  }

  revision 2021-01-16 {
    description '1.Remove container feature of configuration/sqa/tests/test/light-twamp/light-twamp/interval-unit.' ;
  }

  revision 2020-12-24 {
    description '1.Add  configuration/sqa/tests/test/light-twamp/light-twamp/delay-mode.' ;
  }

  revision 2020-12-07 {
    description '1.Add  configuration/sqa/tests/test/light-twamp/light-twamp/sr-policy.' ;
  }

  revision 2020-09-07 {
    description '1.Add choice type at configuration/sqa/tests/test/policy.
2.Add case branches of loop-time and frequency at configuration/sqa/tests/test/policy/type.
3.Move leaf node loop-time to case branch of configuration/sqa/tests/test/policy/type/loop-time.
4.Add leaf node frequency to case branch of configuration/sqa/tests/test/policy/type/frequency.
5.Add feature policy-frequency support products of T8000 and 15K.' ;
  }

  revision 2020-08-11 {
    description '1.Add choice ip-addr-family at configuration/sqa/tests/test/icmpjitter.
2.Add case branches of ipv4 and ipv6 at configuration/sqa/tests/test/icmpjitter/ip-addr-family.
3.Modify description of destination-ip and source-ip at configuration/sqa/tests/test/icmpjitter.
4.Move leaf nodes destination-ip and source-ip to case branch of configuration/sqa/tests/test/icmpjitter/ip-addr-family/ipv4.
5.Add leaf nodes destination-ipv6 and source-ipv6 to case branch of configuration/sqa/tests/test/icmpjitter/ip-addr-family/ipv6.
6.Add leaf nodes min-rtt,max-rtt,avg-rtt,sum-rtt,cur-rtt,min-delay-jitter,max-delay-jitter,avg-delay-jitter,sum-delay-jitter,cur-delay-jitter,cur-delay-jitter-sd,cur-delay-jitter-ds,pkt-loss-num,pkt-loss-rate and destination-ipv6 at state/sqa/icmpjitter-results/icmpjitter-result.
7.Add leaf nodes min-rtt,max-rtt,avg-rtt,sum-rtt,cur-rtt,min-delay-jitter,max-delay-jitter,avg-delay-jitter,sum-delay-jitter,cur-delay-jitter,cur-delay-jitter-sd,cur-delay-jitter-ds,pkt-loss-num,pkt-loss-rate and destination-ipv6 at icmpjitter-event/icmpjitter-result.
8.Modify description of state/sqa/icmpjitter-results/icmpjitter-result/destination-ip.
9.Modify description of icmpjitter-event/icmpjitter-result/destination-ip.
10.Move size node at configuration/sqa/tests/test/icmp to configuration/sqa/tests/test/icmp/ip-addr-family/ipv4.
11.Add leaf node size-ipv6 at configuration/sqa/tests/test/icmp/ip-addr-family/ipv6.
12.Move size node at configuration/sqa/tests/test/icmpjitter to configuration/sqa/tests/test/icmpjitter/ip-addr-family/ipv4.
13.Add leaf node size-ipv6 at configuration/sqa/tests/test/icmpjitter/ip-addr-family/ipv6.' ;
  }

  revision 2020-07-16 {
    description '1.Obsolete sqa:state/sqa/light-twamp-result.
2.Add sqa:state/sqa/light-twamp-results/light-twamp-result.' ;
  }

  revision 2020-06-16 {
    description '1.Modify range and description for configuration/sqa/tests/test/ftp/encrypted-password.
2.Modify range and description for configuration/sqa/tests/test/snmp/encrypted-community.' ;
  }

  revision 2020-04-08 {
    description '1.Add choice ip-addr-family at configuration/sqa/tests/test/proactive-ping.
2.Add leaf node destination-ipv6 at configuration/sqa/tests/test/proactive-ping.
3.Add leaf node source-ipv6 at configuration/sqa/tests/test/proactive-ping.
4.Add leaf node nexthop-address-ipv6 at configuration/sqa/tests/test/proactive-ping.
5.Add case ipv4 that contains leaves of source-ip,destination-ip and nexthop-address at the choice of configuration/sqa/tests/test/proactive-ping/ip-addr-family. 
6.Add case ipv6 that contains leaves of source-ipv6,destination-ipv6 and nexthop-address-ipv6 at the choice of configuration/sqa/tests/test/proactive-ping/ip-addr-family.' ;
  }

  revision 2020-03-18 {
    description '1.Add leaf node destination-ipv6 at state/sqa/icmp-results/icmp-result.
2.Modify the description of state/sqa/icmp-results/icmp-result/destination-ip.
3.Add leaf node destination-ipv6 at state/sqa/udp-results/udp-result.
4.Modify the description of state/sqa/udp-results/udp-result/destination-ip.
5.Add leaf node destination-ipv6 at state/sqa/tcp-results/tcp-result.
6.Modify the description of state/sqa/tcp-results/tcp-result/destination-ip.
7.Add leaf node destination-ipv6 at state/sqa/udpjitter-results/udpjitter-result.
8.Modify the description of state/sqa/udpjitter-results/udpjitter-result/destination-ip.
9.Add leaf node destination-ipv6 at icmp-event/icmp-result.
10.Modify the description of icmp-event/icmp-result/destination-ip.
11.Add leaf node destination-ipv6 at udp-event/udp-result.
12.Modify the description of udp-event/udp-result/destination-ip.
13.Add leaf node destination-ipv6 at tcp-event/tcp-result.
14.Modify the description of tcp-event/tcp-result/destination-ip.
15.Add leaf node destination-ipv6 at udpjitter-event/udpjitter-result.
16.Modify the description of udpjitter-event/udpjitter-result/destination-ip.' ;
  }

  revision 2020-02-18 {
    description '1.Add project label switch99 in the feature of policy-loop.
2.Add choice ip-addr-family at configuration/sqa/tests/test/icmp.
3.Add leaf node destination-ipv6 at configuration/sqa/tests/test/icmp.
4.Add leaf node source-ipv6 at configuration/sqa/tests/test/icmp.
5.Add case ipv4 that contains leaves of destination-ip and source-ip at the choice of configuration/sqa/tests/test/icmp/ip-addr-family. 
6.Add case ipv6 that contains leaves of destination-ipv6 and source-ipv6 at the choice of configuration/sqa/tests/test/icmp/ip-addr-family.
7.Add choice ip-addr-family at configuration/sqa/tests/test/udp.
8.Add leaf node destination-ipv6 at configuration/sqa/tests/test/udp.
9.Add case ipv4 that contains leaves of destination-ip at the choice of configuration/sqa/tests/test/udp/ip-addr-family. 
10.Add case ipv6 that contains leaves of destination-ipv6 at the choice of configuration/sqa/tests/test/udp/ip-addr-family.
11.Add choice ip-addr-family at configuration/sqa/tests/test/tcp.
12.Add leaf node destination-ipv6 at configuration/sqa/tests/test/tcp.
13.Add case ipv4 that contains leaves of destination-ip at the choice of configuration/sqa/tests/test/tcp/ip-addr-family. 
14.Add case ipv6 that contains leaves of destination-ipv6 at the choice of configuration/sqa/tests/test/tcp/ip-addr-family.
15.Add choice ip-addr-family at configuration/sqa/tests/test/udpjitter.
16.Add leaf node destination-ipv6 at configuration/sqa/tests/test/udpjitter.
17.Add case ipv4 that contains leaves of destination-ip at the choice of configuration/sqa/tests/test/udpjitter/ip-addr-family. 
18.Add case ipv6 that contains leaves of destination-ipv6 at the choice of configuration/sqa/tests/test/udpjitter/ip-addr-family.' ;
  }

  revision 2019-11-27 {
    description '1 Add leaf node of configuration/sqa/tests/test/test-type/proactive-ping/proactive-ping/pattern.' ;
  }

  revision 2019-08-23 {
    description '1.Add a enumeration value of state/sqa/twamp-reflector-informations/twamp-reflector-information/test-mode.' ;
  }

  revision 2019-07-22 {
    description '1.Add configuration/sqa/tests/test/light-twamp/light-twamp/vrf-name.' ;
  }

  revision 2019-06-24 {
    description '1.Add state/sqa/light-twamp-result.' ;
  }

  revision 2019-06-17 {
    description '1.Modify length and description for configuration/sqa/tests/test/ftp/password/password.
2.Modify length and description for configuration/sqa/tests/test/ftp/encrypted-password/encrypted-password.' ;
  }

  revision 2019-05-17 {
    description '1.Add feature delay-statistics-mode.
2.Add configuration/sqa/tests/test/light-twamp/light-twamp/delay-statistics-mode.' ;
  }

  revision 2019-04-30 {
    description '1.Add feature ipv6-address, nd-na-status and nd-na-interval.
2.Add choice configuration/sqa/tests/test/generalflow/generalflow/ipv4-or-ipv6.
3.Add case configuration/sqa/tests/test/generalflow/generalflow/ipv4-or-ipv6/ipv4 that contains leaves of source-ip and destination-ip. 
4.Add case configuration/sqa/tests/test/generalflow/generalflow/ipv4-or-ipv6/ipv6 that contains leaves of source-ipv6 and destination-ipv6.
5.Add configuration/sqa/tests/test/generalflow/generalflow/nd-na-status.
6.Add configuration/sqa/tests/test/generalflow/generalflow/nd-na-interval.
7.Add choice configuration/sqa/tests/test/light-twamp/light-twamp/ipv4-or-ipv6.
8.Add case configuration/sqa/tests/test/light-twamp/light-twamp/ipv4-or-ipv6/ipv4 that contains leaves of source-ip and destination-ip.
9.Add case configuration/sqa/tests/test/light-twamp/light-twamp/ipv4-or-ipv6/ipv6 that contains leaves of source-ipv6 and destination-ipv6.
10.Add configuration/sqa/tests/test/light-twamp/light-twamp/nd-na-status.
11.Add configuration/sqa/tests/test/light-twamp/light-twamp/nd-na-interval.
12.Add choice configuration/sqa/reflectors/reflector/ipv4-or-ipv6.
13.Add case configuration/sqa/reflectors/reflector/ipv4-or-ipv6/ipv4 that contains leaves of source-ip and destination-ip.
14.Add case configuration/sqa/reflectors/reflector/ipv4-or-ipv6/ipv6 that contains leaves of source-ipv6 and destination-ipv6.
15.Add configuration/sqa/reflector-nd-nas/reflector-nd-na and the leaves.
16.Add choice configuration/sqa/twamp-reflectors/twamp-reflector/ipv4-or-ipv6.
17.Add case configuration/sqa/twamp-reflectors/twamp-reflector/ipv4-or-ipv6/ipv4 that contains leaves of source-ip and destination-ip.
18.Add case configuration/sqa/twamp-reflectors/twamp-reflector/ipv4-or-ipv6/ipv6 that contains leaves of source-ipv6 and destination-ipv6.' ;
  }

  revision 2019-04-02 {
    description '1 Modify the upper limit for configuration/sqa/tests/test/test-type/light-twamp/light-twamp/padding-length which depends on the device.' ;
  }

  revision 2019-01-05 {
    description '1.Add feature vrf-name.
2.Add configuration/sqa/twamp-reflectors/twamp-reflector/vrf-name.
3.Change the configuration/sqa/twamp-reflectors/twamp-reflector/inbound-interface from mandatory to optional.
4.Modify range and description for configuration/sqa/tests/test/light-twamp/source-port.
5.Modify range and description for configuration/sqa/tests/test/light-twamp/destination-port.
6.Modify range and description for configuration/sqa/twamp-reflectors/twamp-reflector/source-port. 
7.Modify range and description for configuration/sqa/twamp-reflectors/twamp-reflector/destination-port.
8.Change the configuration/sqa/tests/test/generalflow/y1564/cir from mandatory to optional.
9.Change the configuration/sqa/tests/test/generalflow/y1564/eir from mandatory to optional.
10.Change the configuration/sqa/tests/test/generalflow/y1564/overload from mandatory to optional.
11.Remove the presence feature of configuration/sqa/tests/test/generalflow/y1564.' ;
  }

  revision 2018-10-17 {
    description '1.Add configuration/sqa/tests/test/generalflow/generalflow/y1564.
2.Add y1564-event notification.' ;
  }

  revision 2018-05-03 {
    description '1.Modify range for configuration/sqa/tests/test/test-type/generalflow/generalflow/packet-size/size.
2.Modify range for configuration/sqa/tests/test/test-type/generalflow/generalflow/throughput/one-rate/rate.
3.Modify range for configuration/sqa/tests/test/test-type/generalflow/generalflow/throughput/two-rate/low-rate/rate.
4.Modify range for configuration/sqa/tests/test/test-type/generalflow/generalflow/throughput/two-rate/high-rate/rate.
5.Modify range for configuration/sqa/tests/test/test-type/generalflow/generalflow/loss/rate.
6.Modify range for configuration/sqa/tests/test/test-type/generalflow/generalflow/delay/rate.
7.Add configuration/sqa/tests/test/test-type/light-twamp/packet-matching-mode.
8.Add configuration/sqa/tests/test/test-type/light-twamp/performance-statistics.
9.Add configuration/sqa/tests/test/test-type/proactive-ping/bind-oma-interface.
10.Add configuration/sqa/tests/test/test-type/proactive-ping/specify-interface.
11.Modify description for state/sqa/twamp-reflector-informations/twamp-reflector-information/source-port.' ;
  }

  revision 2018-03-29 {
    description 'Change the configuration/sqa/twamp-reflectors/reflector/source-port from mandatory to optional' ;
  }

  revision 2017-10-18 {
    description 'Modify default for configuration/sqa/twamp-reflectors/reflector/ageing-time' ;
  }

  revision 2017-09-05 {
    description 'Add configuration/sqa/tests/test/test-type/light-twamp/interval-unit.
Add configuration/sqa/tests/test/test-type/light-twamp/statistics-interval.
Add configuration/sqa/tests/test/test-type/light-twamp/timeout.
Add feature interval-unit.
Add feature statistics-interval.
Add feature timeout.' ;
  }

  revision 2017-08-15 {
    description 'Add configuration/sqa/tests/test/test-type/proactive-ping.
Add configuration/sqa/tests/test/test-type/generalflow/member-port.
Add configuration/sqa/tests/test/test-type/light-twamp/reflector-mode.
Add configuration/sqa/tests/test/test-type/light-twamp/timestamp-format.
Add configuration/sqa/twamp-reflectors/twamp-reflector/timestamp-format.
Add state/sqa/twamp-reflector-informations/twamp-reflector-information/timestamp-format.
Add feature timestamp-format.
Add feature reflector-mode.' ;
  }

  revision 2017-08-02 {
    description 'Add 59,89,5960,59-GM,89-GM,5960-GM label for policy-loop feature.' ;
  }

  revision 2017-07-07 {
    description '1 Obsolete detect-path node of general flow test.
2 Obsolete vrf-name node of general flow test.' ;
  }

  revision 2017-06-14 {
    description '1 Feature policy-loop is available for 15K product.
2 Feature delay-threshold is available for 15K product.
3 Add container of configuration/sqa/tests/test/delay-threshold, and add delay-threshold-value, delay-threshold-type to this container.
4 Add container of configuration/sqa/tests/test/policy, and add loop-time node to this container.' ;
  }

  revision 2017-05-10 {
    description '1 Feature detect-path is available for 15K product.
2 Feature vrf-sqa is available for 15K product.' ;
  }

  revision 2017-03-03 {
    description '1.Add configuration/sqa/tests/test/generalflow/generalflow/detect-path.
2.Add configuration/sqa/tests/test/generalflow/generalflow/vrf-name.' ;
  }

  revision 2016-08-19 {
    description '1.Modify range for configuration/sqa/tests/test/test-type/generalflow/generalflow/delay/rate.
2.Modify range for configuration/sqa/tests/test/test-type/generalflow/generalflow/loss/duration.' ;
  }

  revision 2016-07-04 {
    description '1.Add configuration/sqa/tests/test/generalflow/generalflow/source-port.
2.Add configuration/sqa/tests/test/generalflow/generalflow/destination-port.' ;
  }

  revision 2016-02-27 {
    description '1.Add configuration/sqa/tests/test/light-twamp.
2.Add configuration/sqa/twamp-reflectors.
3.Add state/sqa/twamp-reflector-informations.
4.Add lighttwamp-event notification.' ;
  }

  revision 2016-02-26 {
    description '1.Modify range for configuration/sqa/tests/test/test-type/generalflow/generalflow/throughput/one-or-two-rate/one-rate/one-rate/rate.' ;
  }

  revision 2016-02-15 {
    description '1.Add Presence and OperationChangeType for configuration/sqa/tests/test/test-type/generalflow/throughput.
2.Add Presence and OperationChangeType for configuration/sqa/tests/test/test-type/generalflow/loss.
3.Add Presence and OperationChangeType for configuration/sqa/tests/test/test-type/generalflow/delay.' ;
  }

  revision 2015-11-24 {
    description '1.Add throughput-event,loss-event,delay-event.
2.Add configuration/sqa/tests/test/generalflow.
3.Add state/sqa/reflector-information.
4.Add configuration/sqa/reflector and configuration/sqa/reflector-free-arp.
5.Modify import.' ;
  }

  revision 2015-08-20 {
    description 'Add icmp-event,udp-event,tcp-event,ftp-event,dns-event,udpjitter-event,snmp-event,http-event,icmpjitter-event notification.' ;
  }

  revision 2015-08-03 {
    description '1.Add tos node for configuration/sqa/tests/test/test-type/udp.
2.Add tos node for configuration/sqa/tests/test/test-type/udpjitter.' ;
  }

  revision 2015-05-21 {
    description '1.Modify length for configuration/sqa/tests/test/test-number.
2.Modify length for state/sqa/icmp-results/icmp-result/test-number.
3.Modify length for state/sqa/udp-results/udp-result/test-number.
4.Modify length for state/sqa/tcp-results/tcp-result/test-number.
5.Modify length for state/sqa/ftp-results/ftp-result/number.
6.Modify length for state/sqa/dns-results/dns-result/test-number.
7.Modify length for state/sqa/udpjitter-results/udpjitter-result/test-number.
8.Modify length for state/sqa/snmp-results/snmp-result/test-number.
9.Modify length for state/sqa/http-results/http-result/test-number.
10.Modify length for state/sqa/icmpjitter-results/icmpjitter-result/test-number.
11.Modify length for operation/sqa/test-operations/test-operation/test-number.
12.Delete Max-elements for configuration/sqa/tests/test.' ;
  }

  revision 2015-02-26 {
    description '1.Add destination-url node for state/sqa/dns-results/dns-result.
2.Add length and modify basetype for configuration/sqa/tests/test/udp/size.
3.Add length for modify basetype for configuration/sqa/tests/test/dns/repeat.' ;
  }

  revision 2014-12-16 {
    description 'Move vrf-name node and source-ip node from vrf container and source-ip container to another container:
1.Move vrf-name node and source-ip node from vrf container and source-ip container to ICMP container.
2.Move vrf-name node from vrf container to UDP container.
3.Move vrf-name node from vrf container to TCP container.
4.Move vrf-name node from vrf container to FTP container.
5.Move vrf-name node from vrf container to DNS container.
6.Move vrf-name node from vrf container to UDPjitter container.
7.Move vrf-name node from vrf container to SNMP container.
8.Move vrf-name node from vrf container to HTTP container.
9.Move vrf-name node and source-ip node from vrf container and source-ip container to ICMPjitter container.' ;
  }

  revision 2014-07-14 {
    description 'Add length for some nodes.
1.Add length for state/sqa/icmp-results/icmp-result/repeat-count and response-count and pkt-loss-rate and probe-time.
2.Add length for state/sqa/udp-results/udp-result/repeat-count and response-count and pkt-loss-rate and probe-time.
3.Add length for state/sqa/tcp-results/tcp-result/repeat-count and response-count and probe-time.
4.Add length for state/sqa/ftp-results/ftp-result/probe-time.
5.Add length for state/sqa/dns-results/dns-result/repeat-count and response-count and probe-time.
6.Add length for state/sqa/udpjitter-results/udpjitter-result/repeat-count and response-count and probe-time.
7.Add length for state/sqa/snmp-results/snmp-result/probe-time.
8.Add length for state/sqa/http-results/http-result/repeat-count and response-count and probe-time.
9.Add length for state/sqa/icmpjitter-results/icmpjitter-result/repeat-count and response-count and probe-time.' ;
  }

  revision 2014-04-23 {
    description "Delete the patterns of icmp's source-ip node." ;
  }

  revision 2013-11-23 {
    description 'Initial version.' ;
  }

  feature generalflow-port {
    description 'Generalflow test source or destination port config.' ;
  }

  feature detect-path {
    description 'Detect path type,including down and up(default:up).' ;
  }

  feature vrf-sqa {
    description 'Support the SQA for the VPN of layer3.' ;
  }

  feature policy-loop {
    description 'Support the cycle testing policy.' ;
  }

  feature delay-threshold {
    description 'Delay-threshold config.' ;
  }

  feature timestamp-format {
    description 'Timestamp format,including PTP and NTP(default:PTP).' ;
  }

  feature reflector-mode {
    description 'Reflector mode,including standard mode and loopback mode(default:standard mode).' ;
  }

  feature interval-unit-us {
    description 'Interval unit,including 100millisecond and 100microsecond(default:100millisecond).' ;
  }

  feature interval-unit-minute {
    description 'Interval unit,including minute.' ;
    ncd:revise-date 2025-01-21 ;
  }

  feature statistics-interval {
    description 'The value of statistics interval,ranges from 5s to 60s(default:15s).' ;
  }

  feature timeout {
    description 'The value of timeout,ranges from 1s to 10s(default:5s).' ;
  }

  feature interval-unit {
    description 'Interval unit.' ;
  }

  feature packet-matching-mode {
    description 'Packet matching mode.' ;
  }

  feature specify-interface {
    description 'Specify interface.' ;
  }

  feature bind-oma-interface {
    description 'Bind OMA interface.' ;
  }

  feature performance-statistics {
    description 'performance statistics.' ;
  }

  feature vrf-name {
    description 'The VRF name.' ;
  }

  feature ipv6-address {
    description 'The ipv6 address.' ;
  }

  feature nd-na-status {
    description 'The status of ND NA,including enable and disable(default:disable).' ;
  }

  feature nd-na-interval {
    description 'The interval of ND NA,ranges from 1s to 14400s(default:30s).' ;
  }

  feature delay-statistics-mode {
    description 'The delay statistics mode,including bidirection,unidirection and both.' ;
  }

  feature pattern {
    description 'The TLV value of proactive-ping function,from <0-9>,<a-f>or<A-F>.' ;
  }

  feature policy-frequency {
    description 'Support the cycle frequency testing policy.' ;
  }

  feature sr-policy {
    description 'SR policy support.' ;
  }

  feature delay-mode {
    description 'delay mode' ;
  }

  feature ses-measure ;

  feature te-tunnel {
    description 'TE tunnel support.' ;
  }

  feature jitter-threshold {
    description 'Jitter-threshold config.' ;
  }

  feature reflector-state-mode {
    description 'Reflector state mode.' ;
    ncd:revise-date 2021-12-06 ;
  }

  feature flex-algo {
    description 'TE flex-algo support.' ;
    ncd:revise-date 2022-01-17 ;
  }

  feature lag-mode {
    description 'LAG mode support.' ;
    ncd:revise-date 2022-02-14 ;
  }

  feature ignore-priority {
    description 'Support ignore priority.' ;
    ncd:revise-date 2022-03-28 ;
  }

  feature result-and-success-count {
    description 'Support result number , lower and upper threshold of success count for a SQA test.' ;
    ncd:revise-date 2023-08-30 ;
  }

  feature flow-policy {
    description 'Support flow policy.' ;
    ncd:revise-date 2023-10-30 ;
  }

  feature ethernet-loopback {
    description 'Support ethernet loopback.' ;
    ncd:revise-date 2024-10-16 ;
  }

  feature hqos-sensitive {
    ncd:revise-date 2024-11-11 ;
  }

  container configuration {
    description 'Configuration model info.' ;
    container sqa {
      description 'SQA instances configuration.' ;
      container ethernet-Loopbacks {
        list Ethernet-Loopback {
          leaf if-name {
            type ncd:ifname {
              length 1..31 ;

            }

            description 'Interface name.' ;
          }

          leaf mode {
            type enumeration {
              enum internal {
                value 1 ;
                description 'Internal mode.' ;
              }

            }

            description 'Loopback mode.' ;
            mandatory true ;
          }

          leaf ageing-time {
            type uint32 {
              range "0|10..172800" ;

            }

            description 'Ageing time.' ;
            units s ;
            default 300 ;
          }

          description 'Interface Ethernet loopback function configuration.' ;
          key if-name ;
        }

        description 'Interface Ethernet loopback function configuration.' ;
        if-feature ethernet-loopback ;

        ncd:revise-date 2024-10-16 ;
      }

      container global {
        description 'Configure SQA global parameters.' ;
        leaf twamp-hqos-sensitive {
          type enumeration {
            enum disable {
              value 0 ;
              description 'Disable' ;
            }

            enum enable {
              description 'Enable' ;
              value 1 ;
            }

          }

          description 'Light TWAMP HQOS sensitive status(default:disable).' ;
          default disable ;
          if-feature hqos-sensitive ;

        }

        ncd:revise-date 2024-11-11 ;
      }

      container tests {
        description 'Configure SQA test info.' ;
        list test {
          description 'Configure SQA test info.' ;
          key test-number ;
          leaf test-number {
            description 'The configuration of test number,the upper limit of this parameter depend on the device.' ;
            type uint32 {
              range 1..65535 {
                description 'The range of the test number.' ;
              }

            }

          }

          leaf description {
            description 'The configuration of test description.' ;
            type string {
              length 1..127 {
                description 'The range of description length.' ;
              }

            }

            ncd:revise-date 2021-11-17 ;
          }

          choice test-type {
            description 'Configure SQA test type.' ;
            mandatory true ;
            case icmp {
              description 'Configure ICMP test parameters.' ;
              container icmp {
                description 'Configure ICMP test parameters.' ;
                leaf vrf-name {
                  description 'The name of VRF,this string length ranges from 1 to 32.' ;
                  type string {
                    length 1..32 {
                      description 'This string length ranges from 1 to 32.' ;
                    }

                  }

                }

                choice ip-addr-family {
                  description 'Choose one from IPv4 and IPv6.' ;
                  mandatory true ;
                  case ipv4 {
                    description 'Type is IPv4.' ;
                    leaf destination-ip {
                      description 'The destination IPv4 address.' ;
                      type ncd:ipv4-address ;

                      mandatory true ;
                    }

                    leaf source-ip {
                      description 'The source IPv4 address.' ;
                      type ncd:ipv4-address ;

                    }

                    leaf size {
                      description 'The size of ICMP packet,ranges from 36bytes to 8192bytes(default:36bytes).' ;
                      type uint16 {
                        range 36..8192 {
                          description 'This parameter ranges from 36 to 8192(default:36).' ;
                        }

                      }

                      units byte ;
                      default 36 ;
                    }

                  }

                  case ipv6 {
                    description 'Type is IPv6.' ;
                    leaf destination-ipv6 {
                      description 'The destination IPv6 address.' ;
                      type ncd:ipv6-address ;

                      mandatory true ;
                    }

                    leaf source-ipv6 {
                      description 'The source IPv6 address.' ;
                      type ncd:ipv6-address ;

                    }

                    leaf size-ipv6 {
                      description 'The size of ICMPv6 packet,ranges from 64bytes to 8192bytes(default:64bytes).' ;
                      type uint16 {
                        range 64..8192 {
                          description 'This parameter ranges from 64 to 8192(default:64).' ;
                        }

                      }

                      units byte ;
                      default 64 ;
                      ncd:revise-date 2020-08-11 ;
                    }

                    ncd:revise-date 2020-02-18 ;
                  }

                }

                leaf repeat {
                  description 'The number of repeat,ranges from 1 to 65535(default:1).' ;
                  type uint16 {
                    range 1..65535 {
                      description 'This parameter ranges from 1 to 65535(default:1).' ;
                    }

                  }

                  default 1 ;
                }

                leaf interval {
                  description 'The sending period of icmp packets,ranges from 50ms to 65535ms(default:100ms).' ;
                  type uint16 {
                    range 50..65535 {
                      description 'This parameter ranges from 50 to 65535(default:100).' ;
                    }

                  }

                  units ms ;
                  default 100 ;
                }

                leaf ttl {
                  description 'The TTL value in ICMP packets,ranges from 1 to 255(default:255).' ;
                  type uint8 {
                    range 1..255 {
                      description 'This parameter ranges from 1 to 255(default:255).' ;
                    }

                  }

                  default 255 ;
                }

                choice tos-or-dscp {
                  description 'Choose one from TOS and DSCP.' ;
                  default tos ;
                  case tos {
                    description 'TOS configuration.' ;
                    container tos {
                      description 'TOS configuration.' ;
                      leaf tos {
                        description 'The TOS value in ICMP packets,ranges from 0 to 255(default:0).' ;
                        type uint16 {
                          range 0..255 {
                            description 'This parameter ranges from 0 to 255(default:0).' ;
                          }

                        }

                        default 0 ;
                      }

                    }

                  }

                  case dscp {
                    description 'DSCP configuration.' ;
                    container dscp {
                      description 'DSCP configuration.' ;
                      leaf dscp {
                        description 'The DSCP value,ranges from 0 to 63.' ;
                        type uint8 {
                          range 0..63 {
                            description 'This parameter ranges from 0 to 63.' ;
                          }

                        }

                        default 0 ;
                      }

                    }

                  }

                }

                leaf out-interface {
                  type ncd:ifname ;

                  description 'Interface name.' ;
                  ncd:revise-date 2023-06-27 ;
                }

                choice nexthop {
                  case ipv4 {
                    leaf nexthop-address {
                      type ncd:ipv4-address-none-zero ;

                      description 'Next hop IPv4 address.' ;
                    }

                    ncd:revise-date 2023-06-27 ;
                  }

                  case ipv6 {
                    leaf nexthop-address-ipv6 {
                      type ncd:ipv6-address-none-zero ;

                      description 'Next hop IPv6 address.' ;
                    }

                    ncd:revise-date 2023-06-27 ;
                  }

                  description 'Nexthop address.' ;
                }

                leaf timeout {
                  type uint16 {
                    range 1..60 ;

                  }

                  description 'Timeout in seconds.' ;
                  default 2 ;
                  ncd:revise-date 2025-02-26 ;
                }

              }

            }

            case udp {
              description 'Configure UDP test parameters.' ;
              container udp {
                description 'Configure UDP test parameters.' ;
                leaf vrf-name {
                  description 'The name of VRF,this string length ranges from 1 to 32.' ;
                  type string {
                    length 1..32 {
                      description 'This string length ranges from 1 to 32.' ;
                    }

                  }

                }

                choice ip-addr-family {
                  description 'Choose one from IPv4 and IPv6.' ;
                  mandatory true ;
                  case ipv4 {
                    description 'Type is IPv4.' ;
                    leaf source-ip {
                      description 'The source IPv4 address.' ;
                      type ncd:ipv4-address ;

                      ncd:revise-date 2021-12-31 ;
                    }

                    leaf destination-ip {
                      description 'The destination IPv4 address.' ;
                      type ncd:ipv4-address ;

                      mandatory true ;
                    }

                  }

                  case ipv6 {
                    description 'Type is IPv6.' ;
                    leaf source-ipv6 {
                      description 'The source IPv6 address.' ;
                      type ncd:ipv6-address ;

                      ncd:revise-date 2021-12-31 ;
                    }

                    leaf destination-ipv6 {
                      description 'The destination IPv6 address.' ;
                      type ncd:ipv6-address ;

                      mandatory true ;
                    }

                    ncd:revise-date 2020-02-18 ;
                  }

                }

                leaf source-port {
                  description 'The source port number,ranges from 1025 to 65535.' ;
                  type uint16 {
                    range 1025..65535 {
                      description 'This parameter ranges from 1025 to 65535.' ;
                    }

                  }

                  ncd:revise-date 2021-12-31 ;
                }

                leaf destination-port {
                  description 'The destination port number,ranges from 1025 to 65535.' ;
                  type uint16 {
                    range 1025..65535 {
                      description 'This parameter ranges from 1025 to 65535.' ;
                    }

                  }

                  mandatory true ;
                }

                leaf interval {
                  description 'The sending period of udp packets,ranges from 50ms to 2000ms(default:100ms).' ;
                  type uint16 {
                    range 50..2000 {
                      description 'This parameter ranges from 50 to 2000(default:100).' ;
                    }

                  }

                  units ms ;
                  default 100 ;
                }

                leaf repeat {
                  description 'The number of repeat,ranges from 1 to 1000(default:1).' ;
                  type uint16 {
                    range 1..1000 {
                      description 'This parameter ranges from 1 to 1000(default:1).' ;
                    }

                  }

                  default 1 ;
                }

                leaf size {
                  description 'The size of UDP packet,ranges from 50bytes to 1500bytes(default:50bytes).' ;
                  type uint16 {
                    range 50..1500 {
                      description 'This parameter ranges from 50 to 1500(default:50).' ;
                    }

                  }

                  units byte ;
                  default 50 ;
                }

                leaf tos {
                  description 'The TOS value in UDP packets,ranges from 0 to 255(default:0).' ;
                  type uint16 {
                    range 0..255 {
                      description 'This parameter ranges from 0 to 255(default:0).' ;
                    }

                  }

                  default 0 ;
                  ncd:revise-date 2015-08-03 ;
                }

                leaf ttl {
                  description 'The TTL value in packets,ranges from 1 to 255(default:255).' ;
                  type uint8 {
                    range 1..255 {
                      description 'This parameter ranges from 1 to 255(default:255).' ;
                    }

                  }

                  default 255 ;
                  ncd:revise-date 2021-12-31 ;
                }

              }

            }

            case tcp {
              description 'Configure TCP test parameters.' ;
              container tcp {
                description 'Configure TCP test parameters.' ;
                leaf vrf-name {
                  description 'The name of VRF,this string length ranges from 1 to 32.' ;
                  type string {
                    length 1..32 {
                      description 'This string length ranges from 1 to 32.' ;
                    }

                  }

                }

                choice ip-addr-family {
                  description 'Choose one from IPv4 and IPv6.' ;
                  mandatory true ;
                  case ipv4 {
                    description 'Type is IPv4.' ;
                    leaf destination-ip {
                      description 'The destination IPv4 address.' ;
                      type ncd:ipv4-address ;

                      mandatory true ;
                    }

                    leaf source-ip {
                      description 'The source IPv4 address.' ;
                      type ncd:ipv4-address-none-zero ;

                      ncd:revise-date 2021-11-12 ;
                    }

                  }

                  case ipv6 {
                    description 'Type is IPv6.' ;
                    leaf destination-ipv6 {
                      description 'The destination IPv6 address.' ;
                      type ncd:ipv6-address ;

                      mandatory true ;
                    }

                    leaf source-ipv6 {
                      description 'The source IPv6 address.' ;
                      type ncd:ipv6-address-none-zero ;

                      ncd:revise-date 2021-11-12 ;
                    }

                    ncd:revise-date 2020-02-18 ;
                  }

                }

                leaf destination-port {
                  description 'The destination port number,ranges from 1025 to 65535.' ;
                  type uint16 {
                    range 1025..65535 {
                      description 'This parameter ranges from 1025 to 65535.' ;
                    }

                  }

                  mandatory true ;
                }

                leaf interval {
                  description 'The sending period of establishing TCP link,ranges from 1000ms to 4000ms(default:1000ms).' ;
                  type uint16 {
                    range 1000..4000 {
                      description 'This parameter ranges from 1000 to 4000(default:1000).' ;
                    }

                  }

                  units ms ;
                  default 1000 ;
                }

                leaf repeat {
                  description 'The number of repeat,ranges from 1 to 200(default:1).' ;
                  type uint16 {
                    range 1..200 {
                      description 'This parameter ranges from 1 to 200(default:1).' ;
                    }

                  }

                  default 1 ;
                }

                leaf source-port {
                  description 'The source port number,ranges from 1025 to 65535.' ;
                  type uint16 {
                    range 1025..65535 {
                      description 'This parameter ranges from 1025 to 65535.' ;
                    }

                  }

                  ncd:revise-date 2021-11-12 ;
                }

              }

            }

            case ftp {
              description 'Configure FTP test parameters.' ;
              container ftp {
                description 'Configure FTP test parameters.' ;
                leaf vrf-name {
                  description 'The name of VRF,this string length ranges from 1 to 32.' ;
                  type string {
                    length 1..32 {
                      description 'This string length ranges from 1 to 32.' ;
                    }

                  }

                }

                leaf destination-ip {
                  description 'The IP address of FTP server.' ;
                  type ncd:ipv4-address ;

                  mandatory true ;
                }

                leaf filename {
                  description 'The source file name,this string length ranges from 1 to 79.' ;
                  type string {
                    length 1..79 {
                      description 'This string length ranges from 1 to 79.' ;
                    }

                  }

                  mandatory true ;
                }

                leaf root {
                  description 'The target path and file name,this string length ranges from 1 to 151.' ;
                  type string {
                    length 1..151 {
                      description 'This string length ranges from 1 to 151.' ;
                    }

                  }

                  mandatory true ;
                }

                leaf destination-port {
                  description 'The destination port number,ranges from 1 to 65535(default:21).' ;
                  type uint16 {
                    range 1..65535 {
                      description 'This parameter ranges from 1 to 65535(default:21).' ;
                    }

                  }

                  default 21 ;
                }

                leaf username {
                  description 'Configure the username of connecting to FTP server,this string length ranges from 1 to 31.' ;
                  type string {
                    length 1..31 {
                      description 'This string length ranges from 1 to 31.' ;
                    }

                  }

                  mandatory true ;
                }

                choice encrypted-or-not-encrypted {
                  description 'Choose one from password and encrypted password.' ;
                  mandatory true ;
                  case password {
                    description 'Configure the password of connecting to FTP server.' ;
                    container password {
                      description 'Configure the password of connecting to FTP server.' ;
                      leaf password {
                        description 'Configure the password of connecting to FTP server,this string length ranges from 1 to 128.' ;
                        type string {
                          length 1..128 {
                            description 'This string length ranges from 1 to 128.' ;
                          }

                        }

                        mandatory true ;
                      }

                    }

                  }

                  case encrypted-password {
                    description 'Configure the encrypted password of connecting to FTP server.' ;
                    container encrypted-password {
                      description 'Configure the encrypted password of connecting to FTP server.' ;
                      leaf encrypted-password {
                        description 'Configure the encrypted password of connecting to FTP server,this string length ranges from 1 to 236.' ;
                        type string {
                          length 1..236 {
                            description 'This string length ranges from 1 to 236.' ;
                          }

                        }

                        mandatory true ;
                      }

                    }

                  }

                }

              }

            }

            case dns {
              description 'Configure DNS test parameters.' ;
              container dns {
                description 'Configure DNS test parameters.' ;
                leaf vrf-name {
                  description 'The name of VRF,this string length ranges from 1 to 32.' ;
                  type string {
                    length 1..32 {
                      description 'This string length ranges from 1 to 32.' ;
                    }

                  }

                }

                leaf destination-url {
                  description 'Configure the domain name to be resolved,this string length ranges from 1 to 128.' ;
                  type string {
                    length 1..128 {
                      description 'This string length ranges from 1 to 128.' ;
                    }

                  }

                  mandatory true ;
                }

                leaf server-ip {
                  description 'The IP address of domain name server.' ;
                  type ncd:ipv4-address ;

                  mandatory true ;
                }

                leaf repeat {
                  description 'The number of repeat,ranges from 1 to 10(default:1).' ;
                  type uint16 {
                    range 1..10 {
                      description 'This parameter ranges from 1 to 10(default:1).' ;
                    }

                  }

                  default 1 ;
                }

              }

            }

            case udpjitter {
              description 'Configure UDP jitter test parameters.' ;
              container udpjitter {
                description 'Configure UDP jitter test parameters.' ;
                leaf vrf-name {
                  description 'The name of VRF,this string length ranges from 1 to 32.' ;
                  type string {
                    length 1..32 {
                      description 'This string length ranges from 1 to 32.' ;
                    }

                  }

                }

                choice ip-addr-family {
                  description 'Choose one from IPv4 and IPv6.' ;
                  mandatory true ;
                  case ipv4 {
                    description 'Type is IPv4.' ;
                    leaf source-ip {
                      description 'The source IPv4 address.' ;
                      type ncd:ipv4-address ;

                      ncd:revise-date 2021-12-31 ;
                    }

                    leaf destination-ip {
                      description 'The destination IPv4 address.' ;
                      type ncd:ipv4-address ;

                      mandatory true ;
                    }

                  }

                  case ipv6 {
                    description 'Type is IPv6.' ;
                    leaf source-ipv6 {
                      description 'The source IPv6 address.' ;
                      type ncd:ipv6-address ;

                      ncd:revise-date 2021-12-31 ;
                    }

                    leaf destination-ipv6 {
                      description 'The destination IPv6 address.' ;
                      type ncd:ipv6-address ;

                      mandatory true ;
                    }

                    ncd:revise-date 2020-02-18 ;
                  }

                }

                leaf source-port {
                  description 'The source port number,ranges from 1025 to 65535.' ;
                  type uint16 {
                    range 1025..65535 {
                      description 'This parameter ranges from 1025 to 65535.' ;
                    }

                  }

                  ncd:revise-date 2021-12-31 ;
                }

                leaf destination-port {
                  description 'The destination port number,ranges from 1025 to 65535.' ;
                  type uint16 {
                    range 1025..65535 {
                      description 'This parameter ranges from 1025 to 65535.' ;
                    }

                  }

                  mandatory true ;
                }

                leaf interval {
                  description 'The sending period of UDP packets,ranges from 50ms to 2000ms(default:100ms).' ;
                  type uint16 {
                    range 50..2000 {
                      description 'This parameter ranges from 50 to 2000(default:100).' ;
                    }

                  }

                  units ms ;
                  default 100 ;
                }

                leaf repeat {
                  description 'The number of repeat,ranges from 1 to 1000(default:1).' ;
                  type uint16 {
                    range 1..1000 {
                      description 'This parameter ranges from 1 to 1000(default:1).' ;
                    }

                  }

                  default 1 ;
                }

                leaf size {
                  description 'The size of UDP packet,ranges from 50bytes to 1500bytes(default:50bytes).' ;
                  type uint16 {
                    range 50..1500 {
                      description 'This parameter ranges from 50 to 1500(default:50).' ;
                    }

                  }

                  units byte ;
                  default 50 ;
                }

                leaf tos {
                  description 'The TOS value in UDP packets,ranges from 0 to 255(default:0).' ;
                  type uint16 {
                    range 0..255 {
                      description 'This parameter ranges from 0 to 255(default:0).' ;
                    }

                  }

                  default 0 ;
                  ncd:revise-date 2015-08-03 ;
                }

                leaf ttl {
                  description 'The TTL value in packets,ranges from 1 to 255(default:255).' ;
                  type uint8 {
                    range 1..255 {
                      description 'This parameter ranges from 1 to 255(default:255).' ;
                    }

                  }

                  default 255 ;
                  ncd:revise-date 2021-12-31 ;
                }

              }

            }

            case snmp {
              description 'Configure SNMP test parameters.' ;
              container snmp {
                description 'Configure SNMP test parameters.' ;
                leaf vrf-name {
                  description 'The name of VRF,this string length ranges from 1 to 32.' ;
                  type string {
                    length 1..32 {
                      description 'This string length ranges from 1 to 32.' ;
                    }

                  }

                }

                leaf destination-ip {
                  description 'The destination IP address.' ;
                  type ncd:ipv4-address ;

                  mandatory true ;
                }

                leaf destination-port {
                  description 'The destination port number,ranges from 1024 to 20000,or 161(default:161).' ;
                  type uint16 {
                    range "161|1024..20000" {
                      description 'This parameter ranges from 1024 to 20000,or 161(default:161).' ;
                    }

                  }

                  default 161 ;
                }

                choice encrypted-or-not-encrypted {
                  description 'Choose one from community and encrypted community.' ;
                  case community {
                    description 'The community in SNMP packet.' ;
                    container community {
                      description 'The community in SNMP packet.' ;
                      leaf community {
                        description 'The community in SNMP packet,this string length ranges from 1 to 32.' ;
                        type string {
                          length 1..32 {
                            description 'This string length ranges from 1 to 32.' ;
                          }

                        }

                        mandatory true ;
                      }

                    }

                  }

                  case encrypted-community {
                    description 'The encrypted community in SNMP packet.' ;
                    container encrypted-community {
                      description 'The encrypted community in SNMP packet.' ;
                      leaf encrypted-community {
                        description 'The encrypted community in SNMP packet,this string length ranges from 1 to 108.' ;
                        type string {
                          length 1..108 {
                            description 'This string length ranges from 1 to 108.' ;
                          }

                        }

                        mandatory true ;
                      }

                    }

                  }

                }

              }

            }

            case http {
              description 'Configure HTTP test parameters.' ;
              container http {
                description 'Configure HTTP test parameters.' ;
                leaf vrf-name {
                  description 'The name of VRF,this string length ranges from 1 to 32.' ;
                  type string {
                    length 1..32 {
                      description 'This string length ranges from 1 to 32.' ;
                    }

                  }

                }

                choice url-or-ip {
                  description 'Choose one from destination url and destination IP address.' ;
                  mandatory true ;
                  case destination-url {
                    description 'Configure the destination url and the IP address of DNS.' ;
                    container url {
                      description 'Configure the destination url and the IP address of DNS.' ;
                      leaf url {
                        description 'The destination domain name,this string length ranges from 1 to 128.' ;
                        type string {
                          length 1..128 {
                            description 'This string length ranges from 1 to 128.' ;
                          }

                        }

                        mandatory true ;
                      }

                      leaf dns-ip {
                        description 'The IP address of domain name server.' ;
                        type ncd:ipv4-address ;

                        mandatory true ;
                      }

                    }

                  }

                  case destination-ip {
                    description 'Configure the destination IP address.' ;
                    container ip {
                      description 'Configure the destination IP address.' ;
                      leaf ip {
                        description 'The destination IP address.' ;
                        type ncd:ipv4-address ;

                        mandatory true ;
                      }

                    }

                  }

                }

                leaf repeat {
                  description 'The number of repeat,ranges from 1 to 10(default:1).' ;
                  type uint16 {
                    range 1..10 {
                      description 'This parameter ranges from 1 to 10(default:1).' ;
                    }

                  }

                  default 1 ;
                }

              }

            }

            case icmpjitter {
              description 'Configure ICMP jitter test parameters.' ;
              container icmpjitter {
                description 'Configure ICMP jitter test parameters.' ;
                leaf vrf-name {
                  description 'The name of VRF,this string length ranges from 1 to 32.' ;
                  type string {
                    length 1..32 {
                      description 'This string length ranges from 1 to 32.' ;
                    }

                  }

                }

                choice ip-addr-family {
                  description 'Choose one from IPv4 and IPv6.' ;
                  case ipv4 {
                    description 'Type is IPv4.' ;
                    leaf destination-ip {
                      description 'The destination IPv4 address.' ;
                      type ncd:ipv4-address ;

                      mandatory true ;
                    }

                    leaf source-ip {
                      description 'The Source IPv4 address.' ;
                      type ncd:ipv4-address ;

                    }

                    leaf size {
                      description 'The size of ICMP packet,ranges from 40bytes to 8192bytes(default:40bytes).' ;
                      type uint16 {
                        range 40..8192 {
                          description 'This parameter ranges from 40 to 8192(default:40).' ;
                        }

                      }

                      units byte ;
                      default 40 ;
                    }

                  }

                  case ipv6 {
                    description 'Type is IPv6.' ;
                    leaf destination-ipv6 {
                      description 'The destination IPv6 address.' ;
                      type ncd:ipv6-address-none-zero ;

                      mandatory true ;
                    }

                    leaf source-ipv6 {
                      description 'The source IPv6 address.' ;
                      type ncd:ipv6-address-none-zero ;

                    }

                    leaf size-ipv6 {
                      description 'The size of ICMPv6 packet,ranges from 64bytes to 8192bytes(default:64bytes).' ;
                      type uint16 {
                        range 64..8192 {
                          description 'This parameter ranges from 64 to 8192(default:64).' ;
                        }

                      }

                      units byte ;
                      default 64 ;
                    }

                    ncd:revise-date 2020-08-11 ;
                  }

                }

                leaf repeat {
                  description 'The number of repeat,ranges from 1 to 65535(default:1).' ;
                  type uint16 {
                    range 1..65535 {
                      description 'This parameter ranges from 1 to 65535(default:1).' ;
                    }

                  }

                  default 1 ;
                }

                leaf interval {
                  description 'The sending period of icmp packets,ranges from 50ms to 65535ms(default:100ms).' ;
                  type uint16 {
                    range 50..65535 {
                      description 'This parameter ranges from 50 to 65535(default:100).' ;
                    }

                  }

                  units ms ;
                  default 100 ;
                }

                leaf ttl {
                  description 'The TTL value in ICMP packets,ranges from 1 to 255(default:255).' ;
                  type uint8 {
                    range 1..255 {
                      description 'This parameter ranges from 1 to 255(default:255).' ;
                    }

                  }

                  default 255 ;
                }

                choice tos-or-dscp {
                  description 'Choose one from TOS and DSCP.' ;
                  default tos ;
                  case tos {
                    description 'TOS configuration.' ;
                    container tos {
                      description 'TOS configuration.' ;
                      leaf tos {
                        description 'The TOS value in ICMP packets,ranges from 0 to 255(default:0).' ;
                        type uint16 {
                          range 0..255 {
                            description 'This parameter ranges from 0 to 255(default:0).' ;
                          }

                        }

                        default 0 ;
                      }

                    }

                  }

                  case dscp {
                    description 'DSCP configuration.' ;
                    container dscp {
                      description 'DSCP configuration.' ;
                      leaf dscp {
                        description 'The DSCP value,choose one from TOS and DSCP,ranges from 0 to 63.' ;
                        type uint8 {
                          range 0..63 {
                            description 'This parameter ranges from 0 to 63.' ;
                          }

                        }

                        default 0 ;
                      }

                    }

                  }

                }

                leaf timeout {
                  type uint16 {
                    range 1..60 ;

                  }

                  description 'Timeout in seconds.' ;
                  default 2 ;
                  ncd:revise-date 2025-02-26 ;
                }

              }

            }

            case generalflow {
              description 'Configure generalflow test parameters.' ;
              container generalflow {
                description 'Configure generalflow test parameters.' ;
                leaf reflector-mode {
                  description 'Reflector mode,including L2 mode,L3 mode and default mode(default:default mode).' ;
                  type enumeration {
                    enum l2 {
                      value 2 ;
                      description 'The reflector mode is L2.' ;
                    }

                    enum l3 {
                      value 3 ;
                      description 'The reflector mode is L3.' ;
                    }

                    enum default {
                      value 5 ;
                      description 'The reflector mode is default.' ;
                    }

                  }

                  default default ;
                }

                leaf client-mode {
                  description 'Client mode, including L2 UNI mode,L3 UNI mode and L2 bridge UNI mode.' ;
                  type enumeration {
                    enum l2-uni {
                      value 1 ;
                      description 'The client mode is L2 UNI.' ;
                    }

                    enum l3-uni {
                      value 2 ;
                      description 'The client mode is L3 UNI.' ;
                    }

                    enum l2-bridge-uni {
                      value 3 ;
                      description 'The client mode is L2 bridge UNI.' ;
                    }

                  }

                }

                leaf test-mode {
                  description 'Test mode,including online and offline.' ;
                  type enumeration {
                    enum online {
                      value 1 ;
                      description 'The mode is online.' ;
                    }

                    enum offline {
                      value 2 ;
                      description 'The mode is offline.' ;
                    }

                  }

                }

                leaf detect-path {
                  if-feature detect-path ;

                  status obsolete {
                    ncd:revise-date 2017-07-07 ;
                  }

                  description 'Detect path type,including down and up(default:up).' ;
                  type enumeration {
                    enum down {
                      value 1 ;
                      description 'Down detect.' ;
                    }

                    enum up {
                      value 2 ;
                      description 'Up detect.' ;
                    }

                  }

                  default up ;
                  ncd:revise-date 2017-03-03 ;
                }

                leaf inbound-interface {
                  description 'Interface name.' ;
                  type ncd:ifname {
                    length 1..31 {
                      description 'The range of interface name length.' ;
                    }

                  }

                }

                leaf member-port {
                  description 'Member port name.' ;
                  type ncd:ifname ;

                  ncd:revise-date 2017-08-15 ;
                }

                leaf interface-mode {
                  description 'Interface mode,including share mode,exclusive mode(default:share mode).' ;
                  type enumeration {
                    enum share {
                      value 1 ;
                      description 'The interface mode is share mode.' ;
                    }

                    enum exclusive {
                      value 2 ;
                      description 'The interface mode is exclusive mode.' ;
                    }

                  }

                  default share ;
                }

                choice ipv4-or-ipv6 {
                  description 'Choose one from ipv4 and ipv6.' ;
                  case ipv4 {
                    description 'Type is ipv4.' ;
                    leaf source-ip {
                      description 'The source IPv4 address.' ;
                      type ncd:ipv4-address-none-zero ;

                    }

                    leaf destination-ip {
                      description 'The destination IPv4 address.' ;
                      type ncd:ipv4-address-none-zero ;

                    }

                  }

                  case ipv6 {
                    description 'Type is ipv6.' ;
                    leaf source-ipv6 {
                      if-feature ipv6-address ;

                      description 'The source ipv6 address.' ;
                      type ncd:ipv6-address ;

                    }

                    leaf destination-ipv6 {
                      if-feature ipv6-address ;

                      description 'The destination ipv6 address.' ;
                      type ncd:ipv6-address ;

                    }

                    ncd:revise-date 2019-04-30 ;
                  }

                }

                leaf source-mac {
                  description 'The source MAC address.' ;
                  type ncd:mac-address-none-zero ;

                }

                leaf source-port {
                  if-feature generalflow-port ;

                  description 'The source port,ranges from 1025 to 65535(default:49184).' ;
                  type uint16 {
                    range 1025..65535 {
                      description 'The range of port number.' ;
                    }

                  }

                  default 49184 ;
                  ncd:revise-date 2016-07-04 ;
                }

                leaf destination-mac {
                  description 'The destination MAC address.' ;
                  type ncd:mac-address-none-zero ;

                }

                leaf destination-port {
                  if-feature generalflow-port ;

                  description 'The destination port,ranges from 1025 to 65535(default:7).' ;
                  type uint16 {
                    range "7|1025..65535" {
                      description 'The range of port number.' ;
                    }

                  }

                  default 7 ;
                  ncd:revise-date 2016-07-04 ;
                }

                leaf vrf-name {
                  if-feature vrf-sqa ;

                  status obsolete {
                    ncd:revise-date 2017-07-07 ;
                  }

                  description 'The VRF name,the length of this string is from 1 to 32.' ;
                  type string {
                    length 1..32 {
                      description 'The length of this string is from 1 to 32.' ;
                    }

                  }

                  ncd:revise-date 2017-03-03 ;
                }

                choice vlan-or-qinq {
                  description 'Choose one from vlan and qinq.' ;
                  case vlan {
                    description 'Vlan information.' ;
                    container vlan {
                      description 'Vlan information.' ;
                      presence "vlan ID" ;
                      leaf id {
                        description 'The value of vlan ID,ranges from 1 to 4094.' ;
                        type uint16 {
                          range 1..4094 {
                            description 'The range of vlan ID.' ;
                          }

                        }

                        mandatory true ;
                      }

                    }

                  }

                  case qinq {
                    description 'Qinq information.' ;
                    container qinq {
                      description 'Qinq information.' ;
                      presence qinq ;
                      leaf internal-vlan-id {
                        description 'The value of internal vlan ID,ranges from 1 to 4094.' ;
                        type uint16 {
                          range 1..4094 {
                            description 'The range of vlan ID.' ;
                          }

                        }

                        mandatory true ;
                      }

                      leaf external-vlan-id {
                        description 'The value of external vlan ID,ranges from 1 to 4094.' ;
                        type uint16 {
                          range 1..4094 {
                            description 'The range of vlan ID.' ;
                          }

                        }

                        mandatory true ;
                      }

                    }

                  }

                }

                leaf priority-8021p {
                  description 'The value of priority-8021p,ranges from 0 to 7(default:0).' ;
                  type uint8 {
                    range 0..7 {
                      description 'The range of priority-8021p(default:0).' ;
                    }

                  }

                  default 0 ;
                }

                leaf dscp {
                  description 'The value of DSCP,ranges from 0 to 63(default:0).' ;
                  type uint8 {
                    range 0..63 {
                      description 'The range of DSCP(default:0).' ;
                    }

                  }

                  default 0 ;
                }

                leaf ignore-priority {
                  if-feature ignore-priority ;

                  description 'SQA general flow test ignore priority configuration.' ;
                  type enumeration {
                    enum enable {
                      value 1 ;
                      description 'User ignore priority' ;
                    }

                    enum disable {
                      value 0 ;
                      description 'User concern priority' ;
                    }

                  }

                  default disable ;
                  ncd:revise-date 2022-03-28 ;
                }

                leaf free-arp-status {
                  description 'The status of free ARP,including enable and disable(default:disable).' ;
                  type enumeration {
                    enum disable {
                      value 0 ;
                      description 'The status of free-arp is disable.' ;
                    }

                    enum enable {
                      value 1 ;
                      description 'The status of free-arp is enable.' ;
                    }

                  }

                  default disable ;
                }

                leaf free-arp-interval {
                  description 'The interval of free ARP,ranges from 1s to 14400s(default:30s).' ;
                  type uint32 {
                    range 1..14400 {
                      description 'The range of free-arp interval(default:30s).' ;
                    }

                  }

                  units s ;
                  default 30 ;
                }

                leaf nd-na-status {
                  if-feature nd-na-status ;

                  description 'The status of ND NA,including enable and disable(default:disable).' ;
                  type enumeration {
                    enum disable {
                      value 0 ;
                      description 'The status of ND NA is disable.' ;
                    }

                    enum enable {
                      value 1 ;
                      description 'The status of ND NA is enable.' ;
                    }

                  }

                  default disable ;
                  ncd:revise-date 2019-04-30 ;
                }

                leaf nd-na-interval {
                  if-feature nd-na-interval ;

                  description 'The interval of ND NA,ranges from 1s to 14400s(default:30s).' ;
                  type uint32 {
                    range 1..14400 {
                      description 'The range of free-arp interval(default:30s).' ;
                    }

                  }

                  units s ;
                  default 30 ;
                  ncd:revise-date 2019-04-30 ;
                }

                leaf disnontest-8021p {
                  description 'The value of discard-non-test priority-8021p in share mode,ranges from 0 to 7.' ;
                  type uint8 {
                    range 0..7 {
                      description 'The range of priority-8021p.' ;
                    }

                  }

                }

                leaf disnontest-dscp {
                  description 'The value of discard-non-test DSCP in share mode,ranges from 0 to 63.' ;
                  type uint8 {
                    range 0..63 {
                      description 'The range of DSCP.' ;
                    }

                  }

                }

                list packet-size {
                  description 'Configure the packet size.' ;
                  key size ;
                  leaf size {
                    description 'The packet size,the upper limit of this parameter depend on the device.' ;
                    type uint16 {
                      range 64..10000 {
                        description 'The range of packet size.' ;
                      }

                    }

                    units byte ;
                  }

                }

                container throughput {
                  description 'Configure throughput information.' ;
                  presence throughput ;
                  leaf status {
                    description 'The status of throughput,including enable and disable(default:disable).' ;
                    type enumeration {
                      enum disable {
                        value 0 ;
                        description 'The throughput status is disable.' ;
                      }

                      enum enable {
                        value 1 ;
                        description 'The throughput status is enable.' ;
                      }

                    }

                    default disable ;
                  }

                  leaf rate-type {
                    description 'The rate type,including information rate and ulr(default:information rate).' ;
                    type enumeration {
                      enum ir {
                        value 1 ;
                        description 'The rate type is information rate.' ;
                      }

                      enum ulr {
                        value 2 ;
                        description 'The rate type is ulr.' ;
                      }

                    }

                    default ir ;
                  }

                  choice one-or-two-rate {
                    description 'Choose one from one rate and two rate.' ;
                    case one-rate {
                      description 'One rate.' ;
                      container one-rate {
                        description 'One rate.' ;
                        presence "one rate" ;
                        leaf rate {
                          description 'The value of one rate,the upper limit of this parameter depend on the device.' ;
                          type uint32 {
                            range 2..400000000 {
                              description 'The range of rate.' ;
                            }

                          }

                          units kbps ;
                          mandatory true ;
                        }

                      }

                    }

                    case two-rate {
                      description 'Two rate.' ;
                      container two-rate {
                        description 'Two rate.' ;
                        presence "two rate" ;
                        leaf low-rate {
                          description 'The value of low rate,the upper limit of this parameter depend on the device.' ;
                          type uint32 {
                            range 1..400000000 {
                              description 'The range of rate.' ;
                            }

                          }

                          units kbps ;
                          mandatory true ;
                        }

                        leaf high-rate {
                          description 'The value of high rate,the upper limit of this parameter depend on the device.' ;
                          type uint32 {
                            range 1..400000000 {
                              description 'The range of rate.' ;
                            }

                          }

                          units kbps ;
                          mandatory true ;
                        }

                      }

                    }

                  }

                  leaf one-rate-duration {
                    description 'The duration of one rate,ranges from 1s to 60s(default:4s).' ;
                    type uint16 {
                      range 1..60 {
                        description 'The range of one rate duration(default:4s).' ;
                      }

                    }

                    units s ;
                    default 4 ;
                  }

                  leaf duration {
                    description 'The duration of one packet size,ranges from 10s to 172800s,if this value is not configured,the duration continues until the end of the test.' ;
                    type uint32 {
                      range 10..172800 {
                        description 'The range of duration.' ;
                      }

                    }

                    units s ;
                  }

                  leaf precision {
                    description 'The value of precision,ranges from 1kbps to 10000kbps(default:1000kbps).' ;
                    type uint32 {
                      range 1..10000 {
                        description 'The range of precision(default:1000kbps).' ;
                      }

                    }

                    units kbps ;
                    default 1000 ;
                  }

                  leaf timeout {
                    description 'The value of timeout,ranges from 1s to 60s(default:4s).' ;
                    type uint16 {
                      range 1..60 {
                        description 'The range of timeout(default:4s).' ;
                      }

                    }

                    units s ;
                    default 4 ;
                  }

                  leaf loss-ratio-threshold {
                    description 'The value of loss threshold,ranges from 0 to 100(default:0).' ;
                    type uint32 {
                      range 0..100 {
                        description 'The range of loss-threshold(default:0).' ;
                      }

                    }

                    default 0 ;
                  }

                }

                container loss {
                  description 'Configure loss information.' ;
                  presence loss ;
                  leaf status {
                    description 'The status of loss,including enable and disable(default:disable).' ;
                    type enumeration {
                      enum disable {
                        value 0 ;
                        description 'The loss status is disable.' ;
                      }

                      enum enable {
                        value 1 ;
                        description 'The throughput status is enable.' ;
                      }

                    }

                    default disable ;
                  }

                  leaf rate-type {
                    description 'The rate type,including information rate and ulr(default:information rate).' ;
                    type enumeration {
                      enum ir {
                        value 1 ;
                        description 'The rate type is information rate.' ;
                      }

                      enum ulr {
                        value 2 ;
                        description 'The rate type is ulr.' ;
                      }

                    }

                    default ir ;
                  }

                  leaf rate {
                    description 'The value of rate,the upper limit of this parameter depend on the device(default:1000kbps).' ;
                    type uint32 {
                      range 1..400000000 {
                        description 'The range of rate(default:1000kbps).' ;
                      }

                    }

                    units kbps ;
                    default 1000 ;
                  }

                  leaf duration {
                    description 'The value of duration,ranges from 10s to 172800s(default:60s).' ;
                    type uint32 {
                      range 10..172800 {
                        description 'The range of duration.' ;
                      }

                    }

                    units s ;
                    default 60 ;
                  }

                  leaf timeout {
                    description 'The value of timeout,ranges from 1s to 60s(default:4s).' ;
                    type uint16 {
                      range 1..60 {
                        description 'The range of timeout(default:4s).' ;
                      }

                    }

                    units s ;
                    default 4 ;
                  }

                  leaf loss-ratio-threshold {
                    description 'The value of loss-ratio-threshold,ranges from 0 to 100(default:0).' ;
                    type uint32 {
                      range 0..100 {
                        description 'the range of loss-ratio-threshold(default:0).' ;
                      }

                    }

                    default 0 ;
                  }

                }

                container delay {
                  description 'Configure delay information.' ;
                  presence delay ;
                  leaf status {
                    description 'The status of delay,including enable and disable(default:disable).' ;
                    type enumeration {
                      enum disable {
                        value 0 ;
                        description 'The delay status is disable.' ;
                      }

                      enum enable {
                        value 1 ;
                        description 'The delay status is enable.' ;
                      }

                    }

                    default disable ;
                  }

                  leaf rate-type {
                    description 'The rate type,including information rate and ulr(default:information rate).' ;
                    type enumeration {
                      enum ir {
                        value 1 ;
                        description 'The rate type is information rate.' ;
                      }

                      enum ulr {
                        value 2 ;
                        description 'The rate type is ulr.' ;
                      }

                    }

                    default ir ;
                  }

                  leaf rate {
                    description 'The value of rate,the upper limit of this parameter depend on the device(default:1000kbps).' ;
                    type uint32 {
                      range 0..400000000 {
                        description 'The range of rate(default:1000kbps).' ;
                      }

                    }

                    units kbps ;
                    default 1000 ;
                  }

                  leaf interval {
                    description 'The value of interval,ranges from 1s to 60s(default:4s).' ;
                    type uint8 {
                      range 1..60 {
                        description 'The range of interval(default:4s).' ;
                      }

                    }

                    units s ;
                    default 4 ;
                  }

                  leaf duration {
                    description 'The value of duration,ranges from 10s to 172800s(default:60s).' ;
                    type uint32 {
                      range 10..172800 {
                        description 'The range of duration(default:60s).' ;
                      }

                    }

                    units s ;
                    default 60 ;
                  }

                  leaf delay-threshold {
                    description 'The value of delay threshold,ranges from 1us to 1000000us(default:20000us).' ;
                    type uint32 {
                      range 1..1000000 {
                        description 'The range of delay-threshold(default:20000us).' ;
                      }

                    }

                    units us ;
                    default 20000 ;
                  }

                  leaf jitter-threshold {
                    description 'The value of jitter threshold,ranges from 1us to 1000000us(default:25000us).' ;
                    type uint32 {
                      range 1..1000000 {
                        description 'The range of jitter-threshold(default:25000us).' ;
                      }

                    }

                    units us ;
                    default 25000 ;
                  }

                }

                container y1564 {
                  description 'Configure Y1564 information.' ;
                  leaf status {
                    description 'The status of Y1564 test.' ;
                    type enumeration {
                      enum disable {
                        value 0 ;
                        description 'The Y1564 status is disable.' ;
                      }

                      enum enable {
                        value 1 ;
                        description 'The Y1564 status is enable.' ;
                      }

                    }

                    default disable ;
                  }

                  leaf cir {
                    description 'The value of CIR rate in Y1564 test.' ;
                    type uint32 {
                      range 1..10000000 {
                        description 'The range of cir rate(unit:kbps).' ;
                      }

                    }

                    units kbps ;
                  }

                  leaf eir {
                    description 'The value of EIR rate in Y1564 test.' ;
                    type uint32 {
                      range 0..10000000 {
                        description 'The range of eir rate(unit:kbps).' ;
                      }

                    }

                    units kbps ;
                  }

                  leaf overload {
                    description 'The value of overload rate in Y1564 test.' ;
                    type uint32 {
                      range 0..10000000 {
                        description 'The range of eir rate(unit:kbps).' ;
                      }

                    }

                    units kbps ;
                  }

                  leaf cir-test-type {
                    description 'The CIR test type of Y1564.' ;
                    type enumeration {
                      enum simple {
                        value 1 ;
                        description 'The simple CIR test type.' ;
                      }

                      enum step-load {
                        value 2 ;
                        description 'The step-load CIR test type.' ;
                      }

                    }

                    default simple ;
                  }

                  leaf interval {
                    description 'The packet interval of Y1564 delay test.' ;
                    type uint8 {
                      range 1..60 {
                        description 'The range of interval(default:4s).' ;
                      }

                    }

                    units s ;
                    default 4 ;
                  }

                  leaf duration {
                    description 'The duration of each rate in Y1564 test.' ;
                    type uint32 {
                      range 10..172800 {
                        description 'The range of duration(default:60s).' ;
                      }

                    }

                    units s ;
                    default 60 ;
                  }

                  leaf timeout {
                    description 'The value of timeout in Y1564 packet loss test.' ;
                    type uint16 {
                      range 1..60 {
                        description 'The range of timeout(default:4s).' ;
                      }

                    }

                    units s ;
                    default 4 ;
                  }

                  leaf loss-ratio-threshold {
                    description 'The value of loss-ratio-threshold(units:1/10000).' ;
                    type uint32 {
                      range 0..100 {
                        description 'The range of loss-ratio-threshold(default:0).' ;
                      }

                    }

                    default 0 ;
                  }

                  leaf delay-threshold {
                    description 'The value of delay test threshold.' ;
                    type uint32 {
                      range 1..1000000 {
                        description 'The range of delay-threshold(default:20000us).' ;
                      }

                    }

                    units us ;
                    default 20000 ;
                  }

                  leaf jitter-threshold {
                    description 'The value of jitter threshold.' ;
                    type uint32 {
                      range 1..1000000 {
                        description 'The range of jitter-threshold(default:25000us).' ;
                      }

                    }

                    units us ;
                    default 25000 ;
                  }

                  leaf test-mode {
                    description 'The test mode of Y1564.' ;
                    type enumeration {
                      enum configuration {
                        value 1 ;
                        description 'The configuration test mode.' ;
                      }

                      enum performance {
                        value 2 ;
                        description 'The performance test mode.' ;
                      }

                    }

                    default configuration ;
                  }

                  leaf ses-measure {
                    if-feature ses-measure ;

                    description 'The SES of Y1564 test.' ;
                    type enumeration {
                      enum enable {
                        value 1 ;
                        description 'The SES measure is enable.' ;
                      }

                      enum disable {
                        value 0 ;
                        description 'The SES measure is disable.' ;
                      }

                    }

                    default disable ;
                    ncd:revise-date 2021-02-18 ;
                  }

                  leaf ses-threshold {
                    if-feature ses-measure ;

                    description 'The value of SES threshold.' ;
                    type int16 {
                      range 10..80 {
                        description 'The range of ses-threshold.' ;
                      }

                    }

                    units "1/100" ;
                    default 30 ;
                    ncd:revise-date 2021-02-18 ;
                  }

                  ncd:revise-date 2018-10-17 ;
                }

              }

              ncd:revise-date 2015-11-24 ;
            }

            case light-twamp {
              description 'Configure light TWAMP test parameters.' ;
              container light-twamp {
                description 'Configure light TWAMP test parameters.' ;
                leaf client-mode {
                  description 'Client mode, including L2 UNI mode,L2 bridge UNI mode,L3 UNI mode and L3 mode.' ;
                  type enumeration {
                    enum l2-uni {
                      value 1 ;
                      description 'The client mode is L2 UNI.' ;
                    }

                    enum l3-uni {
                      value 2 ;
                      description 'The client mode is L3 UNI.' ;
                    }

                    enum l2-bridge-uni {
                      value 3 ;
                      description 'The client mode is L2 bridge UNI.' ;
                    }

                    enum l3 {
                      value 4 ;
                      description 'The client mode is L3.' ;
                    }

                    enum srv6-policy-sl {
                      value 5 ;
                      description 'The client mode is SRv6 policy SL.' ;
                    }

                    enum sr-mpls-policy-sl {
                      value 6 ;
                      description 'The client mode is SR MPLS policy SL.' ;
                    }

                    enum te-tunnel {
                      value 7 ;
                      description 'The client mode is TE tunnel.' ;
                    }

                    enum lag {
                      value 8 ;
                      description 'The client mode is LAG.' ;
                    }

                  }

                }

                leaf reflector-mode {
                  if-feature reflector-mode ;

                  description 'Reflector mode,including standard mode and loopback mode(default:standard mode).' ;
                  type enumeration {
                    enum standard {
                      value 1 ;
                      description 'Standard mode.' ;
                    }

                    enum loopback {
                      value 2 ;
                      description 'Loopback mode.' ;
                    }

                  }

                  default standard ;
                  ncd:revise-date 2017-08-15 ;
                }

                leaf test-mode {
                  description 'Test mode,including online and offline.' ;
                  type enumeration {
                    enum online {
                      value 1 ;
                      description 'The mode is online.' ;
                    }

                    enum offline {
                      value 2 ;
                      description 'The mode is offline.' ;
                    }

                  }

                }

                leaf inbound-interface {
                  description 'Interface name.' ;
                  type ncd:ifname {
                    length 1..31 {
                      description 'The range of interface name length.' ;
                    }

                  }

                }

                leaf member-port {
                  description 'Member port name.' ;
                  type ncd:ifname {
                    length 1..31 {
                      description 'The range of interface name length.' ;
                    }

                  }

                }

                choice ipv4-or-ipv6 {
                  description 'Choose one from ipv4 and ipv6.' ;
                  case ipv4 {
                    description 'Type is ipv4.' ;
                    leaf source-ip {
                      description 'The source IPv4 address.' ;
                      type ncd:ipv4-address-none-zero ;

                    }

                    leaf destination-ip {
                      description 'The destination IPv4 address.' ;
                      type ncd:ipv4-address-none-zero ;

                    }

                  }

                  case ipv6 {
                    description 'Type is ipv6.' ;
                    leaf source-ipv6 {
                      if-feature ipv6-address ;

                      description 'The source ipv6 address.' ;
                      type ncd:ipv6-address ;

                    }

                    leaf destination-ipv6 {
                      if-feature ipv6-address ;

                      description 'The destination ipv6 address.' ;
                      type ncd:ipv6-address ;

                    }

                    ncd:revise-date 2019-04-30 ;
                  }

                }

                leaf source-mac {
                  description 'The source MAC address.' ;
                  type ncd:mac-address-none-zero ;

                }

                leaf source-port {
                  description 'The source port,ranges from 1025 to 65535,or 862.' ;
                  type uint16 {
                    range "862|1025..65535" {
                      description 'The range of port number.' ;
                    }

                  }

                }

                leaf destination-mac {
                  description 'The destination MAC address.' ;
                  type ncd:mac-address-none-zero ;

                }

                leaf destination-port {
                  description 'The destination port,ranges from 1025 to 65535,or 862.' ;
                  type uint16 {
                    range "862|1025..65535" {
                      description 'The range of port number.' ;
                    }

                  }

                }

                choice vlan-or-qinq {
                  description 'Choose one from vlan and qinq.' ;
                  case vlan {
                    description 'Vlan information.' ;
                    container vlan {
                      description 'Vlan information.' ;
                      presence "vlan ID" ;
                      leaf id {
                        description 'The value of vlan ID,ranges from 1 to 4094.' ;
                        type uint16 {
                          range 1..4094 {
                            description 'The range of vlan ID.' ;
                          }

                        }

                        mandatory true ;
                      }

                    }

                  }

                  case qinq {
                    description 'Qinq information.' ;
                    container qinq {
                      description 'Qinq information.' ;
                      presence qinq ;
                      leaf internal-vlan-id {
                        description 'The value of internal vlan ID,ranges from 1 to 4094.' ;
                        type uint16 {
                          range 1..4094 {
                            description 'The range of vlan ID.' ;
                          }

                        }

                        mandatory true ;
                      }

                      leaf external-vlan-id {
                        description 'The value of external vlan ID,ranges from 1 to 4094.' ;
                        type uint16 {
                          range 1..4094 {
                            description 'The range of vlan ID.' ;
                          }

                        }

                        mandatory true ;
                      }

                    }

                  }

                }

                leaf priority-8021p {
                  description 'The value of priority-8021p,ranges from 0 to 7(default:0).' ;
                  type uint8 {
                    range 0..7 {
                      description 'The range of priority-8021p(default:0).' ;
                    }

                  }

                  default 0 ;
                }

                leaf dscp {
                  description 'The value of DSCP,ranges from 0 to 63(default:0).' ;
                  type uint8 {
                    range 0..63 {
                      description 'The range of DSCP(default:0).' ;
                    }

                  }

                  default 0 ;
                }

                leaf free-arp-status {
                  description 'The status of free ARP,including enable and disable(default:disable).' ;
                  type enumeration {
                    enum disable {
                      value 0 ;
                      description 'The status of free-arp is disable.' ;
                    }

                    enum enable {
                      value 1 ;
                      description 'The status of free-arp is enable.' ;
                    }

                  }

                  default disable ;
                }

                leaf free-arp-interval {
                  description 'The interval of free ARP,ranges from 1s to 14400s(default:30s).' ;
                  type uint32 {
                    range 1..14400 {
                      description 'The range of free-arp interval(default:30s).' ;
                    }

                  }

                  units s ;
                  default 30 ;
                }

                leaf nd-na-status {
                  if-feature nd-na-status ;

                  description 'The status of ND NA,including enable and disable(default:disable).' ;
                  type enumeration {
                    enum disable {
                      value 0 ;
                      description 'The status of ND NA is disable.' ;
                    }

                    enum enable {
                      value 1 ;
                      description 'The status of ND NA is enable.' ;
                    }

                  }

                  default disable ;
                  ncd:revise-date 2019-04-30 ;
                }

                leaf nd-na-interval {
                  if-feature nd-na-interval ;

                  description 'The interval of ND NA,ranges from 1s to 14400s(default:30s).' ;
                  type uint32 {
                    range 1..14400 {
                      description 'The range of free-arp interval(default:30s).' ;
                    }

                  }

                  units s ;
                  default 30 ;
                  ncd:revise-date 2019-04-30 ;
                }

                leaf duration {
                  description 'The value of duration,ranges from 0,10s to 86400s,0 means continuous testing(default:60s).' ;
                  type uint32 {
                    range "0|10..86400" {
                      description 'The range of duration(default:60s).' ;
                    }

                  }

                  units s ;
                  default 60 ;
                }

                leaf interval {
                  description 'The value of interval,ranges from 1 to 600 when unit is 100ms,ranges from 1 to 1000 when unit is 100us,ranges from 50 to 100000 when unit is us(default:10),ranges from 1 to 15 when unit is min.' ;
                  type uint32 {
                    range 1..100000 {
                      description 'The range of interval(default:10).' ;
                    }

                  }

                  default 10 ;
                }

                leaf padding-length {
                  description 'Padding length,the upper limit of this parameter depends on the device.(default:29bytes).' ;
                  type uint16 {
                    range 29..65535 {
                      description 'The value of this parameter ranges from 29bytes to 65535bytes(default:29bytes),the upper limit of this parameter depend on the device.' ;
                    }

                  }

                  units byte ;
                  default 29 ;
                }

                leaf report-interval {
                  description 'The report interval,ranges from 1s to 86400s.' ;
                  type uint32 {
                    range 1..86400 {
                      description 'The range of report interval.' ;
                    }

                  }

                  units s ;
                }

                leaf timestamp-format {
                  if-feature timestamp-format ;

                  description 'Timestamp format,including PTP and NTP(default:PTP).' ;
                  type enumeration {
                    enum ptp {
                      value 1 ;
                      description 'PTP format.' ;
                    }

                    enum ntp {
                      value 2 ;
                      description 'NTP format.' ;
                    }

                  }

                  default ptp ;
                  ncd:revise-date 2017-08-15 ;
                }

                leaf delay-statistics-mode {
                  if-feature delay-statistics-mode ;

                  description 'The delay statistics mode,including bidirection,unidirection and both(default:bidirection).' ;
                  type enumeration {
                    enum bidirection {
                      value 1 ;
                      description 'The delay statistics mode is bidirection.' ;
                    }

                    enum unidirection {
                      value 2 ;
                      description 'The delay statistics mode is unidirection.' ;
                    }

                    enum both {
                      value 3 ;
                      description 'The delay statistics mode is both bidirection and unidirection.' ;
                    }

                  }

                  default bidirection ;
                  ncd:revise-date 2019-05-17 ;
                }

                leaf proactive-test {
                  description 'Start or stop proactive test.' ;
                  type enumeration {
                    enum stop {
                      value 0 ;
                      description 'Stop test.' ;
                    }

                    enum start {
                      value 1 ;
                      description 'Start test.' ;
                    }

                  }

                  default stop ;
                }

                leaf statistics-interval {
                  if-feature statistics-interval ;

                  description 'The value of statistics interval,ranges from 5s to 900s(default:15s).' ;
                  type uint16 {
                    range 5..900 {
                      description 'The range of interval(default:15s).' ;
                    }

                  }

                  units s ;
                  default 15 ;
                  ncd:revise-date 2017-09-05 ;
                }

                leaf timeout {
                  if-feature timeout ;

                  description 'The value of timeout,ranges from 1s to 10s(default:5s).' ;
                  type uint16 {
                    range 1..10 {
                      description 'The range of timeout(default:5s).' ;
                    }

                  }

                  units s ;
                  default 5 ;
                  ncd:revise-date 2017-09-05 ;
                }

                container interval-unit {
                  description 'Interval unit.' ;
                  choice interval-unit {
                    description 'Interval unit.' ;
                    default unit-100millisecond ;
                    case unit-100millisecond {
                      description 'Interval unit is 100millisecond.' ;
                      leaf unit-100millisecond {
                        description 'Interval unit is 100millisecond.' ;
                        type empty ;

                      }

                    }

                    case unit-microsecond {
                      description 'Interval unit is microsecond.' ;
                      leaf unit-microsecond {
                        if-feature interval-unit-us ;

                        description 'Interval unit is microsecond.' ;
                        type empty ;

                      }

                    }

                    case unit-minute {
                      leaf unit-minute {
                        type empty ;

                        description 'Interval unit is minute.' ;
                        if-feature interval-unit-minute ;

                      }

                      description 'Interval unit is minute.' ;
                      ncd:revise-date 2025-01-21 ;
                    }

                  }

                  ncd:revise-date 2017-09-05 ;
                }

                leaf packet-matching-mode {
                  if-feature packet-matching-mode ;

                  description 'Packet matching mode,including extend mode and standard mode(default:extend mode).' ;
                  type enumeration {
                    enum extend {
                      value 1 ;
                      description 'Extend mode.' ;
                    }

                    enum standard {
                      value 2 ;
                      description 'Standard mode.' ;
                    }

                  }

                  default extend ;
                  ncd:revise-date 2018-05-03 ;
                }

                leaf performance-statistics {
                  if-feature performance-statistics ;

                  description 'performance statistics,including enable and disable(default:enable).' ;
                  type enumeration {
                    enum enable {
                      value 1 ;
                      description 'Status is enable.' ;
                    }

                    enum disable {
                      value 0 ;
                      description 'Status is disable.' ;
                    }

                  }

                  default enable ;
                  ncd:revise-date 2018-05-03 ;
                }

                leaf vrf-name {
                  if-feature vrf-name ;

                  description 'The VRF name,the length of this string is from 1 to 32.' ;
                  type string {
                    length 1..32 {
                      description 'The length of this string is from 1 to 32.' ;
                    }

                  }

                  ncd:revise-date 2019-07-22 ;
                }

                container sr-policy {
                  if-feature sr-policy ;

                  description 'Configure sr-policy parameters.' ;
                  presence sr-policy ;
                  leaf color {
                    description 'The color of policy.' ;
                    type uint32 {
                      range 1..4294967295 ;

                    }

                    mandatory true ;
                  }

                  container end-point {
                    description 'Configure end point.' ;
                    choice ip-addr-family {
                      mandatory true ;
                      case ipv4 {
                        description 'Type of IPv4 address.' ;
                        leaf end-point-v4 {
                          description 'The ipv4 address of end-point.' ;
                          type ncd:ipv4-address-none-zero ;

                          mandatory true ;
                        }

                      }

                      case ipv6 {
                        description 'Type of IPv6 address.' ;
                        leaf end-point-v6 {
                          description 'The ipv6 address of end-point.' ;
                          type ncd:ipv6-address-none-zero ;

                          mandatory true ;
                        }

                      }

                      ncd:revise-date 2021-03-31 ;
                    }

                  }

                  container protocol-origin {
                    description 'Configure Protocol origin.' ;
                    choice type {
                      description 'Protocol type.' ;
                      mandatory true ;
                      case bgp {
                        description 'Protocol BGP.' ;
                        container bgp {
                          description 'Protocol BGP.' ;
                          leaf discriminator {
                            description 'BGP discriminator.' ;
                            type uint32 {
                              range 0..4294967295 ;

                            }

                            mandatory true ;
                          }

                        }

                      }

                      case configuration {
                        description 'Protocol configuration.' ;
                        container configuration {
                          description 'Protocol configuration.' ;
                          leaf discriminator {
                            description 'Configuration discriminator.' ;
                            type uint32 {
                              range 0..4294967295 ;

                            }

                            mandatory true ;
                          }

                        }

                      }

                      case pcep {
                        description 'Protocol PCEP' ;
                        container pcep {
                          description 'Protocol PCEP' ;
                          leaf originator-as-num {
                            description 'PCEP originator as num' ;
                            type uint32 {
                              range 0..4294967295 ;

                            }

                            mandatory true ;
                          }

                          choice originator-address {
                            case ipv4 {
                              description 'Type of ipv4 address' ;
                              leaf originator-addr-v4 {
                                description 'The ipv4 address of originator' ;
                                type ncd:ipv4-address-none-zero ;

                                mandatory true ;
                              }

                            }

                            case ipv6 {
                              description 'Type of ipv6 address' ;
                              leaf originator-addr-v6 {
                                description 'The ipv6 address of originator' ;
                                type ncd:ipv6-address-none-zero ;

                                mandatory true ;
                              }

                            }

                          }

                          leaf discriminator {
                            description 'PCEP discriminator' ;
                            type uint32 {
                              range 0..4294967295 ;

                            }

                            mandatory true ;
                          }

                        }

                        ncd:revise-date 2022-09-27 ;
                      }

                    }

                  }

                  leaf sl-index {
                    description 'The segment-list index.' ;
                    type uint8 {
                      range 0..255 ;

                    }

                    mandatory true ;
                  }

                  ncd:revise-date 2020-12-07 ;
                }

                leaf delay-mode {
                  if-feature delay-mode ;

                  description 'The delay mode,including accurate,average(default:average).' ;
                  type enumeration {
                    enum average {
                      value 1 ;
                      description 'The delay mode is average.' ;
                    }

                    enum accurate {
                      value 2 ;
                      description 'The delay mode is accurate.' ;
                    }

                  }

                  default average ;
                  ncd:revise-date 2020-12-24 ;
                }

                leaf tunnel-id {
                  if-feature te-tunnel ;

                  description 'TE tunnel ID.' ;
                  type uint32 {
                    range 1..65535 ;

                  }

                  ncd:revise-date 2021-03-31 ;
                }

                leaf flex-algo-id {
                  if-feature flex-algo ;

                  description 'Flex-algo ID.' ;
                  type uint8 {
                    range 128..255 ;

                  }

                  ncd:revise-date 2022-01-17 ;
                }

                leaf bind-lag-interface {
                  if-feature lag-mode ;

                  description 'LAG interface name.' ;
                  type ncd:ifname {
                    length 1..31 {
                      description 'The range of interface name length.' ;
                    }

                  }

                  ncd:revise-date 2022-02-14 ;
                }

                leaf ignore-priority {
                  if-feature ignore-priority ;

                  description 'SQA light TWAMP ignore priority configuration.' ;
                  type enumeration {
                    enum enable {
                      value 1 ;
                      description 'User ignore priority' ;
                    }

                    enum disable {
                      value 0 ;
                      description 'User concern priority' ;
                    }

                  }

                  default disable ;
                  ncd:revise-date 2022-03-28 ;
                }

                leaf report-mode {
                  description 'Telemetry reporting mode of test result.' ;
                  type enumeration {
                    enum event {
                      value 0 ;
                      description 'Event mode.' ;
                    }

                    enum period {
                      value 1 ;
                      description 'Period mode' ;
                    }

                  }

                  default event ;
                  ncd:revise-date 2022-07-04 ;
                }

                leaf template-name {
                  type string {
                    length 1..31 {
                      description 'The range of template name length.' ;
                    }

                  }

                  description 'The parameter template name of light TWAMP,the length of this string ranges from 1 to 31.' ;
                  ncd:revise-date 2023-06-20 ;
                }

                leaf flow-policy {
                  type enumeration {
                    enum in-suit {
                      value 0 ;
                      description 'The flow policy is in-suit.' ;
                    }

                    enum oam-first {
                      value 1 ;
                      description 'The flow policy is oam-first.' ;
                    }

                  }

                  default in-suit ;
                  description 'The flow policy of the test, including in-suit and oam-first(default:in-suit).' ;
                  if-feature flow-policy ;

                  ncd:revise-date 2023-10-30 ;
                }

              }

              ncd:revise-date 2016-02-17 ;
            }

            case proactive-ping {
              description 'Configure proactive PING test parameters.' ;
              container proactive-ping {
                description 'Configure proactive PING test parameters.' ;
                leaf type {
                  description 'Test type,including standard, nni and uni.' ;
                  type enumeration {
                    enum standard {
                      value 0 ;
                      description 'The type is standard.' ;
                    }

                    enum uni {
                      value 1 ;
                      description 'The type is UNI.' ;
                    }

                    enum nni {
                      value 2 ;
                      description 'The type is NNI.' ;
                    }

                  }

                  default standard ;
                }

                choice ip-addr-family {
                  description 'Choose one from ipv4 and ipv6.' ;
                  case ipv4 {
                    description 'Type is ipv4.' ;
                    leaf source-ip {
                      description 'The source IPv4 address.' ;
                      type ncd:ipv4-address-none-zero ;

                    }

                    leaf destination-ip {
                      description 'The destination IPv4 address.' ;
                      type ncd:ipv4-address-none-zero ;

                    }

                  }

                  case ipv6 {
                    description 'Type is ipv6.' ;
                    leaf source-ipv6 {
                      description 'The source IPv6 address.' ;
                      type ncd:ipv6-address-none-zero ;

                    }

                    leaf destination-ipv6 {
                      description 'The destination IPv6 address.' ;
                      type ncd:ipv6-address-none-zero ;

                    }

                    ncd:revise-date 2020-04-08 ;
                  }

                }

                choice nexthop {
                  description 'Nexthop address.' ;
                  case ipv4 {
                    description 'Type is ipv4.' ;
                    leaf nexthop-address {
                      description 'Next hop IPv4 address.' ;
                      type ncd:ipv4-address-none-zero ;

                    }

                  }

                  case ipv6 {
                    description 'Type is ipv6.' ;
                    leaf nexthop-address-ipv6 {
                      description 'Next hop IPv6 address.' ;
                      type ncd:ipv6-address-none-zero ;

                    }

                  }

                  ncd:revise-date 2021-05-25 ;
                }

                leaf vrf-name {
                  description 'The VRF name,the length of this string is from 1 to 32.' ;
                  type string {
                    length 1..32 {
                      description 'This string length ranges from 1 to 32.' ;
                    }

                  }

                }

                leaf out-interface {
                  description 'Interface name.' ;
                  type ncd:ifname {
                    length 1..31 {
                      description 'The range of interface name length.' ;
                    }

                  }

                }

                leaf dscp {
                  description 'The value of DSCP,ranges from 0 to 63(default:0).' ;
                  type uint8 {
                    range 0..63 {
                      description 'The range of DSCP(default:0).' ;
                    }

                  }

                  default 0 ;
                }

                leaf interval {
                  description 'The value of interval,ranges from 1 to 600(default:10).' ;
                  type uint32 {
                    range 1..600 {
                      description 'The range of interval(default:10).' ;
                    }

                  }

                  units 100ms ;
                  default 10 ;
                }

                leaf packet-size {
                  description 'Packet size,ranges from 36bytes to 1500bytes(default:36bytes).' ;
                  type uint16 {
                    range 36..1500 {
                      description 'The range of packet size(default:36bytes).' ;
                    }

                  }

                  units byte ;
                  default 36 ;
                }

                leaf performance-statistics-status {
                  description 'The status of performance statistics,including enable and disable(default:enable).' ;
                  type enumeration {
                    enum disable {
                      value 0 ;
                      description 'Performance statistics disable.' ;
                    }

                    enum enable {
                      value 1 ;
                      description 'Performance statistics enable.' ;
                    }

                  }

                  default enable ;
                }

                leaf proactive-test {
                  description 'Start or stop proactive test(default:stop).' ;
                  type enumeration {
                    enum stop {
                      value 0 ;
                      description 'Stop test.' ;
                    }

                    enum start {
                      value 1 ;
                      description 'Start test.' ;
                    }

                  }

                  default stop ;
                }

                leaf bind-oma-interface {
                  if-feature bind-oma-interface ;

                  description 'Bind OMA interface.' ;
                  type ncd:ifname {
                    length 1..31 {
                      description 'The range of interface name length.' ;
                    }

                  }

                  ncd:revise-date 2018-05-03 ;
                }

                leaf specify-interface {
                  if-feature specify-interface ;

                  description 'specify interface.' ;
                  type ncd:ifname {
                    length 1..31 {
                      description 'The range of interface name length.' ;
                    }

                  }

                  ncd:revise-date 2018-05-03 ;
                }

                leaf pattern {
                  if-feature pattern ;

                  description 'The pattern of proactive-ping, from <0-9>,<a-f>or<A-F>.' ;
                  type string {
                    length 4 {
                      description 'The pattern string.' ;
                    }

                  }

                  ncd:revise-date 2019-11-27 ;
                }

                leaf send-trap-interval {
                  type uint16 {
                    range 10..900 ;

                  }

                  default 30 ;
                  units s ;
                  description 'The value of send SNMP trap interval,ranges from 10s to 900s(default:30s).' ;
                  ncd:revise-date 2023-10-19 ;
                }

              }

              ncd:revise-date 2017-08-15 ;
            }

          }

          choice trap-switch {
            description 'Turn on or turn off trap function.' ;
            default disable ;
            case enable {
              description 'Turn on trap function.' ;
              container enable {
                description 'Turn on trap function.' ;
                leaf trap-percent {
                  description 'Turning on trap function,and configure trap percent.' ;
                  type uint32 {
                    range 1..100 {
                      description 'The loss ratio threshold ranges from 1 to 100.' ;
                    }

                  }

                  mandatory true ;
                }

              }

            }

            case disable {
              description 'Turn off trap function.' ;
              container disable {
                description 'Turn off trap function.' ;
                leaf disable {
                  description 'Turn off trap function.' ;
                  type empty ;

                }

              }

            }

          }

          container timing {
            description 'Start a test at certain times.' ;
            presence "use timerange to start test" ;
            leaf timerange-name {
              description 'The configuration of timerange name,this configuration can be used to start a test at certain times,this string length ranges from 1 to 31.' ;
              type string {
                length 1..31 {
                  description 'this string length ranges from 1 to 31.' ;
                }

              }

              mandatory true ;
            }

          }

          container policy {
            description 'Start a cycle test.' ;
            presence "use looptime to start test" ;
            choice type {
              description 'Configure the type of policy in continuous cycle test.' ;
              case loop-time {
                description 'The cycle test policy type is loop-time.' ;
                leaf loop-time {
                  if-feature policy-loop ;

                  description 'Configure SQA test loop-time, ranges from 1s to 86400s.' ;
                  type uint32 {
                    range 1..86400 {
                      description 'Configure SQA test loop-time, ranges from 1s to 86400s.' ;
                    }

                  }

                  mandatory true ;
                }

              }

              case frequency {
                description 'The cycle test policy type is frequency.' ;
                leaf frequency {
                  if-feature policy-frequency ;

                  description 'Configure SQA frequency of cycle test, ranges from 10s to 86400s.' ;
                  type uint32 {
                    range 10..86400 {
                      description 'Configure SQA frequency of continuous test, ranges from 10s to 86400s.' ;
                    }

                  }

                  mandatory true ;
                }

                ncd:revise-date 2020-09-07 ;
              }

            }

            ncd:revise-date 2017-06-14 ;
          }

          container delay-threshold {
            description 'Configure delay-threshold.' ;
            presence "configure delay-threshold for a test" ;
            leaf delay-threshold-value {
              if-feature delay-threshold ;

              description 'Configure delay-threshold value, ranges from 1ms to 10000ms.' ;
              type uint32 {
                range 1..10000 {
                  description 'The value of delay-threshold, ranges from 1ms to 10000ms.' ;
                }

              }

              mandatory true ;
            }

            leaf delay-threshold-type {
              if-feature delay-threshold ;

              description 'The delay-threshold type, including bidirectional, forward and reverse.' ;
              type enumeration {
                enum bidirectional {
                  value 1 ;
                  description 'Bidirectional delay.' ;
                }

                enum forward {
                  value 2 ;
                  description 'Forward delay.' ;
                }

                enum reverse {
                  value 3 ;
                  description 'Reverse delay.' ;
                }

              }

              mandatory true ;
            }

            ncd:revise-date 2017-06-14 ;
          }

          container jitter-threshold {
            if-feature jitter-threshold ;

            description 'Configure jitter-threshold.' ;
            presence "configure jitter-threshold for a test" ;
            leaf jitter-threshold-value {
              if-feature jitter-threshold ;

              description 'Configure jitter-threshold value, ranges from 1ms to 10000ms.' ;
              type uint32 {
                range 1..10000 {
                  description 'The value of jitter-threshold, ranges from 1ms to 10000ms.' ;
                }

              }

            }

            ncd:revise-date 2021-06-03 ;
          }

          container result-policy {
            leaf result-trap {
              default disable ;
              description 'Configure the switch for reporting SQA test results to SNMP trap.' ;
              type enumeration {
                enum enable {
                  value 1 ;
                  description 'Enable the result trap send function.' ;
                }

                enum disable {
                  value 0 ;
                  description 'Disable the result trap send function.' ;
                }

              }

            }

            leaf result-number {
              type uint32 {
                range 5..20 ;

              }

              default 5 ;
              description 'Configure the number of reserved SQA test results, ranges from 5 to 20.' ;
              if-feature result-and-success-count ;

            }

            description 'Configure result related parameters for a test.' ;
            container success-count {
              leaf success-count-low {
                type uint16 {
                  range 2..18 ;

                }

                mandatory true ;
                description 'Configure the low thresholds count of successful test results which is used to determine whether the final test is successful, ranges from 2 to 18.' ;
              }

              leaf success-count-high {
                type uint16 {
                  range 3..19 ;

                }

                mandatory true ;
                description 'Configure the high thresholds count of successful test results which is used to determine whether the final test is successful, ranges from 3 to 19.' ;
              }

              presence success-count ;
              description 'Configure the threshold count of successful tests to determine the final test result.' ;
              if-feature result-and-success-count ;

            }

            ncd:revise-date 2023-08-30 ;
          }

        }

      }

      container servers {
        description 'Configure SQA server info.' ;
        list server {
          description 'Configure SQA server info.' ;
          key type ;
          leaf type {
            description 'Configure SQA UDP or TCP server.' ;
            type enumeration {
              enum tcp-server {
                value 2 ;
                description 'Configure SQA TCP server.' ;
              }

              enum udp-server {
                value 9 ;
                description 'Configure SQA UDP server.' ;
              }

            }

          }

          choice ip-addr-family {
            description 'Choose one from IPv4 and IPv6.' ;
            mandatory true ;
            case ipv4 {
              description 'Type is IPv4.' ;
              leaf destination-ip {
                description 'Listening IPv4 address.' ;
                type ncd:ipv4-address ;

                mandatory true ;
              }

            }

            case ipv6 {
              description 'Type is IPv6.' ;
              leaf destination-ipv6 {
                description 'Listening IPv6 address.' ;
                type ncd:ipv6-address ;

                mandatory true ;
              }

              leaf vrf-name {
                description 'The VRF name,the length of this string is from 1 to 32.' ;
                type string {
                  length 1..32 {
                    description 'The length of this string is from 1 to 32.' ;
                  }

                }

              }

              ncd:revise-date 2020-02-18 ;
            }

          }

          leaf destination-port {
            description 'Listening port number,ranges from 1025 to 65535.' ;
            type uint16 {
              range 1025..65535 {
                description 'This parameter ranges from 1025 to 65535.' ;
              }

            }

            mandatory true ;
          }

        }

      }

      container reflectors {
        description 'Reflector information.' ;
        list reflector {
          description 'Reflector information.' ;
          key reflector-id ;
          leaf reflector-id {
            description 'Reflector ID,ranges from 1 to 65535.' ;
            type uint16 {
              range 1..65535 {
                description 'The range of reflector ID.' ;
              }

            }

          }

          leaf description {
            description 'The reflector description.' ;
            type string {
              length 1..127 {
                description 'The range of description length.' ;
              }

            }

            ncd:revise-date 2021-11-17 ;
          }

          leaf inbound-interface {
            description 'Interface name.' ;
            type ncd:ifname {
              length 1..31 {
                description 'The range of interface name length.' ;
              }

            }

            mandatory true ;
          }

          leaf reflector-mode {
            description 'Reflector mode,including L2 mode and L3 mode.' ;
            type enumeration {
              enum l2 {
                value 2 ;
                description 'The reflector mode is L2.' ;
              }

              enum l3 {
                value 3 ;
                description 'The reflector mode is L3.' ;
              }

            }

            mandatory true ;
          }

          leaf test-mode {
            description 'Test mode,including online and offline.' ;
            type enumeration {
              enum online {
                value 1 ;
                description 'The mode is online.' ;
              }

              enum offline {
                value 2 ;
                description 'The mode is offline.' ;
              }

            }

            mandatory true ;
          }

          leaf source-mac {
            description 'The source MAC address.' ;
            type ncd:mac-address-none-zero ;

          }

          choice ipv4-or-ipv6 {
            description 'Choose one from ipv4 and ipv6.' ;
            case ipv4 {
              description 'Type is ipv4.' ;
              leaf source-ip {
                description 'The source IPv4 address.' ;
                type ncd:ipv4-address-none-zero ;

              }

              leaf destination-ip {
                description 'The destination IPv4 address.' ;
                type ncd:ipv4-address-none-zero ;

              }

            }

            case ipv6 {
              description 'Type is ipv6.' ;
              leaf source-ipv6 {
                if-feature ipv6-address ;

                description 'The source IPv6 address.' ;
                type ncd:ipv6-address ;

              }

              leaf destination-ipv6 {
                if-feature ipv6-address ;

                description 'The destination IPv6 address.' ;
                type ncd:ipv6-address ;

              }

              ncd:revise-date 2019-04-30 ;
            }

          }

          leaf destination-mac {
            description 'The destination MAC address.' ;
            type ncd:mac-address-none-zero ;

          }

          leaf source-port {
            description 'The source port,ranges from 1 to 65535(default:49184).' ;
            type uint16 {
              range 1..65535 {
                description 'The range of port number(default:49184).' ;
              }

            }

            default 49184 ;
          }

          leaf destination-port {
            description 'The destination port,ranges from 1 to 65535(default:7).' ;
            type uint16 {
              range 1..65535 {
                description 'The range of port number(default:7).' ;
              }

            }

            default 7 ;
          }

          choice vlan-or-qinq {
            description 'Choose one from vlan and qinq.' ;
            case vlan {
              description 'Vlan information.' ;
              container vlan {
                description 'Vlan information.' ;
                presence "vlan ID" ;
                leaf id {
                  description 'The value of vlan ID,ranges from 1 to 4094.' ;
                  type uint16 {
                    range 1..4094 {
                      description 'The range of vlan ID.' ;
                    }

                  }

                  mandatory true ;
                }

              }

            }

            case qinq {
              description 'Qinq information.' ;
              container qinq {
                description 'Qinq information.' ;
                presence qinq ;
                leaf internal-vlan-id {
                  description 'The value of internal vlan ID,ranges from 1 to 4094.' ;
                  type uint16 {
                    range 1..4094 {
                      description 'The range of vlan ID.' ;
                    }

                  }

                  mandatory true ;
                }

                leaf external-vlan-id {
                  description 'The value of external vlan ID,ranges from 1 to 4094.' ;
                  type uint16 {
                    range 1..4094 {
                      description 'The range of vlan ID.' ;
                    }

                  }

                  mandatory true ;
                }

              }

            }

          }

          leaf priority-8021p {
            description 'The value of priority-8021p,ranges from 0 to 7(default:0).' ;
            type uint8 {
              range 0..7 {
                description 'The range of priority-8021p(default:0).' ;
              }

            }

          }

          leaf dscp {
            description 'The value of DSCP,ranges from 0 to 63(default:0).' ;
            type uint8 {
              range 0..63 {
                description 'The range of DSCP(default:0).' ;
              }

            }

          }

          choice interface-mode {
            description 'Interface mode.' ;
            default share ;
            case share {
              description 'Share mode.' ;
              container share {
                description 'Share mode.' ;
                leaf disnontest-8021p {
                  description 'The value of discard-non-test priority-8021p in share mode,ranges from 0 to 7.' ;
                  type uint8 {
                    range 0..7 {
                      description 'The range of priority-8021p.' ;
                    }

                  }

                }

                leaf disnontest-dscp {
                  description 'The value of discard-non-test DSCP in share mode,ranges from 0 to 63.' ;
                  type uint8 {
                    range 0..63 {
                      description 'The range of DSCP.' ;
                    }

                  }

                }

              }

            }

            case exclusive {
              description 'Exclusive mode.' ;
              container exclusive {
                description 'Exclusive mode.' ;
                leaf exclusive {
                  description 'Exclusive mode.' ;
                  type empty ;

                  mandatory true ;
                }

              }

            }

          }

          leaf ignore-udp-port {
            description 'Whether to ignore UDP port,including enable and disable(default:disable).' ;
            type enumeration {
              enum disable {
                value 0 ;
              }

              enum enable {
                value 1 ;
              }

            }

            default disable ;
            ncd:revise-date 2021-10-28 ;
          }

          leaf ageing-time {
            description 'The value of ageing time,ranges from 10s to 173400s(default:14400s),0 means continuous.' ;
            type uint32 {
              range "0|10..173400" {
                description 'The range is 10s to 173400s(default:14400s),0 means continuous.' ;
              }

            }

            units s ;
            default 14400 ;
          }

        }

        ncd:revise-date 2015-11-24 ;
      }

      container reflector-free-arps {
        description 'The free ARP information of reflector.' ;
        list reflector-free-arp {
          description 'The free ARP information of reflector.' ;
          key reflector-id ;
          leaf reflector-id {
            description 'Reflector ID,ranges from 1 to 65535.' ;
            type uint16 {
              range 1..65535 {
                description 'The range of reflector ID.' ;
              }

            }

          }

          leaf local-ipv4 {
            description 'The local IPv4 address.' ;
            type ncd:ipv4-address-none-zero ;

            mandatory true ;
          }

          leaf interval {
            description 'The value of interval,ranges from 1s to 14400s(default:30s).' ;
            type uint32 {
              range 1..14400 {
                description 'The range of interval(default:30s).' ;
              }

            }

            units s ;
            default 30 ;
          }

          choice vlan-or-qinq {
            description 'Choose one from vlan and qinq.' ;
            case vlan {
              description 'Vlan information.' ;
              container vlan {
                description 'Vlan information.' ;
                presence "vlan ID" ;
                leaf id {
                  description 'The value of vlan ID,ranges from 1 to 4094.' ;
                  type uint16 {
                    range 1..4094 {
                      description 'The range of vlan ID.' ;
                    }

                  }

                  mandatory true ;
                }

              }

            }

            case qinq {
              description 'Qinq information.' ;
              container qinq {
                description 'Qinq information.' ;
                presence qinq ;
                leaf internal-vlan-id {
                  description 'The value of internal vlan ID,ranges from 1 to 4094.' ;
                  type uint16 {
                    range 1..4094 {
                      description 'The range of vlan ID.' ;
                    }

                  }

                  mandatory true ;
                }

                leaf external-vlan-id {
                  description 'The value of external vlan ID,ranges from 1 to 4094.' ;
                  type uint16 {
                    range 1..4094 {
                      description 'The range of vlan ID.' ;
                    }

                  }

                  mandatory true ;
                }

              }

            }

          }

        }

        ncd:revise-date 2015-11-24 ;
      }

      container reflector-nd-nas {
        description 'The ND NA information of reflector.' ;
        list reflector-nd-na {
          description 'The ND NA information of reflector.' ;
          key reflector-id ;
          leaf reflector-id {
            description 'Reflector ID,ranges from 1 to 65535.' ;
            type uint16 {
              range 1..65535 {
                description 'The range of reflector ID.' ;
              }

            }

          }

          leaf local-ipv6 {
            if-feature ipv6-address ;

            description 'The local IPv6 address.' ;
            type ncd:ipv6-address ;

            mandatory true ;
          }

          leaf interval {
            description 'The value of interval,ranges from 1s to 14400s(default:30s).' ;
            type uint32 {
              range 1..14400 {
                description 'The range of interval(default:30s).' ;
              }

            }

            units s ;
            default 30 ;
          }

          choice vlan-or-qinq {
            description 'Choose one from vlan and qinq.' ;
            case vlan {
              description 'Vlan information.' ;
              container vlan {
                description 'Vlan information.' ;
                presence "vlan ID" ;
                leaf id {
                  description 'The value of vlan ID,ranges from 1 to 4094.' ;
                  type uint16 {
                    range 1..4094 {
                      description 'The range of vlan ID.' ;
                    }

                  }

                  mandatory true ;
                }

              }

            }

            case qinq {
              description 'Qinq information.' ;
              container qinq {
                description 'Qinq information.' ;
                presence qinq ;
                leaf internal-vlan-id {
                  description 'The value of internal vlan ID,ranges from 1 to 4094.' ;
                  type uint16 {
                    range 1..4094 {
                      description 'The range of vlan ID.' ;
                    }

                  }

                  mandatory true ;
                }

                leaf external-vlan-id {
                  description 'The value of external vlan ID,ranges from 1 to 4094.' ;
                  type uint16 {
                    range 1..4094 {
                      description 'The range of vlan ID.' ;
                    }

                  }

                  mandatory true ;
                }

              }

            }

          }

        }

        ncd:revise-date 2019-04-30 ;
      }

      container twamp-reflectors {
        description 'TWAMP reflector information.' ;
        list twamp-reflector {
          description 'TWAMP reflector information.' ;
          key reflector-id ;
          leaf reflector-id {
            description 'Reflector ID,ranges from 1 to 65535.' ;
            type uint16 {
              range 1..65535 {
                description 'The range of reflector ID.' ;
              }

            }

          }

          leaf description {
            description 'The reflector description.' ;
            type string {
              length 1..127 {
                description 'The range of description length.' ;
              }

            }

            ncd:revise-date 2021-11-17 ;
          }

          leaf inbound-interface {
            description 'Interface name.' ;
            type ncd:ifname {
              length 1..31 {
                description 'The range of interface name length.' ;
              }

            }

          }

          leaf vrf-name {
            if-feature vrf-name ;

            description 'The VRF name,the length of this string ranges from 1 to 32.' ;
            type string {
              length 1..32 {
                description 'The length of this string is from 1 to 32.' ;
              }

            }

            ncd:revise-date 2019-01-05 ;
          }

          leaf test-mode {
            description 'Test mode,including online and offline.' ;
            type enumeration {
              enum online {
                value 1 ;
                description 'The mode is online.' ;
              }

              enum offline {
                value 2 ;
                description 'The mode is offline.' ;
              }

            }

          }

          choice ipv4-or-ipv6 {
            description 'Choose one from ipv4 and ipv6.' ;
            mandatory true ;
            case ipv4 {
              description 'Type is ipv4.' ;
              leaf source-ip {
                description 'The source IPv4 address.' ;
                type ncd:ipv4-address-none-zero ;

              }

              leaf destination-ip {
                description 'The destination IPv4 address.' ;
                type ncd:ipv4-address-none-zero ;

                mandatory true ;
              }

            }

            case ipv6 {
              description 'Type is ipv6.' ;
              leaf source-ipv6 {
                if-feature ipv6-address ;

                description 'The source IPv6 address.' ;
                type ncd:ipv6-address ;

              }

              leaf destination-ipv6 {
                if-feature ipv6-address ;

                description 'The destination IPv6 address.' ;
                type ncd:ipv6-address ;

                mandatory true ;
              }

              ncd:revise-date 2019-04-30 ;
            }

          }

          leaf source-port {
            description 'The source port,ranges from 1025 to 65535,or 862.' ;
            type uint16 {
              range "862|1025..65535" {
                description 'The range of port number.' ;
              }

            }

          }

          leaf destination-port {
            description 'The destination port,ranges from 1025 to 65535,or 862.' ;
            type uint16 {
              range "862|1025..65535" {
                description 'The range of port number.' ;
              }

            }

            mandatory true ;
          }

          leaf source-mac {
            description 'The source MAC address.' ;
            type ncd:mac-address-none-zero ;

          }

          leaf destination-mac {
            description 'The destination MAC address.' ;
            type ncd:mac-address-none-zero ;

          }

          choice vlan-or-qinq {
            description 'Choose one from vlan and qinq.' ;
            case vlan {
              description 'Vlan information.' ;
              container vlan {
                description 'Vlan information.' ;
                presence "vlan ID" ;
                leaf id {
                  description 'The value of vlan ID,ranges from 1 to 4094.' ;
                  type uint16 {
                    range 1..4094 {
                      description 'The range of vlan ID.' ;
                    }

                  }

                  mandatory true ;
                }

              }

            }

            case qinq {
              description 'Qinq information.' ;
              container qinq {
                description 'Qinq information.' ;
                presence qinq ;
                leaf internal-vlan-id {
                  description 'The value of internal vlan ID,ranges from 1 to 4094.' ;
                  type uint16 {
                    range 1..4094 {
                      description 'The range of vlan ID.' ;
                    }

                  }

                  mandatory true ;
                }

                leaf external-vlan-id {
                  description 'The value of external vlan ID,ranges from 1 to 4094.' ;
                  type uint16 {
                    range 1..4094 {
                      description 'The range of vlan ID.' ;
                    }

                  }

                  mandatory true ;
                }

              }

            }

          }

          leaf priority-8021p {
            description 'The value of priority-8021p,ranges from 0 to 7.' ;
            type uint8 {
              range 0..7 {
                description 'The range of priority-8021p.' ;
              }

            }

          }

          leaf dscp {
            description 'The value of DSCP,ranges from 0 to 63.' ;
            type uint8 {
              range 0..63 {
                description 'The range of DSCP.' ;
              }

            }

          }

          leaf timestamp-format {
            if-feature timestamp-format ;

            description 'Timestamp format,including PTP and NTP(default:PTP).' ;
            type enumeration {
              enum ptp {
                value 1 ;
                description 'PTP format.' ;
              }

              enum ntp {
                value 2 ;
                description 'NTP format.' ;
              }

            }

            default ptp ;
            ncd:revise-date 2017-08-15 ;
          }

          leaf reflector-mode {
            if-feature reflector-state-mode ;

            description 'Reflector state mode,including stateful and stateless(default:stateful).' ;
            type enumeration {
              enum stateful {
                value 0 ;
                description 'Stateful mode.' ;
              }

              enum stateless {
                value 1 ;
                description 'Stateless mode.' ;
              }

            }

            default stateful ;
            ncd:revise-date 2021-12-06 ;
          }

          leaf on-lag {
            if-feature lag-mode ;

            description 'Reflector on LAG flag.' ;
            type uint8 {
              range 1 ;

            }

            ncd:revise-date 2022-02-14 ;
          }

          leaf ageing-time {
            description 'The value of ageing time,ranges from 10s to 173400s(default:0s),0 means continuous.' ;
            type uint32 {
              range "0|10..173400" {
                description 'The range is 10s to 173400s(default:0s),0 means continuous.' ;
              }

            }

            units s ;
            default 0 ;
          }

          leaf flow-policy {
            type enumeration {
              enum in-suit {
                value 0 ;
                description 'The flow policy is in-suit.' ;
              }

              enum oam-first {
                value 1 ;
                description 'The flow policy is oam-first.' ;
              }

            }

            default in-suit ;
            description 'Test flow policy of the test, including in-suit and oam-first(default: in-suit).' ;
            if-feature flow-policy ;

            ncd:revise-date 2023-10-30 ;
          }

        }

        ncd:revise-date 2016-02-17 ;
      }

      container sqa-templates {
        description 'SQA parameter template information.' ;
        list sqa-template {
          key template-name ;
          description 'SQA parameter template information.' ;
          leaf template-name {
            type string {
              length 1..31 {
                description 'The range of template name length.' ;
              }

            }

            description 'The parameter template name,the length of this string ranges from 1 to 31.' ;
          }

          choice test-type {
            description 'Configure SQA test type.' ;
            case light-twamp {
              container light-twamp {
                presence light-twamp ;
                description 'Configure light TWAMP test parameters.' ;
                leaf source-port {
                  type uint16 {
                    range "862 | 1025..65535" {
                      description 'The range of port number(default:862).' ;
                    }

                  }

                  default 862 ;
                  description 'The source port,ranges from 1025 to 65535,or 862(default:862).' ;
                }

                leaf destination-port {
                  type uint16 {
                    range "862 | 1025..65535" {
                      description 'The range of port number(default:862).' ;
                    }

                  }

                  default 862 ;
                  description 'The destination port,ranges from 1025 to 65535,or 862(default:862).' ;
                }

                leaf dscp {
                  type uint8 {
                    range 0..63 {
                      description 'The range of DSCP(default:0).' ;
                    }

                  }

                  default 0 ;
                  description 'The value of DSCP,ranges from 0 to 63(default:0).' ;
                }

                leaf priority-8021p {
                  type uint8 {
                    range 0..7 {
                      description 'The range of priority-8021p(default:0).' ;
                    }

                  }

                  default 0 ;
                  description 'The value of priority-8021p,ranges from 0 to 7(default:0).' ;
                }

                leaf report-interval {
                  type uint32 {
                    range 1..86400 {
                      description 'The range of report interval.' ;
                    }

                  }

                  units s ;
                  description 'The report interval,ranges from 1s to 86400s.' ;
                }

                leaf ignore-priority {
                  type enumeration {
                    enum enable {
                      value 1 ;
                      description 'User ignore priority.' ;
                    }

                    enum disable {
                      value 0 ;
                      description 'User concern priority.' ;
                    }

                  }

                  default disable ;
                  description 'SQA light TWAMP ignore priority configuration(default:disable).' ;
                }

                leaf performance-statistics {
                  type enumeration {
                    enum enable {
                      value 1 ;
                      description 'Status is enable.' ;
                    }

                    enum disable {
                      value 0 ;
                      description 'Status is disable.' ;
                    }

                  }

                  default enable ;
                  description 'Status of performance statistics,including enable and disable(default:enable).' ;
                }

                leaf report-mode {
                  type enumeration {
                    enum event {
                      value 0 ;
                      description 'Event mode.' ;
                    }

                    enum period {
                      value 1 ;
                      description 'Period mode.' ;
                    }

                  }

                  default event ;
                  description 'Telemetry reporting mode of test result, including event and period type(default:event type).' ;
                }

                leaf statistics-interval {
                  type uint16 {
                    range 10..900 {
                      description 'The range of interval(default:30s).' ;
                    }

                  }

                  default 30 ;
                  units s ;
                  description 'The value of statistics interval,ranges from 10s to 900s(default:30s).' ;
                }

                leaf timeout {
                  type uint16 {
                    range 1..5 {
                      description 'The range of timeout(default:5s).' ;
                    }

                  }

                  default 5 ;
                  units s ;
                  description 'The value of timeout,ranges from 1s to 5s(default:5s).' ;
                }

                leaf timestamp-format {
                  type enumeration {
                    enum ptp {
                      value 1 ;
                      description 'PTP format.' ;
                    }

                    enum ntp {
                      value 2 ;
                      description 'NTP format.' ;
                    }

                  }

                  default ptp ;
                  description 'Timestamp format,including PTP and NTP(default:PTP).' ;
                }

                leaf delay-statistics-mode {
                  type enumeration {
                    enum bidirection {
                      value 1 ;
                      description 'The delay statistics mode is bidirection.' ;
                    }

                    enum unidirection {
                      value 2 ;
                      description 'The delay statistics mode is unidirection.' ;
                    }

                    enum both {
                      value 3 ;
                      description 'The delay statistics mode is both bidirection and unidirection.' ;
                    }

                  }

                  default bidirection ;
                  description 'The delay statistics mode,including bidirection,unidirection and both(default:bidirection).' ;
                }

                leaf padding-length {
                  type uint16 {
                    range 29..65535 {
                      description 'The value of this parameter ranges from 29bytes to 65535bytes(default:29bytes),the upper limit of this parameter depend on the device.' ;
                    }

                  }

                  default 29 ;
                  units byte ;
                  description 'Padding length,the upper limit of this parameter depends on the device.(default:29bytes).' ;
                }

                choice interval {
                  case unit-100ms {
                    leaf interval-100ms {
                      type uint32 {
                        range 1..600 {
                          description 'The range of unit 100ms(default:10).' ;
                        }

                      }

                      default 10 ;
                      units 100ms ;
                      description 'The value of interval ranges from 1 to 600 when unit is 100ms(default:10).' ;
                    }

                    description 'Interval unit is 100millisecond.' ;
                  }

                  case unit-us {
                    leaf interval-us {
                      type uint32 {
                        range 50..100000 {
                          description 'The range of unit us.' ;
                        }

                      }

                      units us ;
                      description 'The value of interval ranges from  50 to 100000 when unit is us.' ;
                    }

                    description 'Interval unit is microsecond.' ;
                  }

                  default unit-100ms ;
                  description 'The packet send interval ranges from 1 to 600 when unit is 100ms,ranges from 50 to 100000 when unit is us(default:10 unit:100ms),ranges from 1 to 15 when unit is min.' ;
                  case unit-min {
                    leaf interval-min {
                      type uint32 {
                        range 1..15 {
                          description 'The range of unit min.' ;
                        }

                      }

                      description 'The value of interval ranges from 1 to 15 when unit is minute.' ;
                      units min ;
                    }

                    description 'Interval unit is minute.' ;
                    ncd:revise-date 2025-01-21 ;
                  }

                }

              }

            }

          }

        }

        ncd:revise-date 2023-06-20 ;
      }

    }

  }

  container state {
    config false ;
    description 'SQA state model Info.' ;
    container sqa {
      description 'SQA state parameters.' ;
      container ehternet-loopback-informations {
        list ehternet-loopback-information {
          description 'Ethernet loopback configuration information.' ;
          key if-name ;
          leaf if-name {
            type string {
              length 1..31 ;

            }

            description 'Interface name.' ;
          }

          leaf mode {
            type enumeration {
              enum internal {
                value 1 ;
                description 'Internal mode.' ;
              }

            }

            description 'Loopback mode.' ;
          }

          leaf status {
            type enumeration {
              enum active {
                value 1 ;
                description 'Active status' ;
              }

              enum inactive {
                description 'Inactive status ' ;
                value 0 ;
              }

            }

            description 'Ethernet loopback status.' ;
          }

          leaf ageing-time {
            type uint32 {
              range "0|10..172800" ;

            }

            description 'Ageing time.' ;
            units s ;
          }

        }

        description 'Ethernet loopback configuration information.' ;
        ncd:revise-date 2024-10-16 ;
      }

      container icmp-results {
        description 'The ICMP test result.' ;
        list icmp-result {
          description 'The ICMP test result.' ;
          key test-number ;
          leaf test-number {
            description 'The value of test index,the upper limit of this parameter depend on the device.' ;
            type uint32 {
              range 1..4294967295 {
                description 'The range of the test number.' ;
              }

            }

          }

          leaf repeat-count {
            description 'The count of sending ICMP packets.' ;
            type uint16 {
              range 1..65535 {
                description 'The count of sending ICMP packets.' ;
              }

            }

          }

          leaf response-count {
            description 'The count of receiving ICMP packets.' ;
            type uint16 {
              range 0..65535 {
                description 'The count of receiving ICMP packets.' ;
              }

            }

          }

          leaf destination-ip {
            description 'The destination IPv4 address.' ;
            type ncd:ipv4-address ;

          }

          leaf min-rtt {
            description 'The minimal value of RTT.' ;
            type uint32 ;

            units ms ;
          }

          leaf max-rtt {
            description 'The maximal value of RTT.' ;
            type uint32 ;

            units ms ;
          }

          leaf avg-rtt {
            description 'The average value of RTT.' ;
            type uint32 ;

            units ms ;
          }

          leaf sum-rtt {
            description 'The sum value of RTT.' ;
            type uint32 ;

            units ms ;
          }

          leaf min-positive-jitter {
            description 'The minimal value of positive jitter.' ;
            type uint32 ;

            units ms ;
          }

          leaf max-positive-jitter {
            description 'The maximal value of positive jitter.' ;
            type uint32 ;

            units ms ;
          }

          leaf avg-positive-jitter {
            description 'The average value of positive jitter.' ;
            type uint32 ;

            units ms ;
          }

          leaf sum-positive-jitter {
            description 'The sum value of positive jitter.' ;
            type uint32 ;

            units ms ;
          }

          leaf min-negative-jitter {
            description 'The minimal value of negative jitter.' ;
            type uint32 ;

            units ms ;
          }

          leaf max-negative-jitter {
            description 'The maximal value of negative jitter.' ;
            type uint32 ;

            units ms ;
          }

          leaf avg-negative-jitter {
            description 'The average value of negative jitter.' ;
            type uint32 ;

            units ms ;
          }

          leaf sum-negative-jitter {
            description 'The sum value of negative jitter.' ;
            type uint32 ;

            units ms ;
          }

          leaf min-jitter {
            description 'The minimal value of jitter.' ;
            type uint32 ;

            units ms ;
          }

          leaf max-jitter {
            description 'The maximal value of jitter.' ;
            type uint32 ;

            units ms ;
          }

          leaf avg-jitter {
            description 'The average value of jitter.' ;
            type uint32 ;

            units ms ;
          }

          leaf sum-jitter {
            description 'The sum value of jitter.' ;
            type uint32 ;

            units ms ;
          }

          leaf pkt-loss-rate {
            description 'The ratio of lost packets in the ICMP test.' ;
            type string {
              length 2..4 {
                description 'The range of lost packets ratio.' ;
              }

            }

          }

          leaf probe-time {
            description 'The end time of ICMP test.' ;
            type ncd:string-with-blank {
              length 19 {
                description 'The end time of ICMP test.' ;
              }

            }

          }

          leaf destination-ipv6 {
            description 'The destination IPv6 address.' ;
            type ncd:ipv6-address ;

            ncd:revise-date 2020-03-18 ;
          }

        }

      }

      container udp-results {
        description 'The UDP test result.' ;
        list udp-result {
          description 'The UDP test result.' ;
          key test-number ;
          leaf test-number {
            description 'The value of test index,the upper limit of this parameter depend on the device.' ;
            type uint32 {
              range 1..4294967295 {
                description 'The range of the test number.' ;
              }

            }

          }

          leaf repeat-count {
            description 'The count of sending UDP packets.' ;
            type uint16 {
              range 1..1000 {
                description 'The count of sending UDP packets.' ;
              }

            }

          }

          leaf response-count {
            description 'The count of receiving UDP packets.' ;
            type uint16 {
              range 0..1000 {
                description 'The count of receiving UDP packets.' ;
              }

            }

          }

          leaf destination-ip {
            description 'The destination IPv4 address.' ;
            type ncd:ipv4-address ;

          }

          leaf min-rtt {
            description 'The minimal value of RTT.' ;
            type uint32 ;

            units ms ;
          }

          leaf max-rtt {
            description 'The maximal value of RTT.' ;
            type uint32 ;

            units ms ;
          }

          leaf avg-rtt {
            description 'The average value of RTT.' ;
            type uint32 ;

            units ms ;
          }

          leaf sum-rtt {
            description 'The sum value of RTT.' ;
            type uint32 ;

            units ms ;
          }

          leaf min-positive-jitter {
            description 'The minimal value of positive jitter.' ;
            type uint32 ;

            units ms ;
          }

          leaf max-positive-jitter {
            description 'The maximal value of positive jitter.' ;
            type uint32 ;

            units ms ;
          }

          leaf avg-positive-jitter {
            description 'The average value of positive jitter.' ;
            type uint32 ;

            units ms ;
          }

          leaf sum-positive-jitter {
            description 'The sum value of positive jitter.' ;
            type uint32 ;

            units ms ;
          }

          leaf min-negative-jitter {
            description 'The minimal value of negative jitter.' ;
            type uint32 ;

            units ms ;
          }

          leaf max-negative-jitter {
            description 'The maximal value of negative jitter.' ;
            type uint32 ;

            units ms ;
          }

          leaf avg-negative-jitter {
            description 'The average value of negative jitter.' ;
            type uint32 ;

            units ms ;
          }

          leaf sum-negative-jitter {
            description 'The sum value of negative jitter.' ;
            type uint32 ;

            units ms ;
          }

          leaf min-jitter {
            description 'The minimal value of jitter.' ;
            type uint32 ;

            units ms ;
          }

          leaf max-jitter {
            description 'The maximal value of jitter.' ;
            type uint32 ;

            units ms ;
          }

          leaf avg-jitter {
            description 'The average value of jitter.' ;
            type uint32 ;

            units ms ;
          }

          leaf sum-jitter {
            description 'The sum value of jitter.' ;
            type uint32 ;

            units ms ;
          }

          leaf pkt-loss-rate {
            description 'The ratio of lost packets in the UDP test' ;
            type string {
              length 2..4 {
                description 'The range of lost packets ratio.' ;
              }

            }

          }

          leaf probe-time {
            description 'The end time of UDP test.' ;
            type ncd:string-with-blank {
              length 19 {
                description 'The end time of UDP test.' ;
              }

            }

          }

          leaf destination-ipv6 {
            description 'The destination IPv6 address.' ;
            type ncd:ipv6-address ;

            ncd:revise-date 2020-03-18 ;
          }

        }

      }

      container tcp-results {
        description 'The TCP test result.' ;
        list tcp-result {
          description 'The TCP test result.' ;
          key test-number ;
          leaf test-number {
            description 'The value of test index,the upper limit of this parameter depend on the device.' ;
            type uint32 {
              range 1..4294967295 {
                description 'The range of the test number.' ;
              }

            }

          }

          leaf repeat-count {
            description 'The count of sending link requests.' ;
            type uint16 {
              range 1..200 {
                description 'The count of sending link requests.' ;
              }

            }

          }

          leaf response-count {
            description 'The count of receiving link answer.' ;
            type uint16 {
              range 0..200 {
                description 'The count of receiving link answer.' ;
              }

            }

          }

          leaf destination-ip {
            description 'The destination IPv4 address.' ;
            type ncd:ipv4-address ;

          }

          leaf min-rtt {
            description 'The minimal time of establishing TCP link.' ;
            type uint32 ;

            units ms ;
          }

          leaf max-rtt {
            description 'The maximal time of establishing TCP link.' ;
            type uint32 ;

            units ms ;
          }

          leaf avg-rtt {
            description 'The average time of establishing TCP link.' ;
            type uint32 ;

            units ms ;
          }

          leaf sum-rtt {
            description 'The sum time of establishing TCP link.' ;
            type uint32 ;

            units ms ;
          }

          leaf probe-time {
            description 'The end time of TCP test.' ;
            type ncd:string-with-blank {
              length 19 {
                description 'The end time of TCP test.' ;
              }

            }

          }

          leaf destination-ipv6 {
            description 'The destination IPv6 address.' ;
            type ncd:ipv6-address ;

            ncd:revise-date 2020-03-18 ;
          }

        }

      }

      container ftp-results {
        description 'The FTP test result.' ;
        list ftp-result {
          description 'The FTP test result.' ;
          key test-number ;
          leaf test-number {
            description 'The value of test index,the upper limit of this parameter depend on the device.' ;
            type uint32 {
              range 1..4294967295 {
                description 'The range of the test number.' ;
              }

            }

          }

          leaf last-rtt {
            description 'The time is used to transfer this file.' ;
            type uint32 ;

            units s ;
          }

          leaf read-bytes {
            description 'The size of this file.' ;
            type uint32 ;

            units Byte ;
          }

          leaf probe-time {
            description 'The end time of FTP test.' ;
            type ncd:string-with-blank {
              length 19 {
                description 'The end time of FTP test.' ;
              }

            }

          }

        }

      }

      container dns-results {
        description 'The DNS test result.' ;
        list dns-result {
          description 'The DNS test result.' ;
          key test-number ;
          leaf test-number {
            description 'The value of test index,the upper limit of this parameter depend on the device.' ;
            type uint32 {
              range 1..4294967295 {
                description 'The range of the test number.' ;
              }

            }

          }

          leaf repeat-count {
            description 'The count of sending DNS requests.' ;
            type uint16 {
              range 1..10 {
                description 'The count of sending DNS requests.' ;
              }

            }

          }

          leaf response-count {
            description 'The count of receiving right answer.' ;
            type uint16 {
              range 0..10 {
                description 'The count of receiving right answer.' ;
              }

            }

          }

          leaf destination-url {
            description 'The destination domain name.' ;
            type string {
              length 1..128 {
                description 'The destination domain name.' ;
              }

            }

          }

          leaf resolved-ip {
            description 'The domain name was resolved to an IP address through the DNS.' ;
            type ncd:ipv4-address ;

          }

          leaf min-rtt {
            description 'The minimal time of resolving a domain name.' ;
            type uint32 ;

            units ms ;
          }

          leaf max-rtt {
            description 'The maximal time of resolving a domain name.' ;
            type uint32 ;

            units ms ;
          }

          leaf avg-rtt {
            description 'The average time of resolving a domain name.' ;
            type uint32 ;

            units ms ;
          }

          leaf sum-rtt {
            description 'The sum time of resolving a domain name.' ;
            type uint32 ;

            units ms ;
          }

          leaf probe-time {
            description 'The end time of DNS test.' ;
            type ncd:string-with-blank {
              length 19 {
                description 'The end time of DNS test.' ;
              }

            }

          }

        }

      }

      container udpjitter-results {
        description 'The UDP jitter test result.' ;
        list udpjitter-result {
          description 'The UDP jitter test result.' ;
          key test-number ;
          leaf test-number {
            description 'The value of test index,the upper limit of this parameter depend on the device.' ;
            type uint32 {
              range 1..4294967295 {
                description 'The range of the test number.' ;
              }

            }

          }

          leaf repeat-count {
            description 'The count of sending UDP packets.' ;
            type uint16 {
              range 1..1000 {
                description 'The count of sending UDP packets.' ;
              }

            }

          }

          leaf response-count {
            description 'The count of receiving UDP packets.' ;
            type uint16 {
              range 0..1000 {
                description 'The count of receiving UDP packets.' ;
              }

            }

          }

          leaf destination-ip {
            description 'The destination IPv4 address.' ;
            type ncd:ipv4-address ;

          }

          leaf min-rtt-sd {
            description 'The minimal value of delay from source to destination.' ;
            type uint32 ;

            units ms ;
          }

          leaf max-rtt-sd {
            description 'The maximal value of delay from source to destination.' ;
            type uint32 ;

            units ms ;
          }

          leaf avg-rtt-sd {
            description 'The average value of delay from source to destination.' ;
            type uint32 ;

            units ms ;
          }

          leaf sum-rtt-sd {
            description 'The sum value of delay from source to destination.' ;
            type uint32 ;

            units ms ;
          }

          leaf min-rtt-ds {
            description 'The minimal value of delay from destination to source.' ;
            type uint32 ;

            units ms ;
          }

          leaf max-rtt-ds {
            description 'The maximal value of delay from destination to source.' ;
            type uint32 ;

            units ms ;
          }

          leaf avg-rtt-ds {
            description 'The average value of delay from destination to source.' ;
            type uint32 ;

            units ms ;
          }

          leaf sum-rtt-ds {
            description 'The sum value of delay from destination to source.' ;
            type uint32 ;

            units ms ;
          }

          leaf min-positive-jitter-sd {
            description 'The minimal value of positive jitter from source to destination.' ;
            type uint32 ;

            units ms ;
          }

          leaf max-positive-jitter-sd {
            description 'The maximal value of positive jitter from source to destination.' ;
            type uint32 ;

            units ms ;
          }

          leaf avg-positive-jitter-sd {
            description 'The average value of positive jitter from source to destination.' ;
            type uint32 ;

            units ms ;
          }

          leaf sum-positive-jitter-sd {
            description 'The sum value of positive jitter from source to destination.' ;
            type uint32 ;

            units ms ;
          }

          leaf min-negative-jitter-sd {
            description 'The minimal value of negative jitter from source to destination.' ;
            type uint32 ;

            units ms ;
          }

          leaf max-negative-jitter-sd {
            description 'The maximal value of negative jitter from source to destination.' ;
            type uint32 ;

            units ms ;
          }

          leaf avg-negative-jitter-sd {
            description 'The average value of negative jitter from source to destination.' ;
            type uint32 ;

            units ms ;
          }

          leaf sum-negative-jitter-sd {
            description 'The sum value of negative jitter from source to destination.' ;
            type uint32 ;

            units ms ;
          }

          leaf min-positive-jitter-ds {
            description 'The minimal value of positive jitter from destination to source.' ;
            type uint32 ;

            units ms ;
          }

          leaf max-positive-jitter-ds {
            description 'The maximal value of positive jitter from destination to source.' ;
            type uint32 ;

            units ms ;
          }

          leaf avg-positive-jitter-ds {
            description 'The average value of positive jitter from destination to source.' ;
            type uint32 ;

            units ms ;
          }

          leaf sum-positive-jitter-ds {
            description 'The sum value of positive jitter from destination to source.' ;
            type uint32 ;

            units ms ;
          }

          leaf min-negative-jitter-ds {
            description 'The minimal value of negative jitter from destination to source.' ;
            type uint32 ;

            units ms ;
          }

          leaf max-negative-jitter-ds {
            description 'The maximal value of negative jitter from destination to source.' ;
            type uint32 ;

            units ms ;
          }

          leaf avg-negative-jitter-ds {
            description 'The average value of negative jitter from destination to source' ;
            type uint32 ;

            units ms ;
          }

          leaf sum-negative-jitter-ds {
            description 'The sum value of negative jitter from destination to source.' ;
            type uint32 ;

          }

          leaf pkt-loss-number-sd {
            description 'The number of lost packets from source to destination.' ;
            type uint16 ;

          }

          leaf pkt-loss-number-ds {
            description 'The number of lost packets from destination to source.' ;
            type uint16 ;

          }

          leaf probe-time {
            description 'The end time of UDP jitter test.' ;
            type ncd:string-with-blank {
              length 19 {
                description 'The end time of UDP jitter test.' ;
              }

            }

          }

          leaf destination-ipv6 {
            description 'The destination IPv6 address.' ;
            type ncd:ipv6-address ;

            ncd:revise-date 2020-03-18 ;
          }

        }

      }

      container snmp-results {
        description 'The SNMP test result.' ;
        list snmp-result {
          description 'The SNMP test result.' ;
          key test-number ;
          leaf test-number {
            description 'The value of test index,the upper limit of this parameter depend on the device.' ;
            type uint32 {
              range 1..4294967295 {
                description 'The range of the test number.' ;
              }

            }

          }

          leaf last-rtt {
            description 'The time required to complete this test.' ;
            type uint32 ;

            units ms ;
          }

          leaf probe-time {
            description 'The end time of SNMP test.' ;
            type ncd:string-with-blank {
              length 19 {
                description 'The end time of SNMP test.' ;
              }

            }

          }

        }

      }

      container http-results {
        description 'The HTTP test result.' ;
        list http-result {
          description 'The HTTP test result.' ;
          key test-number ;
          leaf test-number {
            description 'The value of test index,the upper limit of this parameter depend on the device.' ;
            type uint32 {
              range 1..4294967295 {
                description 'The range of the test number.' ;
              }

            }

          }

          leaf repeat-count {
            description 'The count of sending HTTP request.' ;
            type uint16 {
              range 1..10 {
                description 'The count of sending HTTP request.' ;
              }

            }

          }

          leaf response-count {
            description 'The count of receiving HTTP answer.' ;
            type uint16 {
              range 0..10 {
                description 'The count of receiving HTTP answer.' ;
              }

            }

          }

          leaf destination-ip {
            description 'The destination IP address.' ;
            type ncd:ipv4-address ;

          }

          leaf destination-url {
            description 'The destination domain name.' ;
            type string {
              length 1..128 {
                description 'The destination domain name.' ;
              }

            }

          }

          leaf min-dns-rtt {
            description 'The minimal time of resolving a domain name.' ;
            type uint32 ;

            units ms ;
          }

          leaf max-dns-rtt {
            description 'The maximal time of resolving a domain name.' ;
            type uint32 ;

            units ms ;
          }

          leaf avg-dns-rtt {
            description 'The average time of resolving a domain name.' ;
            type uint32 ;

            units ms ;
          }

          leaf sum-dns-rtt {
            description 'The sum time of resolving a domain name.' ;
            type uint32 ;

            units ms ;
          }

          leaf min-tcp-connection-rtt {
            description 'The minimal time of establishing link.' ;
            type uint32 ;

            units ms ;
          }

          leaf max-tcp-connection-rtt {
            description 'The maximal time of establishing link.' ;
            type uint32 ;

            units ms ;
          }

          leaf avg-tcp-connection-rtt {
            description 'The average time of establishing link.' ;
            type uint32 ;

            units ms ;
          }

          leaf sum-tcp-connection-rtt {
            description 'The sum time of establishing link.' ;
            type uint32 ;

            units ms ;
          }

          leaf min-http-connection-rtt {
            description 'The minimal time of completing http request.' ;
            type uint32 ;

            units ms ;
          }

          leaf max-http-connection-rtt {
            description 'The maximal time of completing http request.' ;
            type uint32 ;

            units ms ;
          }

          leaf avg-http-connection-rtt {
            description 'The average time of completing http request.' ;
            type uint32 ;

            units ms ;
          }

          leaf sum-http-connection-rtt {
            description 'The sum time of completing http request.' ;
            type uint32 ;

            units ms ;
          }

          leaf min-rtt {
            description 'The minimal time required to complete this whole test.' ;
            type uint32 ;

            units ms ;
          }

          leaf max-rtt {
            description 'The maximal time required to complete this whole test.' ;
            type uint32 ;

            units ms ;
          }

          leaf avg-rtt {
            description 'The average time required to complete this whole test.' ;
            type uint32 ;

            units ms ;
          }

          leaf sum-rtt {
            description 'The sum time required to complete this whole test.' ;
            type uint32 ;

            units ms ;
          }

          leaf probe-time {
            description 'The end time of HTTP test.' ;
            type ncd:string-with-blank {
              length 19 {
                description 'The end time of HTTP test.' ;
              }

            }

          }

        }

      }

      container icmpjitter-results {
        description 'The ICMP jitter test result.' ;
        list icmpjitter-result {
          description 'The ICMP jitter test result.' ;
          key test-number ;
          leaf test-number {
            description 'The value of test index,the upper limit of this parameter depend on the device.' ;
            type uint32 {
              range 1..4294967295 {
                description 'The range of the test number.' ;
              }

            }

          }

          leaf repeat-count {
            description 'The count of sending ICMP packets.' ;
            type uint16 {
              range 1..65535 {
                description 'The count of sending ICMP packets.' ;
              }

            }

          }

          leaf response-count {
            description 'The count of receiving ICMP packets.' ;
            type uint16 {
              range 0..65535 {
                description 'The count of receiving ICMP packets.' ;
              }

            }

          }

          leaf destination-ip {
            description 'The destination IPv4 address.' ;
            type ncd:ipv4-address ;

          }

          leaf min-rtt-sd {
            description 'The minimal value of delay from source to destination.' ;
            type uint32 ;

            units ms ;
          }

          leaf max-rtt-sd {
            description 'The maximal value of delay from source to destination.' ;
            type uint32 ;

            units ms ;
          }

          leaf avg-rtt-sd {
            description 'The average value of delay from source to destination.' ;
            type uint32 ;

            units ms ;
          }

          leaf sum-rtt-sd {
            description 'The sum value of delay from source to destination.' ;
            type uint32 ;

            units ms ;
          }

          leaf min-rtt-ds {
            description 'The minimal value of delay from destination to source.' ;
            type uint32 ;

            units ms ;
          }

          leaf max-rtt-ds {
            description 'The maximal value of delay from destination to source.' ;
            type uint32 ;

            units ms ;
          }

          leaf avg-rtt-ds {
            description 'The average value of delay from destination to source.' ;
            type uint32 ;

            units ms ;
          }

          leaf sum-rtt-ds {
            description 'The sum value of delay from destination to source.' ;
            type uint32 ;

            units ms ;
          }

          leaf min-positive-jitter-sd {
            description 'The minimal value of positive jitter from source to destination.' ;
            type uint32 ;

            units ms ;
          }

          leaf max-positive-jitter-sd {
            description 'The maximal value of positive jitter from source to destination.' ;
            type uint32 ;

            units ms ;
          }

          leaf avg-positive-jitter-sd {
            description 'The average value of positive jitter from source to destination.' ;
            type uint32 ;

            units ms ;
          }

          leaf sum-positive-jitter-sd {
            description 'The sum value of positive jitter from source to destination.' ;
            type uint32 ;

            units ms ;
          }

          leaf min-negative-jitter-sd {
            description 'The minimal value of negative jitter from source to destination.' ;
            type uint32 ;

            units ms ;
          }

          leaf max-negative-jitter-sd {
            description 'The maximal value of negative jitter from source to destination.' ;
            type uint32 ;

            units ms ;
          }

          leaf avg-negative-jitter-sd {
            description 'The average value of negative jitter from source to destination.' ;
            type uint32 ;

            units ms ;
          }

          leaf sum-negative-jitter-sd {
            description 'The sum value of negative jitter from source to destination.' ;
            type uint32 ;

            units ms ;
          }

          leaf min-positive-jitter-ds {
            description 'The minimal value of positive jitter from destination to source.' ;
            type uint32 ;

            units ms ;
          }

          leaf max-positive-jitter-ds {
            description 'The maximal value of positive jitter from destination to source.' ;
            type uint32 ;

            units ms ;
          }

          leaf avg-positive-jitter-ds {
            description 'The average value of positive jitter from destination to source.' ;
            type uint32 ;

            units ms ;
          }

          leaf sum-positive-jitter-ds {
            description 'The sum value of positive jitter from destination to source.' ;
            type uint32 ;

            units ms ;
          }

          leaf min-negative-jitter-ds {
            description 'The minimal value of negative jitter from destination to source.' ;
            type uint32 ;

            units ms ;
          }

          leaf max-negative-jitter-ds {
            description 'The maximal value of negative jitter from destination to source.' ;
            type uint32 ;

            units ms ;
          }

          leaf avg-negative-jitter-ds {
            description 'The average value of negative jitter from destination to source.' ;
            type uint32 ;

            units ms ;
          }

          leaf sum-negative-jitter-ds {
            description 'The sum value of negative jitter from destination to source.' ;
            type uint32 ;

            units ms ;
          }

          leaf probe-time {
            description 'The end time of ICMP jitter test.' ;
            type ncd:string-with-blank {
              length 19 {
                description 'The end time of ICMP jitter test.' ;
              }

            }

          }

          leaf min-rtt {
            description 'The minimum value of RTT.' ;
            type uint32 ;

            units ms ;
            ncd:revise-date 2020-08-11 ;
          }

          leaf max-rtt {
            description 'The maximum value of RTT.' ;
            type uint32 ;

            units ms ;
            ncd:revise-date 2020-08-11 ;
          }

          leaf avg-rtt {
            description 'The average value of RTT.' ;
            type uint32 ;

            units ms ;
            ncd:revise-date 2020-08-11 ;
          }

          leaf sum-rtt {
            description 'The sum value of RTT.' ;
            type uint32 ;

            units ms ;
            ncd:revise-date 2020-08-11 ;
          }

          leaf cur-rtt {
            description 'The current value of RTT.' ;
            type uint32 ;

            units ms ;
            ncd:revise-date 2020-08-11 ;
          }

          leaf min-delay-jitter {
            description 'The minimum value of jitter.' ;
            type uint32 ;

            units ms ;
            ncd:revise-date 2020-08-11 ;
          }

          leaf max-delay-jitter {
            description 'The maximum value of jitter.' ;
            type uint32 ;

            units ms ;
            ncd:revise-date 2020-08-11 ;
          }

          leaf avg-delay-jitter {
            description 'The average value of jitter.' ;
            type uint32 ;

            units ms ;
            ncd:revise-date 2020-08-11 ;
          }

          leaf sum-delay-jitter {
            description 'The sum value of jitter.' ;
            type uint32 ;

            units ms ;
            ncd:revise-date 2020-08-11 ;
          }

          leaf cur-delay-jitter {
            description 'The current value of jitter.' ;
            type uint32 ;

            units ms ;
            ncd:revise-date 2020-08-11 ;
          }

          leaf cur-delay-jitter-sd {
            description 'The current value of jitter from source to destination.' ;
            type uint32 ;

            units ms ;
            ncd:revise-date 2020-08-11 ;
          }

          leaf cur-delay-jitter-ds {
            description 'The current value of jitter from destination to source.' ;
            type uint32 ;

            units ms ;
            ncd:revise-date 2020-08-11 ;
          }

          leaf pkt-loss-num {
            description 'The number of lost packets in the ICMP test.' ;
            type uint16 ;

            ncd:revise-date 2020-08-11 ;
          }

          leaf pkt-loss-rate {
            description 'The ratio of lost packets in the ICMP test.' ;
            type string {
              length 2..4 {
                description 'The range of lost packets ratio.' ;
              }

            }

            ncd:revise-date 2020-08-11 ;
          }

          leaf destination-ipv6 {
            description 'The destination IPv6 address.' ;
            type ncd:ipv6-address ;

            ncd:revise-date 2020-08-11 ;
          }

          leaf vrf-name {
            description 'The VRF name.' ;
            type string {
              length 0..35 ;

            }

            ncd:revise-date 2021-12-28 ;
          }

        }

      }

      container reflector-informations {
        description 'Reflector configuration information.' ;
        list reflector-information {
          description 'Reflector configuration information.' ;
          key reflector-id ;
          leaf reflector-id {
            description 'Reflector ID,ranges from 1 to 65535.' ;
            type uint16 {
              range 1..65535 {
                description 'The range of reflector ID.' ;
              }

            }

          }

          leaf reflector-mode {
            description 'Reflector mode,including L2 mode and L3 mode.' ;
            type enumeration {
              enum l2 {
                value 2 ;
                description 'The reflector mode is L2.' ;
              }

              enum l3 {
                value 3 ;
                description 'The reflector mode is L3.' ;
              }

            }

          }

          leaf inbound-interface {
            description 'Interface name.' ;
            type ncd:ifname {
              length 1..31 {
                description 'The range of interface name length.' ;
              }

            }

          }

          leaf interface-mode {
            description 'Interface mode,including share mode,exclusive mode.' ;
            type enumeration {
              enum share {
                value 1 ;
                description 'The interface mode is share mode.' ;
              }

              enum exclusive {
                value 2 ;
                description 'The interface mode is exclusive mode.' ;
              }

            }

          }

          leaf test-mode {
            description 'Test mode,including online and offline.' ;
            type enumeration {
              enum online {
                value 1 ;
                description 'The mode is online.' ;
              }

              enum offline {
                value 2 ;
                description 'The mode is offline.' ;
              }

            }

          }

          leaf disnontest-8021p {
            description 'The value of discard-non-test priority-8021p in share mode,ranges from 0 to 7.' ;
            type uint8 {
              range "0..7|255" {
                description 'The range of priority-8021p.' ;
              }

            }

          }

          leaf disnontest-dscp {
            description 'The value of discard-non-test DSCP in share mode,ranges from 0 to 63.' ;
            type uint8 {
              range "0..63|255" {
                description 'The range of DSCP.' ;
              }

            }

          }

          leaf ageing-time {
            description 'The value of ageing time,ranges from 10s to 173400s,0 means continuous.' ;
            type uint32 {
              range "0|10..173400" {
                description 'The ranges of ageing time,0 means continuous.' ;
              }

            }

            units s ;
          }

          leaf source-mac {
            description 'The source MAC address.' ;
            type ncd:mac-address-none-zero ;

          }

          leaf destination-mac {
            description 'The destination MAC address.' ;
            type ncd:mac-address-none-zero ;

          }

          leaf source-ip {
            description 'The source IPv4 address.' ;
            type ncd:ipv4-address-none-zero ;

          }

          leaf destination-ip {
            description 'The destination IPv4 address.' ;
            type ncd:ipv4-address-none-zero ;

          }

          leaf source-port {
            description 'The source port,ranges from 1 to 65535.' ;
            type uint16 {
              range 1..65535 {
                description 'The range of port number.' ;
              }

            }

          }

          leaf destination-port {
            description 'The destination port,ranges from 1 to 65535.' ;
            type uint16 {
              range 1..65535 {
                description 'The range of port number.' ;
              }

            }

          }

          leaf vlan-id {
            description 'The value of vlan ID,ranges from 1 to 4094.' ;
            type uint16 {
              range 0..4094 {
                description 'The range of vlan ID.' ;
              }

            }

          }

          leaf internal-vlan-id {
            description 'The value of internal vlan ID,ranges from 1 to 4094.' ;
            type uint16 {
              range 0..4094 {
                description 'The range of vlan ID.' ;
              }

            }

          }

          leaf external-vlan-id {
            description 'The value of external vlan ID,ranges from 1 to 4094.' ;
            type uint16 {
              range 0..4094 {
                description 'The range of vlan ID.' ;
              }

            }

          }

          leaf priority-8021p {
            description 'The value of priority-8021p,ranges from 0 to 7.' ;
            type uint8 {
              range "0..7|255" {
                description 'The range of priority-8021p.' ;
              }

            }

          }

          leaf dscp {
            description 'The value of DSCP,ranges from 0 to 63.' ;
            type uint8 {
              range "0..63|255" {
                description 'The range of DSCP.' ;
              }

            }

          }

          leaf free-arp-status {
            description 'The free ARP status,including enable and disable.' ;
            type enumeration {
              enum disable {
                value 0 ;
                description 'The free ARP status is disable.' ;
              }

              enum enable {
                value 1 ;
                description 'The free ARP status is enable.' ;
              }

            }

          }

          leaf free-arp-ip {
            description 'The local IPv4 address of free ARP.' ;
            type ncd:ipv4-address-none-zero ;

          }

          leaf free-arp-vlan-id {
            description 'The value of vlan ID,ranges from 1 to 4094.' ;
            type uint16 {
              range 0..4094 {
                description 'The range of vlan ID.' ;
              }

            }

          }

          leaf free-arp-internal-id {
            description 'The value of internal vlan ID,ranges from 1 to 4094.' ;
            type uint16 {
              range 0..4094 {
                description 'The range of vlan ID.' ;
              }

            }

          }

          leaf free-arp-external-id {
            description 'The value of external vlan ID,ranges from 1 to 4094.' ;
            type uint16 {
              range 0..4094 {
                description 'The range of vlan ID.' ;
              }

            }

          }

          leaf free-arp-interval {
            description 'The value of interval,ranges from 1s to 14400s.' ;
            type uint32 {
              range 0..14400 {
                description 'The range of free ARP interval.' ;
              }

            }

            units s ;
          }

        }

        ncd:revise-date 2015-11-24 ;
      }

      container twamp-reflector-informations {
        list twamp-reflector-information {
          description 'Light TWAMP reflector  configuration information.' ;
          key reflector-id ;
          leaf reflector-id {
            description 'Reflector ID,ranges from 1 to 65535.' ;
            type uint16 {
              range 1..65535 {
                description 'The range of reflector ID.' ;
              }

            }

          }

          leaf inbound-interface {
            description 'Interface name.' ;
            type ncd:ifname {
              length 1..31 {
                description 'The range of interface name length.' ;
              }

            }

          }

          leaf test-mode {
            description 'Test mode,including online and offline.' ;
            type enumeration {
              enum online {
                value 1 ;
                description 'The mode is online.' ;
              }

              enum offline {
                value 2 ;
                description 'The mode is offline.' ;
              }

              enum null {
                value 0 ;
                description 'The mode is not configured.' ;
              }

            }

          }

          leaf source-mac {
            description 'The source MAC address.' ;
            type ncd:mac-address-none-zero ;

          }

          leaf destination-mac {
            description 'The destination MAC address.' ;
            type ncd:mac-address-none-zero ;

          }

          leaf source-ip {
            description 'The source IPv4 address.' ;
            type ncd:ipv4-address-none-zero ;

          }

          leaf destination-ip {
            description 'The destination IPv4 address.' ;
            type ncd:ipv4-address-none-zero ;

          }

          leaf source-port {
            description 'The source port, ranges from 1025 to 65535 or 862.' ;
            type uint16 {
              range 0..65535 {
                description 'The range of port number.' ;
              }

            }

          }

          leaf destination-port {
            description 'The destination port, ranges from 1025 to 65535 or 862.' ;
            type uint16 {
              range 1..65535 {
                description 'The range of port number.' ;
              }

            }

          }

          leaf vlan-id {
            description 'The value of vlan ID,ranges from 1 to 4094.' ;
            type uint16 {
              range 0..4094 {
                description 'The range of vlan ID.' ;
              }

            }

          }

          leaf internal-vlan-id {
            description 'The value of internal vlan ID,ranges from 1 to 4094.' ;
            type uint16 {
              range 0..4094 {
                description 'The range of vlan ID.' ;
              }

            }

          }

          leaf external-vlan-id {
            description 'The value of external vlan ID,ranges from 1 to 4094.' ;
            type uint16 {
              range 0..4094 {
                description 'The range of vlan ID.' ;
              }

            }

          }

          leaf priority-8021p {
            description 'The value of priority-8021p,ranges from 0 to 7.' ;
            type uint8 {
              range "0..7|255" {
                description 'The range of priority-8021p.' ;
              }

            }

          }

          leaf dscp {
            description 'The value of DSCP,ranges from 0 to 63.' ;
            type uint8 {
              range "0..63|255" {
                description 'The range of DSCP.' ;
              }

            }

          }

          leaf timestamp-format {
            if-feature timestamp-format ;

            description 'Timestamp format,including PTP and NTP.' ;
            type enumeration {
              enum ptp {
                value 1 ;
                description 'PTP format.' ;
              }

              enum ntp {
                value 2 ;
                description 'NTP format.' ;
              }

            }

            ncd:revise-date 2017-08-15 ;
          }

          leaf ageing-time {
            description 'The value of ageing time,ranges from 10s to 173400s,0 means continuous.' ;
            type uint32 {
              range "0|10..173400" {
                description 'The ranges of ageing time,0 means continuous.' ;
              }

            }

            units s ;
          }

          leaf free-arp-status {
            description 'The free ARP status,including enable and disable.' ;
            type enumeration {
              enum disable {
                value 0 ;
                description 'The free ARP status is disable.' ;
              }

              enum enable {
                value 1 ;
                description 'The free ARP status is enable.' ;
              }

            }

          }

          leaf free-arp-ip {
            description 'The local IPv4 address of free ARP.' ;
            type ncd:ipv4-address-none-zero ;

          }

          leaf free-arp-vlan-id {
            description 'The value of vlan ID,ranges from 1 to 4094.' ;
            type uint16 {
              range 0..4094 {
                description 'The range of vlan ID.' ;
              }

            }

          }

          leaf free-arp-internal-id {
            description 'The value of internal vlan ID,ranges from 1 to 4094.' ;
            type uint16 {
              range 0..4094 {
                description 'The range of vlan ID.' ;
              }

            }

          }

          leaf free-arp-external-id {
            description 'The value of external vlan ID,ranges from 1 to 4094.' ;
            type uint16 {
              range 0..4094 {
                description 'The range of vlan ID.' ;
              }

            }

          }

          leaf free-arp-interval {
            description 'The value of interval,ranges from 1s to 14400s.' ;
            type uint32 {
              range 0..14400 {
                description 'The range of free ARP interval.' ;
              }

            }

            units s ;
          }

          leaf reflector-mode {
            if-feature reflector-state-mode ;

            description 'Reflector state mode,including stateful and stateless(default:stateful).' ;
            type enumeration {
              enum stateful {
                value 0 ;
                description 'Stateful mode.' ;
              }

              enum stateless {
                value 1 ;
                description 'Stateless mode.' ;
              }

            }

            ncd:revise-date 2022-03-08 ;
          }

          leaf on-lag {
            if-feature lag-mode ;

            description 'Reflector on LAG flag.' ;
            type uint8 {
              range 1 ;

            }

            ncd:revise-date 2022-03-08 ;
          }

        }

        description 'Light TWAMP reflector configuration information.' ;
        ncd:revise-date 2016-02-17 ;
      }

      container light-twamp-result {
        status obsolete {
          ncd:revise-date 2020-07-16 ;
        }

        description 'The test result of light TWAMP.' ;
        list light-twamp-result {
          key test-number ;
          leaf test-number {
            description 'The value of test index,the upper limit of this parameter depends on the device.' ;
            type uint32 ;

          }

          leaf packet-send-number {
            description 'The count of sending packets.' ;
            type uint32 {
              range 0..4294967295 {
                description 'The range of sending packet number.' ;
              }

            }

          }

          leaf packet-receive-number {
            description 'The count of receiving packets.' ;
            type uint32 {
              range 0..4294967295 {
                description 'The range of receiving packet number.' ;
              }

            }

          }

          leaf packet-loss-number {
            description 'The count of lost packets.' ;
            type uint32 {
              range 0..4294967295 {
                description 'The range of packet lost number.' ;
              }

            }

          }

          leaf packet-loss-ratio {
            description 'The packet loss ratio,precision is 1/1000000.' ;
            type uint32 {
              range 0..4294967295 {
                description 'The range of packet lost ratio.' ;
              }

            }

          }

          leaf two-way-time-delay {
            description 'Two way packet delay.' ;
            type uint64 ;

            units ns ;
          }

          leaf two-way-min-delay {
            description 'The minimum two way packet delay.' ;
            type uint64 ;

            units ns ;
          }

          leaf two-way-max-delay {
            description 'The maximum two way packet delay.' ;
            type uint64 ;

            units ns ;
          }

          leaf two-way-avg-delay {
            description 'The average two way packet delay.' ;
            type uint64 ;

            units ns ;
          }

          leaf two-way-delay-jitter {
            description 'The two way packet delay jitter.' ;
            type uint64 ;

            units ns ;
          }

          leaf two-way-min-jitter {
            description 'The minimum two way packet delay jitter.' ;
            type uint64 ;

            units ns ;
          }

          leaf two-way-max-jitter {
            description 'The maximum two way packet delay jitter.' ;
            type uint64 ;

            units ns ;
          }

          leaf two-way-avg-jitter {
            description 'The average two way packet delay jitter.' ;
            type uint64 ;

            units ns ;
          }

          leaf forward-time-delay {
            description 'The forward packet delay.' ;
            type uint64 ;

            units ns ;
          }

          leaf forward-min-delay {
            description 'The minimum forward packet delay.' ;
            type uint64 ;

            units ns ;
          }

          leaf forward-max-delay {
            description 'The maximum forward packet delay.' ;
            type uint64 ;

            units ns ;
          }

          leaf forward-avg-delay {
            description 'The average forward packet delay.' ;
            type uint64 ;

            units ns ;
          }

          leaf forward-delay-jitter {
            description 'The forward packet delay jitter.' ;
            type uint64 ;

            units ns ;
          }

          leaf forward-min-jitter {
            description 'The minimum forward packet delay jitter.' ;
            type uint64 ;

            units ns ;
          }

          leaf forward-max-jitter {
            description 'The maximum forward packet delay jitter.' ;
            type uint64 ;

            units ns ;
          }

          leaf forward-avg-jitter {
            description 'The average forward packet delay jitter.' ;
            type uint64 ;

            units ns ;
          }

          leaf reverse-time-delay {
            description 'The reverse packet delay.' ;
            type uint64 ;

            units ns ;
          }

          leaf reverse-min-delay {
            description 'The minimum reverse packet delay.' ;
            type uint64 ;

            units ns ;
          }

          leaf reverse-max-delay {
            description 'The maximum reverse packet delay.' ;
            type uint64 ;

            units ns ;
          }

          leaf reverse-avg-delay {
            description 'The average reverse packet delay.' ;
            type uint64 ;

            units ns ;
          }

          leaf reverse-delay-jitter {
            description 'The reverse packet delay jitter.' ;
            type uint64 ;

            units ns ;
          }

          leaf reverse-min-jitter {
            description 'The minimum reverse packet delay jitter.' ;
            type uint64 ;

            units ns ;
          }

          leaf reverse-max-jitter {
            description 'The maximum reverse packet delay jitter.' ;
            type uint64 ;

            units ns ;
          }

          leaf reverse-avg-jitter {
            description 'The average reverse packet delay jitter.' ;
            type uint64 ;

            units ns ;
          }

        }

        ncd:revise-date 2019-06-24 ;
      }

      container light-twamp-results {
        description 'The test result of light TWAMP.Only Telemetry reporting is supported. "Get" is not supported.' ;
        list light-twamp-result {
          description 'The light TWAMP test result.' ;
          key test-number ;
          leaf test-number {
            description 'The value of test index,the upper limit of this parameter depends on the device.' ;
            type uint32 ;

          }

          leaf description {
            description 'The description of this test.' ;
            type string {
              length 0..127 ;

            }

            ncd:revise-date 2021-11-30 ;
          }

          leaf client-mode {
            description 'Client mode, including L2 UNI mode,L2 bridge UNI mode,L3 UNI mode and L3 mode.' ;
            type enumeration {
              enum l2-uni {
                value 1 ;
                description 'The client mode is L2 UNI.' ;
              }

              enum l3-uni {
                value 2 ;
                description 'The client mode is L3 UNI.' ;
              }

              enum l2-bridge-uni {
                value 3 ;
                description 'The client mode is L2 bridge UNI.' ;
              }

              enum l3 {
                value 4 ;
                description 'The client mode is L3.' ;
              }

              enum srv6-policy-sl {
                value 5 ;
                description 'The client mode is SRv6 policy SL.' ;
              }

              enum sr-mpls-policy-sl {
                value 6 ;
                description 'The client mode is SR MPLS policy SL.' ;
              }

              enum te-tunnel {
                value 7 ;
                description 'The client mode is TE tunnel.' ;
              }

            }

            ncd:revise-date 2021-04-20 ;
          }

          leaf packet-send-number {
            description 'The count of sending packets.' ;
            type uint32 {
              range 0..4294967295 {
                description 'The range of sending packet number.' ;
              }

            }

          }

          leaf packet-receive-number {
            description 'The count of receiving packets.' ;
            type uint32 {
              range 0..4294967295 {
                description 'The range of receiving packet number.' ;
              }

            }

          }

          leaf packet-loss-number {
            description 'The count of lost packets.' ;
            type uint32 {
              range 0..4294967295 {
                description 'The range of packet lost number.' ;
              }

            }

          }

          leaf packet-loss-ratio {
            description 'The packet loss ratio,precision is 1/1000000.' ;
            type uint32 {
              range 0..4294967295 {
                description 'The range of packet lost ratio.' ;
              }

            }

          }

          leaf two-way-time-delay {
            description 'Two way packet delay.' ;
            type uint64 ;

            units ns ;
          }

          leaf two-way-min-delay {
            description 'The minimum two way packet delay.' ;
            type uint64 ;

            units ns ;
          }

          leaf two-way-max-delay {
            description 'The maximum two way packet delay.' ;
            type uint64 ;

            units ns ;
          }

          leaf two-way-avg-delay {
            description 'The average two way packet delay.' ;
            type uint64 ;

            units ns ;
          }

          leaf two-way-delay-jitter {
            description 'The two way packet delay jitter.' ;
            type uint64 ;

            units ns ;
          }

          leaf two-way-min-jitter {
            description 'The minimum two way packet delay jitter.' ;
            type uint64 ;

            units ns ;
          }

          leaf two-way-max-jitter {
            description 'The maximum two way packet delay jitter.' ;
            type uint64 ;

            units ns ;
          }

          leaf two-way-avg-jitter {
            description 'The average two way packet delay jitter.' ;
            type uint64 ;

            units ns ;
          }

          leaf forward-time-delay {
            description 'The forward packet delay.' ;
            type uint64 ;

            units ns ;
          }

          leaf forward-min-delay {
            description 'The minimum forward packet delay.' ;
            type uint64 ;

            units ns ;
          }

          leaf forward-max-delay {
            description 'The maximum forward packet delay.' ;
            type uint64 ;

            units ns ;
          }

          leaf forward-avg-delay {
            description 'The average forward packet delay.' ;
            type uint64 ;

            units ns ;
          }

          leaf forward-delay-jitter {
            description 'The forward packet delay jitter.' ;
            type uint64 ;

            units ns ;
          }

          leaf forward-min-jitter {
            description 'The minimum forward packet delay jitter.' ;
            type uint64 ;

            units ns ;
          }

          leaf forward-max-jitter {
            description 'The maximum forward packet delay jitter.' ;
            type uint64 ;

            units ns ;
          }

          leaf forward-avg-jitter {
            description 'The average forward packet delay jitter.' ;
            type uint64 ;

            units ns ;
          }

          leaf reverse-time-delay {
            description 'The reverse packet delay.' ;
            type uint64 ;

            units ns ;
          }

          leaf reverse-min-delay {
            description 'The minimum reverse packet delay.' ;
            type uint64 ;

            units ns ;
          }

          leaf reverse-max-delay {
            description 'The maximum reverse packet delay.' ;
            type uint64 ;

            units ns ;
          }

          leaf reverse-avg-delay {
            description 'The average reverse packet delay.' ;
            type uint64 ;

            units ns ;
          }

          leaf reverse-delay-jitter {
            description 'The reverse packet delay jitter.' ;
            type uint64 ;

            units ns ;
          }

          leaf reverse-min-jitter {
            description 'The minimum reverse packet delay jitter.' ;
            type uint64 ;

            units ns ;
          }

          leaf reverse-max-jitter {
            description 'The maximum reverse packet delay jitter.' ;
            type uint64 ;

            units ns ;
          }

          leaf reverse-avg-jitter {
            description 'The average reverse packet delay jitter.' ;
            type uint64 ;

            units ns ;
          }

          choice path {
            description 'The information of test path.' ;
            case te-tunnel {
              description 'The information of TE tunnel.' ;
              leaf tunnel-id {
                description 'Tunnel ID.' ;
                type uint32 {
                  range 0..4294967295 ;

                }

              }

            }

            case sr-policy {
              description 'The information of SR policy.' ;
              leaf color {
                description 'The color of SR policy.' ;
                type uint32 {
                  range 0..4294967295 ;

                }

              }

              leaf end-point {
                description 'The end-point of SR policy.' ;
                type string {
                  length 0..45 ;

                }

              }

              leaf protocol-origin {
                description 'The protocol origin of SR policy.' ;
                type enumeration {
                  enum bgp {
                    value 20 ;
                    description 'Protocol BGP.' ;
                  }

                  enum configuration {
                    value 30 ;
                    description 'Protocol configuration.' ;
                  }

                  enum pcep {
                    value 10 ;
                    description 'Protocol PCEP.' ;
                  }

                }

              }

              leaf discriminator {
                description 'The discriminator of SR policy.' ;
                type uint32 {
                  range 0..4294967295 ;

                }

              }

              leaf sl-index {
                description 'The segment-list index.' ;
                type uint32 {
                  range 0..4294967295 ;

                }

              }

              leaf originator-as-num {
                description 'The as number of SR policy originator.' ;
                type uint32 {
                  range 0..4294967295 ;

                }

                ncd:revise-date 2022-09-27 ;
              }

              leaf originator-address {
                description 'The originator address of SR policy.' ;
                type string {
                  length 0..45 ;

                }

                ncd:revise-date 2022-09-27 ;
              }

            }

            case ip {
              leaf source-ip {
                description 'The source IP address.' ;
                type string {
                  length 0..45 ;

                }

              }

              leaf destination-ip {
                description 'The destination IP address.' ;
                type string {
                  length 0..45 ;

                }

              }

              leaf vrf-name {
                description 'The VRF name.' ;
                type string {
                  length 0..35 ;

                }

              }

              leaf destination-mac {
                description 'The destination MAC address.' ;
                type string {
                  length 0..16 ;

                }

              }

              leaf uni-interface {
                description 'The UNI interface name.' ;
                type string {
                  length 0..31 ;

                }

              }

              leaf vlan-id {
                description 'The vlan ID.' ;
                type uint32 {
                  range 0..4294967295 ;

                }

              }

              leaf inner-vlan-id {
                description 'Inner vlan ID.' ;
                type uint32 {
                  range 0..4294967295 ;

                }

              }

              leaf dscp {
                description 'The DSCP.' ;
                type uint32 ;

              }

              leaf priority-8021p {
                description 'The priority 802.1p.' ;
                type uint32 ;

              }

              leaf flex-algo-id {
                description 'The flex-algo ID.' ;
                type uint32 ;

                ncd:revise-date 2022-01-17 ;
              }

              leaf source-port {
                description 'The source udp port.' ;
                type uint32 ;

                ncd:revise-date 2022-02-14 ;
              }

              leaf destination-port {
                description 'The destination udp port.' ;
                type uint32 ;

                ncd:revise-date 2022-02-14 ;
              }

              leaf member-interface {
                description 'The member interface name.' ;
                type string {
                  length 0..31 ;

                }

                ncd:revise-date 2022-04-25 ;
              }

              ncd:revise-date 2021-04-20 ;
            }

            ncd:revise-date 2021-03-31 ;
          }

        }

        ncd:revise-date 2020-07-16 ;
      }

      container generalflow-throughput-results {
        description 'The throughput test result.Only Telemetry reporting is supported. "Get" is not supported.' ;
        list generalflow-throughput-result {
          description 'The throughput type test result of generalflow test.' ;
          key 'test-number packet-size' ;
          leaf test-number {
            description 'The value of test index,the upper limit of this parameter depends on the device.' ;
            type uint32 ;

          }

          leaf packet-size {
            description 'The packet size.' ;
            type uint16 {
              range 64..65535 {
                description 'The range of packet size.' ;
              }

            }

            units byte ;
          }

          leaf inbound-interface {
            description 'Interface name.' ;
            type ncd:ifname {
              length 1..31 {
                description 'The range of interface name length.' ;
              }

            }

          }

          leaf priority-8021p {
            description 'The value of priority-8021p,ranges from 0 to 7.' ;
            type uint8 {
              range 0..7 {
                description 'The range of priority-8021p.' ;
              }

            }

          }

          leaf dscp {
            description 'The value of DSCP,ranges from 0 to 63.' ;
            type uint8 {
              range 0..63 {
                description 'The range of DSCP.' ;
              }

            }

          }

          leaf precision {
            description 'The test precision of throughput.' ;
            type uint32 ;

            units kbps ;
          }

          leaf throughput {
            description 'The result of throughput.' ;
            type uint32 ;

            units kbps ;
          }

          leaf information-rate {
            description 'The information rate.' ;
            type uint32 ;

            units kbps ;
          }

          leaf loss-ratio {
            description 'The packet loss ratio,precision is 1/10000.' ;
            type uint32 ;

          }

          leaf duration {
            description 'The duration of test.' ;
            type uint32 ;

            units s ;
          }

          leaf status {
            description 'The result status of test,including success and fail.' ;
            type enumeration {
              enum success {
                value 1 ;
                description 'The test status is success.' ;
              }

              enum fail {
                value 2 ;
                description 'The test result status is fail.' ;
              }

            }

          }

        }

        ncd:revise-date 2022-07-27 ;
      }

      container generalflow-loss-results {
        description 'The loss test result.Only Telemetry reporting is supported. "Get" is not supported.' ;
        list generalflow-loss-result {
          description 'The loss type test result of generalflow test.' ;
          key 'test-number packet-size' ;
          leaf test-number {
            description 'The value of test index,the upper limit of this parameter depends on the device.' ;
            type uint32 ;

          }

          leaf packet-size {
            description 'The packet size.' ;
            type uint16 {
              range 64..65535 {
                description 'The range of packet size.' ;
              }

            }

            units byte ;
          }

          leaf inbound-interface {
            description 'Interface name.' ;
            type ncd:ifname {
              length 1..31 {
                description 'The range of interface name length.' ;
              }

            }

          }

          leaf priority-8021p {
            description 'The value of priority-8021p,ranges from 0 to 7.' ;
            type uint8 {
              range 0..7 {
                description 'The range of priority-8021p.' ;
              }

            }

          }

          leaf dscp {
            description 'The value of DSCP,ranges from 0 to 63.' ;
            type uint8 {
              range 0..63 {
                description 'The range of DSCP.' ;
              }

            }

          }

          leaf rate {
            description 'The rate value of test,ranges from 1kbps to 400000000kbps.' ;
            type uint32 {
              range 1..400000000 {
                description 'The range of rate.' ;
              }

            }

            units kbps ;
          }

          leaf loss-packet-number {
            description 'The packet loss number of test.' ;
            type uint32 ;

          }

          leaf loss-ratio {
            description 'The packet loss ratio,precision is 1/10000.' ;
            type uint32 ;

          }

          leaf duration {
            description 'The duration of test.' ;
            type uint32 ;

            units s ;
          }

          leaf status {
            description 'The result status of test,including success and fail.' ;
            type enumeration {
              enum success {
                value 1 ;
                description 'The test result status is success.' ;
              }

              enum fail {
                value 2 ;
                description 'The test result status is fail.' ;
              }

            }

          }

        }

        ncd:revise-date 2022-07-27 ;
      }

      container generalflow-delay-results {
        description 'The delay test result.Only Telemetry reporting is supported. "Get" is not supported.' ;
        list generalflow-delay-result {
          description 'The delay type test result of generalflow test.' ;
          key 'test-number packet-size' ;
          leaf test-number {
            description 'The value of test index,the upper limit of this parameter depends on the device.' ;
            type uint32 ;

          }

          leaf packet-size {
            description 'The packet size.' ;
            type uint16 {
              range 64..65535 {
                description 'The range of packet size.' ;
              }

            }

            units byte ;
          }

          leaf inbound-interface {
            description 'Interface name.' ;
            type ncd:ifname {
              length 1..31 {
                description 'The range of interface name length.' ;
              }

            }

          }

          leaf priority-8021p {
            description 'The value of priority-8021p,ranges from 0 to 7.' ;
            type uint8 {
              range 0..7 {
                description 'The range of priority-8021p.' ;
              }

            }

          }

          leaf dscp {
            description 'The value of DSCP,ranges from 0 to 63.' ;
            type uint8 {
              range 0..63 {
                description 'The range of DSCP.' ;
              }

            }

          }

          leaf rate {
            description 'The rate value of test,ranges from 0kbps to 400000000kbps.' ;
            type uint32 {
              range 0..400000000 {
                description 'The range of rate.' ;
              }

            }

            units kbps ;
          }

          leaf min-delay {
            description 'The minimal delay of test.' ;
            type uint64 ;

            units us ;
          }

          leaf max-delay {
            description 'The maximal delay of test.' ;
            type uint64 ;

            units us ;
          }

          leaf avg-delay {
            description 'The average delay of test.' ;
            type uint64 ;

            units us ;
          }

          leaf min-jitter {
            description 'The minimal jitter of test.' ;
            type uint64 ;

            units us ;
          }

          leaf max-jitter {
            description 'The maximal jitter of test.' ;
            type uint64 ;

            units us ;
          }

          leaf avg-jitter {
            description 'The average jitter of test.' ;
            type uint64 ;

            units us ;
          }

          leaf duration {
            description 'The duration of test.' ;
            type uint32 ;

            units s ;
          }

          leaf status {
            description 'The result status of test,including success and fail.' ;
            type enumeration {
              enum success {
                value 1 ;
                description 'The test result status is success.' ;
              }

              enum fail {
                value 2 ;
                description 'The test result status is fail.' ;
              }

            }

          }

        }

        ncd:revise-date 2022-07-27 ;
      }

      container y1564-results {
        description 'The Y1564 test result.Only Telemetry reporting is supported. "Get" is not supported.' ;
        list y1564-result {
          description 'The Y1564 type test result of generalflow test.' ;
          key 'test-number packet-size' ;
          leaf test-number {
            description 'The value of test index,the upper limit of this parameter depends on the device.' ;
            type uint32 ;

          }

          leaf packet-size {
            description 'The packet size.' ;
            type uint16 {
              range 64..65535 {
                description 'The range of packet size.' ;
              }

            }

            units byte ;
          }

          leaf inbound-interface {
            description 'The name of inbound interface.' ;
            type ncd:ifname {
              length 1..31 {
                description 'The range of interface name length.' ;
              }

            }

          }

          leaf priority-8021p {
            description 'The value of priority-8021p.' ;
            type uint8 {
              range 0..7 {
                description 'The range of priority-8021p.' ;
              }

            }

            default 0 ;
          }

          leaf dscp {
            description 'The value of DSCP.' ;
            type uint8 {
              range 0..63 {
                description 'The range of DSCP.' ;
              }

            }

            default 0 ;
          }

          leaf test-type {
            description 'Test type.' ;
            type enumeration {
              enum cir {
                value 1 ;
                description 'CIR test type.' ;
              }

              enum "cir/eir" {
                value 2 ;
                description 'CIR and EIR test type.' ;
              }

              enum traffic_policing {
                value 3 ;
                description 'Traffic policing test type.' ;
              }

            }

          }

          leaf rate {
            description 'The rate value of test.' ;
            type uint32 ;

            units kbps ;
          }

          leaf ir {
            description 'Test information rate.' ;
            type uint32 {
              range 0..10000000 {
                description 'The range of test information rate.' ;
              }

            }

            units kbps ;
          }

          leaf loss-packet-number {
            description 'The packet loss number of test.' ;
            type uint32 ;

            default 0 ;
          }

          leaf loss-ratio {
            description 'The packet loss ratio(precision:1/10000).' ;
            type uint32 {
              range 0..10000 {
                description 'The range of loss ratio.' ;
              }

            }

            default 0 ;
          }

          leaf min-delay {
            description 'The minimal delay of test.' ;
            type uint64 ;

            units us ;
            default 0 ;
          }

          leaf max-delay {
            description 'The maximal delay of test.' ;
            type uint64 ;

            units us ;
            default 0 ;
          }

          leaf avg-delay {
            description 'The average delay of test.' ;
            type uint64 ;

            units us ;
            default 0 ;
          }

          leaf min-jitter {
            description 'The minimal jitter of test.' ;
            type uint64 ;

            units us ;
            default 0 ;
          }

          leaf max-jitter {
            description 'The maximal jitter of test.' ;
            type uint64 ;

            units us ;
            default 0 ;
          }

          leaf avg-jitter {
            description 'The average jitter of test.' ;
            type uint64 ;

            units us ;
            default 0 ;
          }

          leaf total-second-count {
            if-feature ses-measure ;

            description 'Total second count of test.' ;
            type uint32 {
              range 0..4294967295 {
                description 'The range of total-count.' ;
              }

            }

            default 0 ;
          }

          leaf errored-second-count {
            if-feature ses-measure ;

            description 'Severely errored second count of test.' ;
            type uint32 {
              range 0..4294967295 {
                description 'The range of ses-count.' ;
              }

            }

            default 0 ;
          }

          leaf errored-second-ratio {
            if-feature ses-measure ;

            description 'Severely error second ratio of test(precision:1/100).' ;
            type uint8 {
              range 0..100 ;

            }

            units "1/100" ;
            default 0 ;
          }

          leaf duration {
            description 'The duration of test.' ;
            type uint32 {
              range 0..172800 {
                description 'The range of test duration.' ;
              }

            }

            units s ;
            default 0 ;
          }

          leaf status {
            description 'The result status of test.' ;
            type enumeration {
              enum pass {
                value 1 ;
                description 'The test result is pass.' ;
              }

              enum fail {
                value 2 ;
                description 'The test result is fail.' ;
              }

            }

          }

        }

        ncd:revise-date 2022-07-27 ;
      }

    }

  }

  container operation {
    config false ;
    description 'SQA operations model Info.' ;
    container sqa {
      description 'SQA operation parameters.' ;
      container test-operations {
        description 'The operation for this test.' ;
        list test-operation {
          description 'The operation for this test.' ;
          key number ;
          leaf number {
            description 'The value of test index,the upper limit of this parameter depend on the device.' ;
            type uint32 {
              range 1..65535 {
                description 'The range of the test number.' ;
              }

            }

          }

          leaf operation {
            description 'Start or stop this test.' ;
            type enumeration {
              enum begin {
                value 1 ;
                description 'Start this test.' ;
              }

              enum stop {
                value 2 ;
                description 'Stop this test.' ;
              }

            }

            mandatory true ;
          }

        }

      }

    }

  }

  notification icmp-event {
    description 'The ICMP test result.' ;
    list icmp-result {
      description 'The ICMP test result.' ;
      key test-number ;
      leaf test-number {
        config false ;
        description 'The value of test index,the upper limit of this parameter depends on the device.' ;
        type uint32 {
          range 1..4294967295 {
            description 'The range of the test number.' ;
          }

        }

      }

      leaf repeat-count {
        config false ;
        description 'The count of sending ICMP packets.' ;
        type uint16 {
          range 1..65535 {
            description 'The count of sending ICMP packets.' ;
          }

        }

      }

      leaf response-count {
        config false ;
        description 'The count of receiving ICMP packets.' ;
        type uint16 {
          range 0..65535 {
            description 'The count of receiving ICMP packets.' ;
          }

        }

      }

      leaf destination-ip {
        config false ;
        description 'The destination IPv4 address.' ;
        type ncd:ipv4-address ;

      }

      leaf min-rtt {
        config false ;
        description 'The minimal value of RTT.' ;
        type uint32 ;

        units ms ;
      }

      leaf max-rtt {
        config false ;
        description 'The maximal value of RTT.' ;
        type uint32 ;

        units ms ;
      }

      leaf avg-rtt {
        config false ;
        description 'The average value of RTT.' ;
        type uint32 ;

        units ms ;
      }

      leaf sum-rtt {
        config false ;
        description 'The sum value of RTT.' ;
        type uint32 ;

        units ms ;
      }

      leaf min-positive-jitter {
        config false ;
        description 'The minimal value of positive jitter.' ;
        type uint32 ;

        units ms ;
      }

      leaf max-positive-jitter {
        config false ;
        description 'The maximal value of positive jitter.' ;
        type uint32 ;

        units ms ;
      }

      leaf avg-positive-jitter {
        config false ;
        description 'The average value of positive jitter.' ;
        type uint32 ;

        units ms ;
      }

      leaf sum-positive-jitter {
        config false ;
        description 'The sum value of positive jitter.' ;
        type uint32 ;

        units ms ;
      }

      leaf min-negative-jitter {
        config false ;
        description 'The minimal value of negative jitter.' ;
        type uint32 ;

        units ms ;
      }

      leaf max-negative-jitter {
        config false ;
        description 'The maximal value of negative jitter.' ;
        type uint32 ;

        units ms ;
      }

      leaf avg-negative-jitter {
        config false ;
        description 'The average value of negative jitter.' ;
        type uint32 ;

        units ms ;
      }

      leaf sum-negative-jitter {
        config false ;
        description 'The sum value of negative jitter.' ;
        type uint32 ;

        units ms ;
      }

      leaf min-jitter {
        config false ;
        description 'The minimal value of jitter.' ;
        type uint32 ;

        units ms ;
      }

      leaf max-jitter {
        config false ;
        description 'The maximal value of jitter.' ;
        type uint32 ;

        units ms ;
      }

      leaf avg-jitter {
        config false ;
        description 'The average value of jitter.' ;
        type uint32 ;

        units ms ;
      }

      leaf sum-jitter {
        config false ;
        description 'The sum value of jitter.' ;
        type uint32 ;

        units ms ;
      }

      leaf pkt-loss-rate {
        config false ;
        description 'The ratio of lost packets in the ICMP test.' ;
        type string {
          length 2..4 {
            description 'The range of lost packets ratio.' ;
          }

        }

      }

      leaf probe-time {
        config false ;
        description 'The end time of ICMP test.' ;
        type ncd:string-with-blank {
          length 19 {
            description 'The end time of ICMP test.' ;
          }

        }

      }

      leaf destination-ipv6 {
        config false ;
        description 'The destination IPv6 address.' ;
        type ncd:ipv6-address ;

        ncd:revise-date 2020-03-18 ;
      }

    }

    ncd:revise-date 2015-08-20 ;
  }

  notification udp-event {
    description 'The UDP test result.' ;
    list udp-result {
      description 'The UDP test result.' ;
      key test-number ;
      leaf test-number {
        config false ;
        description 'The value of test index,the upper limit of this parameter depends on the device.' ;
        type uint32 {
          range 1..4294967295 {
            description 'The range of the test number.' ;
          }

        }

      }

      leaf repeat-count {
        config false ;
        description 'The count of sending UDP packets.' ;
        type uint16 {
          range 1..1000 {
            description 'The count of sending UDP packets.' ;
          }

        }

      }

      leaf response-count {
        config false ;
        description 'The count of receiving UDP packets.' ;
        type uint16 {
          range 0..1000 {
            description 'The count of receiving UDP packets.' ;
          }

        }

      }

      leaf destination-ip {
        config false ;
        description 'The destination IPv4 address.' ;
        type ncd:ipv4-address ;

      }

      leaf min-rtt {
        config false ;
        description 'The minimal value of RTT.' ;
        type uint32 ;

        units ms ;
      }

      leaf max-rtt {
        config false ;
        description 'The maximal value of RTT.' ;
        type uint32 ;

        units ms ;
      }

      leaf avg-rtt {
        config false ;
        description 'The average value of RTT.' ;
        type uint32 ;

        units ms ;
      }

      leaf sum-rtt {
        config false ;
        description 'The sum value of RTT.' ;
        type uint32 ;

        units ms ;
      }

      leaf min-positive-jitter {
        config false ;
        description 'The minimal value of positive jitter.' ;
        type uint32 ;

        units ms ;
      }

      leaf max-positive-jitter {
        config false ;
        description 'The maximal value of positive jitter.' ;
        type uint32 ;

        units ms ;
      }

      leaf avg-positive-jitter {
        config false ;
        description 'The average value of positive jitter.' ;
        type uint32 ;

        units ms ;
      }

      leaf sum-positive-jitter {
        config false ;
        description 'The sum value of positive jitter.' ;
        type uint32 ;

        units ms ;
      }

      leaf min-negative-jitter {
        config false ;
        description 'The minimal value of negative jitter.' ;
        type uint32 ;

        units ms ;
      }

      leaf max-negative-jitter {
        config false ;
        description 'The maximal value of negative jitter.' ;
        type uint32 ;

        units ms ;
      }

      leaf avg-negative-jitter {
        config false ;
        description 'The average value of negative jitter.' ;
        type uint32 ;

        units ms ;
      }

      leaf sum-negative-jitter {
        config false ;
        description 'The sum value of negative jitter.' ;
        type uint32 ;

        units ms ;
      }

      leaf min-jitter {
        config false ;
        description 'The minimal value of jitter.' ;
        type uint32 ;

        units ms ;
      }

      leaf max-jitter {
        config false ;
        description 'The maximal value of jitter.' ;
        type uint32 ;

        units ms ;
      }

      leaf avg-jitter {
        config false ;
        description 'The average value of jitter.' ;
        type uint32 ;

        units ms ;
      }

      leaf sum-jitter {
        config false ;
        description 'The sum value of jitter.' ;
        type uint32 ;

        units ms ;
      }

      leaf pkt-loss-rate {
        config false ;
        description 'The ratio of lost packets in the UDP test' ;
        type string {
          length 2..4 {
            description 'The range of lost packets ratio.' ;
          }

        }

      }

      leaf probe-time {
        config false ;
        description 'The end time of UDP test.' ;
        type ncd:string-with-blank {
          length 19 {
            description 'The end time of UDP test.' ;
          }

        }

      }

      leaf destination-ipv6 {
        config false ;
        description 'The destination IPv6 address.' ;
        type ncd:ipv6-address ;

        ncd:revise-date 2020-03-18 ;
      }

    }

    ncd:revise-date 2015-08-20 ;
  }

  notification tcp-event {
    description 'The TCP test result.' ;
    list tcp-result {
      description 'The TCP test result.' ;
      key test-number ;
      leaf test-number {
        config false ;
        description 'The value of test index,the upper limit of this parameter depends on the device.' ;
        type uint32 {
          range 1..4294967295 {
            description 'The range of the test number.' ;
          }

        }

      }

      leaf repeat-count {
        config false ;
        description 'The count of sending link requests.' ;
        type uint16 {
          range 1..200 {
            description 'The count of sending link requests.' ;
          }

        }

      }

      leaf response-count {
        config false ;
        description 'The count of receiving link answer.' ;
        type uint16 {
          range 0..200 {
            description 'The count of receiving link answer.' ;
          }

        }

      }

      leaf destination-ip {
        config false ;
        description 'The destination IPv4 address.' ;
        type ncd:ipv4-address ;

      }

      leaf min-rtt {
        config false ;
        description 'The minimal time of establishing TCP link.' ;
        type uint32 ;

        units ms ;
      }

      leaf max-rtt {
        config false ;
        description 'The maximal time of establishing TCP link.' ;
        type uint32 ;

        units ms ;
      }

      leaf avg-rtt {
        config false ;
        description 'The average time of establishing TCP link.' ;
        type uint32 ;

        units ms ;
      }

      leaf sum-rtt {
        config false ;
        description 'The sum time of establishing TCP link.' ;
        type uint32 ;

        units ms ;
      }

      leaf probe-time {
        config false ;
        description 'The end time of TCP test.' ;
        type ncd:string-with-blank {
          length 19 {
            description 'The end time of TCP test.' ;
          }

        }

      }

      leaf destination-ipv6 {
        config false ;
        description 'The destination IPv6 address.' ;
        type ncd:ipv6-address ;

        ncd:revise-date 2020-03-18 ;
      }

    }

    ncd:revise-date 2015-08-20 ;
  }

  notification ftp-event {
    description 'The FTP test result.' ;
    list ftp-result {
      description 'The FTP test result.' ;
      key test-number ;
      leaf test-number {
        config false ;
        description 'The value of test index,the upper limit of this parameter depends on the device.' ;
        type uint32 {
          range 1..4294967295 {
            description 'The range of the test number.' ;
          }

        }

      }

      leaf last-rtt {
        config false ;
        description 'The time is used to transfer this file.' ;
        type uint32 ;

        units s ;
      }

      leaf read-bytes {
        config false ;
        description 'The size of this file.' ;
        type uint32 ;

        units Byte ;
      }

      leaf probe-time {
        config false ;
        description 'The end time of FTP test.' ;
        type ncd:string-with-blank {
          length 19 {
            description 'The end time of FTP test.' ;
          }

        }

      }

    }

    ncd:revise-date 2015-08-20 ;
  }

  notification dns-event {
    description 'The DNS test result.' ;
    list dns-result {
      description 'The DNS test result.' ;
      key test-number ;
      leaf test-number {
        config false ;
        description 'The value of test index,the upper limit of this parameter depends on the device.' ;
        type uint32 {
          range 1..4294967295 {
            description 'The range of the test number.' ;
          }

        }

      }

      leaf repeat-count {
        config false ;
        description 'The count of sending DNS requests.' ;
        type uint16 {
          range 1..10 {
            description 'The count of sending DNS requests.' ;
          }

        }

      }

      leaf response-count {
        config false ;
        description 'The count of receiving right answer.' ;
        type uint16 {
          range 0..10 {
            description 'The count of receiving right answer.' ;
          }

        }

      }

      leaf destination-url {
        config false ;
        description 'The destination domain name.' ;
        type string {
          length 1..128 {
            description 'The destination domain name.' ;
          }

        }

      }

      leaf resolved-ip {
        config false ;
        description 'The domain name was resolved to an IP address through the DNS.' ;
        type ncd:ipv4-address ;

      }

      leaf min-rtt {
        config false ;
        description 'The minimal time of resolving a domain name.' ;
        type uint32 ;

        units ms ;
      }

      leaf max-rtt {
        config false ;
        description 'The maximal time of resolving a domain name.' ;
        type uint32 ;

        units ms ;
      }

      leaf avg-rtt {
        config false ;
        description 'The average time of resolving a domain name.' ;
        type uint32 ;

        units ms ;
      }

      leaf sum-rtt {
        config false ;
        description 'The sum time of resolving a domain name.' ;
        type uint32 ;

        units ms ;
      }

      leaf probe-time {
        config false ;
        description 'The end time of DNS test.' ;
        type ncd:string-with-blank {
          length 19 {
            description 'The end time of DNS test.' ;
          }

        }

      }

    }

    ncd:revise-date 2015-08-20 ;
  }

  notification udpjitter-event {
    description 'The UDP jitter test result.' ;
    list udpjitter-result {
      description 'The UDP jitter test result.' ;
      key test-number ;
      leaf test-number {
        config false ;
        description 'The value of test index,the upper limit of this parameter depends on the device.' ;
        type uint32 {
          range 1..4294967295 {
            description 'The range of the test number.' ;
          }

        }

      }

      leaf repeat-count {
        config false ;
        description 'The count of sending UDP packets.' ;
        type uint16 {
          range 1..1000 {
            description 'The count of sending UDP packets.' ;
          }

        }

      }

      leaf response-count {
        config false ;
        description 'The count of receiving UDP packets.' ;
        type uint16 {
          range 0..1000 {
            description 'The count of receiving UDP packets.' ;
          }

        }

      }

      leaf destination-ip {
        config false ;
        description 'The destination IPv4 address.' ;
        type ncd:ipv4-address ;

      }

      leaf min-rtt-sd {
        config false ;
        description 'The minimal value of delay from source to destination.' ;
        type uint32 ;

        units ms ;
      }

      leaf max-rtt-sd {
        config false ;
        description 'The maximal value of delay from source to destination.' ;
        type uint32 ;

        units ms ;
      }

      leaf avg-rtt-sd {
        config false ;
        description 'The average value of delay from source to destination.' ;
        type uint32 ;

        units ms ;
      }

      leaf sum-rtt-sd {
        config false ;
        description 'The sum value of delay from source to destination.' ;
        type uint32 ;

        units ms ;
      }

      leaf min-rtt-ds {
        config false ;
        description 'The minimal value of delay from destination to source.' ;
        type uint32 ;

        units ms ;
      }

      leaf max-rtt-ds {
        config false ;
        description 'The maximal value of delay from destination to source.' ;
        type uint32 ;

        units ms ;
      }

      leaf avg-rtt-ds {
        config false ;
        description 'The average value of delay from destination to source.' ;
        type uint32 ;

        units ms ;
      }

      leaf sum-rtt-ds {
        config false ;
        description 'The sum value of delay from destination to source.' ;
        type uint32 ;

        units ms ;
      }

      leaf min-positive-jitter-sd {
        config false ;
        description 'The minimal value of positive jitter from source to destination.' ;
        type uint32 ;

        units ms ;
      }

      leaf max-positive-jitter-sd {
        config false ;
        description 'The maximal value of positive jitter from source to destination.' ;
        type uint32 ;

        units ms ;
      }

      leaf avg-positive-jitter-sd {
        config false ;
        description 'The average value of positive jitter from source to destination.' ;
        type uint32 ;

        units ms ;
      }

      leaf sum-positive-jitter-sd {
        config false ;
        description 'The sum value of positive jitter from source to destination.' ;
        type uint32 ;

        units ms ;
      }

      leaf min-negative-jitter-sd {
        config false ;
        description 'The minimal value of negative jitter from source to destination.' ;
        type uint32 ;

        units ms ;
      }

      leaf max-negative-jitter-sd {
        config false ;
        description 'The maximal value of negative jitter from source to destination.' ;
        type uint32 ;

        units ms ;
      }

      leaf avg-negative-jitter-sd {
        config false ;
        description 'The average value of negative jitter from source to destination.' ;
        type uint32 ;

        units ms ;
      }

      leaf sum-negative-jitter-sd {
        config false ;
        description 'The sum value of negative jitter from source to destination.' ;
        type uint32 ;

        units ms ;
      }

      leaf min-positive-jitter-ds {
        config false ;
        description 'The minimal value of positive jitter from destination to source.' ;
        type uint32 ;

        units ms ;
      }

      leaf max-positive-jitter-ds {
        config false ;
        description 'The maximal value of positive jitter from destination to source.' ;
        type uint32 ;

        units ms ;
      }

      leaf avg-positive-jitter-ds {
        config false ;
        description 'The average value of positive jitter from destination to source.' ;
        type uint32 ;

        units ms ;
      }

      leaf sum-positive-jitter-ds {
        config false ;
        description 'The sum value of positive jitter from destination to source.' ;
        type uint32 ;

        units ms ;
      }

      leaf min-negative-jitter-ds {
        config false ;
        description 'The minimal value of negative jitter from destination to source.' ;
        type uint32 ;

        units ms ;
      }

      leaf max-negative-jitter-ds {
        config false ;
        description 'The maximal value of negative jitter from destination to source.' ;
        type uint32 ;

        units ms ;
      }

      leaf avg-negative-jitter-ds {
        config false ;
        description 'The average value of negative jitter from destination to source' ;
        type uint32 ;

        units ms ;
      }

      leaf sum-negative-jitter-ds {
        config false ;
        description 'The sum value of negative jitter from destination to source.' ;
        type uint32 ;

      }

      leaf pkt-loss-number-sd {
        config false ;
        description 'The number of lost packets from source to destination.' ;
        type uint16 ;

      }

      leaf pkt-loss-number-ds {
        config false ;
        description 'The number of lost packets from destination to source.' ;
        type uint16 ;

      }

      leaf probe-time {
        config false ;
        description 'The end time of UDP jitter test.' ;
        type ncd:string-with-blank {
          length 19 {
            description 'The end time of UDP jitter test.' ;
          }

        }

      }

      leaf destination-ipv6 {
        config false ;
        description 'The destination IPv6 address.' ;
        type ncd:ipv6-address ;

        ncd:revise-date 2020-03-18 ;
      }

    }

    ncd:revise-date 2015-08-20 ;
  }

  notification snmp-event {
    description 'The SNMP test result.' ;
    list snmp-result {
      description 'The SNMP test result.' ;
      key test-number ;
      leaf test-number {
        config false ;
        description 'The value of test index,the upper limit of this parameter depends on the device.' ;
        type uint32 {
          range 1..4294967295 {
            description 'The range of the test number.' ;
          }

        }

      }

      leaf last-rtt {
        config false ;
        description 'The time required to complete this test.' ;
        type uint32 ;

        units ms ;
      }

      leaf probe-time {
        config false ;
        description 'The end time of SNMP test.' ;
        type ncd:string-with-blank {
          length 19 {
            description 'The end time of SNMP test.' ;
          }

        }

      }

    }

    ncd:revise-date 2015-08-20 ;
  }

  notification http-event {
    description 'The HTTP test result.' ;
    list http-result {
      description 'The HTTP test result.' ;
      key test-number ;
      leaf test-number {
        config false ;
        description 'The value of test index,the upper limit of this parameter depends on the device.' ;
        type uint32 {
          range 1..4294967295 {
            description 'The range of the test number.' ;
          }

        }

      }

      leaf repeat-count {
        config false ;
        description 'The count of sending HTTP request.' ;
        type uint16 {
          range 1..10 {
            description 'The count of sending HTTP request.' ;
          }

        }

      }

      leaf response-count {
        config false ;
        description 'The count of receiving HTTP answer.' ;
        type uint16 {
          range 0..10 {
            description 'The count of receiving HTTP answer.' ;
          }

        }

      }

      leaf destination-ip {
        config false ;
        description 'The destination IP address.' ;
        type ncd:ipv4-address ;

      }

      leaf destination-url {
        config false ;
        description 'The destination domain name.' ;
        type string {
          length 1..128 {
            description 'The destination domain name.' ;
          }

        }

      }

      leaf min-dns-rtt {
        config false ;
        description 'The minimal time of resolving a domain name.' ;
        type uint32 ;

        units ms ;
      }

      leaf max-dns-rtt {
        config false ;
        description 'The maximal time of resolving a domain name.' ;
        type uint32 ;

        units ms ;
      }

      leaf avg-dns-rtt {
        config false ;
        description 'The average time of resolving a domain name.' ;
        type uint32 ;

        units ms ;
      }

      leaf sum-dns-rtt {
        config false ;
        description 'The sum time of resolving a domain name.' ;
        type uint32 ;

        units ms ;
      }

      leaf min-tcp-connection-rtt {
        config false ;
        description 'The minimal time of establishing link.' ;
        type uint32 ;

        units ms ;
      }

      leaf max-tcp-connection-rtt {
        config false ;
        description 'The maximal time of establishing link.' ;
        type uint32 ;

        units ms ;
      }

      leaf avg-tcp-connection-rtt {
        config false ;
        description 'The average time of establishing link.' ;
        type uint32 ;

        units ms ;
      }

      leaf sum-tcp-connection-rtt {
        config false ;
        description 'The sum time of establishing link.' ;
        type uint32 ;

        units ms ;
      }

      leaf min-http-connection-rtt {
        config false ;
        description 'The minimal time of completing http request.' ;
        type uint32 ;

        units ms ;
      }

      leaf max-http-connection-rtt {
        config false ;
        description 'The maximal time of completing http request.' ;
        type uint32 ;

        units ms ;
      }

      leaf avg-http-connection-rtt {
        config false ;
        description 'The average time of completing http request.' ;
        type uint32 ;

        units ms ;
      }

      leaf sum-http-connection-rtt {
        config false ;
        description 'The sum time of completing http request.' ;
        type uint32 ;

        units ms ;
      }

      leaf min-rtt {
        config false ;
        description 'The minimal time required to complete this whole test.' ;
        type uint32 ;

        units ms ;
      }

      leaf max-rtt {
        config false ;
        description 'The maximal time required to complete this whole test.' ;
        type uint32 ;

        units ms ;
      }

      leaf avg-rtt {
        config false ;
        description 'The average time required to complete this whole test.' ;
        type uint32 ;

        units ms ;
      }

      leaf sum-rtt {
        config false ;
        description 'The sum time required to complete this whole test.' ;
        type uint32 ;

        units ms ;
      }

      leaf probe-time {
        config false ;
        description 'The end time of HTTP test.' ;
        type ncd:string-with-blank {
          length 19 {
            description 'The end time of HTTP test.' ;
          }

        }

      }

    }

    ncd:revise-date 2015-08-20 ;
  }

  notification icmpjitter-event {
    description 'The ICMP jitter test result.' ;
    list icmpjitter-result {
      description 'The ICMP jitter test result.' ;
      key test-number ;
      leaf test-number {
        config false ;
        description 'The value of test index,the upper limit of this parameter depends on the device.' ;
        type uint32 {
          range 1..4294967295 {
            description 'The range of the test number.' ;
          }

        }

      }

      leaf repeat-count {
        config false ;
        description 'The count of sending ICMP packets.' ;
        type uint16 {
          range 1..65535 {
            description 'The count of sending ICMP packets.' ;
          }

        }

      }

      leaf response-count {
        config false ;
        description 'The count of receiving ICMP packets.' ;
        type uint16 {
          range 0..65535 {
            description 'The count of receiving ICMP packets.' ;
          }

        }

      }

      leaf destination-ip {
        config false ;
        description 'The destination IPv4 address.' ;
        type ncd:ipv4-address ;

      }

      leaf min-rtt-sd {
        config false ;
        description 'The minimal value of delay from source to destination.' ;
        type uint32 ;

        units ms ;
      }

      leaf max-rtt-sd {
        config false ;
        description 'The maximal value of delay from source to destination.' ;
        type uint32 ;

        units ms ;
      }

      leaf avg-rtt-sd {
        config false ;
        description 'The average value of delay from source to destination.' ;
        type uint32 ;

        units ms ;
      }

      leaf sum-rtt-sd {
        config false ;
        description 'The sum value of delay from source to destination.' ;
        type uint32 ;

        units ms ;
      }

      leaf min-rtt-ds {
        config false ;
        description 'The minimal value of delay from destination to source.' ;
        type uint32 ;

        units ms ;
      }

      leaf max-rtt-ds {
        config false ;
        description 'The maximal value of delay from destination to source.' ;
        type uint32 ;

        units ms ;
      }

      leaf avg-rtt-ds {
        config false ;
        description 'The average value of delay from destination to source.' ;
        type uint32 ;

        units ms ;
      }

      leaf sum-rtt-ds {
        config false ;
        description 'The sum value of delay from destination to source.' ;
        type uint32 ;

        units ms ;
      }

      leaf min-positive-jitter-sd {
        config false ;
        description 'The minimal value of positive jitter from source to destination.' ;
        type uint32 ;

        units ms ;
      }

      leaf max-positive-jitter-sd {
        config false ;
        description 'The maximal value of positive jitter from source to destination.' ;
        type uint32 ;

        units ms ;
      }

      leaf avg-positive-jitter-sd {
        config false ;
        description 'The average value of positive jitter from source to destination.' ;
        type uint32 ;

        units ms ;
      }

      leaf sum-positive-jitter-sd {
        config false ;
        description 'The sum value of positive jitter from source to destination.' ;
        type uint32 ;

        units ms ;
      }

      leaf min-negative-jitter-sd {
        config false ;
        description 'The minimal value of negative jitter from source to destination.' ;
        type uint32 ;

        units ms ;
      }

      leaf max-negative-jitter-sd {
        config false ;
        description 'The maximal value of negative jitter from source to destination.' ;
        type uint32 ;

        units ms ;
      }

      leaf avg-negative-jitter-sd {
        config false ;
        description 'The average value of negative jitter from source to destination.' ;
        type uint32 ;

        units ms ;
      }

      leaf sum-negative-jitter-sd {
        config false ;
        description 'The sum value of negative jitter from source to destination.' ;
        type uint32 ;

        units ms ;
      }

      leaf min-positive-jitter-ds {
        config false ;
        description 'The minimal value of positive jitter from destination to source.' ;
        type uint32 ;

        units ms ;
      }

      leaf max-positive-jitter-ds {
        config false ;
        description 'The maximal value of positive jitter from destination to source.' ;
        type uint32 ;

        units ms ;
      }

      leaf avg-positive-jitter-ds {
        config false ;
        description 'The average value of positive jitter from destination to source.' ;
        type uint32 ;

        units ms ;
      }

      leaf sum-positive-jitter-ds {
        config false ;
        description 'The sum value of positive jitter from destination to source.' ;
        type uint32 ;

        units ms ;
      }

      leaf min-negative-jitter-ds {
        config false ;
        description 'The minimal value of negative jitter from destination to source.' ;
        type uint32 ;

        units ms ;
      }

      leaf max-negative-jitter-ds {
        config false ;
        description 'The maximal value of negative jitter from destination to source.' ;
        type uint32 ;

        units ms ;
      }

      leaf avg-negative-jitter-ds {
        config false ;
        description 'The average value of negative jitter from destination to source.' ;
        type uint32 ;

        units ms ;
      }

      leaf sum-negative-jitter-ds {
        config false ;
        description 'The sum value of negative jitter from destination to source.' ;
        type uint32 ;

        units ms ;
      }

      leaf probe-time {
        config false ;
        description 'The end time of ICMP jitter test.' ;
        type ncd:string-with-blank {
          length 19 {
            description 'The end time of ICMP jitter test.' ;
          }

        }

      }

      leaf min-rtt {
        config false ;
        description 'The minimum value of RTT.' ;
        type uint32 ;

        units ms ;
        ncd:revise-date 2020-08-11 ;
      }

      leaf max-rtt {
        config false ;
        description 'The maximum value of RTT.' ;
        type uint32 ;

        units ms ;
        ncd:revise-date 2020-08-11 ;
      }

      leaf avg-rtt {
        config false ;
        description 'The average value of RTT.' ;
        type uint32 ;

        units ms ;
        ncd:revise-date 2020-08-11 ;
      }

      leaf sum-rtt {
        config false ;
        description 'The sum value of RTT.' ;
        type uint32 ;

        units ms ;
        ncd:revise-date 2020-08-11 ;
      }

      leaf cur-rtt {
        config false ;
        description 'The current value of RTT.' ;
        type uint32 ;

        units ms ;
        ncd:revise-date 2020-08-11 ;
      }

      leaf min-delay-jitter {
        config false ;
        description 'The minimum value of jitter.' ;
        type uint32 ;

        units ms ;
        ncd:revise-date 2020-08-11 ;
      }

      leaf max-delay-jitter {
        config false ;
        description 'The maximum value of jitter.' ;
        type uint32 ;

        units ms ;
        ncd:revise-date 2020-08-11 ;
      }

      leaf avg-delay-jitter {
        config false ;
        description 'The average value of jitter.' ;
        type uint32 ;

        units ms ;
        ncd:revise-date 2020-08-11 ;
      }

      leaf sum-delay-jitter {
        config false ;
        description 'The sum value of jitter.' ;
        type uint32 ;

        units ms ;
        ncd:revise-date 2020-08-11 ;
      }

      leaf cur-delay-jitter {
        config false ;
        description 'The current value of jitter.' ;
        type uint32 ;

        units ms ;
        ncd:revise-date 2020-08-11 ;
      }

      leaf cur-delay-jitter-sd {
        config false ;
        description 'The current value of jitter from source to destination.' ;
        type uint32 ;

        units ms ;
        ncd:revise-date 2020-08-11 ;
      }

      leaf cur-delay-jitter-ds {
        config false ;
        description 'The current value of jitter from destination to source.' ;
        type uint32 ;

        units ms ;
        ncd:revise-date 2020-08-11 ;
      }

      leaf pkt-loss-num {
        config false ;
        description 'The number of lost packets in the ICMP test.' ;
        type uint16 ;

        ncd:revise-date 2020-08-11 ;
      }

      leaf pkt-loss-rate {
        config false ;
        description 'The ratio of lost packets in the ICMP test.' ;
        type string {
          length 2..4 {
            description 'The range of lost packets ratio.' ;
          }

        }

        ncd:revise-date 2020-08-11 ;
      }

      leaf destination-ipv6 {
        config false ;
        description 'The destination IPv6 address.' ;
        type ncd:ipv6-address ;

        ncd:revise-date 2020-08-11 ;
      }

    }

    ncd:revise-date 2015-08-20 ;
  }

  notification throughput-event {
    description 'The throughput test result.' ;
    list throughput-result {
      description 'The throughput test result.' ;
      key 'test-number packet-size' ;
      leaf test-number {
        config false ;
        description 'The value of test index,the upper limit of this parameter depends on the device.' ;
        type uint32 ;

      }

      leaf packet-size {
        config false ;
        description 'The packet size.' ;
        type uint16 {
          range 64..65535 {
            description 'The range of packet size.' ;
          }

        }

        units byte ;
      }

      leaf inbound-interface {
        config false ;
        description 'Interface name.' ;
        type ncd:ifname {
          length 1..31 {
            description 'The range of interface name length.' ;
          }

        }

      }

      leaf priority-8021p {
        config false ;
        description 'The value of priority-8021p,ranges from 0 to 7.' ;
        type uint8 {
          range 0..7 {
            description 'The range of priority-8021p.' ;
          }

        }

      }

      leaf dscp {
        config false ;
        description 'The value of DSCP,ranges from 0 to 63.' ;
        type uint8 {
          range 0..63 {
            description 'The range of DSCP.' ;
          }

        }

      }

      leaf precision {
        config false ;
        description 'The test precision of throughput.' ;
        type uint32 ;

        units kbps ;
      }

      leaf throughput {
        config false ;
        description 'The result of throughput.' ;
        type uint32 ;

        units kbps ;
      }

      leaf information-rate {
        config false ;
        description 'The information rate.' ;
        type uint32 ;

        units kbps ;
      }

      leaf loss-ratio {
        config false ;
        description 'The packet loss ratio,precision is 1/10000.' ;
        type uint32 ;

      }

      leaf duration {
        config false ;
        description 'The duration of test.' ;
        type uint32 ;

        units s ;
      }

      leaf status {
        config false ;
        description 'The result status of test,including success,fail(1) and fail(2),fail(1) means could not find throughput in the specified time,fail(2) means configuration of the lowest rate can not meet the requirements of packet loss rate.' ;
        type enumeration {
          enum success {
            value 1 ;
            description 'The test status is success.' ;
          }

          enum fail-1 {
            value 2 ;
            description 'Could not find throughput in the specified time.' ;
          }

          enum fail-2 {
            value 3 ;
            description 'Configuration of the lowest rate can not meet the requirements of packet loss rate.' ;
          }

        }

      }

    }

    ncd:revise-date 2015-11-24 ;
  }

  notification loss-event {
    description 'The loss test result.' ;
    list loss-result {
      description 'The loss test result.' ;
      key 'test-number packet-size' ;
      leaf test-number {
        config false ;
        description 'The value of test index,the upper limit of this parameter depends on the device.' ;
        type uint32 ;

      }

      leaf packet-size {
        config false ;
        description 'The packet size.' ;
        type uint16 {
          range 64..65535 {
            description 'The range of packet size.' ;
          }

        }

        units byte ;
      }

      leaf inbound-interface {
        config false ;
        description 'Interface name.' ;
        type ncd:ifname {
          length 1..31 {
            description 'The range of interface name length.' ;
          }

        }

      }

      leaf priority-8021p {
        config false ;
        description 'The value of priority-8021p,ranges from 0 to 7.' ;
        type uint8 {
          range 0..7 {
            description 'The range of priority-8021p.' ;
          }

        }

      }

      leaf dscp {
        config false ;
        description 'The value of DSCP,ranges from 0 to 63.' ;
        type uint8 {
          range 0..63 {
            description 'The range of DSCP.' ;
          }

        }

      }

      leaf loss-rate {
        config false ;
        description 'The rate value of test,ranges from 1kbps to 400000000kbps.' ;
        type uint32 {
          range 1..400000000 {
            description 'The range of rate.' ;
          }

        }

        units kbps ;
      }

      leaf loss-packet-number {
        config false ;
        description 'The packet loss number of test.' ;
        type uint32 ;

      }

      leaf loss-ratio {
        config false ;
        description 'The packet loss ratio,precision is 1/10000.' ;
        type uint32 ;

      }

      leaf duration {
        config false ;
        description 'The duration of test.' ;
        type uint32 ;

        units s ;
      }

      leaf status {
        config false ;
        description 'The result status of test,including success and fail.' ;
        type enumeration {
          enum success {
            value 1 ;
            description 'The test result status is success.' ;
          }

          enum fail {
            value 2 ;
            description 'The test result status is fail.' ;
          }

        }

      }

    }

    ncd:revise-date 2015-11-24 ;
  }

  notification delay-event {
    description 'The delay test result.' ;
    list delay-result {
      description 'The delay test result.' ;
      key 'test-number packet-size' ;
      leaf test-number {
        config false ;
        description 'The value of test index,the upper limit of this parameter depends on the device.' ;
        type uint32 ;

      }

      leaf packet-size {
        config false ;
        description 'The packet size.' ;
        type uint16 {
          range 64..65535 {
            description 'The range of packet size.' ;
          }

        }

        units byte ;
      }

      leaf inbound-interface {
        config false ;
        description 'Interface name.' ;
        type ncd:ifname {
          length 1..31 {
            description 'The range of interface name length.' ;
          }

        }

      }

      leaf priority-8021p {
        config false ;
        description 'The value of priority-8021p,ranges from 0 to 7.' ;
        type uint8 {
          range 0..7 {
            description 'The range of priority-8021p.' ;
          }

        }

      }

      leaf dscp {
        config false ;
        description 'The value of DSCP,ranges from 0 to 63.' ;
        type uint8 {
          range 0..63 {
            description 'The range of DSCP.' ;
          }

        }

      }

      leaf delay-rate {
        config false ;
        description 'The rate value of test,ranges from 0kbps to 400000000kbps.' ;
        type uint32 {
          range 0..400000000 {
            description 'The range of rate.' ;
          }

        }

        units kbps ;
      }

      leaf min-delay {
        config false ;
        description 'The minimal delay of test.' ;
        type uint64 ;

        units us ;
      }

      leaf max-delay {
        config false ;
        description 'The maximal delay of test.' ;
        type uint64 ;

        units us ;
      }

      leaf avg-delay {
        config false ;
        description 'The average delay of test.' ;
        type uint64 ;

        units us ;
      }

      leaf min-jitter {
        config false ;
        description 'The minimal jitter of test.' ;
        type uint64 ;

        units us ;
      }

      leaf max-jitter {
        config false ;
        description 'The maximal jitter of test.' ;
        type uint64 ;

        units us ;
      }

      leaf avg-jitter {
        config false ;
        description 'The average jitter of test.' ;
        type uint64 ;

        units us ;
      }

      leaf duration {
        config false ;
        description 'The duration of test.' ;
        type uint32 ;

        units s ;
      }

      leaf status {
        config false ;
        description 'The result status of test,including success and fail.' ;
        type enumeration {
          enum success {
            value 1 ;
            description 'The test result status is success.' ;
          }

          enum fail {
            value 2 ;
            description 'The test result status is fail.' ;
          }

        }

      }

    }

    ncd:revise-date 2015-11-24 ;
  }

  notification lighttwamp-event {
    description 'The test result of light TWAMP.' ;
    list lighttwamp-result {
      description 'The test result of light TWAMP.' ;
      key test-number ;
      leaf test-number {
        config false ;
        description 'The value of test index,the upper limit of this parameter depends on the device.' ;
        type uint32 ;

      }

      leaf packet-send-number {
        config false ;
        description 'The count of sending packets.' ;
        type uint32 {
          range 0..4294967295 {
            description 'The range of sending packet number.' ;
          }

        }

      }

      leaf packet-receive-number {
        config false ;
        description 'The count of receiving packets.' ;
        type uint32 {
          range 0..4294967295 {
            description 'The range of receiving packet number.' ;
          }

        }

      }

      leaf packet-loss-number {
        config false ;
        description 'The count of lost packets.' ;
        type uint32 {
          range 0..4294967295 {
            description 'The range of packet lost number.' ;
          }

        }

      }

      leaf packet-loss-ratio {
        config false ;
        description 'The packet loss ratio,precision is 1/1000000.' ;
        type uint32 {
          range 0..4294967295 {
            description 'The range of packet lost ratio.' ;
          }

        }

      }

      leaf two-way-time-delay {
        config false ;
        description 'Two way packet delay.' ;
        type uint64 ;

        units ns ;
      }

      leaf two-way-min-delay {
        description 'The minimum two way packet delay.' ;
        type uint64 ;

        units ns ;
      }

      leaf two-way-max-delay {
        config false ;
        description 'The maximum two way packet delay.' ;
        type uint64 ;

        units ns ;
      }

      leaf two-way-avg-delay {
        config false ;
        description 'The average two way packet delay.' ;
        type uint64 ;

        units ns ;
      }

      leaf two-way-delay-jitter {
        config false ;
        description 'The two way packet delay jitter.' ;
        type uint64 ;

        units ns ;
      }

      leaf two-way-min-jitter {
        config false ;
        description 'The minimum two way packet delay jitter.' ;
        type uint64 ;

        units ns ;
      }

      leaf two-way-max-jitter {
        config false ;
        description 'The maximum two way packet delay jitter.' ;
        type uint64 ;

        units ns ;
      }

      leaf two-way-avg-jitter {
        config false ;
        description 'The average two way packet delay jitter.' ;
        type uint64 ;

        units ns ;
      }

      leaf forward-time-delay {
        config false ;
        description 'The forward packet delay.' ;
        type uint64 ;

        units ns ;
      }

      leaf forward-min-delay {
        config false ;
        description 'The minimum forward packet delay.' ;
        type uint64 ;

        units ns ;
      }

      leaf forward-max-delay {
        config false ;
        description 'The maximum forward packet delay.' ;
        type uint64 ;

        units ns ;
      }

      leaf forward-avg-delay {
        config false ;
        description 'The average forward packet delay.' ;
        type uint64 ;

        units ns ;
      }

      leaf forward-delay-jitter {
        config false ;
        description 'The forward packet delay jitter.' ;
        type uint64 ;

        units ns ;
      }

      leaf forward-min-jitter {
        config false ;
        description 'The minimum forward packet delay jitter.' ;
        type uint64 ;

        units ns ;
      }

      leaf forward-max-jitter {
        config false ;
        description 'The maximum forward packet delay jitter.' ;
        type uint64 ;

        units ns ;
      }

      leaf forward-avg-jitter {
        config false ;
        description 'The average forward packet delay jitter.' ;
        type uint64 ;

        units ns ;
      }

      leaf reverse-time-delay {
        config false ;
        description 'The reverse packet delay.' ;
        type uint64 ;

        units ns ;
      }

      leaf reverse-min-delay {
        config false ;
        description 'The minimum reverse packet delay.' ;
        type uint64 ;

        units ns ;
      }

      leaf reverse-max-delay {
        config false ;
        description 'The maximum reverse packet delay.' ;
        type uint64 ;

        units ns ;
      }

      leaf reverse-avg-delay {
        config false ;
        description 'The average reverse packet delay.' ;
        type uint64 ;

        units ns ;
      }

      leaf reverse-delay-jitter {
        config false ;
        description 'The reverse packet delay jitter.' ;
        type uint64 ;

        units ns ;
      }

      leaf reverse-min-jitter {
        config false ;
        description 'The minimum reverse packet delay jitter.' ;
        type uint64 ;

        units ns ;
      }

      leaf reverse-max-jitter {
        config false ;
        description 'The maximum reverse packet delay jitter.' ;
        type uint64 ;

        units ns ;
      }

      leaf reverse-avg-jitter {
        config false ;
        description 'The average reverse packet delay jitter.' ;
        type uint64 ;

        units ns ;
      }

      leaf out-interface {
        config false ;
        description 'The out interface name.' ;
        type string {
          length 0..31 ;

        }

        ncd:revise-date 2022-03-08 ;
      }

    }

    ncd:revise-date 2016-02-27 ;
  }

  notification y1564-event {
    description 'The Y1564 test result.' ;
    list y1564-result {
      description 'The Y1564 test result.' ;
      key 'test-number packet-size' ;
      leaf test-number {
        config false ;
        description 'The value of test index,the upper limit of this parameter depends on the device.' ;
        type uint32 ;

      }

      leaf packet-size {
        config false ;
        description 'The packet size.' ;
        type uint16 {
          range 64..65535 {
            description 'The range of packet size.' ;
          }

        }

        units byte ;
      }

      leaf inbound-interface {
        config false ;
        description 'The name of inbound interface.' ;
        type ncd:ifname {
          length 1..31 {
            description 'The range of interface name length.' ;
          }

        }

      }

      leaf priority-8021p {
        config false ;
        description 'The value of priority-8021p.' ;
        type uint8 {
          range 0..7 {
            description 'The range of priority-8021p.' ;
          }

        }

        default 0 ;
      }

      leaf dscp {
        config false ;
        description 'The value of DSCP.' ;
        type uint8 {
          range 0..63 {
            description 'The range of DSCP.' ;
          }

        }

        default 0 ;
      }

      leaf test-type {
        description 'Test type.' ;
        type enumeration {
          enum cir {
            value 1 ;
            description 'CIR test type.' ;
          }

          enum "cir/eir" {
            value 2 ;
            description 'CIR and EIR test type.' ;
          }

          enum traffic_policing {
            value 3 ;
            description 'Traffic policing test type.' ;
          }

        }

      }

      leaf ir {
        description 'Test information rate.' ;
        type uint32 {
          range 0..10000000 {
            description 'The range of test information rate.' ;
          }

        }

        units kbps ;
      }

      leaf loss-packet-number {
        config false ;
        description 'The packet loss number of test.' ;
        type uint32 ;

        default 0 ;
      }

      leaf loss-ratio {
        config false ;
        description 'The packet loss ratio(precision:1/10000).' ;
        type uint32 {
          range 0..10000 {
            description 'The range of loss ratio.' ;
          }

        }

        default 0 ;
      }

      leaf min-delay {
        config false ;
        description 'The minimal delay of test.' ;
        type uint64 ;

        units us ;
        default 0 ;
      }

      leaf max-delay {
        config false ;
        description 'The maximal delay of test.' ;
        type uint64 ;

        units us ;
        default 0 ;
      }

      leaf avg-delay {
        config false ;
        description 'The average delay of test.' ;
        type uint64 ;

        units us ;
        default 0 ;
      }

      leaf min-jitter {
        config false ;
        description 'The minimal jitter of test.' ;
        type uint64 ;

        units us ;
        default 0 ;
      }

      leaf max-jitter {
        config false ;
        description 'The maximal jitter of test.' ;
        type uint64 ;

        units us ;
        default 0 ;
      }

      leaf avg-jitter {
        config false ;
        description 'The average jitter of test.' ;
        type uint64 ;

        units us ;
        default 0 ;
      }

      leaf status {
        config false ;
        description 'The result status of test.' ;
        type enumeration {
          enum pass {
            value 1 ;
            description 'The test result is pass.' ;
          }

          enum fail {
            value 2 ;
            description 'The test result is fail.' ;
          }

        }

      }

      leaf duration {
        config false ;
        description 'The duration of test.' ;
        type uint32 {
          range 0..172800 {
            description 'The range of test duration.' ;
          }

        }

        units s ;
        default 0 ;
      }

      leaf ses-count {
        if-feature ses-measure ;

        description 'Severely errored second count of test.' ;
        type uint32 {
          range 0..4294967295 {
            description 'The range of ses-count.' ;
          }

        }

        default 0 ;
        ncd:revise-date 2021-02-18 ;
      }

      leaf total-count {
        if-feature ses-measure ;

        description 'Total second count of test.' ;
        type uint32 {
          range 0..4294967295 {
            description 'The range of total-count.' ;
          }

        }

        default 0 ;
        ncd:revise-date 2021-02-18 ;
      }

      leaf sesr {
        if-feature ses-measure ;

        description 'Severely error second ratio of test(precision:1/100).' ;
        type uint8 {
          range 0..100 ;

        }

        units "1/100" ;
        default 0 ;
        ncd:revise-date 2021-02-18 ;
      }

    }

    ncd:revise-date 2018-10-17 ;
  }

}
