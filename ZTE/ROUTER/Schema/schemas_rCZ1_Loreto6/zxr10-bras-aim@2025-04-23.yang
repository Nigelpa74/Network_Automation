module zxr10-bras-aim {
  namespace "http://www.zte.com.cn/zxr10/netconf/schema/bras/aim" ;
  prefix aim ;
  yang-version 1 ;
  import zxr10-netconf-defs {
    prefix ncd ;
  }

  organization "ZTE Corporation" ;
  contact "ZTE Corporation
  Nanjing Institute of ZTE Corporation
  No.68 Zijinghua Rd. Yuhuatai District, Nanjing, China
  Tel: +86-25-52870000" ;
  description 'This module describes the netconf model about Aim.' ;
  revision 2025-04-23 {
    description 'add acct-session-id-format' ;
  }

  revision 2024-03-27 {
    description 'add authentic-request-control lac user' ;
  }

  revision 2024-02-20 {
    description 'redirect-url-ipv6 web-server fault solve' ;
  }

  revision 2023-09-04 {
    description 'add new command (no) radius-attribute extend {port}' ;
  }

  revision 2023-08-10 {
    description 'add new command ipv6 address/nd-prefix/pd-prefix' ;
  }

  revision 2023-05-17 {
    description 'netconf encrypted-password <datatype>ciphertext</datatype>  add <log-type>password</log-type>' ;
  }

  revision 2023-03-23 {
    description 'new commond in aim accounting-template mode:
attribute zte_user_mac format {octets | string [{xx-xx-xx-xx-xx-xx|xx.xx.xx.xx.xx.xx|xx:xx:xx:xx:xx:xx|xxxx-xxxx-xxxx|xxxx.xxxx.xxxx|xxxx:xxxx:xxxx|xxxxxxxxxxxx}]}' ;
  }

  revision 2022-12-08 {
    description 'Modify bandwidth smartgroup load-sharing' ;
  }

  revision 2022-11-17 {
    description 'AIM choice' ;
  }

  revision 2022-11-07 {
    description 'Add the default of redirect-url-ipv4 and redirect-url-ipv6' ;
  }

  revision 2022-10-22 {
    description 'Attribute flow-extend {enable|disable}' ;
  }

  revision 2022-08-18 {
    description 'Add bandwidth trunck mode under author template.' ;
  }

  revision 2022-05-19 {
    description 'leaf "domain""advertise-url""nat-domain-name" add length range' ;
  }

  revision 2022-05-12 {
    description 'Add urpf-checkout attribute under security-template.' ;
  }

  revision 2022-02-10 {
    description 'Add lns-web-acl-ipv6.
Add lns-special-acl-ipv6.' ;
  }

  revision 2021-12-15 {
    description 'profile name length extend to 127' ;
  }

  revision 2021-12-14 {
    description 'Add default-username-template.
Add default-password-template.' ;
  }

  revision 2021-11-22 {
    description 'Obsolete leaf related to smlog' ;
  }

  revision 2021-08-05 {
    description 'add dhcp-lease-reonline switch' ;
  }

  revision 2021-07-20 {
    description 'obsolete queue-share node' ;
  }

  revision 2021-06-29 {
    description 'add option for copy-to-radius-group' ;
  }

  revision 2021-06-10 {
    description 'change subcar' ;
  }

  revision 2021-04-26 {
    description 'Add cmd intelligent-speed' ;
  }

  revision 2021-03-02 {
    description 'add performance-statistics switch' ;
  }

  revision 2021-01-28 {
    description 'add authentication request control' ;
  }

  revision 2021-01-19 {
    description 'password hex' ;
  }

  revision 2020-12-16 {
    description 'Encryption algorithm upgrade.' ;
  }

  revision 2020-10-10 {
    description 'set monitor session to 200' ;
  }

  revision 2020-06-24 {
    description 'Change default value of event num and event switch' ;
  }

  revision 2020-06-10 {
    description 'add dsl-agent-circuit-id command' ;
  }

  revision 2020-04-17 {
    description 'Obsolete radius-authen-password under domain and add new node choose-password' ;
  }

  revision 2020-03-12 {
    description 'Add ipv6-nd-ra-suppress under authorization-template-ex.' ;
  }

  revision 2020-03-02 {
    description 'Add flow-statistic container' ;
  }

  revision 2020-02-20 {
    description 'Add the access delay rule for bras and slot.' ;
  }

  revision 2020-01-21 {
    description 'Add ipv6-urpf-checkout attribute under security-template.' ;
  }

  revision 2020-01-13 {
    description 'Add radius username case sensitive.' ;
  }

  revision 2019-12-11 {
    description 'Add mac-ipv6-tables container' ;
  }

  revision 2019-10-16 {
    description 'accounting template policy' ;
  }

  revision 2019-09-19 {
    description 'Reauthen from other domain when no response from radius server' ;
  }

  revision 2019-08-23 {
    description 'user event log' ;
  }

  revision 2019-03-21 {
    description 'authentication max-session 1024000' ;
  }

  revision 2019-01-30 {
    description 'basic service' ;
  }

  revision 2019-01-28 {
    description 'add sustained advertisement online-effect switch' ;
  }

  revision 2019-01-11 {
    description 'configure nat-domain-name' ;
  }

  revision 2018-10-16 {
    description 'configure block rule for bras and slot.' ;
  }

  revision 2018-05-08 {
    description 'openflow-reconnect' ;
  }

  revision 2017-12-28 {
    description 'add copy accounting radius group' ;
  }

  revision 2017-12-06 {
    description 'add username replace switch' ;
  }

  revision 2017-12-04 {
    description 'Configure default domain by user type' ;
  }

  revision 2017-11-30 {
    description 'Add leaf of match-username force.' ;
  }

  revision 2017-11-28 {
    description 'add leaf of attribute nat-multi-portrange switch' ;
  }

  revision 2017-11-13 {
    description 'add check other vendor id switch' ;
  }

  revision 2017-10-10 {
    description 'Add openflow-disconnect' ;
  }

  revision 2017-06-26 ;

  revision 2016-03-02 {
    description 'Initial version.' ;
  }

  container configuration {
    description 'Global configuration model.' ;
    container subscriber-manager {
      description 'Submanager configuration model.' ;
      container sals {
        description 'The configuration infomation of sal. sal:server access list' ;
        list sal {
          description 'Sal configuration list' ;
          max-elements 256 ;
          key salname ;
          leaf salname {
            description 'Sal name' ;
            type string {
              length 1..32 ;

            }

          }

          leaf default-domain {
            description 'Default domain' ;
            type string {
              length 1..31 ;

            }

          }

          container none-domains {
            description 'None domain info' ;
            presence none-domains ;
            leaf none-domain {
              description 'None domain' ;
              type string {
                length 1..31 ;

              }

              mandatory true ;
            }

            leaf keep {
              description 'None domain keep switch' ;
              type enumeration {
                enum FALSE {
                  value 0 ;
                }

                enum TRUE {
                  value 1 ;
                }

              }

            }

          }

          container translatedomains {
            description 'Translate domain configuration' ;
            presence translatedomain ;
            list translatedomain {
              description 'Translate domain list' ;
              max-elements 64 ;
              key source-doamin ;
              leaf source-doamin {
                description 'Source domain' ;
                type string {
                  length 0..31 ;

                }

              }

              leaf dest-domain {
                description 'Destination domain' ;
                type string {
                  length 1..31 ;

                }

                mandatory true ;
              }

            }

          }

          leaf translateanydomain {
            description 'Translate any domain to this domain' ;
            type string {
              length 1..31 ;

            }

          }

          choice deny-permit {
            description 'Deny or permit all domain' ;
            default permit-any ;
            case deny-any {
              description 'Deny all domain access' ;
              leaf denyany {
                description 'Deny all domain access' ;
                type uint8 {
                  range 1 ;

                }

              }

            }

            case permit-any {
              description 'Permit all domain access' ;
              leaf permitany {
                description 'Permit all domain access' ;
                type uint8 {
                  range 0 ;

                }

              }

            }

          }

          container deny-permit-one-domain {
            description 'Deny or permit one domain access' ;
            presence deny-permit-one-domain ;
            list deny-permit-one-domain {
              description 'Deny or permit one domain access' ;
              max-elements 64 ;
              key domain-name ;
              leaf domain-name {
                description 'Domain name' ;
                type string {
                  length 1..31 ;

                }

              }

              choice permit-deny-domain {
                description 'Deny or permit one domain' ;
                mandatory true ;
                case permit-domain {
                  description 'Permit one domain' ;
                  leaf permitdomain {
                    description 'Permit one domain' ;
                    type uint8 {
                      range 0 ;

                    }

                  }

                }

                case deny-domain {
                  description 'Deny one domain' ;
                  leaf denydomain {
                    description 'Deny one domain' ;
                    type uint8 {
                      range 1 ;

                    }

                  }

                }

              }

            }

          }

          container change-domains {
            description 'Change domain configuration' ;
            presence change-domain ;
            list change-domain {
              description 'Change domain list' ;
              max-elements 16 ;
              key domain-name ;
              leaf domain-name {
                description 'Change domain name' ;
                type string {
                  length 1..31 ;

                }

              }

              leaf local-domain {
                description 'Local domain name' ;
                type string {
                  length 1..31 ;

                }

                mandatory true ;
              }

            }

          }

          container match-addresss {
            description 'Get domain by match ipv4 address' ;
            presence match-address ;
            list match-address {
              description 'Get domain by match ipv4 address' ;
              max-elements 64 ;
              key addrMatchName ;
              leaf addrMatchName {
                description 'Match item name' ;
                type string {
                  length 1..32 ;

                }

              }

              leaf domain-name {
                description 'Domain name' ;
                type string {
                  length 1..31 ;

                }

                mandatory true ;
              }

              leaf ipaddress {
                description 'IPv4 address' ;
                type ncd:ipv4-address ;

                mandatory true ;
              }

              leaf ipaddrMaskLen {
                description 'IPv4 mask' ;
                type ncd:ipv4-mask ;

                mandatory true ;
              }

            }

          }

          container match-usernames {
            description 'Get domain by match username' ;
            presence match-username ;
            list match-username {
              description 'Get domain by match username' ;
              max-elements 64 ;
              key username ;
              leaf username {
                description 'User name' ;
                type string {
                  length 1..32 ;

                }

              }

              leaf domainname {
                description 'Domain name' ;
                type string {
                  length 1..32 ;

                }

                mandatory true ;
              }

              leaf force {
                description 'Match username force.' ;
                type int8 {
                  range 0..1 {
                    description 'Force to map' ;
                  }

                }

              }

            }

          }

          container match-vlans {
            description 'Get domain by match vlan' ;
            presence matchvlan ;
            list match-vlan {
              description 'Get domain by match vlan' ;
              max-elements 64 ;
              key match-vlan-name ;
              leaf external-vlan {
                description 'External vlan range' ;
                type ncd:range ;

                mandatory true ;
              }

              leaf match-vlan-name {
                description 'Match item name' ;
                type string {
                  length 1..32 ;

                }

              }

              leaf internal-vlan {
                description 'Internal vlan range' ;
                type ncd:range {
                  pattern "(([0-9]+-[0-9]+)|([1-9][0-9]*)){1,1}" {
                    description '(([0-9]+-[0-9]+)|([1-9][0-9]*)){1,1}' ;
                  }

                }

              }

              leaf domainname {
                description 'Domain name' ;
                type string {
                  length 1..31 ;

                }

                mandatory true ;
              }

            }

          }

          container default-user-types {
            description 'Configure default domain by user type' ;
            presence user-type ;
            list user-type {
              description 'Configure default domain by user type' ;
              key user-type ;
              leaf user-type {
                description 'user type' ;
                type enumeration {
                  enum pppox {
                    value 1 ;
                    description 'Set PPPoX and LAC subscriber' ;
                  }

                  enum ipox {
                    value 2 ;
                    description 'Set IPoX subscriber' ;
                  }

                  enum multi-hop {
                    value 4 ;
                    description 'Set Multi-Hop and IPox L3 subscriber' ;
                  }

                  enum lns {
                    value 3 ;
                    description 'Set LNS subscriber' ;
                  }

                }

              }

              leaf domain {
                description 'domain name' ;
                type string {
                  length 1..31 ;

                }

              }

            }

          }

        }

      }

      container authorization-templates {
        description 'Authorization template information' ;
        list authorization-template {
          description 'Authorizatin template list' ;
          max-elements 20000 ;
          key authorization-name ;
          leaf authorization-name {
            description 'Authorization name' ;
            type string {
              length 1..31 ;

            }

          }

          leaf authorization-type {
            description 'Set authorization type' ;
            type enumeration {
              enum diameter {
                value 1 ;
                description 'Diameter authorization' ;
              }

              enum radius {
                value 2 ;
                description 'RADIUS authorization' ;
              }

              enum mix-diameter {
                value 3 ;
                description 'Mix-Diameter authorization' ;
              }

              enum mix-radius {
                value 4 ;
                description 'Mix-Radius authorization' ;
              }

              enum none {
                value 6 ;
                description 'No authorization' ;
              }

            }

          }

          leaf bind-nat-domain {
            status obsolete {
              ncd:revise-date 2019-12-11 ;
            }

            description 'Bind nat domain' ;
            type string {
              length 1..31 ;

            }

          }

          leaf access-list-input-ipv4 {
            description 'Configure ipv4 input access list' ;
            type string {
              length 1..31 ;

            }

          }

          leaf access-list-input-ipv6 {
            description 'Configure ipv6 input access list' ;
            type string {
              length 1..31 ;

            }

          }

          leaf access-list-output-ipv4 {
            description 'Configure ipv4 output access list' ;
            type string {
              length 1..31 ;

            }

          }

          leaf access-list-output-ipv6 {
            description 'Configure ipv6 output access list' ;
            type string {
              length 1..31 ;

            }

          }

          leaf vpdn-group {
            description 'Vpdn group configuration' ;
            type string {
              length 1..31 ;

            }

          }

          leaf timeout-absolute {
            description 'User absolutely timeout' ;
            type uint32 {
              range 60..2147483647 ;

            }

          }

          leaf session-timeout-switch {
            description 'Config relet or absolute type' ;
            type enumeration {
              enum relet {
                value 1 ;
              }

              enum absolute {
                value 0 ;
              }

              enum relet-from-now {
                value 2 ;
              }

            }

            default absolute ;
          }

          leaf service-priority {
            description 'Configure service priority' ;
            type uint8 {
              range 1..4 ;

            }

          }

          leaf service-bandwidth {
            description 'Configure service bandwidth' ;
            type uint32 {
              range 66..16777215 ;

            }

          }

          leaf qos-queue-statistics {
            description 'Set qos queue statistics function' ;
            type enumeration {
              enum enable {
                value 1 ;
              }

              enum disable {
                value 0 ;
              }

            }

            default disable ;
          }

          leaf nat-type {
            description 'Nat type' ;
            type enumeration {
              enum none {
                value 0 ;
              }

              enum inside {
                value 1 ;
              }

            }

          }

          leaf nat-service {
            description 'Nat service switch' ;
            type enumeration {
              enum enable {
                value 0 ;
              }

              enum disable {
                value 1 ;
              }

            }

          }

          leaf igmp-service-profile {
            type uint8 {
              range 1..100 ;

            }

          }

          leaf lns-load-sharing {
            description 'Lns load share configuration switch' ;
            type enumeration {
              enum enable {
                value 1 ;
              }

              enum disable {
                value 0 ;
              }

            }

          }

          leaf lns-web-acl {
            description 'Lns web acl' ;
            type string {
              length 1..31 ;

            }

          }

          leaf dhcp-lease-reonline {
            description 'dhcp-lease-reonline switch.' ;
            type enumeration {
              enum enable {
                value 1 ;
                description 'Enable dhcp-lease-reonline function.' ;
              }

              enum disable {
                value 0 ;
                description 'Disable dhcp-lease-reonline function.' ;
              }

            }

            ncd:revise-date 2021-08-05 ;
          }

          container advertise {
            description 'Advertisement information configuration' ;
            leaf keep-time {
              description 'Keep advertisement time' ;
              type uint32 {
                range 10..3600 ;

              }

            }

            leaf online-effect {
              description 'Online-effect switch' ;
              type enumeration {
                enum FALSE {
                  value 0 ;
                }

                enum TRUE {
                  value 1 ;
                }

              }

            }

            container advertise-mode {
              description 'Advertise mode information' ;
              presence url-mode ;
              choice mode {
                description 'Advertise redirect mode' ;
                case portal {
                  description 'Portal' ;
                  leaf portal {
                    description 'Portal advertisement' ;
                    type enumeration {
                      enum portal {
                        value 0 ;
                      }

                    }

                    mandatory true ;
                  }

                  leaf delay {
                    description 'Portal advertisment delay time' ;
                    type uint8 {
                      range 0..3 ;

                    }

                  }

                }

                case padm {
                  description 'Padm advertisement mode' ;
                  leaf padm {
                    type enumeration {
                      enum padm {
                        value 2 ;
                      }

                    }

                  }

                }

              }

            }

            container web-force {
              description 'Configure advertise web-force  timer and count' ;
              presence web-force ;
              leaf web-force-timer {
                description 'Advertise period' ;
                type uint32 {
                  range 5..71582788 ;

                }

                mandatory true ;
              }

              leaf web-force-count {
                description 'Advertise counter' ;
                type uint32 {
                  range 1..2147483647 ;

                }

                mandatory true ;
              }

            }

            container url-ipv4 {
              description 'Configure advertise url' ;
              choice url-mode {
                description 'Url mode' ;
                case url {
                  description 'Advertise url' ;
                  leaf advertise-url {
                    description 'Advertise url' ;
                    type string {
                      length 1..127 ;

                    }

                  }

                }

                case web-server-number {
                  description 'Bind web server with v4 advertise' ;
                  leaf number {
                    description 'Web server number <1-128>' ;
                    type uint8 {
                      range 1..128 ;

                    }

                  }

                }

              }

            }

            container url-ipv6 {
              description 'Configure advertise url-ipv6' ;
              choice url-mode {
                description 'Url mode' ;
                case url {
                  description 'Advertise url' ;
                  leaf advertise-url {
                    description 'Advertise url' ;
                    type string {
                      length 1..127 ;

                    }

                  }

                }

                case web-server-number {
                  description 'Bind web server with v4 advertise' ;
                  leaf number {
                    description 'Web server number <1-128>' ;
                    type uint8 {
                      range 1..128 ;

                    }

                  }

                }

              }

            }

          }

          container force {
            leaf redirect-web {
              description 'Force redirct web' ;
              type uint32 {
                range 1 ;

              }

            }

            leaf timer {
              description 'Configure timer' ;
              type uint32 {
                range 1..71582788 ;

              }

            }

            leaf count {
              description 'Web force count' ;
              type uint32 {
                range 1..2147483647 ;

              }

            }

          }

          container monitor-bind-sessions {
            description 'Monitor information' ;
            list monitor-bind-session {
              description 'Monitor configuration' ;
              max-elements 2 ;
              key direction ;
              leaf direction {
                description 'Monitor direction' ;
                type enumeration {
                  enum both {
                    value 1 ;
                  }

                  enum rx {
                    value 2 ;
                  }

                  enum tx {
                    value 3 ;
                  }

                }

              }

              leaf session-num {
                description 'Monitor session number' ;
                type uint32 {
                  range 1..200 ;

                }

              }

            }

          }

          container authen-fail {
            description 'Authentication fail policy information' ;
            choice policy {
              description 'Policy choice' ;
              case offline {
                description 'Offline policy' ;
                leaf offline {
                  description 'Kickoff the user immediately' ;
                  type enumeration {
                    enum offline {
                      value 0 ;
                    }

                  }

                }

              }

              case redirect-web {
                description 'Redirect web choice' ;
                leaf redirect-web {
                  description 'Redirect the user to a fixed web page' ;
                  type enumeration {
                    enum redirect-web {
                      value 1 ;
                    }

                  }

                }

                leaf none-accounting {
                  description 'Stop accounting' ;
                  type enumeration {
                    enum FALSE {
                      value 0 ;
                    }

                    enum TRUE {
                      value 1 ;
                    }

                  }

                  default FALSE ;
                }

              }

            }

          }

          container user-group {
            description 'User group information' ;
            container bandwidth {
              description 'User group bandwidth information' ;
              presence bandwidth ;
              leaf input {
                description 'Input' ;
                type uint32 {
                  range 66..16777215 ;

                }

              }

              leaf output {
                description 'Output' ;
                type uint32 {
                  range 66..16777215 ;

                }

              }

            }

            leaf local-start {
              description 'User group local start' ;
              type enumeration {
                enum local-start {
                  value 1 ;
                }

              }

            }

            container service-priority {
              description 'User group service priority information' ;
              leaf input {
                description 'Input' ;
                type uint32 {
                  range 1..4 ;

                }

                default 3 ;
              }

              leaf output {
                description 'Output' ;
                type uint32 {
                  range 1..4 ;

                }

                default 3 ;
              }

            }

          }

          container traffic-rate-mode {
            description 'Traffic rate mode' ;
            leaf input {
              description 'Input' ;
              type enumeration {
                enum together {
                  value 1 ;
                }

                enum separate {
                  value 2 ;
                }

              }

              default together ;
            }

            leaf output {
              description 'Output' ;
              type enumeration {
                enum together {
                  value 1 ;
                }

                enum separate {
                  value 2 ;
                }

              }

              default together ;
            }

          }

          container prepay {
            leaf flow {
              description 'Prepay flow' ;
              type uint32 {
                range 0..4294967294 ;

              }

              default 0 ;
            }

            leaf type {
              description 'Prepay type' ;
              type enumeration {
                enum up {
                  value 3 ;
                }

                enum down {
                  value 4 ;
                }

                enum dual {
                  value 2 ;
                }

              }

              default dual ;
            }

            leaf time {
              description 'Prepay time' ;
              type uint32 {
                range "0 | 60..4294967294" ;

              }

              default 0 ;
            }

          }

          container mld {
            description 'Mld information' ;
            leaf service-profile {
              description 'Service profile number' ;
              type uint8 {
                range 0..100 ;

              }

              default 0 ;
            }

          }

          container authorization-template-ex {
            leaf userquota-exceed-support-prepay {
              description 'User quota exceed support prepay switch' ;
              type enumeration {
                enum open {
                  value 0 ;
                }

                enum close {
                  value 1 ;
                }

              }

              default open ;
            }

            leaf laft6-bind-tunnel-if-name {
              description 'Laft6 tunnel interface name' ;
              type ncd:ifname {
                length 0..31 ;

              }

            }

            leaf nat-bind-ip-attribute {
              description 'Is support bind' ;
              type enumeration {
                enum TRUE {
                  value 1 ;
                }

                enum FALSE {
                  value 0 ;
                }

              }

              default FALSE ;
            }

            leaf qos-pmap-error {
              description 'Configure subscriber online or offline if radius authorization policy-map does not exist' ;
              type enumeration {
                enum online {
                  value 0 ;
                }

                enum offline {
                  value 1 ;
                }

              }

              default online ;
            }

            leaf smart-traffic-operation-switch {
              description 'Smart traffic operation switch' ;
              type enumeration {
                enum enable {
                  value 1 ;
                }

                enum disable {
                  value 2 ;
                }

              }

            }

            leaf ipv6-nd-ra-suppress {
              type enumeration {
                enum disable {
                  value 0 ;
                  description 'Open IPv6 router advertisements' ;
                }

                enum enable {
                  value 1 ;
                  description 'Close IPv6 router advertisements' ;
                }

              }

              default disable ;
              ncd:revise-date 2020-03-12 ;
            }

          }

          container url-log {
            description 'Set url-log function' ;
            leaf url-log-switch {
              description 'Url log switch' ;
              type enumeration {
                enum enable {
                  value 1 ;
                }

                enum disable {
                  value 0 ;
                }

              }

            }

          }

          container username-replace {
            description 'Set username replace switch' ;
            leaf username-replace-switch {
              description 'Username replace switch' ;
              type enumeration {
                enum enable {
                  value 1 ;
                }

                enum disable {
                  value 0 ;
                }

              }

              default disable ;
            }

          }

          container user-quota {
            description 'Configure user quota exceed policy' ;
            presence user-quota ;
            leaf userquota-exceed-policy {
              description 'User quota exceed policy' ;
              type enumeration {
                enum kickoff {
                  value 1 ;
                }

                enum hold {
                  value 2 ;
                }

                enum redirect-web {
                  value 3 ;
                }

              }

              mandatory true ;
            }

            leaf userquota-exceed-send-stop-account {
              description 'Send stop accounting packet' ;
              type enumeration {
                enum send-stop-accounting {
                  value 1 ;
                }

              }

            }

          }

          container user-priority-output {
            description 'User input priority information' ;
            choice priority-mode {
              description 'User output priority mode choice' ;
              case dscp {
                description 'Configure dscp field' ;
                leaf dscp {
                  description 'Configure dscp field' ;
                  type enumeration {
                    enum dscp {
                      value 1 ;
                    }

                  }

                  mandatory true ;
                }

                leaf priority-num1 {
                  description 'Dscp value' ;
                  type uint32 {
                    range 0..63 ;

                  }

                  mandatory true ;
                }

              }

              case inherit-from {
                description 'Config user priority inherit from DSCP/ MPLS-EXP' ;
                leaf priority-num2 {
                  description 'Use IP DSCP and MPLS-EXP for user priority' ;
                  type enumeration {
                    enum dscp {
                      value 10 ;
                    }

                    enum mpls-exp {
                      value 11 ;
                    }

                  }

                }

              }

              case priority {
                description 'User priority number' ;
                leaf priority-num3 {
                  description 'User priority number' ;
                  type uint32 {
                    range 0..7 ;

                  }

                }

              }

            }

          }

          container user-priority-input {
            description 'User input priority information' ;
            choice priority-mode {
              description 'User input priority mode choice' ;
              case dscp {
                description 'Configure dscp field' ;
                leaf dscp {
                  description 'Configure dscp field' ;
                  type enumeration {
                    enum dscp {
                      value 1 ;
                    }

                  }

                  mandatory true ;
                }

                leaf priority-num1 {
                  description 'Dscp value' ;
                  type uint32 {
                    range 0..63 ;

                  }

                  mandatory true ;
                }

              }

              case inherit-from {
                description 'Configure user priority inherit from 802.1P' ;
                leaf priority-num2 {
                  description 'Use inner 802.1P and outer 802.1P for user priority' ;
                  type enumeration {
                    enum in-8021p {
                      value 8 ;
                    }

                    enum out-8021p {
                      value 9 ;
                    }

                  }

                }

              }

              case priority {
                description 'User priority number' ;
                leaf priority-num3 {
                  description 'User priority number' ;
                  type uint32 {
                    range 0..7 ;

                  }

                }

              }

            }

          }

          container qos-policy-inputs {
            description 'User input qos policy information' ;
            list qos-policy-input {
              description 'User input qos policy' ;
              max-elements 3 ;
              key v4_or_v6_flag ;
              leaf v4_or_v6_flag {
                description 'Qos policy type' ;
                type enumeration {
                  enum ipv4 {
                    value 1 ;
                  }

                  enum ipv6 {
                    value 2 ;
                  }

                  enum user {
                    value 3 ;
                  }

                }

              }

              leaf policy-name {
                description 'Qos policy name' ;
                type string {
                  length 1..31 ;

                }

              }

            }

          }

          container qos-policy-outputs {
            description 'User output qos policy information' ;
            list qos-policy-output {
              description 'User output qos policy' ;
              max-elements 3 ;
              key v4_or_v6_flag ;
              leaf v4_or_v6_flag {
                description 'Qos policy type' ;
                type enumeration {
                  enum ipv4 {
                    value 1 ;
                  }

                  enum ipv6 {
                    value 2 ;
                  }

                  enum user {
                    value 3 ;
                  }

                }

              }

              leaf policy-name {
                description 'Qos policy name' ;
                type string {
                  length 1..31 ;

                }

              }

            }

          }

          container sub-car-input {
            description 'Configure the input car of subscriber' ;
            container user {
              description 'Used by integrated user' ;
              presence ipv6 ;
              leaf cir {
                description 'Configure committed information rate' ;
                type uint32 {
                  range 66..16777215 ;

                }

                mandatory true ;
              }

              leaf cbs {
                description 'Configure committed burst size' ;
                type uint32 {
                  range 15..512000 ;

                }

              }

              leaf pir {
                description 'Configure peak information rate' ;
                type uint32 {
                  range 66..16777215 ;

                }

              }

              leaf pbs {
                description 'Configure peak burst size' ;
                type uint32 {
                  range 15..512000 ;

                }

              }

            }

            container ipv4 {
              description 'Used by ipv4 user' ;
              presence ipv4 ;
              leaf cir {
                description 'Configure committed information rate' ;
                type uint32 {
                  range 66..16777215 ;

                }

                mandatory true ;
              }

              leaf cbs {
                description 'Configure committed burst size' ;
                type uint32 {
                  range 15..512000 ;

                }

              }

              leaf pir {
                description 'Configure peak information rate' ;
                type uint32 {
                  range 66..16777215 ;

                }

              }

              leaf pbs {
                description 'Configure peak burst size' ;
                type uint32 {
                  range 15..512000 ;

                }

              }

            }

            container ipv6 {
              description 'Used by ipv6 user' ;
              presence ipv6 ;
              leaf cir {
                description 'Configure committed information rate' ;
                type uint32 {
                  range 66..16777215 ;

                }

                mandatory true ;
              }

              leaf cbs {
                description 'Configure committed burst size' ;
                type uint32 {
                  range 15..512000 ;

                }

              }

              leaf pir {
                description 'Configure peak information rate' ;
                type uint32 {
                  range 66..16777215 ;

                }

              }

              leaf pbs {
                description 'Configure peak burst size' ;
                type uint32 {
                  range 15..512000 ;

                }

              }

            }

          }

          container sub-car-output {
            description 'Configure the output car of subscriber' ;
            container user {
              description 'Used by integrated user' ;
              presence ipv6 ;
              leaf cir {
                description 'Configure committed information rate' ;
                type uint32 {
                  range 66..16777215 ;

                }

                mandatory true ;
              }

              leaf cbs {
                description 'Configure committed burst size' ;
                type uint32 {
                  range 15..512000 ;

                }

              }

              leaf pir {
                description 'Configure peak information rate' ;
                type uint32 {
                  range 66..16777215 ;

                }

              }

              leaf pbs {
                description 'Configure peak burst size' ;
                type uint32 {
                  range 15..512000 ;

                }

              }

            }

            container ipv4 {
              description 'Used by ipv4 user' ;
              presence ipv4 ;
              leaf cir {
                description 'Configure committed information rate' ;
                type uint32 {
                  range 66..16777215 ;

                }

                mandatory true ;
              }

              leaf cbs {
                description 'Configure committed burst size' ;
                type uint32 {
                  range 15..512000 ;

                }

              }

              leaf pir {
                description 'Configure peak information rate' ;
                type uint32 {
                  range 66..16777215 ;

                }

              }

              leaf pbs {
                description 'Configure peak burst size' ;
                type uint32 {
                  range 15..512000 ;

                }

              }

            }

            container ipv6 {
              description 'Used by ipv6 user' ;
              presence ipv6 ;
              leaf cir {
                description 'Configure committed information rate' ;
                type uint32 {
                  range 66..16777215 ;

                }

                mandatory true ;
              }

              leaf cbs {
                description 'Configure committed burst size' ;
                type uint32 {
                  range 15..512000 ;

                }

              }

              leaf pir {
                description 'Configure peak information rate' ;
                type uint32 {
                  range 66..16777215 ;

                }

              }

              leaf pbs {
                description 'Configure peak burst size' ;
                type uint32 {
                  range 15..512000 ;

                }

              }

            }

          }

          container redirect-url-ipv4s {
            description 'Config redirect url for subscriber' ;
            choice redirect-url-ipv4 {
              description 'Config redirect url for subscriber' ;
              default web-server-ipv4 ;
              case url-ipv4 {
                description 'Redirect ipv4 url' ;
                leaf url {
                  description 'Uniform Resoure Locator' ;
                  type string {
                    length 0..127 ;

                  }

                }

              }

              case web-server-ipv4 {
                description 'Bind web server with v4 redirect' ;
                leaf web-server {
                  description 'Web server number' ;
                  type uint8 {
                    range 0..128 ;

                  }

                  default 0 ;
                }

              }

            }

          }

          container redirect-url-ipv6s {
            description 'Config redirect url ipv6 for subscriber' ;
            choice redirect-url-ipv6 {
              default web-server-ipv6 ;
              case url-ipv6 {
                leaf url {
                  description 'Uniform Resoure Locator' ;
                  type string {
                    length 0..127 ;

                  }

                }

              }

              case web-server-ipv6 {
                leaf web-server {
                  description 'Web server number' ;
                  type uint8 {
                    range 0..128 ;

                  }

                  default 0 ;
                }

              }

            }

          }

          container nat44-service-unavaiable {
            description 'Configure nat44-service unavailable type' ;
            presence nat44 ;
            leaf vpdn-group-name {
              type string {
                length 1..31 ;

              }

              mandatory true ;
            }

            leaf pppox-switch-to-l2tp {
              description 'Pppox Nat44 subtype switch to lac' ;
              type enumeration {
                enum TRUE {
                  value 1 ;
                }

                enum FALSE {
                  value 0 ;
                }

              }

              mandatory true ;
            }

          }

          container nat44-service {
            container unavaiable {
              description 'Configure nat44-service unavailable type' ;
              choice type {
                case alloc-public-address {
                  leaf alloc-public-address {
                    description 'Set nat44-service switch to alloc public address' ;
                    type uint32 {
                      range 0 ;

                    }

                  }

                }

                case alloc-private-address {
                  leaf alloc-private-address {
                    description 'Set nat44-service switch to alloc private address' ;
                    type uint32 {
                      range 1 ;

                    }

                  }

                }

                case remote-nat {
                  leaf remote-nat {
                    description 'Configure nat44-service switch to remote nat' ;
                    type uint32 {
                      range 2 ;

                    }

                    mandatory true ;
                  }

                  leaf route-map {
                    description 'Route map name' ;
                    type string {
                      length 1..31 ;

                    }

                  }

                  leaf gre-l3vpn {
                    description 'Route map name of gre condition or l3vpn condition' ;
                    type enumeration {
                      enum gre {
                        value 1 ;
                      }

                      enum l3vpn {
                        value 2 ;
                      }

                    }

                  }

                }

              }

            }

          }

          container bind-nat-domain-names {
            description 'nat-domain-name' ;
            presence nat-domain-name ;
            list bind-nat-domain-name {
              description 'nat-domain-name configuration' ;
              max-elements 2 ;
              key type ;
              leaf type {
                description 'nat-domain-name type' ;
                type enumeration {
                  enum ipv4 {
                    value 1 ;
                  }

                  enum ipv6 {
                    value 2 ;
                  }

                }

              }

              leaf nat-domain-name {
                description 'nat-domain-name' ;
                type string {
                  length 1..31 ;

                }

                mandatory true ;
              }

            }

          }

          container flow-statistic {
            description 'Set flow-statistic function' ;
            leaf mode {
              description 'Set flow-statistic frequency mode' ;
              type enumeration {
                enum normal {
                  value 0 ;
                  description 'Set to normal flow-statistic frequency mode' ;
                }

                enum fast {
                  value 1 ;
                  description 'Set to fast flow-statistic frequency mode' ;
                }

              }

            }

            leaf switch {
              description 'Disable/enable flow-statistic function' ;
              type enumeration {
                enum enable {
                  value 1 ;
                  description 'Enable flow-statistic function' ;
                }

                enum disable {
                  value 0 ;
                  description 'Disable flow-statistic function' ;
                }

              }

            }

            ncd:revise-date 2020-03-02 ;
          }

          container intelligent-speed {
            leaf qos-policy {
              type enumeration {
                enum isolated {
                  value 1 ;
                }

              }

            }

            ncd:revise-date 2021-04-26 ;
          }

          leaf lns-web-acl-ipv6 {
            description 'web acl ipv6 for lns PPP' ;
            type string {
              length 1..31 ;

            }

            ncd:revise-date 2022-02-10 ;
          }

          leaf lns-special-acl-ipv6 {
            description 'special acl ipv6 for lns.' ;
            type string {
              length 1..31 ;

            }

            ncd:revise-date 2022-02-10 ;
          }

          container bandwidth-sg-load-sharings {
            description 'Configure mode of bandwidth' ;
            list bandwidth-sg-load-sharing {
              key 'user-type direction' ;
              leaf user-type {
                type enumeration {
                  enum ip-host {
                    value 1 ;
                  }

                }

              }

              leaf direction {
                type enumeration {
                  enum input {
                    value 1 ;
                  }

                }

              }

            }

            ncd:revise-date 2022-12-08 ;
          }

        }

      }

      container authentication-templates {
        description 'AIM authentication template model.' ;
        list authentication-template {
          description 'AIM authentication template configuration list.' ;
          max-elements 2000 ;
          key authen-name ;
          leaf authen-name {
            description 'AIM authentication template name.' ;
            type string {
              length 1..31 {
                description 'AIM authentication template name (1-31 characters).' ;
              }

            }

          }

          leaf authen-type {
            description 'AIM authentication type.' ;
            type enumeration {
              enum none {
                value 1 ;
                description 'None authentication.' ;
              }

              enum local {
                value 2 ;
                description 'Local authentication.' ;
              }

              enum radius {
                value 3 ;
                description 'Radius authentication.' ;
              }

              enum local-radius {
                value 4 ;
                description 'Local radius authentication.' ;
              }

              enum radius-local {
                value 5 ;
                description 'Radius local authentication.' ;
              }

              enum radius-none {
                value 6 ;
                description 'Radius none authentication.' ;
              }

              enum diameter {
                value 7 ;
                description 'Diameter authentication.' ;
              }

              enum local-diameter {
                value 8 ;
                description 'Local diameter authentication.' ;
              }

              enum diameter-local {
                value 9 ;
                description 'Diameter local authentication.' ;
              }

              enum diameter-none {
                value 10 ;
                description 'Diameter none authentication.' ;
              }

              enum 0 {
                value 0 ;
              }

            }

            default 0 ;
          }

          leaf max-session {
            description 'AIM authentication template max-access-session.' ;
            type uint32 {
              range 1..1024000 {
                description 'Max-session (1-1024000).' ;
              }

            }

            default 1024000 ;
          }

          leaf none-username-access {
            description 'Switch of permiting none username access' ;
            type enumeration {
              enum disable {
                value 0 ;
                description 'Disable none-username-access' ;
              }

              enum enable {
                value 1 ;
                description 'Enable none-username-access' ;
              }

            }

            default disable ;
          }

          leaf single-login {
            description 'Switch of permiting to single login' ;
            type enumeration {
              enum disable {
                value 0 ;
                description 'Disable single-login' ;
              }

              enum enable {
                value 1 ;
                description 'Enable single-login' ;
              }

            }

            default disable ;
          }

          leaf radius-group-name {
            description 'Radius group name.' ;
            type string {
              length 1..31 {
                description 'RADIUS group name (1-31 characters).' ;
              }

            }

          }

          leaf diameter-group-name {
            description 'DIAMETER group name' ;
            type string {
              length 1..32 {
                description 'DIAMETER group name (1-32 characters).' ;
              }

            }

          }

          leaf radius-down-redirect-domain {
            description 're-authen domain when radius server down or timeout' ;
            type string {
              length 1..31 {
                description 'Reauthen domain name(1-31 characters).' ;
              }

            }

          }

          leaf authen-fail-redirect-domain {
            description 'Reauthen domain name.' ;
            type string {
              length 1..31 {
                description 'Reauthen domain name(1-31 characters).' ;
              }

            }

          }

          list password-hex {
            key passwd-hex ;
            leaf passwd-hex {
              type enumeration {
                enum dhcpv4-option60 {
                  value 1 ;
                }

                enum dhcpv6-option16 {
                  value 2 ;
                }

                enum all {
                  value 16 ;
                }

              }

            }

            ncd:revise-date 2021-01-19 ;
          }

        }

      }

      container domains {
        description 'BRAS domain manage configuration model.' ;
        list domain {
          description 'BRAS domain configuration model list.' ;
          max-elements 4000 ;
          key domain-name ;
          leaf domain-name {
            description 'Domain name.' ;
            type string {
              length 1..31 {
                description 'Domain name (1-31 characters).' ;
              }

            }

          }

          leaf account-share {
            description 'Account share switch.' ;
            type enumeration {
              enum enable {
                value 0 ;
                description 'Open account share switch.' ;
              }

              enum disable {
                value 1 ;
                description 'Close account share switch.' ;
              }

            }

            default enable ;
          }

          leaf advertise {
            description 'Domain advertise switch.' ;
            type enumeration {
              enum disable {
                value 0 ;
                description 'Close advertise switch.' ;
              }

              enum enable {
                value 1 ;
                description 'Open advertise switch.' ;
              }

            }

            default disable ;
          }

          leaf ancp {
            description 'Ancp switch.' ;
            type enumeration {
              enum disable {
                value 0 ;
                description 'Close ancp function.' ;
              }

              enum enable {
                value 1 ;
                description 'Open ancp function.' ;
              }

            }

            default disable ;
          }

          leaf bind-accounting-template {
            description 'Accounting template name.' ;
            type string {
              length 1..31 {
                description 'Accounting template name (1-31 characters).' ;
              }

            }

          }

          leaf bind-authentication-template {
            description 'Authentication template name .' ;
            type string {
              length 1..31 {
                description 'Authentication template name (1-31 characters).' ;
              }

            }

          }

          leaf bind-authorization-template {
            description 'Authorization template name (1-31 characters).' ;
            type string {
              length 1..31 {
                description 'Authorization template name (1-31 characters).' ;
              }

            }

          }

          leaf bind-security-template {
            description 'Security template name (1-31 characters).' ;
            type string {
              length 1..31 {
                description 'Security template name (1-31 characters).' ;
              }

            }

          }

          leaf dhcp-mode {
            description 'Set dhcp mode.' ;
            type enumeration {
              enum server {
                value 0 ;
                description 'Set dhcp server mode.' ;
              }

              enum relay {
                value 1 ;
                description 'Set dhcp relay mode.' ;
              }

            }

            default server ;
          }

          leaf dhcpv6-mode {
            description 'Set DHCPV6 mode.' ;
            type enumeration {
              enum server {
                value 0 ;
                description 'Set DHCPV6 server mode.' ;
              }

              enum relay {
                value 1 ;
                description 'Set DHCPV6 relay mode' ;
              }

            }

            default server ;
          }

          leaf domain-priority {
            description 'Domain priority.' ;
            type uint8 {
              range 1..4 {
                description 'Domain priority.' ;
              }

            }

          }

          leaf domain-status {
            description 'Set domain status.' ;
            type enumeration {
              enum enable {
                value 0 ;
                description 'Enable domain.' ;
              }

              enum disable {
                value 1 ;
                description 'Disable domain.' ;
              }

              enum lock {
                value 2 ;
                description 'Lock domain.' ;
              }

              enum unlock {
                value 3 ;
                description 'Unlock domain.' ;
              }

            }

            default enable ;
          }

          leaf ip-vrf {
            description 'Vrf name.' ;
            type string {
              length 1..32 {
                description 'Ip vrf name (1-32 characters).' ;
              }

            }

          }

          leaf ipv4-vrf {
            description 'Ipv4 vrf name.' ;
            type string {
              length 1..32 {
                description 'Ipv4 vrf name (1-32 characters).' ;
              }

            }

          }

          leaf ipv6-vrf {
            description 'Ipv6 vrf name.' ;
            type string {
              length 1..32 {
                description 'Ipv6 vrf name (1-32 characters).' ;
              }

            }

          }

          leaf mac-ip-table-lookup {
            description 'Mac ip table lookup switch.' ;
            type enumeration {
              enum disable {
                value 0 ;
                description 'Close mac ip table lookup switch.' ;
              }

              enum enable {
                value 1 ;
                description 'Open mac ip table lookup switch.' ;
              }

            }

            default disable ;
          }

          leaf mac-ipv6-table-lookup {
            description 'Mac ipv6 table lookup switch.' ;
            type enumeration {
              enum disable {
                value 0 ;
                description 'Close mac ipv6 table lookup switch.' ;
              }

              enum enable {
                value 1 ;
                description 'Open mac ipv6 table lookup switch.' ;
              }

            }

            default disable ;
          }

          leaf queue-share {
            status obsolete {
              ncd:revise-date 2021-07-20 ;
            }

            description 'Queue share switch.' ;
            type enumeration {
              enum disable {
                value 0 ;
                description 'Close queue share switch.' ;
              }

              enum enable {
                value 1 ;
                description 'Open queue share switch.' ;
              }

            }

            default disable ;
          }

          leaf radius-authen-password {
            status obsolete {
              ncd:revise-date 2020-04-17 ;
            }

            description 'Authentication password for domain.' ;
            type string {
              length 1..31 {
                description 'Set auth password for domain(1-31 characters).' ;
              }

            }

          }

          leaf service-type {
            description 'Set user access service type.' ;
            type enumeration {
              enum login {
                value 1 ;
                description 'Login service type.' ;
              }

              enum framed {
                value 2 ;
                description 'Framed service type.' ;
              }

              enum callback-login {
                value 3 ;
                description 'Callback-login service type.' ;
              }

              enum callback-framed {
                value 4 ;
                description 'Callback-framed service type.' ;
              }

              enum outbound {
                value 5 ;
                description 'Outbound service type.' ;
              }

              enum administrative {
                value 6 ;
                description 'Administrative service type.' ;
              }

              enum nas-prompt {
                value 7 ;
                description 'Nas-prompt service type.' ;
              }

              enum authenticate-only {
                value 8 ;
                description 'Authenticate-only service type.' ;
              }

              enum callback-nas-prompt {
                value 9 ;
                description 'Callback-nas-prompt service type.' ;
              }

              enum call-check {
                value 10 ;
                description 'Call-check sevice type.' ;
              }

              enum callback-administrative {
                value 11 ;
                description 'Callback-administrative sevice type.' ;
              }

            }

          }

          leaf tunnel-domain {
            description 'Tunnel domain switch.' ;
            type enumeration {
              enum disable {
                value 0 ;
                description 'Close tunnel-domain switch.' ;
              }

              enum enable {
                value 1 ;
                description 'Open tunnel-domain switch.' ;
              }

            }

            default disable ;
          }

          leaf username-trim {
            description 'Username-trim switch.' ;
            type enumeration {
              enum disable {
                value 0 ;
                description 'Close username-trim switch.' ;
              }

              enum enable {
                value 1 ;
                description 'Open username-trim switch' ;
              }

            }

            default disable ;
          }

          leaf web-acl-name {
            description 'Web acl name.' ;
            type string {
              length 1..31 {
                description 'Web acl name (1-31 characters).' ;
              }

            }

          }

          leaf web-acl-ipv6-name {
            description 'Web ipv6 acl name.' ;
            type string {
              length 1..31 {
                description 'WEB ipv6 acl name (1-31 characters).' ;
              }

            }

          }

          container web-servers {
            description 'Web server id.' ;
            list web-server {
              description 'Web server id.' ;
              max-elements 2 ;
              key web-sever-number ;
              leaf web-sever-number {
                description 'Web server number.' ;
                type uint8 {
                  range 1..128 {
                    description 'Web server number.' ;
                  }

                }

              }

              leaf secondary-web-server {
                description 'Second server flag.' ;
                type enumeration {
                  enum first {
                    value 1 ;
                    description 'First web server.' ;
                  }

                  enum second {
                    value 2 ;
                    description 'Second web server.' ;
                  }

                }

              }

            }

          }

          container ultrashort-acct-time {
            description 'Config ultrashort acct time.' ;
            presence acct-time ;
            leaf acct-unit-time {
              description 'Acctounting unit time.' ;
              type uint16 {
                range 30..3600 {
                  description 'Acct-unit-time(s)' ;
                }

              }

              mandatory true ;
            }

            leaf ultrashort-time-threshold {
              description 'Ultrashort-time-threshold(s)' ;
              type uint16 {
                range 10..3600 {
                  description 'Ultrashort-time-threshold(s)' ;
                }

              }

              mandatory true ;
            }

          }

          container web-ipv6-servers {
            description 'Web ipv6 server id.' ;
            list web-ipv6-server {
              description 'web ipv6 server id.' ;
              max-elements 2 ;
              key web-ipv6-sever-num ;
              leaf web-ipv6-sever-num {
                description 'Web ipv6 server number.' ;
                type uint8 {
                  range 1..128 {
                    description 'Web server number.' ;
                  }

                }

              }

              leaf secondary-ipv6-web-server {
                description 'Secondary server number.' ;
                type enumeration {
                  enum first {
                    value 1 ;
                    description 'First web server number.' ;
                  }

                  enum second {
                    value 2 ;
                    description 'Second web server number.' ;
                  }

                }

              }

            }

          }

          container slaac-share-prefix {
            description 'Slaac share prefix address.' ;
            presence slaac-ipv6-prefix ;
            leaf slaac-share-prefix {
              description 'Slaac share prefix address.' ;
              type ncd:ipv6-address ;

              mandatory true ;
            }

            leaf slaac-share-prefix-prefixlen {
              description 'Slaac share prefix masklen.' ;
              type uint8 {
                range 0..128 {
                  description 'Slaac share prefix mask len.' ;
                }

              }

              mandatory true ;
            }

          }

          container user-service-ip-type {
            leaf ipv4 {
              type uint8 {
                range 0..1 ;

              }

              default 0 ;
            }

            leaf ipv6 {
              type uint8 {
                range 0..1 ;

              }

              default 0 ;
            }

            leaf ipv6-pd {
              type uint8 {
                range 0..1 ;

              }

              default 0 ;
            }

          }

          leaf account-template-policy {
            description 'accounting template policy' ;
            type enumeration {
              enum radius-domain {
                value 0 ;
                description 'radius-domain' ;
              }

              enum authen-domain {
                value 1 ;
                description 'authen-domain' ;
              }

            }

            default radius-domain ;
          }

          container radius-authen-password-new {
            choice choose-password {
              case passwd {
                leaf radius-authen-password-ex {
                  type string {
                    length 1..31 ;

                  }

                }

                leaf showclear {
                  status obsolete {
                    ncd:revise-date 2020-12-16 ;
                  }

                  type uint8 {
                    range 0..2 ;

                  }

                  default 2 ;
                }

              }

              case encry-passwd {
                leaf radius_auth_encrypted_passwd {
                  type string {
                    length 64..84 ;

                  }

                }

              }

            }

            ncd:revise-date 2020-04-17 ;
          }

          container dsl-agent-circuit-id {
            leaf format {
              type enumeration {
                enum inherit-nas-port-id {
                  value 1 ;
                }

              }

            }

            ncd:revise-date 2020-06-10 ;
          }

        }

      }

      container accounting-templates {
        description 'AIM accounting template configure.' ;
        list accounting-template {
          description 'Aim accounting template configuration list.' ;
          max-elements 2000 ;
          key accountName ;
          leaf accountName {
            description 'Aim accounting template name configure.' ;
            type string {
              length 1..31 {
                description 'WORD  Accounting template name (1-31 characters)' ;
              }

            }

          }

          leaf account-type {
            description 'AIM accounting type configure.' ;
            type enumeration {
              enum none {
                value 1 ;
                description 'No accounting' ;
              }

              enum radius {
                value 2 ;
                description 'RADIUS accounting' ;
              }

              enum diameter {
                value 3 ;
                description 'Diameter accounting' ;
              }

            }

          }

          leaf calling-station {
            description 'AIM calling-station-id get config' ;
            type enumeration {
              enum server-first {
                value 0 ;
                description 'Server first' ;
              }

              enum local-first {
                value 1 ;
                description 'Local first' ;
              }

            }

          }

          leaf flow-bill {
            description 'AIM user flow bill configure' ;
            type enumeration {
              enum ipv4 {
                value 0 ;
                description 'User flow bill only include ipv4 flow' ;
              }

              enum ipv6 {
                value 1 ;
                description 'User flow bill only include ipv6 flow' ;
              }

              enum dual {
                value 2 ;
                description 'User flow bill only include dual flow' ;
              }

              enum user {
                value 3 ;
                description 'User flow bill only include integrated flow' ;
              }

            }

          }

          leaf l2tp-accounting {
            description 'AIM l2tp accounting mode configure.' ;
            type enumeration {
              enum none {
                value 2 ;
                description 'Close l2tp accounting switch' ;
              }

              enum class1 {
                value 3 ;
                description 'Open l2tp accounting of class1(as vpdn)' ;
              }

              enum class2 {
                value 1 ;
                description 'Open l2tp accounting of class2(as ppp)' ;
              }

            }

            default class1 ;
          }

          leaf l2tp-tunnel-accounting {
            description 'AIM l2tp tunnel accounting switch configure.' ;
            type enumeration {
              enum enable {
                value 1 ;
                description 'Open l2tp tunnel accounting switch' ;
              }

              enum disable {
                value 0 ;
                description 'Close l2tp tunnel accounting switch' ;
              }

            }

          }

          leaf accounting-start-fail {
            description 'AIM accounting start-fail policy configure.' ;
            type enumeration {
              enum online {
                value 0 ;
                description 'Accounting start-fail online' ;
              }

              enum offline {
                value 1 ;
                description 'Accounting start-fail offline' ;
              }

            }

          }

          container accounting-update-fail {
            description 'AIM accounting start-fail and update-fail policy configure.' ;
            presence accounting ;
            leaf update-fail {
              description 'AIM accounting update-fail policy configure.' ;
              type enumeration {
                enum online {
                  value 0 ;
                  description 'Accounting update-fail online' ;
                }

                enum offline {
                  value 1 ;
                  description 'Accounting update-fail offline' ;
                }

              }

            }

            leaf max-times {
              description 'AIM accounting update-fail max times configure.' ;
              type uint32 {
                range 1..255 {
                  description '<1-255>  Max times of accounting update-fail' ;
                }

              }

            }

          }

          container accounting-diameter-group {
            description 'AIM accounting Diameter group configure.' ;
            presence accounting-diameter-group ;
            leaf acctDiameterGrp {
              description 'AIM Diameter accounting group configure.' ;
              type string {
                length 1..32 {
                  description 'WORD  Diameter group name (1-32 characters)' ;
                }

              }

            }

          }

          container accounting-radius-group {
            description 'AIM accounting RADIUS group configure.' ;
            presence accounting-radius-group ;
            leaf radius_group {
              description 'AIM First RADIUS accounting group configure.' ;
              type string {
                length 1..31 {
                  description 'WORD  First RADIUS group name (1-31 characters)' ;
                }

              }

            }

            leaf second_radius_group {
              description 'AIM Second RADIUS accounting group configure.' ;
              type string {
                length 1..31 {
                  description 'WORD  Second RADIUS group name (1-31 characters)' ;
                }

              }

            }

          }

          container accounting-start-delay {
            description 'AIM accounting-start delay configure.' ;
            presence accounting-start ;
            leaf delay {
              description 'AIM accounting start delay configure.' ;
              type uint32 {
                range 1..300 {
                  description '<1-300>  Accounting start delay period(s)' ;
                }

              }

            }

            leaf offline {
              description 'AIM Offline enable configuration.' ;
              type enumeration {
                enum offline {
                  value 1 ;
                  description 'Offline enable configuration' ;
                }

                enum 0 {
                  value 0 ;
                  description 'Invalid value' ;
                }

              }

              default 0 ;
            }

          }

          leaf accounting-update-delay {
            description 'AIM accounting update delay period configure.' ;
            type uint32 {
              range 1..300 {
                description '<1-300>  Accounting update delay period(s)' ;
              }

            }

          }

          leaf accounting-update-immediately {
            description 'AIM immediate account update configure.' ;
            type enumeration {
              enum immediately {
                value 1 ;
                description 'Immediate account update' ;
              }

              enum 0 {
                value 0 ;
                description 'Invalid value' ;
              }

            }

            default 0 ;
          }

          container accounting-update-interval {
            description 'AIM accounting update configure.' ;
            presence accounting-update ;
            choice period-or-disable {
              description 'AIM accounting update period configure or AIM accounting update close configure.' ;
              default period ;
              case period {
                description 'AIM accounting update period configure.' ;
                leaf update-period {
                  description 'AIM accounting update period configure.' ;
                  type uint32 {
                    range 60..604800 {
                      description '<60-604800>  Accounting update period(s)' ;
                    }

                  }

                  default 600 ;
                }

              }

              case disable {
                description 'AIM accounting update close configure.' ;
                leaf disable {
                  description 'AIM accounting update close configure.' ;
                  type uint32 {
                    range 0 {
                      description 'Close accounting update' ;
                    }

                  }

                  default 0 ;
                }

              }

            }

          }

          container f-charge {
            description 'AIM f-charge configure.' ;
            presence f-charge ;
            list account-fcharge {
              description 'AIM f-charge configure list.' ;
              max-elements 4 ;
              key 'acl_out_in_flag acl_v6_v4_flag' ;
              leaf acl_name {
                description 'AIM accounting f-charge acl name configure.' ;
                type string {
                  length 1..31 {
                    description 'WORD  The acl name (1-31 characters)' ;
                  }

                }

              }

              leaf acl_out_in_flag {
                description 'AIM accounting f-charge in acl or out acl configure.' ;
                type enumeration {
                  enum in {
                    value 1 ;
                    description 'The in acl' ;
                  }

                  enum out {
                    value 2 ;
                    description 'The out acl' ;
                  }

                }

              }

              leaf acl_v6_v4_flag {
                description 'AIM accounting acl or ipv6 acl configure.' ;
                type enumeration {
                  enum acl {
                    value 1 ;
                    description 'Configure the in and out name of acl' ;
                  }

                  enum ipv6-acl {
                    value 2 ;
                    description 'Configure the in and out name of ipv6 acl' ;
                  }

                }

              }

            }

          }

          container attribute {
            description 'AIM accounting support attribute switch configure' ;
            presence attribute ;
            leaf framed-ipv6-address {
              description 'AIM acccounting attribute framed-ipv6-address switch configure.' ;
              type enumeration {
                enum enable {
                  value 1 ;
                  description 'attribute framed-ipv6-address enable' ;
                }

                enum disable {
                  value 0 ;
                  description 'attribute framed-ipv6-address disable' ;
                }

              }

            }

            leaf nat-multi-portrange {
              description 'AIM acccounting attribute nat-multi-portrange switch configure.' ;
              type enumeration {
                enum enable {
                  value 1 ;
                  description 'attribute nat-multi-portrange enable' ;
                }

                enum disable {
                  value 0 ;
                  description 'attribute nat-multi-portrange disable' ;
                }

              }

            }

            leaf flow-extend {
              description 'AIM accounting attribute flow-extend {enable|disable}' ;
              type enumeration {
                enum enable {
                  value 1 ;
                  description 'Attribute flow-extend enable' ;
                }

                enum disable {
                  value 0 ;
                  description 'Attribute flow-extend disable' ;
                }

              }

              ncd:revise-date 2022-10-22 ;
            }

            container zte-user-mac {
              presence mac-string ;
              choice zte-user-mac-format {
                case octets {
                  description 'take mac in the way of octets' ;
                  leaf octets {
                    description 'take mac in the way of octets' ;
                    type enumeration {
                      enum octets {
                        value 1 ;
                      }

                    }

                    mandatory true ;
                  }

                }

                case string {
                  description 'take mac in the way of string' ;
                  leaf string {
                    description 'take mac in the way of octets' ;
                    type enumeration {
                      enum string {
                        value 2 ;
                      }

                    }

                    mandatory true ;
                  }

                  leaf mac-format {
                    description 'string mac form' ;
                    type enumeration {
                      enum xx-xx-xx-xx-xx-xx {
                        value 1 ;
                      }

                      enum xx.xx.xx.xx.xx.xx {
                        value 7 ;
                      }

                      enum xx:xx:xx:xx:xx:xx {
                        value 2 ;
                      }

                      enum xxxx-xxxx-xxxx {
                        value 4 ;
                      }

                      enum xxxx.xxxx.xxxx {
                        value 6 ;
                      }

                      enum xxxx:xxxx:xxxx {
                        value 3 ;
                      }

                      enum xxxxxxxxxxxx {
                        value 5 ;
                      }

                    }

                  }

                }

              }

              ncd:revise-date 2023-03-23 ;
            }

          }

          container copy-radius-group {
            description 'copy accounting infomation to slave radius group' ;
            list radius-group-name {
              description 'configure slave radius group name' ;
              max-elements 8 ;
              key group-name ;
              leaf group-name {
                description 'Radius group name' ;
                type string {
                  length 1..31 ;

                }

              }

              leaf li-only {
                type uint8 {
                  range 0..1 ;

                }

                default 0 ;
                ncd:revise-date 2021-06-29 ;
              }

            }

          }

          leaf acct-session-id-format {
            type enumeration {
              enum mexico-izzi {
                value 1 ;
                description 'Format:username@nas-port-id@pmap_time' ;
              }

            }

            description 'Configure acct-session-id format' ;
            ncd:revise-date 2025-04-23 ;
          }

        }

      }

      container global-configuration {
        container domainname-parse-direction {
          description 'domain name parser direction' ;
          leaf ritht-to-left {
            description 'Parse direction is right to left' ;
            type enumeration {
              enum FALSE {
                value 0 ;
              }

              enum TRUE {
                value 1 ;
              }

            }

            default FALSE ;
          }

        }

        leaf domain-delimiter {
          description 'Domain delimiter' ;
          type enumeration {
            enum @ {
              value 64 ;
            }

            enum "#" {
              value 35 ;
            }

            enum "%" {
              value 37 ;
            }

            enum "/" {
              value 47 ;
            }

          }

          default @ ;
        }

        leaf domain-case-sensitive-switch {
          description 'Configure domain name case sensitive' ;
          type enumeration {
            enum enable {
              value 0 ;
            }

            enum disable {
              value 1 ;
            }

          }

        }

        leaf coa-vendor-check {
          description 'Configure check vendor id when coa' ;
          type enumeration {
            enum enable {
              value 1 ;
            }

            enum disable {
              value 0 ;
            }

          }

        }

        container access-block {
          leaf bras-access-block {
            type enumeration {
              enum access-block-enable {
                value 1 ;
                description 'enable bras access block' ;
              }

              enum access-block-disable {
                value 0 ;
                description 'disable bras access block' ;
              }

            }

          }

          list slot-block {
            max-elements 18 ;
            key slot-access-block ;
            leaf slot-access-block {
              type uint16 {
                range 0..17 ;

              }

            }

          }

        }

        container access-delay {
          description 'configure access delay rule.' ;
          list slot-access-delay {
            max-elements 18 ;
            key slot-access-delay ;
            leaf slot-access-delay {
              type uint8 {
                range 0..17 ;

              }

            }

            leaf step {
              type uint16 {
                range 100..10000 ;

              }

            }

            leaf mim-time {
              type uint16 {
                range 0..20000 ;

              }

            }

            leaf max-time {
              type uint16 {
                range 50..20000 ;

              }

            }

          }

          container bras-access-delay {
            leaf step {
              type uint16 {
                range 100..10000 ;

              }

            }

            leaf min-time {
              type uint16 {
                range 0..20000 ;

              }

            }

            leaf max-time {
              type uint16 {
                range 50..20000 ;

              }

            }

          }

          ncd:revise-date 2020-02-20 ;
        }

        container user {
          description 'Configure user offline record and online record' ;
          leaf online-abnormal-event-log {
            status obsolete {
              ncd:revise-date 2021-11-22 ;
            }

            description 'event log switch' ;
            type enumeration {
              enum enable {
                value 1 ;
                description 'enable' ;
              }

              enum disable {
                value 0 ;
                description 'disable' ;
              }

            }

            default enable ;
          }

          leaf event-log-num {
            status obsolete {
              ncd:revise-date 2021-11-22 ;
            }

            description 'the number of event log' ;
            type uint32 {
              range 4000..512000 ;

            }

            default 256000 ;
          }

          leaf offline-abnormal-event-log {
            status obsolete {
              ncd:revise-date 2021-11-22 ;
            }

            description 'event log switch' ;
            type enumeration {
              enum enable {
                value 1 ;
                description 'enable' ;
              }

              enum disable {
                value 0 ;
                description 'disable' ;
              }

            }

            default enable ;
          }

          leaf normal-event-log {
            status obsolete {
              ncd:revise-date 2021-11-22 ;
            }

            description 'event log switch' ;
            type enumeration {
              enum enable {
                value 1 ;
                description 'enable' ;
              }

              enum disable {
                value 0 ;
                description 'disable' ;
              }

            }

            default disable ;
          }

        }

        container mac-ipv6-tables {
          description 'Mac ipv6 table.' ;
          list mac-ipv6-table {
            description 'Mac ipv6 configuration list.' ;
            max-elements 1000 ;
            key 'mac ipv6-address' ;
            leaf mac {
              description 'Mac address' ;
              type ncd:mac-address ;

            }

            leaf ipv6-address {
              description 'Ipv6 address.' ;
              type ncd:ipv6-address ;

              mandatory true ;
            }

          }

        }

        container mac-prefix-tables {
          description 'Mac prefix table.' ;
          list mac-prefix-table {
            description 'Mac prefix configuration list.' ;
            max-elements 2000 ;
            key 'mac prefix-address prefix-type' ;
            leaf mac {
              description 'Mac address' ;
              type ncd:mac-address ;

            }

            leaf prefix-address {
              description 'Prefix address.' ;
              type ncd:ipv6-address ;

              mandatory true ;
            }

            leaf prefix-type {
              description 'Prefix address type.' ;
              type enumeration {
                enum pd-prefix {
                  value 1 ;
                  description 'PD prefix.' ;
                }

                enum nd-prefix {
                  value 2 ;
                  description 'ND prefix.' ;
                }

              }

              mandatory true ;
            }

            leaf prefix-len {
              description 'Prefix masklen.' ;
              type uint32 {
                range 1..128 {
                  description 'Prefix len.' ;
                }

              }

              mandatory true ;
            }

          }

        }

        leaf radius-username-case-sensitive {
          description 'Config radius username case sensitive.' ;
          type enumeration {
            enum enable {
              value 0 ;
              description 'Radius username case sensitive enable.' ;
            }

            enum disable {
              value 1 ;
              description 'Radius username case sensitive disable.' ;
            }

          }

          ncd:revise-date 2020-01-13 ;
        }

        container authentic-request-ctrl {
          leaf control {
            type enumeration {
              enum enable {
                value 1 ;
              }

              enum disable {
                value 0 ;
              }

            }

            default disable ;
          }

          container range-time-count {
            leaf time-range {
              type uint16 {
                range 1..3600 ;

              }

            }

            leaf request-count {
              type uint16 {
                range 1..1000 ;

              }

            }

            leaf forbid-period {
              type uint16 {
                range 1..3600 ;

              }

            }

            leaf all-request {
              type enumeration {
                enum all-request {
                  value 1 ;
                }

              }

            }

            leaf permac-multi-session {
              type enumeration {
                enum permac-multi-session {
                  value 1 ;
                }

              }

            }

          }

          container request-count-control {
            leaf request-interval {
              type uint16 {
                range 1..3600 ;

              }

            }

            leaf request-count {
              type uint16 {
                range 1..1000 ;

              }

            }

            leaf forbid-period {
              type uint16 {
                range 1..3600 ;

              }

            }

            leaf reset-period {
              type uint16 {
                range 1..48 ;

              }

            }

          }

          leaf user-type {
            type enumeration {
              enum lac {
                value 1 ;
              }

            }

            ncd:revise-date 2024-03-27 ;
          }

          ncd:revise-date 2021-01-28 ;
        }

        leaf performance-statistics {
          type enumeration {
            enum enable {
              value 1 ;
            }

            enum disable {
              value 0 ;
            }

          }

          ncd:revise-date 2021-03-02 ;
        }

        leaf radius-attribute-extend-port {
          description 'Config radius extend port' ;
          type uint32 {
            range 0..1 ;

          }

          ncd:revise-date 2023-09-04 ;
        }

      }

      container profiles {
        list profile {
          key profile-name ;
          leaf profile-name {
            type string {
              length 1..127 ;

            }

          }

          leaf url {
            type string {
              length 1..127 ;

            }

          }

          leaf url-ipv6 {
            type string {
              length 1..127 ;

            }

          }

        }

      }

      container web-off-triggered-by {
        description 'Configure what types of triggered by web-off' ;
        leaf clear {
          description 'Um clear' ;
          type enumeration {
            enum weboff {
              value 1 ;
            }

            enum offline {
              value 0 ;
            }

          }

        }

        leaf radius-dm {
          description 'Radius DM' ;
          type enumeration {
            enum weboff {
              value 1 ;
            }

            enum offline {
              value 0 ;
            }

          }

        }

        leaf absolute-timeout {
          description 'Absolute timeoute' ;
          type enumeration {
            enum weboff {
              value 1 ;
            }

            enum offline {
              value 0 ;
            }

          }

        }

        leaf idle-timeout {
          description 'Idle timeout' ;
          type enumeration {
            enum weboff {
              value 1 ;
            }

            enum offline {
              value 0 ;
            }

          }

        }

        leaf quota-timeout {
          description 'Quota timeout' ;
          type enumeration {
            enum weboff {
              value 1 ;
            }

            enum offline {
              value 0 ;
            }

          }

        }

        leaf quota-flowout {
          description 'Quota flowout' ;
          type enumeration {
            enum weboff {
              value 1 ;
            }

            enum offline {
              value 0 ;
            }

          }

        }

      }

      container openflow-disconnect {
        description 'Set' ;
        choice response-delay {
          case nolimitflag {
            leaf forever {
              description 'set wait forever flag' ;
              type enumeration {
                enum forever {
                  value 1 ;
                }

              }

            }

          }

          case range {
            leaf delay-time {
              description 'Set delay time range' ;
              type uint32 {
                range 0..2880 ;

              }

            }

          }

        }

      }

      container openflow-reconnect {
        description 'set' ;
        choice response-delay {
          case range {
            leaf delay-time {
              description 'Set delay time range' ;
              type uint32 {
                range 1..120 ;

              }

            }

          }

        }

      }

      container security-template {
        list security-template {
          description 'AIM security template configuration list.' ;
          max-elements 2000 ;
          key security-name ;
          leaf security-name {
            description 'Aim security template name configure.' ;
            type string {
              length 1..31 {
                description 'WORD  Security template name (1-31 characters)' ;
              }

            }

          }

          leaf ipv6-urpf-check {
            description 'Set v6 user check urpf function' ;
            type enumeration {
              enum disable {
                value 1 ;
                description 'Turn off the URPF check of IPv6' ;
              }

              enum enable {
                value 0 ;
                description 'Turn on the URPF check of IPv6' ;
              }

            }

            default disable ;
          }

          choice urpf-check {
            case disable {
              leaf urpf-check-disable {
                description 'Close ipv4 urpf-checkout switch.' ;
                type enumeration {
                  enum disable {
                    value 1 ;
                    description 'Close ipv4 urpf-checkout switch.' ;
                  }

                }

              }

            }

            case enable {
              leaf urpf-check-enable {
                description 'Open ipv4 urpf-checkout switch.' ;
                type enumeration {
                  enum enable {
                    value 0 ;
                    description 'Open ipv4 urpf-checkout switch.' ;
                  }

                }

              }

              leaf subnet {
                description 'ipv4 subnet-check switch.' ;
                type enumeration {
                  enum TRUE {
                    value 1 ;
                    description 'Open ipv4 subnet-check switch.' ;
                  }

                  enum FALSE {
                    value 0 ;
                    description 'Close ipv4 subnet-check switch' ;
                  }

                }

                default FALSE ;
              }

            }

            ncd:revise-date 2022-08-18 ;
          }

        }

        ncd:revise-date 2020-01-21 ;
      }

      container circuit-maps {
        description 'Circuit map infomation configuration' ;
        list circuit-map {
          description 'Circuit map infomation configuration' ;
          max-elements 1000 ;
          key 'externalvlan internalvlan interface' ;
          leaf externalvlan {
            type ncd:single-range ;

          }

          leaf internalvlan {
            type ncd:single-range ;

          }

          leaf interface {
            type ncd:ifname {
              length 1..31 ;

            }

          }

          leaf username {
            type string {
              length 1..127 ;

            }

            mandatory true ;
          }

          leaf domainname {
            type string {
              length 1..31 ;

            }

            mandatory true ;
          }

          choice choose-password {
            mandatory true ;
            case passwd {
              leaf password-ex {
                type string {
                  length 1..31 ;

                }

              }

            }

            case encry-passwd {
              leaf cir_map_encrypted_passwd {
                type string {
                  length 64..84 ;

                }

              }

            }

          }

        }

        ncd:revise-date 2020-12-16 ;
      }

      container local-subscribers {
        list local-subscriber {
          max-elements 10000 ;
          key 'localSubName domain-name' ;
          leaf localSubName {
            type string {
              length 1..127 ;

            }

          }

          leaf domain-name {
            type string {
              length 1..31 ;

            }

          }

          choice choose-password {
            mandatory true ;
            case passwd {
              leaf password-ex {
                type string {
                  length 1..31 ;

                }

              }

            }

            case encry-passwd {
              leaf local-sub-encrypted-passwd {
                type string {
                  length 64..84 ;

                }

              }

            }

          }

          container ipv6-address {
            presence ipv6-address ;
            leaf ipv6-address {
              description 'LocSub Appoint IPV6 Address' ;
              type ncd:ipv6-address ;

              mandatory true ;
            }

            ncd:revise-date 2023-08-10 ;
          }

          container ipv6-nd-prefix {
            presence ipv6-nd-prefix ;
            leaf nd-prefix {
              description 'LocSub Appoint IPV6 ND Prefix' ;
              type ncd:ipv6-address ;

              mandatory true ;
            }

            leaf nd-prefix-len {
              description 'LocSub Appoint IPV6 ND Prefix Len' ;
              type uint32 {
                range 1..128 ;

              }

              mandatory true ;
            }

            ncd:revise-date 2023-08-10 ;
          }

          container ipv6-pd-prefix {
            presence ipv6-pd-prefix ;
            leaf pd-prefix {
              description 'LocSub Appoint IPV6 PD Prefix' ;
              type ncd:ipv6-address ;

              mandatory true ;
            }

            leaf pd-prefix-len {
              description 'LocSub Appoint IPV6 PD Prefix Len' ;
              type uint32 {
                range 1..128 ;

              }

              mandatory true ;
            }

            ncd:revise-date 2023-08-10 ;
          }

        }

        ncd:revise-date 2020-12-16 ;
      }

      container default-username-templates {
        description 'Default username template model.' ;
        list default-username-template {
          description 'Default username template configuration list.' ;
          max-elements 100 ;
          key default-username-template-name ;
          leaf default-username-template-name {
            description 'Default username template name.' ;
            type string {
              length 1..31 ;

            }

          }

          leaf default-username-type {
            description 'Default username type.' ;
            type enumeration {
              enum mac {
                value 1 ;
                description 'Use the mac as user name' ;
              }

              enum agent-circuit-id {
                value 2 ;
                description 'Use the agent-circuit-id as user name' ;
              }

              enum config {
                value 3 ;
                description 'Configure user name.' ;
              }

            }

          }

          leaf default-username-name {
            description 'Default username.' ;
            type string {
              length 1..127 ;

            }

          }

        }

        ncd:revise-date 2021-12-15 ;
      }

      container default-password-templates {
        description 'Default password template model.' ;
        list default-password-template {
          description 'Default password template configuration list.' ;
          max-elements 100 ;
          key default-password-template-name ;
          leaf default-password-template-name {
            description 'Default password template name.' ;
            type string {
              length 1..31 ;

            }

          }

          choice choose-password {
            case password {
              description 'Default password.' ;
              leaf password-ex {
                type string {
                  length 1..31 ;

                }

              }

            }

            case encry-passwd {
              description 'Default encrypted password.' ;
              leaf encrypted-password {
                type string {
                  length 64..84 ;

                }

              }

            }

          }

        }

        ncd:revise-date 2021-12-15 ;
      }

    }

  }

}
