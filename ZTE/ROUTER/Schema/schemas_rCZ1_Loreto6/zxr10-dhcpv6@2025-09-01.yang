module zxr10-dhcpv6 {
  namespace "http://www.zte.com.cn/zxr10/netconf/schema/rosng/dhcpv6" ;
  prefix dhcpv6 ;
  yang-version 1 ;
  import zxr10-netconf-defs {
    prefix ncd ;
    revision-date 2013-11-22 ;
  }

  organization "ZTE Corporation" ;
  contact "ZTE Corporation
  Nanjing Institute of ZTE Corporation
  No.68 Zijinghua Rd. Yuhuatai District, Nanjing, China
  Tel: +86-25-52870000" ;
  description 'The netconf module to describe DHCPv6.' ;
  revision 2025-09-01 {
    description 'Modify misspelled words in the description field of nodes' ;
  }
  
  revision 2023-06-09 {
    description '1. Change list bind-mac-address key from "mac address" to "mac", set address mandatory.
2. Change list bind-mac-address-vrf key from "mac vrf-name address" to "mac vrf-name", set address mandatory.
3. Change list bind-mac-prefix key from "mac prefix prefix-len" to "mac", set prefix and prefix-len mandatory.
4. Change list bind-mac-prefix-vrf key from "mac vrf-name prefix prefix-len" to "mac vrf-name", set prefix and prefix-len mandatory.
' ;
  }

  revision 2023-04-11 {
    description 'Modify range of leaf nodes from 1~8 to 1~64,nodes path are follow:
/dhcpv6:configuration/dhcpv6:dhcpv6/dhcpv6:relay/dhcpv6:instances/dhcpv6:instance/dhcpv6:server-group-no
/dhcpv6:configuration/dhcpv6:dhcpv6/dhcpv6:relay/dhcpv6:server-groups/dhcpv6:server-group/dhcpv6:group-no
/dhcpv6:configuration/dhcpv6:dhcpv6/dhcpv6:relay/dhcpv6:server-groups/dhcpv6:server-group/dhcpv6:servers/dhcpv6:server/dhcpv6:index
/dhcpv6:configuration/dhcpv6:dhcpv6/dhcpv6:relay/dhcpv6:policy-groups/dhcpv6:policy-group/dhcpv6:default-server-group
/dhcpv6:configuration/dhcpv6:dhcpv6/dhcpv6:interfaces/dhcpv6:interface/dhcpv6:relay-if/dhcpv6:relay-server-group-number' ;
  }

  revision 2022-09-21 {
    description '1)Modify leaf node "description" max len under this path:/configuration/dhcpv6/relay/interface-based-instances;
2)Modify leaf node "description" max len under this path:/configuration/dhcpv6/server/interface-based-instances;' ;
  }

  revision 2022-06-16 {
    description '1.Add leaf node "relay-file-auto-save" under the path /configuration/dhcpv6/relay/global-config".' ;
  }

  revision 2022-04-02 {
    description '1.Add leaf node "packet-rate-limit" under path "configuration/dhcpv6/global".' ;
  }

  revision 2022-03-07 {
    description '1.Add relay-inter-chassis enable leaf under the path /configuration/dhcpv6/relay/global-config.
2.Add relay reply-unrestrict leaf under the path /configuration/dhcpv6/interfaces/interface/relay-if.' ;
  }

  revision 2022-02-28 {
    description 'Add leaf node "relay-update-nd" under the path configuration/relay/global-config' ;
  }

  revision 2022-01-12 {
    description 'Add "insert-vss-option" container and leaf nodes under the path :/configuration/dhcpv6/relay/interface-based-instances' ;
  }

  revision 2021-08-19 {
    description '1.Add option16-match container and leafs under path :/configuration/dhcpv6/server/policys.
2.Add policy container and leafs under path :/configuration/dhcpv6/client.' ;
  }

  revision 2021-06-03 {
    description 'Add leaf "relay-server-group-number" under this path :/configuration/dhcpv6/interfaces/interface/relay-if' ;
  }

  revision 2021-04-26 {
    description 'Add leaf node "broadband-user-access" under path :/configuration/dhcpv6/interfaces/interface' ;
  }

  revision 2021-04-01 {
    description '1.Modify the type length of all duid leaf nodes under this path /configuration/dhcpv6/server/pools/pool/bindings;
2.Modify the type length of the leaf nodes under path /configuration/dhcpv6/client/client-user/detail/client-duid,/configuration/dhcpv6/server/server-user/detail/client-duid;' ;
  }

  revision 2021-03-19 {
    description 'Add leafs as follows:operation\dhcpv6\relay-kick-user\type\duid\client-duid, operation\dhcpv6\relay-kick-user\type\mac\mac-addr, operation\dhcpv6\server-kick-user\type\duid\client-duid, operation\dhcpv6\server-kick-user\type\mac\mac-addr.' ;
  }

  revision 2021-02-02 {
    description 'Add leaf "user-interact" under path /configuration/dhcpv6/global' ;
  }

  revision 2021-01-04 {
    description '1.Add container "option-templates" under path:/configuration/dhcpv6/global.
2.Add leaf "option-template-name" under path:/configuration/dhcpv6/server/pools/pool/bind-mac-address.
3.Add leaf "option-template-name" under path:/configuration/dhcpv6/server/pools/pool/bind-mac-address-vrf.' ;
  }

  revision 2020-11-20 {
    description '1.Add container "authen-templates" under path:/configuration/dhcpv6/global.
2.Add leaf "authen-template-name" under path:/configuration/dhcpv6/relay/interface-based-instances.
3.Add leaf "authen-template-name" under path:/configuration/dhcpv6/server/interface-based-instances.' ;
  }

  revision 2020-09-22 {
    description '1.Add container named "option-modify-config" and leafs under this path:/configuration/dhcpv6/relay/instances/instance.
2.Add container named "option-modify-config" and leafs under this path:/configuration/dhcpv6/relay/interface-based-instances/interface-based-instance.
3.Add container named "suboption-modify-config" and leafs under this path:/configuration/dhcpv6/relay/instances/instance.
4.Add container named "suboption-modify-config" and leafs under this path:/configuration/dhcpv6/relay/interface-based-instances/interface-based-instance.' ;
  }

  revision 2020-08-20 {
    description '1.Add leaf node named "ignore-request-list" under path:/configuration/dhcpv6/server/pools/pool
2.Add leaf node named "force-reply" under path:/configuration/dhcpv6/server/pools/pool/options/option' ;
  }

  revision 2020-08-11 {
    description '1.Add container named "suppress-packet" under path:/configuration/dhcpv6/global' ;
  }

  revision 2020-08-05 {
    description 'Modify leaf node length from 140 to 254: /configuration/dhcpv6/server/global-config/duid' ;
  }

  revision 2020-07-21 {
    description 'Modify leaf node "intfid-policy" under path:configuration/dhcpv6/relay/global-config,modify the enumeration of this leaf node,add new value type "no-check-from-request-packet".' ;
  }

  revision 2020-06-18 {
    description 'Add leaf node "intfid-policy" under path: configuration/dhcpv6/relay/global-config' ;
  }

  revision 2020-06-09 {
    description '1)Add container node "interface-based-instances" under this path:/configuration/dhcpv6/relay/interface-based-instances;
2)Add container node "interface-based-instances" under this path:/configuration/dhcpv6/server/interface-based-instances;
3)Add leaf node "bind-relay-instance" under this path:/configuration/dhcpv6/interfaces/interface/relay-if;
4)Add leaf node "bind-server-instance" under this path:/configuration/dhcpv6/interfaces/interface/server-if;' ;
  }

  revision 2020-06-02 {
    description 'Modify leaf node "intfid-format" under path /configuration/dhcpv6/relay/global-config,modify type value.' ;
  }

  revision 2020-05-26 {
    description '1.Add leaf node named "check-invalid-option" under path /configuration/dhcpv6/global' ;
  }

  revision 2020-05-06 {
    description '1) Update length to 64 such as pool-name,policy-name,etc.' ;
  }

  revision 2020-04-22 {
    description 'Add vrf nodes under path:/configuration/dhcpv6/relay/server-groups/server-group/servers/server/' ;
  }

  revision 2020-04-11 {
    description '1)Add container node "short-time" under this path:/configuration/dhcpv6/interfaces/interface/relay-if;
2)Add leaf node "short-valid-time" under this path:/configuration/dhcpv6/interfaces/interface/relay-if/short-time;
3)Add leaf node "short-preferred-time" under this path:/configuration/dhcpv6/interfaces/interface/relay-if/short-time.' ;
  }

  revision 2020-04-09 {
    description 'Add leaf under:
path:configuration/dhcpv6/global/upgrade-lease-time' ;
  }

  revision 2020-04-01 {
    description '1.Add choice case node named "bind-mac_adress" under path:configuration/dhcpv6/server/pools/pool' ;
  }

  revision 2020-03-18 {
    description '1.Change parameter to performance parameter under path:
path:configuration/dhcpv6/relay/instances/instance/instance-no
path:configuration/dhcpv6/relay/server-groups/server-group/instances/instance/instance-no
path:configuration/dhcpv6/relay/server-groups/server-group/group-no
path:configuration/dhcpv6/relay/server-groups/server-group/servers/server/index.' ;
  }

  revision 2020-02-17 {
    description '1.Add choice case node named "source-ip-config" under path:configuration/dhcpv6/interfaces/interface/relay-if.
2.Change the status to "deprecated" of container under the path:configuration/dhcpv6/relay/interfaces,and the path :configuration/dhcpv6/server/interfaces' ;
  }

  revision 2020-01-15 {
    description '1.Add choice named "source-ip-config" and case leafs under it,under path:configuration/dhcpv6/relay/instances/instance.
2.Add choice case leaf named "source-ip-config" under path:configuration/dhcpv6/relay/interfaces/interface,and add case leafs under it.' ;
  }

  revision 2019-12-23 {
    description '1)Add leaf node online-user-solicit-reonline under this path:/configuration/dhcpv6/global;
2)Add leaf node request-packet-address-check under this path:/configuration/dhcpv6/relay/global-config.' ;
  }

  revision 2019-08-01 {
    description 'Add container named "user-connect-statistics" and leafs under path:/state/dhcpv6/relay.' ;
  }

  revision 2019-05-31 {
    description 'Add leaf node ramble under global.' ;
  }

  revision 2019-03-27 {
    description 'Add leaf node cos under relay server-groups.' ;
  }

  revision 2018-08-29 {
    description '1.Extend the range of leaf "max-user" under this path:/configuration/dhcpv6/relay/global-config/max-user.
2.Extend the range of leaf "max-user" under this path:/configuration/dhcpv6/server/global-config/max-user.
3.Delete the SystemControlled Default of leaf "max-user" under this path:/configuration/dhcpv6/relay/global-config/max-user.
4.Delete the SystemControlled Default of leaf "max-user" under this path:/configuration/dhcpv6/server/global-config/max-user.
5.Modify the description of leaf "max-user" under this path:/configuration/dhcpv6/relay/global-config/max-user.
6.Modify the description of leaf "max-user" under this path:/configuration/dhcpv6/server/global-config/max-user.' ;
  }

  revision 2018-07-23 {
    description '1.Extend the range of leaf "max-retry" under this path:/configuration/dhcpv6/relay/server-groups/server-group/max-retry.
2.Modify the description of leaf "max-retry" under this path:/configuration/dhcpv6/relay/server-groups/server-group/max-retry.' ;
  }

  revision 2018-03-14 {
    description '1)Modify the leaf nodes under this path /configuration/dhcpv6/relay/server-groups/server-group/deadtime.
2)Modify the leaf nodes under this path /configuration/dhcpv6/relay/server-groups/server-group/max-timeout.' ;
  }

  revision 2017-06-08 {
    description '1)Modify the leaf nodes under this path /configuration/dhcpv6/interfaces/interface/dscp.
2)Modify the leaf nodes under this path /configuration/dhcpv6/relay/server-groups/server-group/servers/server/dscp.' ;
  }

  revision 2017-03-09 {
    description '1)Add container bind-pcp-servers under pools.
2)Add container pcp-servers under server.' ;
  }

  revision 2016-04-06 {
    description '1)Add container short-leasetime under relay instance.
2)Add leaf node short-valid-leasetime under short-leasetime.
3)Add leaf node short-preferred-leasetime under short-leasetime.' ;
  }

  revision 2016-03-09 {
    description '1)Add leaf node relay-forward-mode under this path:/configuration/dhcpv6/interfaces/interface/relay-if/' ;
  }

  revision 2016-01-14 {
    description '1)Add leaf node vrf under this path:/state/dhcpv6/relay/relay-user/detail/.
1)Add leaf node vrf under this path:/state/dhcpv6/server/server-user/detail/.' ;
  }

  revision 2015-08-11 {
    description 'Modify the config from true to false under the state and operation containers.' ;
  }

  revision 2015-03-11 {
    description '1)Remove the choice node address-config and case node address-switch and case node address-auto-config,under this path:/configuration/dhcpv6/client/;
2)Modify the container name addr-switch and addr-auto-config,change to address-switch and address-auto-config,under this path:/configuration/dhcpv6/client/;
3)Add new container named intefaces,under these two path:/configuration/dhcpv6/client/address-switch and /configuration/dhcpv6/client/address-auto-config;
4)Add leaf node max-timeout under relay server-groups.
5)Modify the string length of this leaf under the path:/configuration/dhcpv6/server/pools/pool/address-pools/address-pool-name, change the length from 1..15 to 1..31;
6)Modify the string length of this leaf under the path:/configuration/dhcpv6/server/pools/pool/prefix-pools/prefix-pool-name, change the length from 1..15 to 1..31.' ;
  }

  revision 2015-02-28 {
    description '1)Modify the container under this path /configuration/dhcpv6/server/pools/pool/address-pools/ and /configuration/dhcpv6/server/pools/pool/prefix-pools, and two leaf nodes address-pool-name and prefix-pool-name under this node, change the mandatory of these nodes from false to true.' ;
  }

  revision 2015-02-04 {
    description '1)Modify the leaf nodes under this path /configuration/dhcpv6/server/pools/pool/after.
2)Change these leaf nodes under this path /configuration/dhcpv6/server/pools/pool/options/option/type, and modify the case switch ip,changes the leaf nodes address-1 to address-8.' ;
  }

  revision 2014-12-02 {
    description '1.Add relay-if container: \configuration\dhcpv6\interfaces\interface\relay-if.
2.Add server-if container: \configuration\dhcpv6\interfaces\interface\server-if.' ;
  }

  revision 2014-09-10 {
    description '1)Add leaf node relay-source-ip under relay interface.
2)Add leaf node forward-reply under global-config.
3)Create a server global-config container which contains server max-user,duid,rapid-redial and single-user-quota configuration.' ;
  }

  revision 2014-01-16 {
    description 'Initial version.' ;
  }

  feature relay-user_connect_statistic {
    description 'DHCPv6 relay user connect statistics on the board.' ;
  }

  container configuration {
    description 'Configuration.' ;
    container dhcpv6 {
      description 'DHCPv6 config.' ;
      container global {
        description 'DHCPv6 global common config.' ;
        leaf enable-state {
          description 'Enable DHCPv6 process.' ;
          type enumeration {
            enum disable {
              value 0 ;
              description 'DHCPv6 disable.' ;
            }

            enum enable {
              value 1 ;
              description 'DHCPv6 enable.' ;
            }

          }

          default disable ;
        }

        container client {
          description 'DHCPv6 client global config.' ;
          leaf enable-state {
            description 'Enable DHCPv6 client process.' ;
            type enumeration {
              enum enable {
                value 0 ;
                description 'DHCPv6 client enable.' ;
              }

              enum disable {
                value 1 ;
                description 'DHCPv6 client disable.' ;
              }

            }

            default enable ;
          }

        }

        leaf ramble {
          description 'Enable DHCPv6 user ramble.' ;
          type enumeration {
            enum ramble-disable {
              value 0 ;
              description 'Turn off DHCPv6 ramble.' ;
            }

            enum ramble-enable {
              value 1 ;
              description 'Turn on DHCPv6 ramble.' ;
            }

          }

          default ramble-enable ;
          ncd:revise-date 2019-05-31 ;
        }

        leaf online-user-solicit-reonline {
          description "Configure the suppression time of DHCPv6 online user re-online receciving solicit packet.
          It's toplimit depends on ability of the device." ;
          type uint32 {
            range 0..3600 {
              description 'The range of the value is 0 to 3600.' ;
            }

          }

          ncd:revise-date 2019-12-23 ;
        }

        leaf upgrade-lease-time {
          description 'Upgrade lease time.' ;
          type uint32 {
            range 60..4294967295 {
              description 'Upgrade lease time(second).' ;
            }

          }

          ncd:revise-date 2020-04-09 ;
        }

        leaf check-invalid-option {
          description 'Configure check or not check invalid options in client packets.' ;
          type enumeration {
            enum off {
              value 0 ;
              description 'Not check invalid options.' ;
            }

            enum on {
              value 1 ;
              description 'Check invalid options.' ;
            }

          }

          default off ;
          ncd:revise-date 2020-05-26 ;
        }

        container suppress-packet {
          description 'DHCPV6 suppress packet' ;
          presence suppress-packet ;
          leaf packet-type {
            description 'DHCPV6 suppress packet type.' ;
            type enumeration {
              enum request-packet {
                value 1 ;
                description 'All request packet.' ;
              }

            }

            mandatory true ;
          }

          leaf packet-count {
            description 'The received packet count before packet suppression.' ;
            type uint32 {
              range 1..10000 {
                description 'Packet count.[1,10000].' ;
              }

            }

            mandatory true ;
          }

          leaf check-period {
            description 'Check period.' ;
            type uint32 {
              range 1..3600 {
                description 'Check period.[1,3600].' ;
              }

            }

            mandatory true ;
          }

          leaf suppress-period {
            description 'Suppress period.' ;
            type uint32 {
              range 1..3600 {
                description 'Suppress period.[1,3600].' ;
              }

            }

            mandatory true ;
          }

          ncd:revise-date 2020-08-11 ;
        }

        container authen-templates {
          description 'DHCPv6 authentication template configuration.' ;
          list authen-template {
            description 'DHCPv6 authentication template configuration.' ;
            key template-name ;
            leaf template-name {
              description 'DHCPv6 authentication template name.' ;
              type string {
                length 1..64 {
                  description 'DHCPv6 authentication template name.' ;
                }

              }

            }

            leaf radius-group-name {
              description 'DHCPv6 authentication radius group name.' ;
              type string {
                length 1..31 {
                  description 'Authentication radius group name.' ;
                }

              }

            }

            container radius-attributes {
              description 'DHCPv6 authentication radius attributes configuration.' ;
              list radius-attribute {
                description 'DHCPv6 authentication radius attributes configuration.' ;
                key attribute-type ;
                leaf attribute-type {
                  description 'DHCPv6 authentication radius attributes type.' ;
                  type enumeration {
                    enum user-name {
                      value 1 ;
                      description 'Radius attribute is user-name.' ;
                    }

                    enum user-password {
                      value 2 ;
                      description 'Radius attribute is user-password.' ;
                    }

                    enum nas-port-id {
                      value 3 ;
                      description 'Radius attribute is nas-port-id.' ;
                    }

                  }

                }

                leaf attribute-source {
                  description 'DHCPv6 authentication radius attributes source.' ;
                  type enumeration {
                    enum mac {
                      value 1 ;
                      description 'Radius source is from MAC.' ;
                    }

                    enum china-tel-option18 {
                      value 2 ;
                      description 'Radius source is from China-tel-option18.' ;
                    }

                  }

                  mandatory true ;
                }

              }

            }

          }

          ncd:revise-date 2020-11-20 ;
        }

        container option-templates {
          description 'DHCPv6 option template configuration.' ;
          list option-template {
            description 'DHCPv6 option template configuration.' ;
            key template-name ;
            leaf template-name {
              description 'DHCPv6 option template name.' ;
              type string {
                length 1..64 {
                  description 'DHCPv6 option template name.' ;
                }

              }

            }

            container options {
              description 'Configure option.' ;
              list option {
                description 'Configure option.' ;
                key option-id ;
                leaf option-id {
                  description 'Configure option ID.' ;
                  type uint16 {
                    range 1..65535 {
                      description 'The option code.' ;
                    }

                  }

                }

                choice type {
                  description 'DHCPv6 option type of option template.' ;
                  mandatory true ;
                  case ascii {
                    description 'DHCPv6 option type is ASCII string.' ;
                    leaf ascii-string {
                      description 'ASCII string.' ;
                      type string {
                        length 1..64 {
                          description 'The length of ASCII string.' ;
                        }

                      }

                      mandatory true ;
                    }

                  }

                  case hex {
                    description 'DHCPv6 option type is HEX string.' ;
                    leaf hex-string {
                      description 'HEX string.' ;
                      type string {
                        length 1..128 {
                          description 'The length of HEX string.' ;
                        }

                      }

                      mandatory true ;
                    }

                  }

                  case ip {
                    description 'DHCPv6 option type is IP.' ;
                    container ip-address {
                      presence ip-address ;
                      leaf address-1 {
                        description 'Configure the frist IPV6 address.' ;
                        type ncd:ipv6-address ;

                        mandatory true ;
                      }

                      container ip-address2 {
                        presence ip-address2 ;
                        leaf address-2 {
                          description 'Configure the second IPV6 address.' ;
                          type ncd:ipv6-address ;

                          mandatory true ;
                        }

                        container ip-address3 {
                          presence ip-address3 ;
                          leaf address-3 {
                            description 'Configure the third IPV6 address.' ;
                            type ncd:ipv6-address ;

                            mandatory true ;
                          }

                          container ip-address4 {
                            presence ip-address4 ;
                            leaf address-4 {
                              description 'Configure the fourth IPV6 address.' ;
                              type ncd:ipv6-address ;

                              mandatory true ;
                            }

                            container ip-address5 {
                              presence ip-address5 ;
                              leaf address-5 {
                                description 'Configure the fifth IPV6 address.' ;
                                type ncd:ipv6-address ;

                                mandatory true ;
                              }

                              container ip-address6 {
                                presence ip-address6 ;
                                leaf address-6 {
                                  description 'Configure the sixth IPV6 address.' ;
                                  type ncd:ipv6-address ;

                                  mandatory true ;
                                }

                                container ip-address7 {
                                  presence ip-address7 ;
                                  leaf address-7 {
                                    description 'Configure the seventh IPV6 address.' ;
                                    type ncd:ipv6-address ;

                                    mandatory true ;
                                  }

                                  container ip-address8 {
                                    presence ip-address8 ;
                                    leaf address-8 {
                                      description 'Configure the eighth IPV6 address.' ;
                                      type ncd:ipv6-address ;

                                      mandatory true ;
                                    }

                                  }

                                }

                              }

                            }

                          }

                        }

                      }

                    }

                  }

                }

              }

            }

          }

          ncd:revise-date 2021-01-04 ;
        }

        leaf user-interact {
          description 'DHCPv6 record user interact configuration.' ;
          type enumeration {
            enum record-off {
              value 0 ;
              description 'Recording user interaction log off.' ;
            }

            enum record-on {
              value 1 ;
              description 'Recording user interaction log on.' ;
            }

          }

          default record-off ;
          ncd:revise-date 2021-02-02 ;
        }

        leaf packet-rate-limit {
          description 'DHCPv6 online packet rate limit.' ;
          type uint16 {
            range 0..65535 ;

          }

          default 65535 ;
          ncd:revise-date 2022-04-02 ;
        }

      }

      container relay {
        description 'DHCPv6 relay config.' ;
        container global-config {
          description 'DHCPv6 Relay Global configuration.' ;
          leaf max-user {
            description "Max user numbers of DHCPv6 relay. It's toplimit depends on ability of the device." ;
            type uint32 {
              range 1..256000 {
                description 'The range of the value is 1 to 256000.' ;
              }

            }

          }

          leaf intfid-policy {
            description 'Config DHCPv6 relay interface-id policy.Add interface-id from local info(0).Add interface-id from request packet(1).Add interface-id from request packet,not check option18(2)' ;
            type enumeration {
              enum from-local-info {
                value 0 ;
                description 'Add interface-id from local information.' ;
              }

              enum from-request-packet {
                value 1 ;
                description 'Add interface-id from client request packet.' ;
              }

              enum no-check-from-request-packet {
                value 2 ;
                description 'Add interface-id from client request packet,not check option18 from user packet.' ;
              }

            }

            default from-local-info ;
            ncd:revise-date 2020-06-18 ;
          }

          leaf intfid-format {
            description 'DHCPv6 relay interface id format.[1,4]china-tel(1),dsl-forum(2),telenor(3),user-configuration(4).' ;
            type enumeration {
              enum default-value {
                value 0 ;
              }

              enum china-tel {
                value 1 ;
              }

              enum dsl-forum {
                value 2 ;
              }

              enum telenor {
                value 3 ;
              }

              enum user-configuration {
                value 4 ;
              }

            }

            default default-value ;
          }

          container remote-id {
            description 'DHCPv6 relay remote id configuration.' ;
            presence "remote id" ;
            leaf enterprise-number {
              description 'Enterprise number.' ;
              type uint32 {
                range 0..4294967295 {
                  description 'The range of enterprise number.' ;
                }

              }

              mandatory true ;
            }

            leaf remote-id-string {
              description 'Remote id string.' ;
              type string {
                length 1..64 {
                  description 'The length of remote-id string.' ;
                }

              }

              mandatory true ;
            }

          }

          leaf forward-reply {
            description 'Forward DHCPv6 reply packet without limit.' ;
            type enumeration {
              enum reply-unrestricted-off {
                value 0 ;
                description 'Turn off relay forward reply unrestricted.' ;
              }

              enum reply-unrestricted-on {
                value 1 ;
                description 'Turn on relay forward reply unrestricted.' ;
              }

            }

            default reply-unrestricted-off ;
          }

          leaf request-packet-address-check {
            description 'Forward DHCPv6 request packet with address check.' ;
            type enumeration {
              enum address-check-off {
                value 0 ;
                description 'Turn off relay request-packet address check.' ;
              }

              enum address-check-on {
                value 1 ;
                description 'Turn on relay request-packet address check.' ;
              }

            }

            default address-check-off ;
            ncd:revise-date 2019-12-23 ;
          }

          leaf relay-update-nd {
            description 'Config relay update nd switch.' ;
            type enumeration {
              enum off {
                value 0 ;
                description 'Turn off relay update nd.' ;
              }

              enum on {
                value 1 ;
                description 'Turn on relay update nd.' ;
              }

            }

            default off ;
            ncd:revise-date 2022-02-28 ;
          }

          leaf relay-inter-chassis {
            description 'Config relay inter-chassis.' ;
            type enumeration {
              enum off {
                value 0 ;
                description 'Turn off relay inter-chassis.' ;
              }

              enum on {
                value 1 ;
                description 'Turn on relay inter-chassis.' ;
              }

            }

            default off ;
            ncd:revise-date 2022-03-07 ;
          }

          leaf relay-file-auto-save {
            description 'Config relay file auto-save.' ;
            type enumeration {
              enum off {
                value 0 ;
                description 'Turn off relay file auto-save.' ;
              }

              enum on {
                value 1 ;
                description 'Turn on relay file auto-save.' ;
              }

            }

            default off ;
            ncd:revise-date 2022-06-16 ;
          }

        }

        container instances {
          description 'DHCPv6 relay instance configuration.' ;
          list instance {
            description 'DHCPv6 relay server policy group.' ;
            max-elements 256 ;
            key instance-no ;
            leaf instance-no {
              description 'DHCPv6 relay instance number.' ;
              type uint32 {
                range 1..256 {
                  description 'The range of relay instance number.' ;
                }

              }

            }

            leaf description {
              description 'Description of DHCPv6 relay instance.' ;
              type string {
                length 1..64 {
                  description 'The length of DHCPv6 relay instance description.' ;
                }

              }

            }

            leaf server-group-no {
              description 'DHCPv6 relay server group No.' ;
              type uint32 {
                range 1..64 {
                  description 'DHCPv6 relay server group-no.[1,64].' ;
                }

              }

            }

            leaf relay-agent {
              description 'DHCPv6 Relay agent IPv6 address.' ;
              type ncd:ipv6-address ;

            }

            leaf relay-interface-id {
              description 'IPv6 DHCP relay instance interface-id.' ;
              type string {
                length 1..64 {
                  description 'The length of relay instance relay interface id.' ;
                }

              }

            }

            container short-leasetime {
              description 'Short lease time for DHCPv6 relay instance.' ;
              presence short-leasetime ;
              leaf short-valid-leasetime {
                description 'Short valid lease time for DHCPv6 relay instance.[60,4294967295].Unit is seconds.' ;
                type uint32 {
                  range 60..4294967295 {
                    description 'The range of short valid lease time for DHCPv6 relay instance.' ;
                  }

                }

                units second ;
                mandatory true ;
              }

              leaf short-preferred-leasetime {
                description 'Short preferred lease time for DHCPv6 relay instance.[60,4294967295].Unit is seconds.' ;
                type uint32 {
                  range 60..4294967295 {
                    description 'The range of short preferred lease time for DHCPv6 relay instance.' ;
                  }

                }

                units second ;
                mandatory true ;
              }

              ncd:revise-date 2016-04-06 ;
            }

            container option-modify-config {
              description 'DHCPv6 packet option configurations.' ;
              list option-modify {
                description 'DHCPv6 packet option configuration.' ;
                key 'packet-direction packet-layer packet-type option-code' ;
                leaf packet-direction {
                  description 'DHCPv6 packet direction.' ;
                  type enumeration {
                    enum input {
                      value 1 ;
                      description 'Modify input packet.' ;
                    }

                    enum output {
                      value 2 ;
                      description 'Modify output packet.' ;
                    }

                    enum all-direct {
                      value 3 ;
                      description 'Modify input and output packet.' ;
                    }

                  }

                }

                leaf packet-layer {
                  description 'DHCPv6 packet layer.' ;
                  type enumeration {
                    enum outer-layer {
                      value 1 ;
                      description 'Outer-layer packet.' ;
                    }

                    enum inner-layer {
                      value 2 ;
                      description 'Inner-layer packet.' ;
                    }

                  }

                }

                leaf packet-type {
                  description 'DHCPv6 packet type.' ;
                  type enumeration {
                    enum solicit {
                      value 1 ;
                      description 'The DHCPv6 packet type is solicit.' ;
                    }

                    enum advertise {
                      value 2 ;
                      description 'The DHCPv6 packet type is advertise.' ;
                    }

                    enum request {
                      value 3 ;
                      description 'The DHCPv6 packet type is request.' ;
                    }

                    enum confirm {
                      value 4 ;
                      description 'The DHCPv6 packet type is confirm.' ;
                    }

                    enum renew {
                      value 5 ;
                      description 'The DHCPv6 packet type is renew.' ;
                    }

                    enum rebind {
                      value 6 ;
                      description 'The DHCPv6 packet type is rebind.' ;
                    }

                    enum reply {
                      value 7 ;
                      description 'The DHCPv6 packet type is reply.' ;
                    }

                    enum release {
                      value 8 ;
                      description 'The DHCPv6 packet type is release.' ;
                    }

                    enum decline {
                      value 9 ;
                      description 'The DHCPv6 packet type is decline.' ;
                    }

                    enum reconfigure {
                      value 10 ;
                      description 'The DHCPv6 packet type is reconfigure.' ;
                    }

                    enum inform-request {
                      value 11 ;
                      description 'The DHCPv6 packet type is inform-request.' ;
                    }

                    enum relay-forward {
                      value 12 ;
                      description 'The DHCPv6 packet type is relay-forward.' ;
                    }

                    enum relay-reply {
                      value 13 ;
                      description 'The DHCPv6 packet type is relay-reply.' ;
                    }

                  }

                }

                leaf option-code {
                  description 'DHCPv6 packet option code.' ;
                  type uint16 {
                    range 1..65535 ;

                  }

                }

                choice oper-type {
                  description 'DHCPv6 packet operation type.' ;
                  case set {
                    description 'DHCPv6 packet operation type is set.' ;
                    leaf set-hex-str {
                      description 'DHCPv6 packet option value is HEX string.' ;
                      type string {
                        length 1..254 {
                          description 'The length of HEX string.' ;
                        }

                      }

                      mandatory true ;
                    }

                  }

                  case add {
                    description 'DHCPv6 packet operation type is add.' ;
                    leaf add-hex-str {
                      description 'DHCPv6 packet option value is HEX string.' ;
                      type string {
                        length 1..254 {
                          description 'The length of HEX string.' ;
                        }

                      }

                      mandatory true ;
                    }

                  }

                  case remove {
                    description 'DHCPv6 packet operation type is remove.' ;
                    leaf remove {
                      description 'DHCPv6 packet operation type is remove.' ;
                      type enumeration {
                        enum on {
                          value 2 ;
                        }

                      }

                      mandatory true ;
                    }

                  }

                }

              }

              ncd:revise-date 2020-09-22 ;
            }

            container suboption-modify-config {
              description 'DHCPv6 packet sub option configurations.' ;
              list option-modify {
                description 'DHCPv6 packet option configuration.' ;
                key 'packet-direction packet-layer packet-type option-code suboption-code' ;
                leaf packet-direction {
                  description 'DHCPv6 packet direction.' ;
                  type enumeration {
                    enum input {
                      value 1 ;
                      description 'Modify input packet.' ;
                    }

                    enum output {
                      value 2 ;
                      description 'Modify output packet.' ;
                    }

                    enum all-direct {
                      value 3 ;
                      description 'Modify input and output packet.' ;
                    }

                  }

                }

                leaf packet-layer {
                  description 'DHCPv6 packet layer.' ;
                  type enumeration {
                    enum outer-layer {
                      value 1 ;
                      description 'Outer-layer packet.' ;
                    }

                    enum inner-layer {
                      value 2 ;
                      description 'Inner-layer packet.' ;
                    }

                  }

                }

                leaf packet-type {
                  description 'DHCPv6 packet type.' ;
                  type enumeration {
                    enum solicit {
                      value 1 ;
                      description 'The DHCPv6 packet type is solicit.' ;
                    }

                    enum advertise {
                      value 2 ;
                      description 'The DHCPv6 packet type is advertise.' ;
                    }

                    enum request {
                      value 3 ;
                      description 'The DHCPv6 packet type is request.' ;
                    }

                    enum confirm {
                      value 4 ;
                      description 'The DHCPv6 packet type is confirm.' ;
                    }

                    enum renew {
                      value 5 ;
                      description 'The DHCPv6 packet type is renew.' ;
                    }

                    enum rebind {
                      value 6 ;
                      description 'The DHCPv6 packet type is rebind.' ;
                    }

                    enum reply {
                      value 7 ;
                      description 'The DHCPv6 packet type is reply.' ;
                    }

                    enum release {
                      value 8 ;
                      description 'The DHCPv6 packet type is release.' ;
                    }

                    enum decline {
                      value 9 ;
                      description 'The DHCPv6 packet type is decline.' ;
                    }

                    enum reconfigure {
                      value 10 ;
                      description 'The DHCPv6 packet type is reconfigure.' ;
                    }

                    enum inform-request {
                      value 11 ;
                      description 'The DHCPv6 packet type is inform-request.' ;
                    }

                    enum relay-forward {
                      value 12 ;
                      description 'The DHCPv6 packet type is relay-forward.' ;
                    }

                    enum relay-reply {
                      value 13 ;
                      description 'The DHCPv6 packet type is relay-reply.' ;
                    }

                  }

                }

                leaf option-code {
                  description 'DHCPv6 packet option code.' ;
                  type uint16 {
                    range 1..65535 ;

                  }

                }

                leaf suboption-code {
                  description 'DHCPv6 packet sub option code.' ;
                  type uint16 {
                    range 1..65535 ;

                  }

                }

                choice oper-type {
                  description 'DHCPv6 packet operation type.' ;
                  case set {
                    description 'DHCPv6 packet operation type is set.' ;
                    leaf set-hex-str {
                      description 'DHCPv6 packet option value is HEX string.' ;
                      type string {
                        length 1..254 {
                          description 'The length of HEX string.' ;
                        }

                      }

                      mandatory true ;
                    }

                  }

                  case add {
                    description 'DHCPv6 packet operation type is add.' ;
                    leaf add-hex-str {
                      description 'DHCPv6 packet option value is HEX string.' ;
                      type string {
                        length 1..254 {
                          description 'The length of HEX string.' ;
                        }

                      }

                      mandatory true ;
                    }

                  }

                  case remove {
                    description 'DHCPv6 packet operation type is remove.' ;
                    leaf remove {
                      description 'DHCPv6 packet operation type is remove.' ;
                      type enumeration {
                        enum on {
                          value 2 ;
                        }

                      }

                      mandatory true ;
                    }

                  }

                }

              }

              ncd:revise-date 2020-09-22 ;
            }

            choice source-ip-config {
              description 'DHCPv6 relay source ipv6 address.' ;
              case ip {
                description 'Source IPv6 address of DHCPv6 relay instance.' ;
                leaf relay-source-ip {
                  description 'Source IPv6 address of DHCPv6 relay instance.' ;
                  type ncd:ipv6-address ;

                }

              }

              case interface {
                description 'Get the IPv6 address of this interface.' ;
                leaf relay-source-interface {
                  description 'Get the IPv6 address of this interface.' ;
                  type ncd:ifname {
                    length 1..31 ;

                  }

                }

              }

              ncd:revise-date 2020-01-15 ;
            }

          }

        }

        container interface-based-instances {
          description 'DHCPv6 relay interface based instance configuration.' ;
          list instance {
            description 'DHCPv6 relay instance configuration.' ;
            max-elements 256 ;
            key instance-no ;
            leaf instance-no {
              description 'DHCPv6 relay instance number.' ;
              type uint32 {
                range 1..256 {
                  description 'The range of relay instance number.' ;
                }

              }

            }

            leaf description {
              description 'Description of DHCPv6 relay instance.' ;
              type string {
                length 1..64 {
                  description 'The length of DHCPv6 relay instance description.' ;
                }

              }

            }

            container option-modify-config {
              description 'DHCPv6 packet option configurations.' ;
              list option-modify {
                description 'DHCPv6 packet option configuration.' ;
                key 'packet-direction packet-type packet-layer option-code' ;
                leaf packet-direction {
                  description 'DHCPv6 packet direction.' ;
                  type enumeration {
                    enum input {
                      value 1 ;
                      description 'Modify input packet.' ;
                    }

                    enum output {
                      value 2 ;
                      description 'Modify output packet.' ;
                    }

                    enum all-direct {
                      value 3 ;
                      description 'Modify input and output packet.' ;
                    }

                  }

                }

                leaf packet-layer {
                  description 'DHCPv6 packet layer.' ;
                  type enumeration {
                    enum outer-layer {
                      value 1 ;
                      description 'Outer-layer packet.' ;
                    }

                    enum inner-layer {
                      value 2 ;
                      description 'Inner-layer packet.' ;
                    }

                  }

                }

                leaf packet-type {
                  description 'DHCPv6 packet type.' ;
                  type enumeration {
                    enum solicit {
                      value 1 ;
                      description 'The DHCPv6 packet type is solicit.' ;
                    }

                    enum advertise {
                      value 2 ;
                      description 'The DHCPv6 packet type is advertise.' ;
                    }

                    enum request {
                      value 3 ;
                      description 'The DHCPv6 packet type is request.' ;
                    }

                    enum confirm {
                      value 4 ;
                      description 'The DHCPv6 packet type is confirm.' ;
                    }

                    enum renew {
                      value 5 ;
                      description 'The DHCPv6 packet type is renew.' ;
                    }

                    enum rebind {
                      value 6 ;
                      description 'The DHCPv6 packet type is rebind.' ;
                    }

                    enum reply {
                      value 7 ;
                      description 'The DHCPv6 packet type is reply.' ;
                    }

                    enum release {
                      value 8 ;
                      description 'The DHCPv6 packet type is release.' ;
                    }

                    enum decline {
                      value 9 ;
                      description 'The DHCPv6 packet type is decline.' ;
                    }

                    enum reconfigure {
                      value 10 ;
                      description 'The DHCPv6 packet type is reconfigure.' ;
                    }

                    enum inform-request {
                      value 11 ;
                      description 'The DHCPv6 packet type is inform-request.' ;
                    }

                    enum relay-forward {
                      value 12 ;
                      description 'The DHCPv6 packet type is relay-forward.' ;
                    }

                    enum relay-reply {
                      value 13 ;
                      description 'The DHCPv6 packet type is relay-reply.' ;
                    }

                  }

                }

                leaf option-code {
                  description 'DHCPv6 packet option code.' ;
                  type uint16 {
                    range 1..65535 ;

                  }

                }

                choice oper-type {
                  description 'DHCPv6 packet operation type.' ;
                  case set {
                    description 'DHCPv6 packet operation type is set.' ;
                    leaf set-hex-str {
                      description 'DHCPv6 packet option value is HEX string.' ;
                      type string {
                        length 1..254 {
                          description 'The length of HEX string.' ;
                        }

                      }

                      mandatory true ;
                    }

                  }

                  case add {
                    description 'DHCPv6 packet operation type is add.' ;
                    leaf add-hex-str {
                      description 'DHCPv6 packet option value is HEX string.' ;
                      type string {
                        length 1..254 {
                          description 'The length of HEX string.' ;
                        }

                      }

                      mandatory true ;
                    }

                  }

                  case remove {
                    description 'DHCPv6 packet operation type is remove.' ;
                    leaf remove {
                      description 'DHCPv6 packet operation type is remove.' ;
                      type enumeration {
                        enum on {
                          value 2 ;
                        }

                      }

                      mandatory true ;
                    }

                  }

                }

              }

              ncd:revise-date 2020-09-22 ;
            }

            container suboption-modify-config {
              description 'DHCPv6 packet sub option configurations.' ;
              list option-modify {
                description 'DHCPv6 packet option configuration.' ;
                key 'packet-direction packet-layer packet-type option-code suboption-code' ;
                leaf packet-direction {
                  description 'DHCPv6 packet direction.' ;
                  type enumeration {
                    enum input {
                      value 1 ;
                      description 'Modify input packet.' ;
                    }

                    enum output {
                      value 2 ;
                      description 'Modify output packet.' ;
                    }

                    enum all-direct {
                      value 3 ;
                      description 'Modify input and output packet.' ;
                    }

                  }

                }

                leaf packet-layer {
                  description 'DHCPv6 packet layer.' ;
                  type enumeration {
                    enum outer-layer {
                      value 1 ;
                      description 'Outer-layer packet.' ;
                    }

                    enum inner-layer {
                      value 2 ;
                      description 'Inner-layer packet.' ;
                    }

                  }

                }

                leaf packet-type {
                  description 'DHCPv6 packet type.' ;
                  type enumeration {
                    enum solicit {
                      value 1 ;
                      description 'The DHCPv6 packet type is solicit.' ;
                    }

                    enum advertise {
                      value 2 ;
                      description 'The DHCPv6 packet type is advertise.' ;
                    }

                    enum request {
                      value 3 ;
                      description 'The DHCPv6 packet type is request.' ;
                    }

                    enum confirm {
                      value 4 ;
                      description 'The DHCPv6 packet type is confirm.' ;
                    }

                    enum renew {
                      value 5 ;
                      description 'The DHCPv6 packet type is renew.' ;
                    }

                    enum rebind {
                      value 6 ;
                      description 'The DHCPv6 packet type is rebind.' ;
                    }

                    enum reply {
                      value 7 ;
                      description 'The DHCPv6 packet type is reply.' ;
                    }

                    enum release {
                      value 8 ;
                      description 'The DHCPv6 packet type is release.' ;
                    }

                    enum decline {
                      value 9 ;
                      description 'The DHCPv6 packet type is decline.' ;
                    }

                    enum reconfigure {
                      value 10 ;
                      description 'The DHCPv6 packet type is reconfigure.' ;
                    }

                    enum inform-request {
                      value 11 ;
                      description 'The DHCPv6 packet type is inform-request.' ;
                    }

                    enum relay-forward {
                      value 12 ;
                      description 'The DHCPv6 packet type is relay-forward.' ;
                    }

                    enum relay-reply {
                      value 13 ;
                      description 'The DHCPv6 packet type is relay-reply.' ;
                    }

                  }

                }

                leaf option-code {
                  description 'DHCPv6 packet option code.' ;
                  type uint16 {
                    range 1..65535 ;

                  }

                }

                leaf suboption-code {
                  description 'DHCPv6 packet sub option code.' ;
                  type uint16 {
                    range 1..65535 ;

                  }

                }

                choice oper-type {
                  description 'DHCPv6 packet operation type.' ;
                  case set {
                    description 'DHCPv6 packet operation type is set.' ;
                    leaf set-hex-str {
                      description 'DHCPv6 packet option value is HEX string.' ;
                      type string {
                        length 1..254 {
                          description 'The length of HEX string.' ;
                        }

                      }

                      mandatory true ;
                    }

                  }

                  case add {
                    description 'DHCPv6 packet operation type is add.' ;
                    leaf add-hex-str {
                      description 'DHCPv6 packet option value is HEX string.' ;
                      type string {
                        length 1..254 {
                          description 'The length of HEX string.' ;
                        }

                      }

                      mandatory true ;
                    }

                  }

                  case remove {
                    description 'DHCPv6 packet operation type is remove.' ;
                    leaf remove {
                      description 'DHCPv6 packet operation type is remove.' ;
                      type enumeration {
                        enum on {
                          value 2 ;
                        }

                      }

                      mandatory true ;
                    }

                  }

                }

              }

              ncd:revise-date 2020-09-22 ;
            }

            leaf authen-template-name {
              description 'Bind DHCPv6 authentication template name.' ;
              type string {
                length 1..64 {
                  description 'Lenght of bind DHCPv6 authentication template name.' ;
                }

              }

              ncd:revise-date 2020-11-20 ;
            }

            container insert-vss-option {
              description 'Insert VSS option in DHCPv6 relay-forward packet.' ;
              presence insert-vss-option ;
              choice vss-type {
                description 'DHCPv6 relay-forward VSS option type.' ;
                case vrf-name {
                  description 'DHCPv6 relay-forward VSS option type is vrf-name.' ;
                  leaf vrf-name {
                    description 'Insert VRF name in VSS option.' ;
                    type string {
                      length 1..32 {
                        description 'VRF name' ;
                      }

                    }

                    mandatory true ;
                  }

                }

                case vpn-id-from-name {
                  description 'DHCPv6 relay-forward VSS option type is VPN ID.' ;
                  leaf vpn-id-from-vrf-name {
                    description 'Insert global vpn id from vrf name in VSS option.' ;
                    type string {
                      length 1..32 {
                        description 'VRF name' ;
                      }

                    }

                    mandatory true ;
                  }

                }

                case public {
                  description 'DHCPv6 relay-forward VSS option type is public.' ;
                  leaf public {
                    description 'Insert public VRF in VSS option.' ;
                    type empty ;

                    mandatory true ;
                  }

                }

              }

              ncd:revise-date 2022-01-12 ;
            }

          }

          ncd:revise-date 2020-06-09 ;
        }

        container server-groups {
          description 'DHCPv6 relay server group configuration.' ;
          list server-group {
            description 'DHCPv6 relay server group configuration.' ;
            max-elements 64 ;
            key group-no ;
            leaf group-no {
              description 'DHCPv6 relay server group No.[1,64].' ;
              type uint32 {
                range 1..64 {
                  description 'DHCPv6 relay server group No.[1,64].' ;
                }

              }

            }

            leaf algorithm {
              description 'DHCPv6 relay server group algorithm.' ;
              type enumeration {
                enum first {
                  value 1 ;
                }

                enum round-robin {
                  value 2 ;
                }

                enum normal {
                  value 3 ;
                }

              }

              default normal ;
            }

            leaf max-timeout {
              description 'Max timeout of DHCPv6 relay server group server.[0,255].' ;
              type uint32 {
                range 0..255 {
                  description 'The range of max-time.[0,255]' ;
                }

              }

              default 10 ;
            }

            leaf deadtime {
              description 'Deadtime of DHCPv6 relay server.[0,3600]. unit is seconds.' ;
              type uint32 {
                range 0..3600 {
                  description 'Deadtime of DHCPv6 relay server.[0,3600]. unit is seconds.' ;
                }

              }

              units second ;
              default 60 ;
            }

            leaf description {
              description 'Description of DHCPv6 relay server group.' ;
              type string {
                length 1..64 {
                  description 'Description of DHCPv6 relay server group.' ;
                }

              }

            }

            leaf max-retry {
              description 'Max retry times of DHCPv6 relay server group server.' ;
              type uint32 {
                range "0 | 5..20" {
                  description 'Max retry times of DHCPv6 relay server group server.' ;
                }

              }

              default 10 ;
            }

            container servers {
              description 'DHCPv6 relay server group server.' ;
              list server {
                description 'DHCPv6 relay server group server.' ;
                max-elements 64 ;
                key index ;
                leaf index {
                  description 'DHCPv6 relay server group server No.[1,64].' ;
                  type uint32 {
                    range 1..64 {
                      description 'server No.[1,64].' ;
                    }

                  }

                }

                leaf ip {
                  description 'The IP address of the relay server group server.' ;
                  type ncd:ipv6-address ;

                  mandatory true ;
                }

                leaf interface-name {
                  description 'Forward destination interface name.' ;
                  type ncd:ifname {
                    length 1..31 {
                      description 'The length of interface name.' ;
                    }

                  }

                }

                leaf dscp {
                  description 'Configure IPv6 DHCP packet DSCP value.' ;
                  type uint8 {
                    range 0..63 {
                      description 'The range of dscp.' ;
                    }

                  }

                }

                leaf master {
                  description 'Relay server group master server.' ;
                  type enumeration {
                    enum slave {
                      value 0 ;
                      description 'The server is slave.' ;
                    }

                    enum master {
                      value 1 ;
                      description 'The server is master.' ;
                    }

                  }

                  default slave ;
                }

                container dhcpv6-net {
                  description 'The DHCPv6 server in DHCPv6 relay server group is private or public.' ;
                  choice vpn {
                    description 'The DHCPv6 server in DHCPv6 relay server group is private or public.' ;
                    case public {
                      description 'The DHCPv6 relay server group server is private or public' ;
                      leaf public {
                        description 'The DHCPv6 relay server group server is private or public. not-public(0),public(1).' ;
                        type boolean ;

                        default false ;
                      }

                    }

                    case vrf {
                      description 'The DHCPv6 server in DHCP relay server group is private.' ;
                      leaf vrf-name {
                        description 'The VRF name configured for DHCPv6 server in DHCP relay server group.' ;
                        type string {
                          length 1..32 {
                            description 'The length of VRF name.' ;
                          }

                        }

                      }

                    }

                  }

                  ncd:revise-date 2020-04-22 ;
                }

              }

            }

            leaf cos {
              description 'Set 802.1P value in packet that relay send to server.[0,7].' ;
              type uint8 {
                range 0..7 {
                  description 'The range of relay cos.[0,7]' ;
                }

              }

              ncd:revise-date 2019-03-27 ;
            }

          }

        }

        container policy-groups {
          description 'DHCPv6 relay server policy group.' ;
          list policy-group {
            description 'DHCPv6 relay server policy group.' ;
            max-elements 64 ;
            key policy-name ;
            leaf policy-name {
              description 'DHCPv6 Relay server policy group name.' ;
              type string {
                length 1..64 {
                  description 'The name of policy.' ;
                }

              }

            }

            leaf default-server-group {
              description 'DHCPv6 relay default server group number.' ;
              type uint32 {
                range 1..64 {
                  description 'DHCPv6 server group-no.[1,64].' ;
                }

              }

            }

          }

        }

        container interfaces {
          status deprecated ;

          description 'DHCPv6 relay interface configuration.' ;
          list interface {
            description 'DHCPv6 relay interface configuration.' ;
            key name ;
            leaf name {
              description 'DHCPv6 interface name.' ;
              type ncd:ifname {
                length 1..31 {
                  description 'The name length of interface.' ;
                }

              }

            }

            leaf relay-agent {
              description 'Relay agent IPv6 address.' ;
              type ncd:ipv6-address ;

            }

            leaf relay-policy {
              description 'IPv6 DHCP relay policy name.' ;
              type string {
                length 1..64 {
                  description 'The length of relay policy name.' ;
                }

              }

            }

            leaf relay-interface-id {
              description 'IPv6 DHCP relay interface-id.' ;
              type string {
                length 1..64 {
                  description 'The length of relay interface id.' ;
                }

              }

            }

            choice source-ip-config {
              description 'DHCPv6 relay source ipv6 address.' ;
              case ip {
                description 'Source IPv6 address of DHCPv6 interface.' ;
                leaf relay-source-ip {
                  description 'Source IPv6 address of DHCPv6 interface.' ;
                  type ncd:ipv6-address ;

                }

              }

              case interface {
                description 'Get the IPv6 address of this interface.' ;
                leaf relay-source-interface {
                  description 'Get the IPv6 address of this interface.' ;
                  type ncd:ifname {
                    length 1..31 ;

                  }

                }

                ncd:revise-date 2020-01-15 ;
              }

            }

          }

        }

      }

      container client {
        description 'DHCPv6 client config.' ;
        container associated-prefix {
          description 'Configure IPv6 DHCP client associated prefix information.' ;
          container interfaces {
            description 'DHCPv6 client interface configuration.' ;
            list interface {
              description 'DHCPv6 client interface configuration on the interface.' ;
              key 'name prefix-name prefix-ip prefix-len' ;
              leaf name {
                description 'Interface name.' ;
                type ncd:ifname {
                  length 1..31 {
                    description 'The name length of interface.' ;
                  }

                }

              }

              leaf prefix-name {
                description 'Prefix name.' ;
                type string {
                  length 1..31 {
                    description 'The length of prefix-name.' ;
                  }

                }

              }

              leaf prefix-ip {
                description 'IPv6 prefix address.' ;
                type ncd:ipv6-address ;

              }

              leaf prefix-len {
                description 'Length of IPv6 prefix address.' ;
                type uint32 {
                  range 1..128 ;

                }

              }

            }

          }

        }

        container prefix-switch {
          description 'Configuration of obtain DHCPv6 prefix address.' ;
          container interfaces {
            description 'DHCPv6 client interface configuration.' ;
            list interface {
              description 'DHCPv6 client interface configuration on the interface.' ;
              key name ;
              leaf name {
                description 'Interface name.' ;
                type ncd:ifname ;

              }

              leaf flag {
                description 'DHCPv6 client obtain prefix address switch.' ;
                type enumeration {
                  enum flag-off {
                    value 0 ;
                    description 'DHCPv6 client obtain prefix address off.' ;
                  }

                  enum flag-on {
                    value 1 ;
                    description 'DHCPv6 client obtain prefix address on.' ;
                  }

                }

                mandatory true ;
              }

              leaf prefix-name {
                description 'Prefix name.' ;
                type string {
                  length 1..31 ;

                }

                mandatory true ;
              }

              leaf rapid-commit {
                description 'DHCPv6 client obtain prefix address rapid commit switch.' ;
                type enumeration {
                  enum rapid-off {
                    value 0 ;
                    description 'DHCPv6 client obtain prefix address rapid commit off.' ;
                  }

                  enum rapid-on {
                    value 1 ;
                    description 'DHCPv6 client obtain prefix address rapid commit on.' ;
                  }

                }

                default rapid-off ;
              }

              leaf policy-name {
                description 'DHCPv6 client policy name.' ;
                type string {
                  length 1..16 {
                    description 'The length of client policy name' ;
                  }

                }

                ncd:revise-date 2021-08-19 ;
              }

            }

          }

        }

        container address-switch {
          description 'Configuration of obtain DHCPv6 address by flag switch.' ;
          container interfaces {
            description 'DHCPv6 client interface configuration.' ;
            list interface {
              description 'DHCPv6 client interface configuration on the interface.' ;
              key name ;
              leaf name {
                description 'Interface name.' ;
                type ncd:ifname {
                  length 1..31 {
                    description 'The name length of interface.' ;
                  }

                }

              }

              leaf flag {
                description 'DHCPv6 client switch.' ;
                type enumeration {
                  enum flag-off {
                    value 0 ;
                    description 'DHCPv6 client turn off.' ;
                  }

                  enum flag-on {
                    value 1 ;
                    description 'DHCPv6 client turn on.' ;
                  }

                }

                mandatory true ;
              }

              leaf rapid-commit {
                description 'DHCPv6 client rapid commit switch.' ;
                type enumeration {
                  enum rapid-off {
                    value 0 ;
                    description 'DHCPv6 client rapid commit off.' ;
                  }

                  enum rapid-on {
                    value 1 ;
                    description 'DHCPv6 client rapid commit on.' ;
                  }

                }

                default rapid-off ;
              }

              leaf policy-name {
                description 'DHCPv6 client policy name.' ;
                type string {
                  length 1..16 {
                    description 'The length of client policy name' ;
                  }

                }

                ncd:revise-date 2021-08-19 ;
              }

            }

          }

        }

        container address-auto-config {
          description 'Configuration of obtain DHCPv6 address by auto-config.' ;
          container interfaces {
            description 'DHCPv6 client interface configuration.' ;
            list interface {
              description 'DHCPv6 client interface configuration on the interface.' ;
              key name ;
              leaf name {
                description 'Interface name.' ;
                type ncd:ifname {
                  length 1..31 {
                    description 'The name length of interface.' ;
                  }

                }

              }

              leaf autoconfig {
                description 'DHCPv6 client autoconfig.' ;
                type enumeration {
                  enum auto-config-off {
                    value 0 ;
                    description 'DHCPv6 auto-config off.' ;
                  }

                  enum auto-config-on {
                    value 1 ;
                    description 'DHCPv6 auto-config on.' ;
                  }

                }

                default auto-config-off ;
              }

              leaf policy-name {
                description 'DHCPv6 client policy name.' ;
                type string {
                  length 1..16 {
                    description 'The length of client policy name' ;
                  }

                }

                ncd:revise-date 2021-08-19 ;
              }

            }

          }

        }

        container policys {
          description 'Configuration of DHCPv6 client policy.' ;
          list policy {
            description 'Configuration of DHCPv6 client policy.' ;
            key name ;
            leaf name {
              description 'DHCPv6 client policy name.' ;
              type string {
                length 1..16 {
                  description 'DHCPv6 client policy name length.' ;
                }

              }

              mandatory true ;
            }

            container option16 {
              description 'Configuration of DHCPv6 client option16 information.' ;
              choice type {
                description 'Configuration of DHCPv6 client option16 type.' ;
                case ascii {
                  description 'Configuration of DHCPv6 client option16 type is ascii.' ;
                  leaf ascii-string {
                    description 'Configuration of DHCPv6 client option16 ascii string.' ;
                    type string {
                      length 1..64 {
                        description 'The length of option16 ascii string' ;
                      }

                    }

                    mandatory true ;
                  }

                }

                case hex {
                  description 'Configuration of DHCPv6 client option16 type is hex.' ;
                  leaf hex-string {
                    description 'Configuration of DHCPv6 client option16 hex string.' ;
                    type string {
                      length 1..64 {
                        description 'The length of option16 ascii string' ;
                      }

                    }

                    mandatory true ;
                  }

                }

              }

            }

            container request-lists {
              description 'Configuration of DHCPv6 client request option lists.' ;
              list request-list {
                description 'Configuration of DHCPv6 client request option lists.' ;
                key request-option-code ;
                leaf request-option-code {
                  description 'Configuration of DHCPv6 client request option code.' ;
                  type enumeration {
                    enum bootfile-param {
                      value 60 ;
                      description 'Request bootfile param(option 60)' ;
                    }

                    enum bootfile-url {
                      value 59 ;
                      description 'Request bootfile url(option 59)' ;
                    }

                    enum domain-name-server {
                      value 23 ;
                      description 'Request domain name server(option 23)' ;
                    }

                  }

                  mandatory true ;
                }

              }

            }

          }

          ncd:revise-date 2021-08-19 ;
        }

      }

      container interfaces {
        description 'Interface-related configurations.' ;
        list interface {
          description 'DHCPv6 interface common configuration.Dependent on the interface.' ;
          key name ;
          leaf name {
            description 'DHCPv6 interface name.' ;
            type ncd:ifname {
              length 1..64 {
                description 'The name length of interface.' ;
              }

            }

          }

          leaf work-mode {
            description 'Configure IPv6 DHCP work mode.[0,2] default-value(0),relay(1),server(2).' ;
            type enumeration {
              enum default-value {
                value 0 ;
                description 'The work mode is not define.' ;
              }

              enum relay {
                value 1 ;
                description 'The work mode is relay.' ;
              }

              enum server {
                value 2 ;
                description 'The work mode is server.' ;
              }

            }

            default default-value ;
          }

          leaf dscp {
            description 'Configure IPv6 DHCP packet DSCP value.' ;
            type uint8 {
              range 0..63 {
                description 'The range of dscp.' ;
              }

            }

          }

          leaf broadband-user-access {
            description 'Configure IPv6 DHCP broadband user access under this interface.' ;
            type enumeration {
              enum enable {
                value 1 ;
                description 'This interface is broadband user access interface.' ;
              }

              enum disable {
                value 0 ;
                description 'This interface is not broadband user access interface.' ;
              }

            }

            default disable ;
            ncd:revise-date 2021-04-26 ;
          }

          container relay-if {
            description 'DHCPv6 interface relay configuration.Dependent on the interface.' ;
            presence relay-if ;
            leaf relay-agent {
              description 'Relay agent IPv6 address.' ;
              type ncd:ipv6-address ;

            }

            leaf relay-policy {
              description 'IPv6 DHCP relay policy name.' ;
              type string {
                length 1..64 {
                  description 'The length of relay policy name' ;
                }

              }

            }

            leaf relay-interface-id {
              description 'IPv6 DHCP relay interface-id.' ;
              type string {
                length 1..64 {
                  description 'The length of relay interface id.' ;
                }

              }

            }

            choice source-ip-config {
              description 'DHCPv6 relay source ipv6 address.' ;
              case ip {
                description 'Source IPv6 address of DHCPv6 interface.' ;
                leaf relay-source-ip {
                  description 'Source IPv6 address of DHCPv6 interface.' ;
                  type ncd:ipv6-address ;

                }

              }

              case interface {
                description 'Get the IPv6 address of this interface.' ;
                leaf relay-source-interface {
                  description 'Get the IPv6 address of this interface.' ;
                  type ncd:ifname {
                    length 1..31 ;

                  }

                }

                ncd:revise-date 2020-02-17 ;
              }

            }

            leaf relay-forward-mode {
              description 'Set DHCPv6 relay forward mode' ;
              type enumeration {
                enum secure-forward {
                  value 3 ;
                  description 'relay forward with user data' ;
                }

                enum fast-forward {
                  value 1 ;
                  description 'relay forward without user data' ;
                }

                enum steady-forward {
                  value 2 ;
                  description 'relay forward with temporary data' ;
                }

              }

              default secure-forward ;
              ncd:revise-date 2016-03-09 ;
            }

            container short-time {
              description 'Short lease time for DHCPv6 relay interface.' ;
              presence short-time ;
              leaf short-valid-time {
                description 'Short valid lease time for DHCPv6 relay interface.[60,4294967295].Unit is seconds.' ;
                type uint32 {
                  range 60..4294967295 {
                    description 'The range of short valid lease time for DHCPv6 relay interface.' ;
                  }

                }

                units second ;
                mandatory true ;
              }

              leaf short-preferred-time {
                description 'Short preferred lease time for DHCPv6 relay interface.[60,4294967295].Unit is seconds.' ;
                type uint32 {
                  range 60..4294967295 {
                    description 'The range of short preferred lease time for DHCPv6 relay interface.' ;
                  }

                }

                units second ;
                mandatory true ;
              }

              ncd:revise-date 2020-04-11 ;
            }

            leaf bind-relay-instance {
              description 'The relay instance of the interface.' ;
              type uint32 {
                range 1..256 {
                  description 'The range of relay instance number.' ;
                }

              }

              ncd:revise-date 2020-06-09 ;
            }

            leaf relay-server-group-number {
              description 'Bind relay server group number under this interface.' ;
              type uint32 {
                range 1..64 {
                  description 'The range of relay server group number.' ;
                }

              }

              ncd:revise-date 2021-06-03 ;
            }

            leaf reply-unrestricted {
              description 'Configure DHCPv6 relay forward reply unrestricted switch under this interface.' ;
              type enumeration {
                enum on {
                  value 1 ;
                  description 'Turn on relay forward reply unrestricted.' ;
                }

                enum off {
                  value 0 ;
                  description 'Turn off relay forward reply unrestricted.' ;
                }

              }

              default off ;
              ncd:revise-date 2022-03-07 ;
            }

          }

          container server-if {
            description 'DHCPv6 interface server configuration.Dependent on the interface.' ;
            presence server-if ;
            leaf server-policy {
              description 'IPv6 DHCP server policy name.' ;
              type string {
                length 1..64 {
                  description 'The length of server policy.' ;
                }

              }

            }

            leaf server-unicast {
              description 'DHCPv6 server unicast option.' ;
              type enumeration {
                enum disable {
                  value 0 ;
                  description 'Turn off server unicast flag.' ;
                }

                enum enable {
                  value 1 ;
                  description 'Turn on server unicast flag.' ;
                }

              }

              default disable ;
            }

            leaf bind-server-instance {
              description 'The server instance of the interface.' ;
              type uint32 {
                range 1..256 {
                  description 'The range of server instance number.' ;
                }

              }

              ncd:revise-date 2020-06-09 ;
            }

          }

        }

      }

      container server {
        description 'DHCPv6 server config.' ;
        container interfaces {
          status deprecated ;

          description 'Interface-related configurations.' ;
          list interface {
            description 'DHCPv6 interface common configuration.Dependent on the interface.' ;
            key name ;
            leaf name {
              description 'DHCPv6 interface name.' ;
              type ncd:ifname {
                length 1..31 {
                  description 'The name length of interface.' ;
                }

              }

            }

            leaf server-policy {
              description 'IPv6 DHCP server policy name.' ;
              type string {
                length 1..64 {
                  description 'The length of server policy.' ;
                }

              }

            }

            leaf server-unicast {
              description 'DHCPv6 server unicast option.' ;
              type enumeration {
                enum disable {
                  value 0 ;
                  description 'Turn off server unicast flag.' ;
                }

                enum enable {
                  value 1 ;
                  description 'Turn on server unicast flag.' ;
                }

              }

              default disable ;
            }

          }

        }

        container policys {
          description 'DHCPv6 policy configuration.' ;
          list policy {
            description 'DHCPv6 policy configuration.' ;
            max-elements 50 ;
            key 'name priority' ;
            leaf name {
              description 'DHCPv6 policy name.' ;
              type string {
                length 1..64 {
                  description 'The length of policy name.' ;
                }

              }

            }

            leaf priority {
              description 'DHCPv6 policy priority.' ;
              type uint32 {
                range 1..128 {
                  description 'The range of policy priority.' ;
                }

              }

            }

            leaf pool-name {
              description 'DHCPv6 pool name configured in the policy.' ;
              type string {
                length 1..64 {
                  description 'The length of pool name.' ;
                }

              }

            }

            leaf link-address {
              description 'IPv6 link address to match.' ;
              type ncd:ipv6-address ;

            }

            container option16-match {
              description 'DHCPv6 policy match option16 configuration.' ;
              choice match-type {
                description 'The match type of option16.' ;
                case exist {
                  description 'If option16 exist in DHCPv6 packet,then match.' ;
                  leaf exist-option16 {
                    description 'If option16 exist in DHCPv6 packet,then match.' ;
                    type empty ;

                    mandatory true ;
                  }

                }

                case partial-match {
                  description 'Match option16 type is partial-match.' ;
                  leaf partial-match-string {
                    description 'Match option16 type is partial-match.' ;
                    type ncd:string-with-blank {
                      length 1..64 {
                        description 'Option16 string length' ;
                      }

                    }

                    mandatory true ;
                  }

                }

                case full-match {
                  description 'Match option16 type is full-match.' ;
                  leaf full-match-string {
                    description 'Match option16 type is full-match.' ;
                    type ncd:string-with-blank {
                      length 1..64 {
                        description 'Option16 string length' ;
                      }

                    }

                    mandatory true ;
                  }

                }

              }

              ncd:revise-date 2021-08-19 ;
            }

          }

        }

        container pools {
          description 'DHCPv6 pool configuration.' ;
          list pool {
            description 'DHCPv6 pool configuration.' ;
            max-elements 100 ;
            key name ;
            leaf name {
              description 'DHCPv6 pool name.' ;
              type string {
                length 1..64 {
                  description 'The length of pool name.' ;
                }

              }

            }

            leaf preference {
              description 'Configure preference option.' ;
              type uint32 {
                range 1..255 {
                  description 'The range of pool preference.' ;
                }

              }

            }

            leaf server-unicast-address {
              description 'Configure enable server unicast address.' ;
              type ncd:ipv6-address ;

            }

            leaf ignore-request-list {
              description 'When DHCPv6 server send response packet,fill in option,ignore request list or not.' ;
              type enumeration {
                enum ignore {
                  value 1 ;
                  description 'When fill in option, ignore request list.' ;
                }

                enum not-ignore {
                  value 0 ;
                  description 'When fill in option,by request list.' ;
                }

              }

              default not-ignore ;
              ncd:revise-date 2020-08-20 ;
            }

            container address-lifetime {
              description 'DHCPv6 address lifetime.' ;
              choice valid-lifetime {
                description 'DHCPv6 address lifetime.' ;
                default addr-valid-value ;
                case addr-valid-value {
                  description 'address valid lifetime.' ;
                  leaf addr-valid-value {
                    description 'Address valid lifetime.[60,4294967295]. unit is seconds.' ;
                    type uint32 {
                      range 60..4294967295 {
                        description 'The range of vaild lifetime.' ;
                      }

                    }

                    units second ;
                    default 3600 ;
                  }

                }

                case addr-valid-infinite {
                  description 'address valid infinite lifetime.' ;
                  leaf addr-valid-infinite {
                    description 'Address valid infinite lifetime.' ;
                    type enumeration {
                      enum infinite-off {
                        value 0 ;
                        description 'Set DHCPv6 address-valid-lifetime finite.' ;
                      }

                      enum infinite-on {
                        value 1 ;
                        description 'Set DHCPv6 address-valid-lifetime infinite.' ;
                      }

                    }

                    default infinite-off ;
                  }

                }

              }

              choice preferred-lifetime {
                description 'DHCPv6 preferred lifetime.' ;
                default addr-preferred-value ;
                case addr-preferred-value {
                  description 'address preferred lifetime.' ;
                  leaf addr-preferred-value {
                    description 'Address preferred lifetime.[60,4294967295]. unit is seconds.' ;
                    type uint32 {
                      range 60..4294967295 {
                        description 'The range of vaild lifetime.' ;
                      }

                    }

                    units second ;
                    default 3600 ;
                  }

                }

                case addr-preferred-infinite {
                  description 'address preferred infinite lifetime.' ;
                  leaf addr-preferred-infinite {
                    description 'Address preferred lifetime.' ;
                    type enumeration {
                      enum infinite-off {
                        value 0 ;
                        description 'Set DHCPv6 address-preferred-lifetime finite.' ;
                      }

                      enum infinite-on {
                        value 1 ;
                        description 'Set DHCPv6 address-preferred-lifetime infinite.' ;
                      }

                    }

                    default infinite-off ;
                  }

                }

              }

            }

            container prefix-lifetime {
              description 'DHCPv6 prefix lifetime.' ;
              choice valid-lifetime {
                description 'DHCPv6 prefix valid lifetime.' ;
                default prefix-valid-value ;
                case prefix-valid-value {
                  description 'DHCPv6 prefix valid lifetime.' ;
                  leaf prefix-valid-value {
                    description 'DHCPv6 prefix valid lifetime.[60,4294967295]. unit is seconds.' ;
                    type uint32 {
                      range 60..4294967295 {
                        description 'The range of vaild lifetime.' ;
                      }

                    }

                    units second ;
                    default 3600 ;
                  }

                }

                case prefix-valid-infinite {
                  description 'DHCPv6 prefix valid  infinite lifetime.' ;
                  leaf prefix-valid-infinite {
                    description 'DHCPv6 prefix valid infinite lifetime.' ;
                    type enumeration {
                      enum infinite-off {
                        value 0 ;
                        description 'Set DHCPv6 prefix-valid-lifetime finite.' ;
                      }

                      enum infinite-on {
                        value 1 ;
                        description 'Set DHCPv6 prefix-valid-lifetime infinite.' ;
                      }

                    }

                    default infinite-off ;
                  }

                }

              }

              choice prefix-preferred-lifetime {
                description 'DHCPv6 prefix preferred lifetime.' ;
                default prefix-preferred-value ;
                case prefix-preferred-value {
                  description 'DHCPv6 prefix preferred lifetime.' ;
                  leaf prefix-preferred-value {
                    description 'prefix preferred lifetime.[60,4294967295]. unit is seconds.' ;
                    type uint32 {
                      range 60..4294967295 {
                        description 'The range of vaild lifetime.' ;
                      }

                    }

                    units second ;
                    default 3600 ;
                  }

                }

                case prefix-preferred-infinite {
                  description 'DHCPv6 prefix preferred infinite lifetime.' ;
                  leaf prefix-preferred-infinite {
                    description 'DHCPv6 prefix preferred infinite lifetime.' ;
                    type enumeration {
                      enum infinite-off {
                        value 0 ;
                        description 'Set DHCPv6 prefix-valid-lifetime finite.' ;
                      }

                      enum infinite-on {
                        value 1 ;
                        description 'Set DHCPv6 prefix-valid-lifetime infinite.' ;
                      }

                    }

                    default infinite-off ;
                  }

                }

              }

            }

            container dns-servers {
              description 'Configure ipv6 DNS.' ;
              list dns-server {
                description 'Configure ipv6 DNS.' ;
                key no ;
                leaf no {
                  description 'DNS number.' ;
                  type uint32 {
                    range 1..2 ;

                  }

                }

                leaf address {
                  description 'DNS IPV6 address.' ;
                  type ncd:ipv6-address ;

                  mandatory true ;
                }

              }

            }

            container domains {
              description 'configure IPV6 DNS server domain.' ;
              list domain {
                description 'configure IPV6 DNS server domain.' ;
                key no ;
                leaf no {
                  description 'Domain number.' ;
                  type uint32 {
                    range 1..2 ;

                  }

                }

                leaf name {
                  description 'Domain name.' ;
                  type string {
                    length 1..64 ;

                  }

                  mandatory true ;
                }

              }

            }

            container address-pools {
              description 'configure address pool.' ;
              presence address-pools ;
              leaf address-pool-name {
                description 'configure address pool name.' ;
                type string {
                  length 1..64 {
                    description 'The length of adrress-pool-name.' ;
                  }

                }

                mandatory true ;
              }

            }

            container prefix-pools {
              description 'configure prefix pool.' ;
              presence prefix-pools ;
              leaf prefix-pool-name {
                description 'configure prefix pool name.' ;
                type string {
                  length 1..64 {
                    description 'The length of prefix-pool-name.' ;
                  }

                }

                mandatory true ;
              }

            }

            container aftr {
              description 'configure AFTR.' ;
              choice aftr {
                description 'configure AFTR.' ;
                case address {
                  description 'Configure DS-Lite address option.' ;
                  leaf server-address {
                    description 'configure tunnel endpoint address.' ;
                    type ncd:ipv6-address ;

                    mandatory true ;
                  }

                }

                case fqdn {
                  description 'Configure AFTR name option.' ;
                  leaf fqdn {
                    description 'configure tunnel endpoint name.' ;
                    type string {
                      length 1..64 ;

                    }

                    mandatory true ;
                  }

                }

              }

              leaf option-code-value {
                description 'Configure the value of option code field.' ;
                type uint16 {
                  range 1..65535 ;

                }

                default 64 ;
              }

            }

            container options {
              description 'Configure option.' ;
              list option {
                description 'Configure option.' ;
                key option-id ;
                leaf option-id {
                  description 'Configure option ID.' ;
                  type uint16 {
                    range 1..65535 ;

                  }

                }

                leaf description {
                  description 'Option description.' ;
                  type string {
                    length 1..64 {
                      description 'The length of description.' ;
                    }

                  }

                }

                leaf force-reply {
                  description 'Force or not fill this option in response packet to client.' ;
                  type enumeration {
                    enum on {
                      value 1 ;
                      description 'Force reply this option in response packet.' ;
                    }

                    enum off {
                      value 0 ;
                      description 'Not force reply this option in response packet.' ;
                    }

                  }

                  default off ;
                  ncd:revise-date 2020-08-20 ;
                }

                choice type {
                  description 'DHCPv6 pool option type.' ;
                  mandatory true ;
                  case ascii {
                    description 'DHCPv6 pool option type is ASCII string.' ;
                    leaf ascii-string {
                      description 'ASCII string.' ;
                      type string {
                        length 1..64 ;

                      }

                      mandatory true ;
                    }

                  }

                  case fqdn {
                    description 'DHCPv6 pool option type is fqdn string.' ;
                    leaf fqdn-string {
                      description 'Fqdn string.' ;
                      type string {
                        length 1..32 ;

                      }

                      mandatory true ;
                    }

                  }

                  case hex {
                    description 'DHCPv6 pool option type is HEX string.' ;
                    leaf hex-string {
                      description 'HEX string.' ;
                      type string {
                        length 1..128 ;

                      }

                      mandatory true ;
                    }

                  }

                  case ip {
                    description 'DHCPv6 pool option type is IP.' ;
                    container ip-address {
                      presence ip-address ;
                      leaf address-1 {
                        description 'Configure the frist IPV6 address.' ;
                        type ncd:ipv6-address ;

                        mandatory true ;
                      }

                      container ip-address2 {
                        presence ip-address2 ;
                        leaf address-2 {
                          description 'Configure the second IPV6 address.' ;
                          type ncd:ipv6-address ;

                          mandatory true ;
                        }

                        container ip-address3 {
                          presence ip-address3 ;
                          leaf address-3 {
                            description 'Configure the third IPV6 address.' ;
                            type ncd:ipv6-address ;

                            mandatory true ;
                          }

                          container ip-address4 {
                            presence ip-address4 ;
                            leaf address-4 {
                              description 'Configure the fourth IPV6 address.' ;
                              type ncd:ipv6-address ;

                              mandatory true ;
                            }

                            container ip-address5 {
                              presence ip-address5 ;
                              leaf address-5 {
                                description 'Configure the fifth IPV6 address.' ;
                                type ncd:ipv6-address ;

                                mandatory true ;
                              }

                              container ip-address6 {
                                presence ip-address6 ;
                                leaf address-6 {
                                  description 'Configure the sixth IPV6 address.' ;
                                  type ncd:ipv6-address ;

                                  mandatory true ;
                                }

                                container ip-address7 {
                                  presence ip-address7 ;
                                  leaf address-7 {
                                    description 'Configure the seventh IPV6 address.' ;
                                    type ncd:ipv6-address ;

                                    mandatory true ;
                                  }

                                  container ip-address8 {
                                    presence ip-address8 ;
                                    leaf address-8 {
                                      description 'Configure the eighth IPV6 address.' ;
                                      type ncd:ipv6-address ;

                                      mandatory true ;
                                    }

                                  }

                                }

                              }

                            }

                          }

                        }

                      }

                    }

                  }

                }

              }

            }

            container bindings {
              description 'Configure static binding information.' ;
              list binding-address {
                description 'Configure static binding information of address with no VRF.' ;
                key 'duid address' ;
                leaf duid {
                  description 'Configure user DUID.' ;
                  type string {
                    length 1..254 {
                      description 'The length of DUID.' ;
                    }

                  }

                }

                leaf address {
                  description 'Configure IPV6 address.' ;
                  type ncd:ipv6-address ;

                }

              }

              list binding-address-with-vrf {
                description 'Configure static binding information of address with VRF.' ;
                key 'duid vrf-name address' ;
                leaf duid {
                  description 'Configure user DUID.' ;
                  type string {
                    length 1..254 {
                      description 'The length of DUID.' ;
                    }

                  }

                }

                leaf vrf-name {
                  description 'Config the VRF name.' ;
                  type string {
                    length 1..32 {
                      description 'The length of VRF name.' ;
                    }

                  }

                }

                leaf address {
                  description 'Configure IPV6 address.' ;
                  type ncd:ipv6-address ;

                }

              }

              list binding-prefix {
                description 'Configure static binding information of prefix with no VRF.' ;
                key 'duid prefix prefix-len' ;
                leaf duid {
                  description 'Configure user DUID.' ;
                  type string {
                    length 1..254 {
                      description 'The length of DUID.' ;
                    }

                  }

                }

                leaf prefix {
                  description 'Configure IPV6 prefix.' ;
                  type ncd:ipv6-address ;

                }

                leaf prefix-len {
                  description 'Configure IPV6 prefix len.' ;
                  type uint8 {
                    range 1..128 {
                      description 'The range of prefix-len.' ;
                    }

                  }

                }

              }

              list binding-prefix-with-vrf {
                description 'Configure static binding information of prefix with VRF.' ;
                key 'duid vrf-name prefix prefix-len' ;
                leaf duid {
                  description 'Configure user DUID.' ;
                  type string {
                    length 1..254 {
                      description 'The length of DUID.' ;
                    }

                  }

                }

                leaf vrf-name {
                  description 'Config the VRF name.' ;
                  type string {
                    length 1..32 {
                      description 'The length of VRF name.' ;
                    }

                  }

                }

                leaf prefix {
                  description 'Configure IPV6 prefix.' ;
                  type ncd:ipv6-address ;

                }

                leaf prefix-len {
                  description 'Configure IPV6 prefix len.' ;
                  type uint8 {
                    range 1..128 {
                      description 'The value range.' ;
                    }

                  }

                }

              }

            }

            container bind-pcp-servers {
              description 'Bind PCP server to DHCPv6 pool.' ;
              list bind-pcp-server {
                description 'Bind PCP server to DHCPv6 pool.' ;
                key pcp-server-name ;
                leaf pcp-server-name {
                  description 'PCP server name.' ;
                  type string {
                    length 1..64 {
                      description 'The length of PCP server name.' ;
                    }

                  }

                }

              }

              ncd:revise-date 2017-03-09 ;
            }

            container bind-mac-address {
              description 'Configure static mac bind address information.' ;
              list bind-mac-address {
                description 'Configure static bind mac information of address with no VRF.' ;
                key mac ;
                leaf mac {
                  description 'Configure user MAC' ;
                  type ncd:mac-address ;

                }

                leaf address {
                  mandatory true ;
                  description 'Configure IPV6 address.' ;
                  type ncd:ipv6-address ;

                }

                leaf option-template {
                  description 'The option template name of this static bind mac information.' ;
                  type string {
                    length 1..64 {
                      description 'The length of option-template name.' ;
                    }

                  }

                  ncd:revise-date 2021-01-04 ;
                }

              }

              ncd:revise-date 2020-04-01 ;
            }

            container bind-mac-address-vrf {
              description 'Configure static mac bind address information with vrf.' ;
              list bind-mac-address-vrf {
                description 'Configure static bind mac information of address with VRF.' ;
                key 'mac vrf-name' ;
                leaf mac {
                  description 'Configure user MAC' ;
                  type ncd:mac-address ;

                }

                leaf vrf-name {
                  description 'Config the VRF name.' ;
                  type string {
                    length 1..32 {
                      description 'The length of VRF name.' ;
                    }

                  }

                }

                leaf address {
                  mandatory true ;
                  description 'Configure IPV6 address.' ;
                  type ncd:ipv6-address ;

                }

                leaf option-template {
                  description 'The option template name of this static bind mac information.' ;
                  type string {
                    length 1..64 {
                      description 'The length of option-template name.' ;
                    }

                  }

                  ncd:revise-date 2021-01-04 ;
                }

              }

              ncd:revise-date 2020-04-01 ;
            }

            container bind-mac-prefix {
              description 'Configure static mac bind prefix information.' ;
              list bind-mac-prefix {
                description 'Configure static bind mac information of prefix with no VRF.' ;
                key mac ;
                leaf mac {
                  description 'Configure user MAC' ;
                  type ncd:mac-address ;

                }

                leaf prefix {
                  mandatory true ;
                  description 'Configure IPV6 prefix.' ;
                  type ncd:ipv6-address ;

                }

                leaf prefix-len {
                  mandatory true ;
                  description 'Configure IPV6 prefix len.' ;
                  type uint8 {
                    range 1..128 {
                      description 'The range of prefix-len.' ;
                    }

                  }

                }

              }

              ncd:revise-date 2020-04-01 ;
            }

            container bind-mac-prefix-vrf {
              description 'Configure static mac bind prefix information with vrf.' ;
              list bind-mac-prefix-with-vrf {
                description 'Configure static bind mac information of prefix with VRF.' ;
                key 'mac vrf-name' ;
                leaf mac {
                  description 'Configure user MAC' ;
                  type ncd:mac-address ;

                }

                leaf vrf-name {
                  description 'Config the VRF name.' ;
                  type string {
                    length 1..32 {
                      description 'The length of VRF name.' ;
                    }

                  }

                }

                leaf prefix {
                  mandatory true ;
                  description 'Configure IPV6 prefix.' ;
                  type ncd:ipv6-address ;

                }

                leaf prefix-len {
                  mandatory true ;
                  description 'Configure IPV6 prefix len.' ;
                  type uint8 {
                    range 1..128 {
                      description 'The range of prefix-len.' ;
                    }

                  }

                }

              }

              ncd:revise-date 2020-04-01 ;
            }

          }

        }

        container instances {
          description 'DHCPv6 server instance configuration.' ;
          list instance {
            description 'DHCPv6 server instance configuration.' ;
            max-elements 256 ;
            key instance-no ;
            leaf instance-no {
              description 'DHCPv6 server instance number.' ;
              type uint32 {
                range 1..256 {
                  description 'The number of instance.' ;
                }

              }

            }

            leaf description {
              description 'Configure description.' ;
              type string {
                length 1..64 {
                  description 'The length of description.' ;
                }

              }

            }

            leaf pool-name {
              description 'Bind DHCPv6 pool.' ;
              type string {
                length 1..64 {
                  description 'The length of pool name.' ;
                }

              }

            }

            leaf server-unicast {
              description 'Turn on DHCPv6 server unicast option.' ;
              type enumeration {
                enum off {
                  value 0 ;
                  description 'Turn off server unicast flag.' ;
                }

                enum on {
                  value 1 ;
                  description 'Turn on server unicast flag.' ;
                }

              }

              default off ;
            }

          }

        }

        container interface-based-instances {
          description 'DHCPv6 server interface based instance configuration.' ;
          list instance {
            description 'DHCPv6 server instance configuration.' ;
            max-elements 256 ;
            key instance-no ;
            leaf instance-no {
              description 'DHCPv6 server instance number.' ;
              type uint32 {
                range 1..256 {
                  description 'The number of instance.' ;
                }

              }

            }

            leaf description {
              description 'Configure description.' ;
              type string {
                length 1..64 {
                  description 'The length of description.' ;
                }

              }

            }

            leaf authen-template-name {
              description 'Bind DHCPv6 authentication template name.' ;
              type string {
                length 1..64 {
                  description 'Lenght of bind DHCPv6 authentication template name.' ;
                }

              }

              ncd:revise-date 2020-11-20 ;
            }

          }

          ncd:revise-date 2020-06-09 ;
        }

        container global-config {
          description 'DHCPv6 Server Global configuration.' ;
          leaf max-user {
            description "Max user numbers of DHCPv6 server. It's toplimit depends on ability of the device." ;
            type uint32 {
              range 1..256000 {
                description 'The range of the value is 1 to 256000.' ;
              }

            }

          }

          leaf duid {
            description 'Configure server DUID.' ;
            type string {
              length 1..254 {
                description 'The length of DUID.' ;
              }

            }

          }

          leaf rapid-redial {
            description 'Enable rapid redial.' ;
            type enumeration {
              enum rapid-redial-off {
                value 0 ;
                description 'Turn off server rapid-redial.' ;
              }

              enum rapid-redial-on {
                value 1 ;
                description 'Turn on server rapid-redial.' ;
              }

            }

            default rapid-redial-off ;
          }

          container single-user-quota {
            description 'Configure quota of address or prefix per user.' ;
            leaf address-quota {
              description 'Configure quota of address  per user.' ;
              type uint16 {
                range 1..65535 {
                  description 'The range of the value is 1 to 65535.' ;
                }

              }

            }

            leaf prefix-quota {
              description 'Configure quota of prefix per user.' ;
              type uint16 {
                range 1..65535 {
                  description 'The range of the value is 1 to 65535.' ;
                }

              }

            }

          }

        }

        container pcp-servers {
          description 'DHCPv6 PCP server configuration.' ;
          list pcp-server {
            description 'DHCPv6 PCP server configuration.' ;
            max-elements 8 ;
            key name ;
            leaf name {
              description 'DHCPv6 PCP server name.' ;
              type string {
                length 1..64 {
                  description 'The length of PCP server name.' ;
                }

              }

            }

            container ipv4-addresses {
              description 'PCP server IPv4 address.' ;
              list ipv4-address {
                description 'PCP server IPv4 address.' ;
                key ipv4-addr ;
                leaf ipv4-addr {
                  description 'PCP server IPv4 address.' ;
                  type ncd:ipv4-address ;

                }

              }

            }

            container ipv6-addresses {
              description 'PCP server IPv6 address.' ;
              list ipv6-address {
                description 'PCP server IPv6 address.' ;
                key ipv6-addr ;
                leaf ipv6-addr {
                  description 'PCP server IPv6 address.' ;
                  type ncd:ipv6-address ;

                }

              }

            }

          }

          ncd:revise-date 2017-03-09 ;
        }

      }

    }

  }

  container state {
    config false ;
    description 'State.' ;
    container dhcpv6 {
      description 'DHCPv6 state.' ;
      container client {
        description 'DHCPv6 client state.' ;
        container client-user {
          description 'DHCPv6 client user state.' ;
          list detail {
            description 'Show DHCPv6 client all user info detail.' ;
            key 'ifname ia-type iaid address prefix-len' ;
            leaf ifname {
              description 'Interface name.' ;
              type string {
                length 1..31 {
                  description 'Interface name.' ;
                }

              }

            }

            leaf ia-type {
              description 'The IA type.' ;
              type enumeration {
                enum IA_NA {
                  value 3 ;
                  description 'The IA type is IA NA.' ;
                }

                enum IA_TA {
                  value 4 ;
                  description 'The IA type is IA TA.' ;
                }

                enum IA_PD {
                  value 25 ;
                  description 'The IA type is IA PD.' ;
                }

              }

            }

            leaf iaid {
              description 'The unique identifier for this IA.' ;
              type uint32 ;

            }

            leaf address {
              description 'The IPv6 address that client obtain.' ;
              type ncd:ipv6-address {
                length 1..64 ;

              }

            }

            leaf prefix-len {
              description 'The length of DHCPv6 client prefix address.' ;
              type uint8 ;

            }

            leaf t1-time {
              description 'T1 is a time duration relative to the current time expressed in units of seconds.' ;
              type uint32 ;

              units second ;
            }

            leaf t2-time {
              description 'T2 is a time duration relative to the current time expressed in units of seconds.' ;
              type uint32 ;

              units second ;
            }

            leaf server-duid {
              description 'The DUID for the server.' ;
              type string {
                length 1..254 {
                  description 'The length of DUID.' ;
                }

              }

            }

            leaf state {
              description 'The client state.' ;
              type enumeration {
                enum Not-bound {
                  value 0 ;
                  description 'The state of DHCPv6 client is not bound.' ;
                }

                enum bound {
                  value 1 ;
                  description 'The state of DHCPv6 client is bound.' ;
                }

                enum renew {
                  value 2 ;
                  description 'The state of DHCPv6 client is renew.' ;
                }

                enum rebind {
                  value 3 ;
                  description 'The state of DHCPv6 client is rebind.' ;
                }

              }

            }

            leaf preferred-lifetime {
              description 'The preferred lifetime for the IPv6 address in the option, expressed in units of seconds.' ;
              type uint32 ;

              units second ;
            }

            leaf valid-lifetime {
              description 'The valid lifetime for the IPv6 address in the option, expressed in units of seconds.' ;
              type uint32 ;

              units second ;
            }

            leaf expiration {
              description 'The expiration time of DHCPv6 client.' ;
              type ncd:string-with-blank ;

            }

            ncd:select ifname ;
          }

        }

      }

      container relay {
        description 'DHCPv6 relay state.' ;
        container user-connect-statistics {
          if-feature relay-user_connect_statistic ;

          description 'DHCPv6 relay user connect statistics on the board.' ;
          list detail {
            description 'Show DHCPv6 relay user connect statistic detail.' ;
            key 'board-name start-time' ;
            leaf board-name {
              description 'Board name of the slot on which DHCPv6 relay user be.' ;
              type string {
                length 1..31 {
                  description 'The length of board name.' ;
                }

              }

            }

            leaf start-time {
              description 'Starting time of each piece of Statistics.' ;
              type ncd:string-with-blank ;

            }

            leaf end-time {
              description 'The end time of each piece of Statistics' ;
              type ncd:string-with-blank ;

            }

            leaf user-capacity {
              description 'DHCPv6 relay user capacity on the board.' ;
              type uint32 ;

            }

            leaf current-online {
              description 'DHCPv6 relay current-online bound-user from board start up to now .' ;
              type uint32 ;

              default 0 ;
            }

            leaf failed-times {
              description 'The failed-times of DHCPv6 relay users generated per 15 minutes on the board.' ;
              type uint32 ;

            }

            ncd:select board-name ;
          }

          ncd:revise-date 2019-08-01 ;
        }

        container relay-user {
          description 'DHCPv6 relay user state.' ;
          list detail {
            description 'Show DHCPv6 relay all user info detail.' ;
            key 'board-name client-duid ia-type ia-id address prefix-len' ;
            leaf board-name {
              description 'Board name of the slot on which DHCPv6 relay user be.' ;
              type string {
                length 1..31 {
                  description 'The length of board-name string.' ;
                }

              }

            }

            leaf client-duid {
              description 'DHCPv6 relay user DUID.' ;
              type string {
                length 1..254 {
                  description 'The length of DUID string.' ;
                }

              }

            }

            leaf ia-type {
              description 'The IA type.' ;
              type enumeration {
                enum IA_NA {
                  value 3 ;
                  description 'The IA type is type IA NA.' ;
                }

                enum IA_TA {
                  value 4 ;
                  description 'The IA type is type IA TA.' ;
                }

                enum IA_PD {
                  value 25 ;
                  description 'The IA type is type IA PD.' ;
                }

              }

            }

            leaf ia-id {
              description 'The unique identifier for this IA.' ;
              type uint32 ;

            }

            leaf address {
              description 'The IPv6 address which server assigned.' ;
              type ncd:ipv6-address {
                length 1..64 {
                  description 'The length of ipv6 address.' ;
                }

              }

            }

            leaf prefix-len {
              description 'The prefix length of the address or prefix which assigned by server.' ;
              type uint8 ;

            }

            leaf interface-name {
              description 'DHCPv6 relay user interface name.' ;
              type string {
                length 1..31 {
                  description 'The length of interface name.' ;
                }

              }

            }

            leaf t1-time {
              description 'T1 is a time duration relative to the current time expressed in units of seconds.' ;
              type uint32 ;

              units second ;
            }

            leaf t2-time {
              description 'T2 is a time duration relative to the current time expressed in units of seconds.' ;
              type uint32 ;

              units second ;
            }

            leaf preferred-lifetime {
              description 'The preferred lifetime for the IPv6 address in the option, expressed in units of seconds.' ;
              type uint32 ;

              units second ;
            }

            leaf valid-lifetime {
              description 'The valid lifetime for the IPv6 address in the option, expressed in units of seconds.' ;
              type uint32 ;

              units second ;
            }

            leaf expiration {
              description 'The expiration time of the address.' ;
              type ncd:string-with-blank {
                length 1..51 {
                  description 'The length of the expiration time of address.' ;
                }

              }

            }

            leaf vrf {
              description 'DHCPv6 relay user vrf-name.' ;
              type string ;

              ncd:revise-date 2016-01-14 ;
            }

            ncd:select interface-name ;
          }

          leaf summary {
            description 'The total count of DHCPv6 relay users.' ;
            type uint32 ;

          }

        }

      }

      container server {
        description 'DHCPv6 server state.' ;
        container server-user {
          description 'DHCPv6 server user state.' ;
          list detail {
            description 'Show DHCPv6 server all user info detail.' ;
            key 'board-name client-duid ia-type ia-id address prefix-len' ;
            leaf board-name {
              description 'Board name of the slot on which DHCPv6 server user be.' ;
              type string {
                length 1..31 {
                  description 'The length of board-name string.' ;
                }

              }

            }

            leaf client-duid {
              description 'DHCPv6 server user DUID.' ;
              type string {
                length 1..254 {
                  description 'The length of DUID string.' ;
                }

              }

            }

            leaf ia-type {
              description 'The IA type.' ;
              type enumeration {
                enum IA_NA {
                  value 3 ;
                  description 'The IA type is type IA NA.' ;
                }

                enum IA_TA {
                  value 4 ;
                  description 'The IA type is type IA TA.' ;
                }

                enum IA_PD {
                  value 25 ;
                  description 'The IA type is type IA PD.' ;
                }

              }

            }

            leaf ia-id {
              description 'The unique identifier for this IA.' ;
              type uint32 ;

            }

            leaf address {
              description 'The IPv6 address which server assigned.' ;
              type ncd:ipv6-address {
                length 1..64 {
                  description 'The length of ipv6 address.' ;
                }

              }

            }

            leaf prefix-len {
              description 'The prefix length of the address or prefix which assigned by server.' ;
              type uint8 ;

            }

            leaf interface-name {
              description 'DHCPv6 server user interface name.' ;
              type string {
                length 1..31 {
                  description 'The length of interface name.' ;
                }

              }

            }

            leaf t1-time {
              description 'T1 is a time duration relative to the current time expressed in units of seconds.' ;
              type uint32 ;

              units second ;
            }

            leaf t2-time {
              description 'T2 is a time duration relative to the current time expressed in units of seconds.' ;
              type uint32 ;

              units second ;
            }

            leaf preferred-lifetime {
              description 'The preferred lifetime for the IPv6 address in the option, expressed in units of seconds.' ;
              type uint32 ;

              units second ;
            }

            leaf valid-lifetime {
              description 'The valid lifetime for the IPv6 address in the option, expressed in units of seconds.' ;
              type uint32 ;

              units second ;
            }

            leaf expiration {
              description 'The expiration time of the address.' ;
              type ncd:string-with-blank {
                length 1..51 {
                  description 'The length of the expiration time of address.' ;
                }

              }

            }

            leaf vrf {
              description 'DHCPv6 server user vrf-name.' ;
              type string ;

              ncd:revise-date 2016-01-14 ;
            }

            ncd:select interface-name ;
          }

        }

        leaf summary {
          description 'DHCPv6 server user total count on this board.' ;
          type uint32 ;

        }

      }

    }

  }

  container operation {
    config false ;
    description 'operation.' ;
    container dhcpv6 {
      description 'DHCPv6 operation.' ;
      container relay-kick-user {
        description 'DHCPv6 relay kick off user.' ;
        choice type {
          description 'DHCPv6 relay kick off user type.' ;
          case all {
            description 'DHCPv6 relay kick off all user.' ;
            leaf all-user {
              description 'DHCPv6 relay kick off all user.' ;
              type enumeration {
                enum not-all {
                  value 0 ;
                  description 'kick off user type is not all.' ;
                }

                enum all {
                  value 1 ;
                  description 'kick off user type is all.' ;
                }

              }

              default not-all ;
            }

          }

          case address {
            description 'DHCPv6 relay kick off user by IPv6 address.' ;
            leaf user-addr {
              description 'DHCPv6 relay kick off user by IPV6 address.' ;
              type ncd:ipv6-address ;

              mandatory true ;
            }

            leaf vrf {
              description 'DHCPv6 relay kick off user by IPV6 address and VPN.' ;
              type string {
                length 1..32 {
                  description 'The length of VRF name.' ;
                }

              }

            }

          }

          case prefix {
            description 'DHCPv6 relay kick off user by IPV6 prefix.' ;
            leaf user-prefix {
              description 'DHCPv6 relay kick off user by IPV6 prefix.' ;
              type ncd:ipv6-address ;

              mandatory true ;
            }

            leaf prefix-len {
              description 'DHCPv6 relay kick off user by IPV6 prefix and prefix length.' ;
              type uint8 {
                range 1..128 {
                  description 'The range of prefix-len.' ;
                }

              }

              mandatory true ;
            }

            leaf vrf-name {
              description 'DHCPv6 relay kick off user by prefix and VPN.' ;
              type string {
                length 1..32 {
                  description 'The legth of VRF name.' ;
                }

              }

            }

          }

          case duid {
            description 'DHCPv6 relay kick off user by DUID.' ;
            leaf client-duid {
              description 'DHCPv6 client DUID.' ;
              type string {
                length 1..254 {
                  description 'The length of DUID string.' ;
                }

              }

            }

            ncd:revise-date 2021-03-19 ;
          }

          case mac {
            description 'DHCPv6 relay kick off user by MAC address.' ;
            leaf mac-addr {
              description 'Source MAC address from DHCPV6 packet.' ;
              type ncd:mac-address ;

            }

            ncd:revise-date 2021-03-19 ;
          }

          case interface {
            description 'DHCPv6 relay kick off user by interface.' ;
            leaf if-name {
              description 'DHCPv6 relay kick off user by interface.' ;
              type ncd:ifname {
                length 1..31 {
                  description 'The interface name length.' ;
                }

              }

            }

          }

        }

      }

      container server-kick-user {
        description 'DHCPv6 server kick off user.' ;
        choice type {
          description 'DHCPv6 server kick off user type.' ;
          case all {
            description 'DHCPv6 server kick off all user.' ;
            leaf all-user {
              description 'DHCPv6 server kick off all user.' ;
              type enumeration {
                enum not-all {
                  value 0 ;
                  description 'kick off user type is not all.' ;
                }

                enum all {
                  value 1 ;
                  description 'kick off user type is all.' ;
                }

              }

              default not-all ;
            }

          }

          case address {
            description 'DHCPv6 server kick off user by IPV6 address and VPN.' ;
            leaf user-addr {
              description 'DHCPv6 server kick off user by IPV6 address.' ;
              type ncd:ipv6-address ;

              mandatory true ;
            }

            leaf vrf {
              description 'DHCPv6 server kick off user by IPV6 address and VPN.' ;
              type string {
                length 1..32 {
                  description 'The length of VRF name.' ;
                }

              }

            }

          }

          case prefix {
            description 'DHCPv6 server kick off user by IPV6 prefix.' ;
            leaf user-prefix {
              description 'DHCPv6 server kick off user by IPV6 prefix.' ;
              type ncd:ipv6-address ;

              mandatory true ;
            }

            leaf prefix-len {
              description 'DHCPv6 server kick off user by IPV6 prefix and prefix length.' ;
              type uint8 {
                range 1..128 {
                  description 'The range of prefix-len.' ;
                }

              }

              mandatory true ;
            }

            leaf vrf-name {
              description 'DHCPv6 server kick off user by prefix and VPN.' ;
              type string {
                length 1..32 {
                  description 'The legth of VRF name.' ;
                }

              }

            }

          }

          case interface {
            description 'DHCPv6 server kick off user by interface.' ;
            leaf if-name {
              description 'DHCPv6 server kick off user by interface.' ;
              type ncd:ifname {
                length 1..31 {
                  description 'The interface name length.' ;
                }

              }

            }

          }

          case duid {
            description 'DHCPv6 server kick off user by DUID.' ;
            leaf client-duid {
              description 'DHCPv6 client DUID.' ;
              type string {
                length 1..254 {
                  description 'The length of DUID string.' ;
                }

              }

            }

            ncd:revise-date 2021-03-19 ;
          }

          case mac {
            description 'DHCPv6 server kick off user by MAC address.' ;
            leaf mac-addr {
              description 'Source MAC address from DHCPV6 packet.' ;
              type ncd:mac-address ;

            }

            ncd:revise-date 2021-03-19 ;
          }

        }

      }

    }

  }

}
