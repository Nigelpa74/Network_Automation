module zxr10-flexe-channel {
  namespace 'http://www.zte.com.cn/zxr10/netconf/schema/rosng/flexe-channel' ;
  prefix flexe-channel ;
  import zxr10-netconf-defs {
    prefix ncd ;
    revision-date 2013-11-22 ;
  }
  organization 'ZTE Corporation' ;
  contact "ZTE Corporation  
\n"
        + "   Nanjing Institute of ZTE Corporation 
\n"
        + "   No.68 Zijinghua Rd. Yuhuatai District, Nanjing, China 
\n"
        + '   Tel: +86-25-52870000'
          ;
  description 'The netconf module to describe the flexE channel relationships '
            + 'between flexE channel interface and Ethernet interface.'
              ;
  revision 2022-03-06 {
    description 'The initial version' ;
  }
  container configuration {
    description 'Configure the binding relation between interfaces.' ;
    container flexe-channel {
      description 'Describe the parameters of the flexE channel relationships to be '
                + 'configured'
                  ;
      container flexe-channel-bind {
        description 'Describe the parameters of the flexE channel relationships to b'
                  + 'e configured'
                    ;
        list interface {
          description 'The list of interfaces for configuring parameters' ;
          key interface-name ;
          leaf interface-name {
            description 'Interface name' ;
            type ncd:ifname ;
          }
          leaf bind-flexe-channel-interface {
            description 'Binded flexe_channel interface name' ;
            type ncd:ifname ;
            mandatory true ;
          }
        }
      }
    }
  }
}
