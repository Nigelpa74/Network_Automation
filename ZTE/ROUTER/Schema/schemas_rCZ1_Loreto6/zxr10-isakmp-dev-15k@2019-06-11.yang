module zxr10-isakmp-dev-15k {
  namespace 'http://www.zte.com.cn/zxr10/netconf/schema/rosng/isakmp-dev-15k'
            ;
  prefix isakmp-dev-15k ;
  yang-version 1 ;
  import zxr10-isakmp {
    prefix isakmp ;
    revision-date 2016-07-12 ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  revision 2019-06-11 {
    description 'del /isakmp:configuration/isakmp:isakmp/isakmp:isakmp-profiles'
              + '/isakmp:isakmp-profile/isakmp:self-identity/isakmp:self-identi'
              + 'ty/isakmp:fqdn'
                ;
  }
  revision 2017-07-03 {
    description '1. del /isakmp:configuration/isakmp:isakmp/isakmp:isakmp-polic'
              + 'ys/isakmp:isakmp-policy/isakmp:encryption'+"\n"
              + ''+"\n"
              + 'Enum Item:sm4'+"\n"
              + ''+"\n"
              + '2. add /isakmp:configuration/isakmp:isakmp/isakmp:isakmp-polic'
              + 'ys/isakmp:isakmp-policy/isakmp:hash'+"\n"
              + ''+"\n"
              + 'replacement'
                ;
  }
  revision 2016-12-06 ;
  deviation '/isakmp:configuration/isakmp:isakmp/isakmp:isakmp-policys/isakmp:i'
          + 'sakmp-policy/isakmp:authentication'
            {
    description 'Set authentication method for protection suite'
                ;
    deviate replace {
      type enumeration {
        enum pre-share {
          value 0 ;
          description 'Pre-Shared key'
                      ;
        }
        enum rsa-sig {
          value 1 ;
          description 'RSA signature'
                      ;
        }
      }
    }
  }
  deviation '/isakmp:configuration/isakmp:isakmp/isakmp:isakmp-policys/isakmp:i'
          + 'sakmp-policy/isakmp:encryption'
            {
    description 'Set encryption algorithm for protection suite'
                ;
    deviate replace {
      type enumeration {
        enum aes-128 {
          value 0 ;
          description 'AES - Advanced Encryption Standard(128 bit keys)'
                      ;
        }
        enum aes-192 {
          value 1 ;
          description 'AES - Advanced Encryption Standard(192 bit keys)'
                      ;
        }
        enum aes-256 {
          value 2 ;
          description 'AES - Advanced Encryption Standard(256 bit keys)'
                      ;
        }
        enum des {
          value 3 ;
          description 'DES - Data Encryption Standard (56 bit keys)'
                      ;
        }
        enum 3des {
          value 4 ;
          description 'Three key triple DES'
                      ;
        }
        enum sm4 {
          value 5 ;
          description 'SM4 - cryptographic algorithm(128 bit keys)'
                      ;
          status obsolete ;
        }
      }
    }
  }
  deviation '/isakmp:configuration/isakmp:isakmp/isakmp:isakmp-policys/isakmp:i'
          + 'sakmp-policy/isakmp:hash'
            {
    deviate replace {
      type enumeration {
        enum md5 {
          value 0 ;
          description 'Message Digest 5'
                      ;
        }
        enum sha1 {
          value 1 ;
          description 'Secure Hash Standard'
                      ;
        }
        enum sha256 {
          value 3 ;
          description 'Secure Hash Standard 256'
                      ;
        }
        enum sha384 {
          value 4 ;
          description 'Secure Hash Standard 384'
                      ;
        }
        enum sha512 {
          value 5 ;
          description 'Secure Hash Standard 512'
                      ;
        }
      }
    }
  }
}
