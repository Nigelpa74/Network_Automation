module zxr10-urpf {
  namespace "http://www.zte.com.cn/zxr10/netconf/schema/rosng/urpf" ;
  prefix urpf ;
  yang-version 1 ;
  import zxr10-netconf-defs {
    prefix ncd ;
  }

  organization "ZTE Corporation" ;
  contact "ZTE Corporation
  Nanjing Institute of ZTE Corporation
  No.68 Zijinghua Rd. Yuhuatai District, Nanjing, China
  Tel: +86-25-52870000" ;
  description 'The netconf module to describe URPF(Unicast Reverse Path Forwarding)' ;
  revision 2025-01-20 {
    description 'This modification is only for polishing the description.' ;
  }

  revision 2019-09-07 {
    description 'Support ignore-multipath-default-route node.
1 configuration/urpf/ipv4/ipv4-urpf/mode/strict/ignore-multipath-default-route;
2 configuration/urpf/ipv6/ipv6-urpf/mode/strict/ignore-multipath-default-route.' ;
  }

  revision 2017-12-11 {
    description 'Change optional urpf-id nodes into mandatory.
1 configuration/urpf/ipv4/ipv4-urpf/mode/neighbour/neighbour/urpf-id;
2 configuration/urpf/ipv6/ipv6-urpf/mode/neighbour/neighbour/urpf-id.' ;
  }

  revision 2017-11-06 {
    description 'Support neighbour mode.
1 configuration/urpf/ipv4/ipv4-urpf/mode/neighbour;
2 configuration/urpf/ipv6/ipv6-urpf/mode/neighbour.' ;
  }

  revision 2017-07-01 {
    description '1.Support to configure URPF based on IP, add new nodes as followed,
feature: ip-urpf
containers:
/configuration/urpf/ip-urpfs.' ;
  }

  revision 2014-03-18 {
    description 'Initial version' ;
  }

  feature ipv4-urpf {
    description 'Support to configure IPv4 Type URPF' ;
  }

  feature ipv6-urpf {
    description 'Support to configure IPv6 Type URPF' ;
  }

  feature ipv4-urpf-acl {
    description 'Support ACL option for IPv4 type URPF' ;
  }

  feature ip-urpf {
    description 'Support to configure IP Type URPF.' ;
  }

  container configuration {
    description 'Configuration model.' ;
    container urpf {
      description 'Configuration related to URPF.' ;
      container ipv4 {
        if-feature ipv4-urpf ;

        description 'IPv4 URPF.' ;
        list ipv4-urpf {
          description 'IPv4 URPF instance.' ;
          key interface ;
          leaf interface {
            description 'Specify the interface name.' ;
            type ncd:ifname ;

          }

          choice mode {
            description 'Select URPF mode.' ;
            mandatory true ;
            case strict {
              description 'Strict mode.' ;
              leaf rx {
                description 'Strict mode.' ;
                type empty ;

              }

              leaf ignore-multipath-def-route {
                description 'Ignore the default multi-path route.' ;
                type empty ;

                ncd:revise-date 2019-09-07 ;
              }

            }

            case loose {
              description 'Loose mode.' ;
              leaf any {
                description 'Loose mode.' ;
                type empty ;

                mandatory true ;
              }

              leaf ignore-def-route {
                description 'Ignore the default route.' ;
                type empty ;

              }

            }

            case neighbour {
              description 'Neighbour mode.' ;
              container neighbour {
                description 'Neighbour mode.' ;
                leaf neighbour {
                  description 'Neighbour mode.' ;
                  type empty ;

                  mandatory true ;
                }

                leaf urpf-id {
                  description 'Specify URPF ID.' ;
                  type uint32 {
                    range 1..65534 ;

                  }

                  mandatory true ;
                }

              }

              ncd:revise-date 2017-11-06 ;
            }

          }

          leaf acl-name {
            if-feature ipv4-urpf-acl ;

            description 'Specify the ACL name.' ;
            type string {
              length 1..31 ;

            }

          }

        }

      }

      container ipv6 {
        if-feature ipv6-urpf ;

        description 'IPv6 URPF.' ;
        list ipv6-urpf {
          description 'IPv6 URPF instance.' ;
          key interface ;
          leaf interface {
            description 'Specify the interface name.' ;
            type ncd:ifname ;

          }

          choice mode {
            description 'Select URPF mode.' ;
            mandatory true ;
            case strict {
              description 'Strict mode.' ;
              leaf rx {
                description 'Strict mode.' ;
                type empty ;

              }

              leaf ignore-multipath-def-route {
                description 'Ignore the default multi-path route.' ;
                type empty ;

                ncd:revise-date 2019-09-07 ;
              }

            }

            case loose {
              description 'Loose mode.' ;
              leaf any {
                description 'Loose mode.' ;
                type empty ;

                mandatory true ;
              }

              leaf ignore-def-route {
                description 'Ignore the default route.' ;
                type empty ;

              }

            }

            case neighbour {
              description 'Neighbour mode.' ;
              container neighbour {
                description 'Neighbour mode.' ;
                leaf neighbour {
                  description 'Neighbour mode.' ;
                  type empty ;

                  mandatory true ;
                }

                leaf urpf-id {
                  description 'Specify URPF ID.' ;
                  type uint32 {
                    range 1..65534 ;

                  }

                  mandatory true ;
                }

              }

              ncd:revise-date 2017-11-06 ;
            }

          }

          leaf acl-name {
            description 'Specify the ACL name.' ;
            type string {
              length 1..31 ;

            }

          }

        }

      }

      container ip-urpfs {
        if-feature ip-urpf ;

        description 'IP URPF.' ;
        list ip-urpf {
          description 'IP URPF instance.' ;
          key interface ;
          leaf interface {
            description 'Specify the interface name.' ;
            type ncd:ifname {
              length 1..31 {
                description 'Interface name, support 1-31 characters.' ;
              }

            }

          }

          container modes {
            description 'Select URPF mode.' ;
            choice mode {
              description 'Select URPF mode.' ;
              mandatory true ;
              case strict {
                description 'Strict mode.' ;
                leaf rx {
                  description 'Strict mode.' ;
                  type empty ;

                  mandatory true ;
                }

              }

              case loose {
                description 'Loose mode.' ;
                container loose {
                  description 'Loose mode.' ;
                  leaf any {
                    description 'Loose mode.' ;
                    type empty ;

                    mandatory true ;
                  }

                  leaf ignore-def-route {
                    description 'Ignore the default route.' ;
                    type empty ;

                  }

                }

              }

            }

          }

        }

        ncd:revise-date 2017-07-01 ;
      }

    }

  }

}
