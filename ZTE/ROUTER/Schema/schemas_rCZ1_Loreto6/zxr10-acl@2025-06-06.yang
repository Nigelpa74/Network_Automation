module zxr10-acl {
  namespace "http://www.zte.com.cn/zxr10/netconf/schema/rosng/acl" ;
  prefix acl ;
  yang-version 1 ;
  import zxr10-netconf-defs {
    prefix ncd ;
  }

  organization "ZTE Corporation" ;
  contact "ZTE Corporation
  Nanjing Institute of ZTE Corporation
  No.68 Zijinghua Rd. Yuhuatai District, Nanjing, China
  Tel: +86-25-52870000" ;
  description 'The netconf module to describe access-list(ACL).' ;
  revision 2025-06-06 {
    description '1. Add the ROSNG-V.VEG product label to the following feature: vxlan-acl-tcp-flag, ip-flags-config.' ;
  }

  revision 2024-12-10 {
    description 'In order to support configuring VRF and label in IPv4 mixed ACL and IPv6 mixed ACL, new nodes are added as follows:
1./configuration/acl/access-list/ipv4-mixed-access-list/rule/vrf;
2./configuration/acl/access-list/ipv6-mixed-access-list/rule/label;
3./configuration/acl/access-list/ipv6-mixed-access-list/rule/label2;
4./configuration/acl/access-list/ipv6-mixed-access-list/rule/vrf.' ;
  }

  revision 2024-11-25 {
    description 'This modification is only for polishing the description.' ;
  }

  revision 2024-08-13 {
    description 'In order to describing link access list and port pool, new nodes are added as follows:
1./configuration/acl/access-list/link-access-list/acl-description;
2./configuration/acl/port-pools/port-pool/port-pool-description.' ;
  }

  revision 2024-06-01 {
    description 'To support TCP flags in VXLAN ACL, add rst, ack, fin, syn, psh, urg leaf nodes the following nodes:
1./configuration/acl/access-list/ipv4-vxlan-access-lists/ipv4-vxlan-access-list/rules/rule/inner-layer/tcp-udp
2./configuration/acl/access-list/ipv4-vxlan-access-lists/ipv4-vxlan-access-list/rules-transit-inner/rule-transit-inner/inner-layer/tcp-udp
3./configuration/acl/access-list/ipv4-vxlan-access-lists/ipv4-vxlan-access-list/rules-vtep-inner/rule-vtep-inner/inner-layer/tcp-udp
4./configuration/acl/access-list/ipv6-vxlan-access-lists/ipv6-vxlan-access-list/rules-transit-inner/rule-transit-inner/inner-layer/tcp-udp
5./configuration/acl/access-list/ipv6-vxlan-access-lists/ipv6-vxlan-access-list/rules-vtep-inner/rule-vtep-inner/inner-layer/tcp-udp' ;
  }

  revision 2024-05-07 {
    description 'Delete project label 15K and T8000 from feature port-pool and prefix-list.' ;
  }

  revision 2024-03-22 {
    description 'To support IP flags in IPv4 VXLAN ACL, add nodes:
1./configuration/acl/access-list/ipv4-vxlan-access-lists/ipv4-vxlan-access-list/rules/rule/inner-layer/ip-flags
2./configuration/acl/access-list/ipv4-vxlan-access-lists/ipv4-vxlan-access-list/rules-transit-inner/rule-transit-inner/inner-layer/ip-flags
3./configuration/acl/access-list/ipv4-vxlan-access-lists/ipv4-vxlan-access-list/rules-vtep-inner/rule-vtep-inner/inner-layer/ip-flags' ;
  }

  revision 2024-02-27 {
    description 'To support SCTP port, add nodes:
1./configuration/acl/access-list/ipv4-mixed-access-list/rule/extended/port
2./configuration/acl/access-list/ipv6-mixed-access-list/rule/port' ;
  }

  revision 2024-01-16 {
    description 'In order to support ACL interface application, add container:
/configuration/acl/interface-applications' ;
  }

  revision 2024-01-04 {
    description 'Add enums of vxlan ACL mode type:
/configuration/acl/access-list/ipv4-vxlan-access-lists/ipv4-vxlan-access-list/mode-type
/configuration/acl/access-list/ipv6-vxlan-access-lists/ipv6-vxlan-access-list/mode-type' ;
  }

  revision 2023-12-12 {
    description '1. To support configuring port pools, add nodes:
/configuration/acl/port-pools;
2. To support matching port pools in IPv4 and IPv6 ACL, add nodes:
/configuration/acl/access-list/ipv4-access-list/rule/rule-type/extend/extended/ipv4-protocol-type/udp-tcp/udp-tcp/source-port/source-port/src-port-pool,
/configuration/acl/access-list/ipv4-access-list/rule/rule-type/extend/extended/ipv4-protocol-type/udp-tcp/udp-tcp/destination-port/destination-port/dst-port-pool,
/configuration/acl/access-list/ipv4-access-list/rule/rule-type/extend/extended/ipv4-protocol-type/icmp/icmp-port/source-port/source-port/src-port-pool,
/configuration/acl/access-list/ipv4-access-list/rule/rule-type/extend/extended/ipv4-protocol-type/icmp/icmp-port/destination-port/destination-port/dst-port-pool,
/configuration/acl/access-list/ipv4-access-list/rule/rule-type/extend/extended/ipv4-protocol-type/ip/port/source-port/source-port/src-port-pool,
/configuration/acl/access-list/ipv4-access-list/rule/rule-type/extend/extended/ipv4-protocol-type/ip/port/destination-port/destination-port/dst-port-pool,
/configuration/acl/access-list/ipv6-access-list/rule/rule-type/udp-tcp/udp-tcp/source-port/source-port/src-port-pool,
/configuration/acl/access-list/ipv6-access-list/rule/rule-type/udp-tcp/udp-tcp/destination-port/destination-port/dst-port-pool,
/configuration/acl/access-list/ipv6-access-list/rule/rule-type/icmp/icmp-port/source-port/source-port/src-port-pool,
/configuration/acl/access-list/ipv6-access-list/rule/rule-type/icmp/icmp-port/destination-port/destination-port/dst-port-pool,
/configuration/acl/access-list/ipv6-access-list/rule/rule-type/ip/port/source-port/source-port/src-port-pool,
/configuration/acl/access-list/ipv6-access-list/rule/rule-type/ip/port/destination-port/destination-port/dst-port-pool;
3. To support matching prefix list in IPv4 and IPv6 ACL, add nodes:
/configuration/acl/access-list/ipv4-access-list/rule/src-addr/src-prefix-list,
/configuration/acl/access-list/ipv4-access-list/rule/rule-type/extend/extended/dest-addr/dest-prefix-list,
/configuration/acl/access-list/ipv6-access-list/rule/src-addr/src-prefix-list,
/configuration/acl/access-list/ipv6-access-list/rule/dest-addr/dest-prefix-list.' ;
  }

  revision 2023-10-07 {
    description 'In order to support statistics for IPv4 and IPv6 VXLAN ACL in outer layer, some nodes are added as follows:
1./configuration/acl/access-list/ipv4-vxlan-access-lists/ipv4-vxlan-access-list/rules-transit-outer/rule-transit-outer/log
2./configuration/acl/access-list/ipv4-vxlan-access-lists/ipv4-vxlan-access-list/rules-vtep-outer/rule-vtep-outer/log
3./configuration/acl/access-list/ipv6-vxlan-access-lists/ipv6-vxlan-access-list/rules-transit-outer/rule-transit-outer/log
4./configuration/acl/access-list/ipv6-vxlan-access-lists/ipv6-vxlan-access-list/rules-vtep-outer/rule-vtep-outer/log' ;
  }

  revision 2022-01-27 {
    description '1. Add log in user defined template ACL:
/configuration/acl/access-list/user-defined-template-acls/user-defined-template-acl/rules/rule/log
2. Support user defined template ACL statistics switch:
/configuration/acl/statistics-switch/user-defined-template-log-switches;
3. Support user defined template ACL statistics clear:
/operation/acl/user-defined-template-log-clears;
4. Add general user defined template:
/configuration/acl/templates/udf-template-generals.' ;
  }

  revision 2022-01-20 {
    description 'In order to support statistics for IPv4 and IPv6 VXLAN ACL, some nodes are added as follows:
1./configuration/acl/access-list/ipv4-vxlan-access-lists/ipv4-vxlan-access-list/rules/rule/log
2./configuration/acl/access-list/ipv4-vxlan-access-lists/ipv4-vxlan-access-list/rules-transit-inner/rule-transit-inner/log
3./configuration/acl/access-list/ipv4-vxlan-access-lists/ipv4-vxlan-access-list/rules-vtep-inner/rule-vtep-inner/log
4./configuration/acl/access-list/ipv6-vxlan-access-lists/ipv6-vxlan-access-list/rules-transit-inner/rule-transit-inner/log
5./configuration/acl/access-list/ipv6-vxlan-access-lists/ipv6-vxlan-access-list/rules-vtep-inner/rule-vtep-inner/log
6./configuration/acl/statistics-switch/ipv4-vxlan-log-switches-by-acl
7./configuration/acl/statistics-switch/ipv6-vxlan-log-switches-by-acl
8./operation/acl/ipv4-vxlan-log-clears-by-acl
9./operation/acl/ipv6-vxlan-log-clears-by-acl
10./state/acl/acl-v4-vxlan-statistics-by-acl
11./state/acl/acl-v6-vxlan-statistics-by-acl' ;
  }

  revision 2021-11-23 {
    description 'To support default action configuration in empty ACL, some leaf nodes are added as follows:
1./configuration/acl/port-acl/if-ipv4/egress/none-rule-default-action;
2./configuration/acl/port-acl/if-ipv4/ingress/none-rule-default-action;
3./configuration/acl/port-acl/if-ipv6/egress/none-rule-default-action;
4./configuration/acl/port-acl/if-ipv6/ingress/none-rule-default-action;
5./configuration/acl/port-acl/if-link/egress/none-rule-default-action;
6./configuration/acl/port-acl/if-link/ingress/none-rule-default-action.' ;
  }

  revision 2021-11-02 {
    description 'To support clear ACL statistics in all interface, some list nodes are changed to choice-case nodes, and some container nodes are added in choice nodes.
1./operation/acl/ipv4-log-clears;
2./operation/acl/ipv6-log-clears;
3./operation/acl/link-log-clears;
4./operation/acl/ipv4-mixed-log-clears;' ;
  }

  revision 2021-10-26 {
    description 'In order to support vxlan link ACL, some nodes are added as follows:
1. /configuration/acl/access-list/ipv4-vxlan-access-lists/ipv4-vxlan-access-list/rules-transit-inner/rule-transit-inner/l2-layer;
2. /configuration/acl/access-list/ipv4-vxlan-access-lists/ipv4-vxlan-access-list/rules-vtep-inner/rule-vtep-inner/l2-layer;
3. /configuration/acl/access-list/ipv6-vxlan-access-lists/ipv6-vxlan-access-list/rules-transit-inner/rule-transit-inner/l2-layer;
4. /configuration/acl/access-list/ipv6-vxlan-access-lists/ipv6-vxlan-access-list/rules-vtep-inner/rule-vtep-inner/l2-layer;' ;
  }

  revision 2021-10-20 {
    description 'Add some nodes to support obtaining statistics by ACL:
1./configuration/acl/statistics-switch/ipv4-log-switchs-by-acl
2./configuration/acl/statistics-switch/ipv6-log-switchs-by-acl
3./configuration/acl/statistics-switch/link-log-switchs-by-acl
4./configuration/acl/statistics-switch/ipv4-mixed-log-switchs-by-acl
5./configuration/acl/statistics-switch/ipv6-mixed-log-switchs-by-acl
6./operation/acl/ipv4-log-clears-by-acl
7./operation/acl/ipv6-log-clears-by-acl
8./operation/acl/link-log-clears-by-acl
9./operation/acl/ipv4-mixed-log-clears-by-acl
10./operation/acl/ipv6-mixed-log-clears-by-acl
11./state/acl/acl-v4-statistics-by-acl
12./state/acl/acl-v6-statistics-by-acl
13./state/acl/acl-link-statistics-by-acl
14./state/acl/acl-v4-mixed-statistics-by-acl
15./state/acl/acl-v6-mixed-statistics-by-acl' ;
  }

  revision 2021-08-09 {
    description 'IPv6 wildcard leaf nodes are changed to choice-case nodes, and wildcard-bits case nodes are added in wildcard choice nodes:
1./acl:configuration/acl:acl/acl:access-list/acl:ipv6-access-list/acl:rule/acl:src-wildcard-type;
2./acl:configuration/acl:acl/acl:access-list/acl:ipv6-access-list/acl:rule/acl:dest-wildcard-type;
3./acl:configuration/acl:acl/acl:access-list/acl:ipv6-mixed-access-list/acl:rule/acl:src-wildcard-type;
4./acl:configuration/acl:acl/acl:access-list/acl:ipv6-mixed-access-list/acl:rule/acl:dest-wildcard-type.' ;
  }

  revision 2021-08-04 {
    description 'Add EXP node in IPv6 ACL:
/configuration/acl/access-list/ipv6-mixed-access-list/rule/exp.' ;
  }

  revision 2021-06-03 {
    description 'In order to support statistics for IPv6 mixed ACL, some nodes are added as follows:
1.Add new feature: ipv6-mixed-log-config
2./configuration/acl/access-list/ipv6-mixed-access-list/rule/log
3./configuration/acl/statistics-switch/ipv6-mixed-log-switchs
4./operation/acl/ipv6-mixed-log-clears
5./state/acl/acl-v6-mixed-statistics' ;
  }

  revision 2021-04-02 {
    description '1.Add time-range nodes in IPv4 vxlan rule as follows:
/configuration/acl/access-list/ipv4-vxlan-access-lists/ipv4-vxlan-access-list/rules/rule/time-range;
/configuration/acl/access-list/ipv4-vxlan-access-lists/ipv4-vxlan-access-list/rules-transit-inner/rule-transit-inner/time-range;
/configuration/acl/access-list/ipv4-vxlan-access-lists/ipv4-vxlan-access-list/rules-transit-outer/rule-transit-outer/time-range;
/configuration/acl/access-list/ipv4-vxlan-access-lists/ipv4-vxlan-access-list/rules-vtep-inner/rule-vtep-inner/time-range;
/configuration/acl/access-list/ipv4-vxlan-access-lists/ipv4-vxlan-access-list/rules-vtep-outer/rule-vtep-outer/time-range.
2.Add time-range nodes in IPv6 vxlan rule as follows:
/configuration/acl/access-list/ipv6-vxlan-access-lists/ipv6-vxlan-access-list/rules-transit-inner/rule-transit-inner/time-range;
/configuration/acl/access-list/ipv6-vxlan-access-lists/ipv6-vxlan-access-list/rules-transit-outer/rule-transit-outer/time-range;
/configuration/acl/access-list/ipv6-vxlan-access-lists/ipv6-vxlan-access-list/rules-vtep-inner/rule-vtep-inner/time-range;
/configuration/acl/access-list/ipv6-vxlan-access-lists/ipv6-vxlan-access-list/rules-vtep-outer/rule-vtep-outer/time-range.' ;
  }

  revision 2020-08-21 {
    description '1 Add dscp-range with if-feature ipv6-dscp-range-config in IPv6 and IPv6 mixed rule:
/configuration/acl/access-list/ipv6-access-list/rule/dscp-range,
/configuration/acl/access-list/ipv6-mixed-access-list/rule/dscp-range.
2 Add cos-range with if-feature ipv6-cos-range-config in IPv6 mixed rule:
/configuration/acl/access-list/ipv6-mixed-access-list/rule/inner-cos-range,
/configuration/acl/access-list/ipv6-mixed-access-list/rule/outer-cos-range.' ;
  }

  revision 2020-08-17 {
    description 'Some vrf leaf nodes are changed to vrf choice-case nodes, and vrf-dcn case nodes are added in vrf choice nodes:
1./acl:configuration/acl:acl/acl:access-list/acl:ipv4-access-list/acl:rule/acl:vrf-config;
2./acl:configuration/acl:acl/acl:access-list/acl:ipv6-access-list/acl:rule/acl:vrf-config.' ;
  }

  revision 2020-07-13 {
    description '1. Add policy-route-id in IPv4 mixed ACL:
/acl:configuration/acl:acl/acl:access-list/acl:ipv4-mixed-access-list/acl:rule/acl:policy-route-id.
2. Add monitor-group-id in IPv4 mixed ACL:
/acl:configuration/acl:acl/acl:access-list/acl:ipv4-mixed-access-list/acl:rule/acl:extended/acl:source-monitor-group-id;
/acl:configuration/acl:acl/acl:access-list/acl:ipv4-mixed-access-list/acl:rule/acl:extended/acl:destination-monitor-group-id.' ;
  }

  revision 2020-06-29 {
    description 'In order to describing access list and port ACL, new nodes are added as follows:
1./acl:configuration/acl:acl/acl:access-list/acl:ipv6-mixed-access-list/acl:acl-description;
2./acl:configuration/acl:acl/acl:port-acl/acl:vlan-ipv4/acl:egress/acl:port-acl-description;
3./acl:configuration/acl:acl/acl:port-acl/acl:vlan-ipv4/acl:ingress/acl:port-acl-description;
4./acl:configuration/acl:acl/acl:port-acl/acl:vlan-ipv4-mixed/acl:egress/acl:port-acl-description;
5./acl:configuration/acl:acl/acl:port-acl/acl:vlan-ipv4-mixed/acl:ingress/acl:port-acl-description;
6./acl:configuration/acl:acl/acl:port-acl/acl:vlan-ipv6/acl:egress/acl:port-acl-description;
7./acl:configuration/acl:acl/acl:port-acl/acl:vlan-ipv6/acl:ingress/acl:port-acl-description;
8./acl:configuration/acl:acl/acl:port-acl/acl:if-ipv6-mixed/acl:egress/acl:port-acl-description;
9./acl:configuration/acl:acl/acl:port-acl/acl:if-ipv6-mixed/acl:ingress/acl:port-acl-description;
10./acl:configuration/acl:acl/acl:port-acl/acl:vlan-ipv6-mixed/acl:egress/acl:port-acl-description;
11./acl:configuration/acl:acl/acl:port-acl/acl:vlan-ipv6-mixed/acl:ingress/acl:port-acl-description.' ;
  }

  revision 2020-06-18 {
    description 'In order to describing access list and port ACL, new nodes are added as follows:
1./acl:configuration/acl:acl/acl:access-list/acl:ipv4-access-list/acl:acl-description;
2./acl:configuration/acl:acl/acl:access-list/acl:ipv4-mixed-access-list/acl:acl-description;
3./acl:configuration/acl:acl/acl:access-list/acl:ipv6-access-list/acl:acl-description;
4./acl:configuration/acl:acl/acl:port-acl/acl:if-ipv4/acl:egress/acl:port-acl-description;
5./acl:configuration/acl:acl/acl:port-acl/acl:if-ipv4/acl:ingress/acl:port-acl-description;
6./acl:configuration/acl:acl/acl:port-acl/acl:if-ipv4-mixed/acl:egress/acl:port-acl-description;
7./acl:configuration/acl:acl/acl:port-acl/acl:if-ipv4-mixed/acl:ingress/acl:port-acl-description;
8./acl:configuration/acl:acl/acl:port-acl/acl:if-ipv6/acl:egress/acl:port-acl-description;
9./acl:configuration/acl:acl/acl:port-acl/acl:if-ipv6/acl:ingress/acl:port-acl-description.' ;
  }

  revision 2020-03-23 {
    description 'Add time-to-live to ipv6-access-lists:
configuration/acl/access-list/ipv6-access-list/rule/time-to-live.' ;
  }

  revision 2020-03-18 {
    description 'In order to support IPv6 Vxlan ACL, some nodes are added as follows:
1./acl:configuration/acl:acl/acl:access-list/acl:ipv6-vxlan-access-lists;
2./acl:configuration/acl:acl/acl:port-acl/acl:if-ipv6-vxlan;
3./acl:configuration/acl:acl/acl:port-acl/acl:vlan-ipv6-vxlan;
4./acl:configuration/acl:acl/acl:port-acl/acl:device-ipv6-vxlans;' ;
  }

  revision 2020-03-05 {
    description 'The product T8000 begins to support the Feature [pri-range-config], but does not support the Feature [pri-value-config] any more.' ;
  }

  revision 2020-01-20 {
    description 'In order to support binding ACL to specified slots, some nodes are added as follows:
1./acl:configuration/acl:acl/acl:port-acl/acl:slot-ipv4s;
2./acl:configuration/acl:acl/acl:port-acl/acl:slot-ipv6s.' ;
  }

  revision 2019-12-11 {
    description 'Add source-monitor-group-id in IPv4 ACL and IPv6 ACL:
1./acl:configuration/acl:acl/acl:access-list/acl:ipv4-access-list/acl:rule/acl:extended/acl:source-monitor-group-id;
2./acl:configuration/acl:acl/acl:access-list/acl:ipv6-access-list/acl:rule/acl:source-monitor-group-id.' ;
  }

  revision 2019-12-06 {
    description '1.Support rule description to IPv4 mixed/IPv6 mixed ACL, new nodes added as follows:
/configuration/acl/access-list/ipv4-mixed-access-list/rule/v4mix-desc
/configuration/acl/access-list/ipv6-mixed-access-list/rule/v6mix-desc;
2. In order to support configuring mixed ACL rule description separately, some mandatory leaf nodes are adjusted  to be optional nodes, modification in detail as follows:
/configuration/acl/access-list/ipv4-mixed-access-list/rule/permit-deny
/configuration/acl/access-list/ipv4-mixed-access-list/rule/src-addr
/configuration/acl/access-list/ipv4-mixed-access-list/rule/rule-type
/configuration/acl/access-list/ipv4-mixed-access-list/rule/src-mac-addr
/configuration/acl/access-list/ipv4-mixed-access-list/rule/dest-mac-addr
/configuration/acl/access-list/ipv6-mixed-access-list/rule/permit-deny
/configuration/acl/access-list/ipv6-mixed-access-list/rule/src-addr
/configuration/acl/access-list/ipv6-mixed-access-list/rule/dst-addr
/configuration/acl/access-list/ipv6-mixed-access-list/rule/rule-type
/configuration/acl/access-list/ipv6-mixed-access-list/rule/src-mac-addr
/configuration/acl/access-list/ipv6-mixed-access-list/rule/dest-mac-addr.' ;
  }

  revision 2019-11-26 {
    description 'Add monitor-group-id in IPv4 ACL and IPv6 ACL:
1./acl:configuration/acl:acl/acl:access-list/acl:ipv4-access-list/acl:rule/acl:extended/acl:monitor-group-id;
2./acl:configuration/acl:acl/acl:access-list/acl:ipv6-access-list/acl:rule/acl:monitor-group-id.' ;
  }

  revision 2019-10-08 {
    description 'Add some nodes to support configuring IPv4 mixed ACL and obtaining its statistics for 15K product. The modifications in detail are as follows:
1.Add new feature: ipv4-mixed-log-config
2./configuration/acl/access-list/ipv4-mixed-access-list/rule/exp
3./configuration/acl/access-list/ipv4-mixed-access-list/rule/label
4./configuration/acl/access-list/ipv4-mixed-access-list/rule/label2
5./configuration/acl/access-list/ipv4-mixed-access-list/rule/log
6./configuration/acl/statistics-switch/link-log-switchs
7./configuration/acl/statistics-switch/ipv4-mixed-log-switchs
8./operation/acl/ipv4-mixed-log-clears
9./state/acl/acl-link-statistics
10./state/acl/acl-v4-mixed-statistics' ;
  }

  revision 2019-09-10 {
    description 'Add policy-route-id in IPv4 ACL and IPv6 ACL:
1./acl:configuration/acl:acl/acl:access-list/acl:ipv4-access-list/acl:rule/acl:policy-route-id
2./acl:configuration/acl:acl/acl:access-list/acl:ipv6-access-list/acl:rule/acl:policy-route-id' ;
  }

  revision 2019-08-14 {
    description 'Add sgt in IPv4 VXLAN ACL:
1./acl:configuration/acl:acl/acl:access-list/acl:ipv4-vxlan-access-lists/acl:ipv4-vxlan-access-list/acl:rules/acl:rule/acl:sgt
2./acl:configuration/acl:acl/acl:access-list/acl:ipv4-vxlan-access-lists/acl:ipv4-vxlan-access-list/acl:rules-transit-inner/acl:rule-transit-inner/acl:sgt
3./acl:configuration/acl:acl/acl:access-list/acl:ipv4-vxlan-access-lists/acl:ipv4-vxlan-access-list/acl:rules-transit-outer/acl:rule-transit-outer/acl:sgt
4./acl:configuration/acl:acl/acl:access-list/acl:ipv4-vxlan-access-lists/acl:ipv4-vxlan-access-list/acl:rules-vtep-inner/acl:rule-vtep-inner/acl:sgt
5./acl:configuration/acl:acl/acl:access-list/acl:ipv4-vxlan-access-lists/acl:ipv4-vxlan-access-list/acl:rules-vtep-outer/acl:rule-vtep-outer/acl:sgt' ;
  }

  revision 2019-06-18 {
    description 'Add label in link ACL, include leafes:
1./acl:configuration/acl:acl/acl:access-list/acl:link-access-list/acl:rule/acl:label
2./acl:configuration/acl:acl/acl:access-list/acl:link-access-list/acl:rule/acl:label2' ;
  }

  revision 2018-09-17 {
    description 'Add mode type node and its rule node in IPv4 VXLAN ACL, add vrf node in rules of default mode:
1./acl:configuration/acl:acl/acl:access-list/acl:ipv4-vxlan-access-lists/acl:ipv4-vxlan-access-list/acl:mode-type
2./acl:configuration/acl:acl/acl:access-list/acl:ipv4-vxlan-access-lists/acl:ipv4-vxlan-access-list/acl:rules/acl:rule/acl:vrf
3./acl:configuration/acl:acl/acl:access-list/acl:ipv4-vxlan-access-lists/acl:ipv4-vxlan-access-list/acl:rules-transit-inner
4./acl:configuration/acl:acl/acl:access-list/acl:ipv4-vxlan-access-lists/acl:ipv4-vxlan-access-list/acl:rules-transit-outer
5./acl:configuration/acl:acl/acl:access-list/acl:ipv4-vxlan-access-lists/acl:ipv4-vxlan-access-list/acl:rules-vtep-inner
6./acl:configuration/acl:acl/acl:access-list/acl:ipv4-vxlan-access-lists/acl:ipv4-vxlan-access-list/acl:rules-vtep-outer' ;
  }

  revision 2018-03-12 {
    description 'Add value range of offset and matchlen node in udf-template-vxlan.
/acl:configuration/acl:acl/acl:templates/acl:udf-template-vxlans/acl:udf-template-vxlan/acl:format/acl:segment3/acl:offset3;
/acl:configuration/acl:acl/acl:templates/acl:udf-template-vxlans/acl:udf-template-vxlan/acl:format/acl:segment4/acl:offset4;
/acl:configuration/acl:acl/acl:templates/acl:udf-template-vxlans/acl:udf-template-vxlan/acl:format/acl:segment5/acl:offset5;
/acl:configuration/acl:acl/acl:templates/acl:udf-template-vxlans/acl:udf-template-vxlan/acl:format/acl:segment6/acl:offset6;
/acl:configuration/acl:acl/acl:templates/acl:udf-template-vxlans/acl:udf-template-vxlan/acl:format/acl:segment7/acl:offset7;
/acl:configuration/acl:acl/acl:templates/acl:udf-template-vxlans/acl:udf-template-vxlan/acl:format/acl:segment8/acl:offset8;
/acl:configuration/acl:acl/acl:templates/acl:udf-template-vxlans/acl:udf-template-vxlan/acl:format/acl:segment2/acl:matchlen2;
/acl:configuration/acl:acl/acl:templates/acl:udf-template-vxlans/acl:udf-template-vxlan/acl:format/acl:segment3/acl:matchlen3;
/acl:configuration/acl:acl/acl:templates/acl:udf-template-vxlans/acl:udf-template-vxlan/acl:format/acl:segment4/acl:matchlen4;
/acl:configuration/acl:acl/acl:templates/acl:udf-template-vxlans/acl:udf-template-vxlan/acl:format/acl:segment5/acl:matchlen5;
/acl:configuration/acl:acl/acl:templates/acl:udf-template-vxlans/acl:udf-template-vxlan/acl:format/acl:segment6/acl:matchlen6;
/acl:configuration/acl:acl/acl:templates/acl:udf-template-vxlans/acl:udf-template-vxlan/acl:format/acl:segment7/acl:matchlen7;
/acl:configuration/acl:acl/acl:templates/acl:udf-template-vxlans/acl:udf-template-vxlan/acl:format/acl:segment8/acl:matchlen8.' ;
  }

  revision 2017-11-24 {
    description '1. In order to support configuring ACL rule description separately, some mandatory leaf nodes are adjusted  to be optional nodes, modification in detail as follows:
/configuration/acl/access-list/ipv4-access-list/rule/permit-deny
/configuration/acl/access-list/ipv4-access-list/rule/src-addr
/configuration/acl/access-list/ipv4-access-list/rule/rule-type
/configuration/acl/access-list/ipv6-access-list/rule/permit-deny
/configuration/acl/access-list/ipv6-access-list/rule/src-addr
/configuration/acl/access-list/ipv6-access-list/rule/dst-addr
/configuration/acl/access-list/ipv6-access-list/rule/rule-type
/configuration/acl/access-list/link-access-list/rule/permit-deny
/configuration/acl/access-list/link-access-list/rule/src-mac-addr
/configuration/acl/access-list/link-access-list/rule/dest-mac-addr.' ;
  }

  revision 2017-07-20 {
    description "1.The original netconf model doesn't support to delete optional configuration of ACL rule independently, such as port, TTL. So, discarding the old configuration, and add new some containers, modification in detail as follows:
    Discarding:
    /configuration/acl/access-list/ipv4-access-list/rule/rule-type/extend/extended/ttl
    /configuration/acl/access-list/ipv4-access-list/rule/rule-type/extend/extended/ipv4-protocol-type/udp-tcp/udp-tcp/src-port
    /configuration/acl/access-list/ipv4-access-list/rule/rule-type/extend/extended/ipv4-protocol-type/udp-tcp/udp-tcp/dest-port
    /configuration/acl/access-list/ipv4-access-list/rule/rule-type/extend/extended/ipv4-protocol-type/icmp/icmp-port/src-port
    /configuration/acl/access-list/ipv4-access-list/rule/rule-type/extend/extended/ipv4-protocol-type/icmp/icmp-port/dest-port
    /configuration/acl/access-list/ipv4-access-list/rule/rule-type/extend/extended/ipv4-protocol-type/ip/port/src-port
    /configuration/acl/access-list/ipv4-access-list/rule/rule-type/extend/extended/ipv4-protocol-type/ip/port/dest-port
    /configuration/acl/access-list/ipv4-mixed-access-list/rule/rule-type/extend/extended/ipv4-protocol-type/udp-tcp/udp-tcp/src-port
    /configuration/acl/access-list/ipv4-mixed-access-list/rule/rule-type/extend/extended/ipv4-protocol-type/udp-tcp/udp-tcp/dest-port
    /configuration/acl/access-list/ipv6-access-list/rule/rule-type/udp-tcp/udp-tcp/src-port
    /configuration/acl/access-list/ipv6-access-list/rule/rule-type/udp-tcp/udp-tcp/dest-port
    /configuration/acl/access-list/ipv6-access-list/rule/rule-type/icmp/icmp-port/src-port
    /configuration/acl/access-list/ipv6-access-list/rule/rule-type/icmp/icmp-port/dest-port
    /configuration/acl/access-list/ipv6-access-list/rule/rule-type/ip/port/src-port
    /configuration/acl/access-list/ipv6-access-list/rule/rule-type/ip/port/dest-port
    /configuration/acl/access-list/ipv6-mixed-access-list/rule/rule-type/udp-tcp/udp-tcp/src-port
    /configuration/acl/access-list/ipv6-mixed-access-list/rule/rule-type/udp-tcp/udp-tcp/dest-port
    /configuration/acl/access-list/ipv4-vxlan-access-lists/ipv4-vxlan-access-list/rules/rule/inner-layer/protocol-type/tcp-udp/tcp-udp/src-port
    /configuration/acl/access-list/ipv4-vxlan-access-lists/ipv4-vxlan-access-list/rules/rule/inner-layer/protocol-type/tcp-udp/tcp-udp/dst-port
    /configuration/acl/access-list/ipv4-vxlan-access-lists/ipv4-vxlan-access-list/rules/rule/outer-layer/src-port
    /configuration/acl/access-list/ipv4-vxlan-access-lists/ipv4-vxlan-access-list/rules/rule/outer-layer/dst-port

    Adding:
    /configuration/acl/access-list/ipv4-access-list/rule/rule-type/extend/extended/time-to-live
    /configuration/acl/access-list/ipv4-access-list/rule/rule-type/extend/extended/ipv4-protocol-type/udp-tcp/udp-tcp/source-port
    /configuration/acl/access-list/ipv4-access-list/rule/rule-type/extend/extended/ipv4-protocol-type/udp-tcp/udp-tcp/destination-port
    /configuration/acl/access-list/ipv4-access-list/rule/rule-type/extend/extended/ipv4-protocol-type/icmp/icmp-port/source-port
    /configuration/acl/access-list/ipv4-access-list/rule/rule-type/extend/extended/ipv4-protocol-type/icmp/icmp-port/destination-port
    /configuration/acl/access-list/ipv4-access-list/rule/rule-type/extend/extended/ipv4-protocol-type/ip/port/source-port
    /configuration/acl/access-list/ipv4-access-list/rule/rule-type/extend/extended/ipv4-protocol-type/ip/port/destination-port
    /configuration/acl/access-list/ipv4-mixed-access-list/rule/rule-type/extend/extended/ipv4-protocol-type/udp-tcp/udp-tcp/source-port
    /configuration/acl/access-list/ipv4-mixed-access-list/rule/rule-type/extend/extended/ipv4-protocol-type/udp-tcp/udp-tcp/destination-port
    /configuration/acl/access-list/ipv6-access-list/rule/rule-type/udp-tcp/udp-tcp/source-port
    /configuration/acl/access-list/ipv6-access-list/rule/rule-type/udp-tcp/udp-tcp/destination-port
    /configuration/acl/access-list/ipv6-access-list/rule/rule-type/icmp/icmp-port/source-port
    /configuration/acl/access-list/ipv6-access-list/rule/rule-type/icmp/icmp-port/destination-port
    /configuration/acl/access-list/ipv6-access-list/rule/rule-type/ip/port/source-port
    /configuration/acl/access-list/ipv6-access-list/rule/rule-type/ip/port/destination-port
    /configuration/acl/access-list/ipv6-mixed-access-list/rule/rule-type/udp-tcp/udp-tcp/source-port
    /configuration/acl/access-list/ipv6-mixed-access-list/rule/rule-type/udp-tcp/udp-tcp/destination-port
    /configuration/acl/access-list/ipv4-vxlan-access-lists/ipv4-vxlan-access-list/rules/rule/inner-layer/protocol-type/tcp-udp/tcp-udp/source-port
    /configuration/acl/access-list/ipv4-vxlan-access-lists/ipv4-vxlan-access-list/rules/rule/inner-layer/protocol-type/tcp-udp/tcp-udp/destination-port
    /configuration/acl/access-list/ipv4-vxlan-access-lists/ipv4-vxlan-access-list/rules/rule/outer-layer/source-port
    /configuration/acl/access-list/ipv4-vxlan-access-lists/ipv4-vxlan-access-list/rules/rule/outer-layer/destination-port" ;
  }

  revision 2017-07-12 {
    description 'Add service access point node:
/acl:configuration/acl:acl/acl:access-list/acl:ipv4-mixed-access-list/acl:rule/acl:link-prot/acl:sap;
/acl:configuration/acl:acl/acl:access-list/acl:ipv6-mixed-access-list/acl:rule/acl:link-prot/acl:sap;
/acl:configuration/acl:acl/acl:access-list/acl:link-access-list/acl:rule/acl:link-prot/acl:sap.' ;
  }

  revision 2017-06-20 {
    description '1.Support matching vrf for IPv4/IPv6/Link ACL, add new nodes as follows:
typedef: acl-vrf-name
nodes:
/configuration/acl/access-list/ipv4-access-list/rule/vrf
/configuration/acl/access-list/ipv6-access-list/rule/vrf
/configuration/acl/access-list/link-access-list/rule/vrf
2.Support matching packet-length for IPv4/IPv6, add new nodes as follows:
typedef: acl-pktlen-opr acl-pktlen-range
nodes:
/configuration/acl/access-list/ipv4-access-list/rule/rule-type/extend/extended/packet-length
/configuration/acl/access-list/ipv6-access-list/rule/packet-length
3.Support matching exp for Link ACL, add new nodes as follows:
nodes:
/configuration/acl/access-list/link-access-list/rule/exp
4.Support matching CFI/DEI for Link and IPv4-Mixed ACL, add new nodes as follows:
nodes:
/configuration/acl/access-list/link-access-list/rule/vlan-conf/vlan-range/cfi
/configuration/acl/access-list/link-access-list/rule/vlan-conf/vlan-range/dei
/configuration/acl/access-list/ipv4-mixed-access-list/rule/vlan-conf/vlan-range/cfi
/configuration/acl/access-list/ipv4-mixed-access-list/rule/vlan-conf/vlan-range/dei' ;
  }

  revision 2017-06-13 {
    description 'Modify user defined template ACL and support any segment,modified nodes as follows:
/acl:configuration/acl:acl/acl:access-list/acl:user-defined-template-acls/acl:user-defined-template-acl/acl:rules/acl:rule/acl:segment/
/acl:configuration/acl:acl/acl:access-list/acl:user-defined-template-acls/acl:user-defined-template-acl/acl:rules/acl:rule/acl:segment/acl:segment-any
/acl:configuration/acl:acl/acl:access-list/acl:user-defined-template-acls/acl:user-defined-template-acl/acl:rules/acl:rule/acl:segment/acl:segment-value' ;
  }

  revision 2017-06-02 {
    description 'Link ACL add link protocol mask:
/acl:configuration/acl:acl/acl:access-list/acl:link-access-list/acl:rule/acl:link-prot/acl:link-protocol/acl:link-protocol-mask;
/acl:configuration/acl:acl/acl:access-list/acl:link-access-list/acl:rule/acl:link-prot/acl:link-protocol-hex/acl:link-protocol-hex-mask.' ;
  }

  revision 2017-05-08 {
    description 'Support user defined template and user defined template ACL and user defined template interface bind, new nodes added as follows:
/acl:configuration/acl:acl/acl:templates
/acl:configuration/acl:acl/acl:access-list/acl:user-defined-template-acls
/acl:configuration/acl:acl/acl:port-acl/acl:if-udf-template' ;
  }

  revision 2017-04-20 {
    description 'These if_features support M6000-S as follows:
user-protocol-feature
acl-statistics
These if_features support 15K as follows:
url-config
These if_features delete M6000-S as follows:
pri-value-config' ;
  }

  revision 2017-01-04 {
    description 'IPv4 mixed ACL and IPv6 mixed ACL do not support link-protocol-hex.
/acl:configuration/acl:acl/acl:access-list/acl:ipv4-mixed-access-list/acl:rule/acl:link-prot/acl:link-protocol-hex;
/acl:configuration/acl:acl/acl:access-list/acl:ipv6-mixed-access-list/acl:rule/acl:link-prot/acl:link-protocol-hex.' ;
  }

  revision 2016-08-18 {
    description 'Support rule description to IPv4/IPv6/Link ACL, new nodes added as follows:
1./acl:configuration/acl:acl/acl:access-list/acl:ipv4-access-list/acl:rule/acl:description;
2./acl:configuration/acl:acl/acl:access-list/acl:ipv6-access-list/acl:rule/acl:description;
3./acl:configuration/acl:acl/acl:access-list/acl:link-access-list/acl:rule/acl:description;' ;
  }

  revision 2016-06-01 {
    description 'Change these leaf nodes below to mandatory:
/acl:configuration/acl:acl/acl:access-list/acl:ipv4-access-list/acl:rule/acl:rule-type/acl:extend/acl:extended/acl:ipv4-protocol-type/acl:ip/acl:ipv4-protocol;
/acl:configuration/acl:acl/acl:access-list/acl:ipv6-access-list/acl:rule/acl:rule-type/acl:ip/acl:ipv6-protocol.' ;
  }

  revision 2016-05-23 {
    description 'Modify the value range of nodes below:
/acl:configuration/acl:acl/acl:access-list/acl:ipv4-vxlan-access-lists/acl:ipv4-vxlan-access-list/acl:rules/acl:rule/acl:inner-layer/acl:tcp-udp/acl:src-port-number
/acl:configuration/acl:acl/acl:access-list/acl:ipv4-vxlan-access-lists/acl:ipv4-vxlan-access-list/acl:rules/acl:rule/acl:outer-layer/acl:src-port/acl:src-oper/acl:src-port-number' ;
  }

  revision 2016-04-08 {
    description 'Add mandatory attribute in those nodes:
/acl:configuration/acl:acl/acl:access-list/acl:user-defined-list/acl:rule/acl:any
/acl:configuration/acl:acl/acl:access-list/acl:user-defined-list/acl:rule/acl:segment-type' ;
  }

  revision 2016-03-04 {
    description 'Add nodes as follows:
/acl:configuration/acl:acl/acl:access-list/acl:ipv4-vxlan-access-lists/acl:ipv4-vxlan-access-list
/acl:configuration/acl:acl/acl:port-acl/acl:if-ipv4-vxlan
/acl:configuration/acl:acl/acl:port-acl/acl:vlan-ipv4-vxlan
/acl:configuration/acl:acl/acl:port-acl/acl:device-ipv4-vxlans
/acl:configuration/acl:acl/acl:vni-acl' ;
  }

  revision 2016-01-13 {
    description 'Add port infomation of any protocol.
/acl:configuration/acl:acl/acl:access-list/acl:ipv4-access-list/acl:rule/acl:extended/acl:icmp-port;
/acl:configuration/acl:acl/acl:access-list/acl:ipv4-access-list/acl:rule/acl:extended/acl:port;
/acl:configuration/acl:acl/acl:access-list/acl:ipv6-access-list/acl:rule/acl:icmp-port;
/acl:configuration/acl:acl/acl:access-list/acl:ipv6-access-list/acl:rule/acl:port.' ;
  }

  revision 2015-12-23 {
    description 'Add nodes as follows:
/acl:configuration/acl:acl/acl:access-list/acl:user-defined-list/acl:acl-name
/acl:configuration/acl:acl/acl:access-list/acl:user-defined-list/acl:rule/acl:ruleid
/acl:configuration/acl:acl/acl:access-list/acl:user-defined-list/acl:rule/acl:permit-deny/acl:deny/acl:deny
/acl:configuration/acl:acl/acl:access-list/acl:user-defined-list/acl:rule/acl:permit-deny/acl:permit/acl:permit
/acl:configuration/acl:acl/acl:access-list/acl:user-defined-list/acl:rule/acl:frame-type
/acl:configuration/acl:acl/acl:access-list/acl:user-defined-list/acl:rule/acl:tag-status
/acl:configuration/acl:acl/acl:access-list/acl:user-defined-list/acl:rule/acl:ip-flag
/acl:configuration/acl:acl/acl:access-list/acl:user-defined-list/acl:rule/acl:segment-type/acl:any-segment/acl:any
/acl:configuration/acl:acl/acl:access-list/acl:user-defined-list/acl:rule/acl:segment-type/acl:segment/acl:segment1/acl:offset
/acl:configuration/acl:acl/acl:access-list/acl:user-defined-list/acl:rule/acl:segment-type/acl:segment/acl:segment1/acl:rule-string
/acl:configuration/acl:acl/acl:access-list/acl:user-defined-list/acl:rule/acl:segment-type/acl:segment/acl:segment1/acl:rule-mask
/acl:configuration/acl:acl/acl:access-list/acl:user-defined-list/acl:rule/acl:segment-type/acl:segment/acl:segment1/acl:segment2/acl:offset
/acl:configuration/acl:acl/acl:access-list/acl:user-defined-list/acl:rule/acl:segment-type/acl:segment/acl:segment1/acl:segment2/acl:rule-string
/acl:configuration/acl:acl/acl:access-list/acl:user-defined-list/acl:rule/acl:segment-type/acl:segment/acl:segment1/acl:segment2/acl:rule-mask
/acl:configuration/acl:acl/acl:access-list/acl:user-defined-list/acl:rule/acl:segment-type/acl:segment/acl:segment1/acl:segment2/acl:segment3/acl:offset
/acl:configuration/acl:acl/acl:access-list/acl:user-defined-list/acl:rule/acl:segment-type/acl:segment/acl:segment1/acl:segment2/acl:segment3/acl:rule-string
/acl:configuration/acl:acl/acl:access-list/acl:user-defined-list/acl:rule/acl:segment-type/acl:segment/acl:segment1/acl:segment2/acl:segment3/acl:rule-mask
/acl:configuration/acl:acl/acl:access-list/acl:user-defined-list/acl:rule/acl:segment-type/acl:segment/acl:segment1/acl:segment2/acl:segment3/acl:segment4/acl:offset
/acl:configuration/acl:acl/acl:access-list/acl:user-defined-list/acl:rule/acl:segment-type/acl:segment/acl:segment1/acl:segment2/acl:segment3/acl:segment4/acl:rule-string
/acl:configuration/acl:acl/acl:access-list/acl:user-defined-list/acl:rule/acl:segment-type/acl:segment/acl:segment1/acl:segment2/acl:segment3/acl:segment4/acl:rule-mask
/acl:configuration/acl:acl/acl:access-list/acl:user-defined-list/acl:rule/acl:time-range.
Feature:user-defined-feature.
Add an if-feature:user-defined-feature in /acl:configuration/acl:acl/acl:port-acl/acl:device-user-defineds' ;
  }

  revision 2015-12-15 {
    description 'Add nodes as follows:
/acl:configuration/acl:acl/acl:port-acl/acl:device-ipv4s/acl:device-ipv4/acl:direction
/acl:configuration/acl:acl/acl:port-acl/acl:device-ipv4s/acl:device-ipv4/acl:acl-name
/acl:configuration/acl:acl/acl:port-acl/acl:device-ipv6s/acl:device-ipv6/acl:direction
/acl:configuration/acl:acl/acl:port-acl/acl:device-ipv6s/acl:device-ipv6/acl:acl-name
/acl:configuration/acl:acl/acl:port-acl/acl:device-links/acl:device-link/acl:direction
/acl:configuration/acl:acl/acl:port-acl/acl:device-links/acl:device-link/acl:acl-name
/acl:configuration/acl:acl/acl:port-acl/acl:device-ipv4-mixeds/acl:device-ipv4-mixed/acl:direction
/acl:configuration/acl:acl/acl:port-acl/acl:device-ipv4-mixeds/acl:device-ipv4-mixed/acl:acl-name
/acl:configuration/acl:acl/acl:port-acl/acl:device-ipv6-mixeds/acl:device-ipv6-mixed/acl:direction
/acl:configuration/acl:acl/acl:port-acl/acl:device-ipv6-mixeds/acl:device-ipv6-mixed/acl:acl-name
/acl:configuration/acl:acl/acl:port-acl/acl:device-user-defineds/acl:device-user-defined/acl:direction
/acl:configuration/acl:acl/acl:port-acl/acl:device-user-defineds/acl:device-user-defined/acl:acl-name
feature:statics-per-device.
Add the range(1~2147483644) of uint32 type of leafs,those leaf as follows:
/acl:state/acl:acl/acl:acl-v6-statistics/acl:acl-v6-statistic/acl:acl-ruleid 
/acl:state/acl:acl/acl:acl-v4-statistics/acl:acl-v4-statistic/acl:acl-ruleid.' ;
  }

  revision 2015-11-04 {
    description 'Add node user-protocol-access-list:
/acl:configuration/acl:acl/acl:access-list/acl:user-protocol-access-list.' ;
  }

  revision 2015-08-21 {
    description 'Change DerivedType of the following leaf node from ipv4-mask to ipv4-address:
/acl:configuration/acl:acl/acl:access-list/acl:ipv4-access-list/acl:rule/acl:src-wildcard;
/acl:configuration/acl:acl/acl:access-list/acl:ipv4-access-list/acl:rule/acl:extended/acl:dest-wildcard;
/acl:configuration/acl:acl/acl:access-list/acl:ipv4-mixed-access-list/acl:rule/acl:src-wildcard;
/acl:configuration/acl:acl/acl:access-list/acl:ipv4-mixed-access-list/acl:rule/acl:extended/acl:dest-wildcard.' ;
  }

  revision 2015-06-08 {
    description 'Add ACL statistics configuration with Feature: acl-statistics, details as follows:
1.Add ACL log switch configuration with the Feature, statistics-switch, new notes added as follows:
Typedef:acl-if-direction
Container: /configuration/acl/statistics-switch/
Container: /configuration/acl/statistics-switch/ipv4-log-switchs
Container: /configuration/acl/statistics-switch/ipv6-log-switchs
2.Add ACL log clear operation with the Feature, statistics-clear, new notes added as follows:
Container: /operation/
Container: /operation/acl/
Container: /operation/acl/statistics-clear/
Container: /operation/acl/statistics-clear/ipv4-log-clears
Container: /operation/acl/statistics-clear/ipv6-log-clears
Container: /operation/acl/statistics-clear/link-log-clears
3.Add ACL log statistics query notes with the Feature, statistics-query, new notes added as follows:
Container: /state/
Container: /state/acl/
Container: /state/acl/acl-v4-statistics/
Container: /state/acl/acl-v6-statistics/.' ;
  }

  revision 2015-04-20 {
    description '1.Support priority(Precedence,DSCP,CoS) range configuration with the feature pre-range-config, new notes added as follows:
Typedef:acl-prec-range
Typedef:acl-dscp-range
Typedef:acl-cos-range
Feature: pri-range-config
Feature: pri-value-config
case: /configuration/acl/access-list/ipv4-access-list/rule/rule-type/extend/extended/priority/prec-range
case: /configuration/acl/access-list/ipv4-access-list/rule/rule-type/extend/extended/priority/dscp-range
leaf: /configuration/acl/access-list/ipv4-mixed-access-list/rule/inner-cos-range
leaf: /configuration/acl/access-list/ipv4-mixed-access-list/rule/outer-cos-range
case: /configuration/acl/access-list/ipv4-mixed-access-list/rule/rule-type/extend/extended/priority/prec-range
case: /configuration/acl/access-list/ipv4-mixed-access-list/rule/rule-type/extend/extended/priority/dscp-range
leaf: /configuration/acl/access-list/link-access-list/rule/inner-cos-range
leaf: /configuration/acl/access-list/link-access-list/rule/outer-cos-range
2.Support IPv6/LINK ACL log configuration, new notes added as follows:
Feature: ipv6-log-config
Feature: link-log-config
leaf:/configuration/acl/access-list/ipv6-access-list/rule/log
leaf:/configuration/acl/access-list/link-access-list/rule/log
3.Add feature:switchvlan-acl for contianer: vlan-ipv4, vlan-ipv6, vlan-link, vlan-ipv4-mixed, vlan-ipv6-mixed.' ;
  }

  revision 2015-02-13 {
    description '1 src-url and dest-url add if_feature url-config:
/acl:configuration/acl:acl/acl:access-list/acl:ipv6-access-list/acl:rule/acl:src-addr/acl:src-url
/acl:configuration/acl:acl/acl:access-list/acl:ipv6-access-list/acl:rule/acl:dest-addr/acl:dest-url.' ;
  }

  revision 2014-04-16 {
    description '1 Add src-url and dest-url with feature url-config:
/acl:configuration/acl:acl/acl:access-list/acl:ipv4-access-list/acl:rule/acl:src-addr/acl:src-url
/acl:configuration/acl:acl/acl:access-list/acl:ipv4-access-list/acl:rule/acl:rule-type/acl:extend/acl:extended/acl:dest-addr/acl:dest-url
/acl:configuration/acl:acl/acl:access-list/acl:ipv6-access-list/acl:rule/acl:src-addr/acl:src-url
/acl:configuration/acl:acl/acl:access-list/acl:ipv6-access-list/acl:rule/acl:dest-addr/acl:dest-url
2 Add feature link-prot-hex-config for case link-protocol-hex:
/acl:configuration/acl:acl/acl:access-list/acl:ipv4-mixed-access-list/acl:rule/acl:link-prot/acl:link-protocol-hex
/acl:configuration/acl:acl/acl:access-list/acl:ipv6-mixed-access-list/acl:rule/acl:link-prot/acl:link-protocol-hex
/acl:configuration/acl:acl/acl:access-list/acl:link-access-list/acl:rule/acl:link-prot/acl:link-protocol-hex
3 Modify value range of leaf link-protocol:
/acl:configuration/acl:acl/acl:access-list/acl:ipv4-mixed-access-list/acl:rule/acl:link-prot/acl:link-protocol/acl:link-protocol
/acl:configuration/acl:acl/acl:access-list/acl:ipv6-mixed-access-list/acl:rule/acl:link-prot/acl:link-protocol/acl:link-protocol
/acl:configuration/acl:acl/acl:access-list/acl:link-access-list/acl:rule/acl:link-prot/acl:link-protocol/acl:link-protocol.' ;
  }

  revision 2013-10-30 {
    description 'Initial version.' ;
  }

  feature ttl-config {
    description 'Match if TTL configures.' ;
  }

  feature log-config {
    description 'Match if log configures.' ;
  }

  feature ipv6-log-config {
    description 'Support IPv6 ACL log.' ;
  }

  feature link-log-config {
    description 'Support LINK ACL log.' ;
  }

  feature link-prot-hex-config {
    description 'Match if link protocol hex configures.' ;
  }

  feature url-config {
    description 'Match if URL configures.' ;
  }

  feature vlan-value-config {
    description 'Match if vlan-value configures.' ;
  }

  feature vlan-range-config {
    description 'Match if vlan-range configures.' ;
  }

  feature mac-range-config {
    description 'Match if MAC address range configures.' ;
  }

  feature pri-value-config {
    description 'Support to configure single priority value, such as Precedence, DSCP, CoS(802.1p).' ;
  }

  feature pri-range-config {
    description 'Support to configure single priority value or range, such as Precedence, DSCP, CoS(802.1p).' ;
  }

  feature ipv4-feature {
    description 'Match if ipv4-access-list configures.' ;
  }

  feature ipv4-mixed-feature {
    description 'Match if ipv4-mixed-access-list configures.' ;
  }

  feature ipv6-feature {
    description 'Match if ipv6-access-list configures.' ;
  }

  feature ipv6-mixed-feature {
    description 'Match if ipv6-mixed-access-list configures.' ;
  }

  feature link-feature {
    description 'Match if link-access-list configures.' ;
  }

  feature switchvlan-acl {
    description 'Match switch-vlan access-list configures.' ;
  }

  feature acl-statistics {
    description 'Match ACL LOG statistics configures.' ;
  }

  feature user-protocol-feature {
    description 'Match if user-protocol-mixed-access-list configures.' ;
  }

  feature statics-per-device {
    description 'Support for configure that global device statistics of rate.' ;
  }

  feature user-defined-feature {
    description 'Match if user-defined-list configures.' ;
  }

  feature ipv4-vxlan-feature {
    description 'Match if ipv4-vxlan-access-list configures.' ;
  }

  feature udf-template-type {
    description 'Match if user-defined-template configures.' ;
  }

  feature sap-feature {
    description 'Match if service access point configures.' ;
  }

  feature ipv4-mixed-log-config {
    description 'Support IPv4 mixed ACL log.' ;
  }

  feature ipv6-ttl-config {
    description 'Match if TTL configures in ipv6.' ;
  }

  feature ipv6-dscp-range-config {
    description 'Match if dscp-range configures in IPv6.' ;
  }

  feature ipv6-cos-range-config {
    description 'Match if cos-range configures in IPv6.' ;
  }

  feature ipv4-mixed-pri-value {
    description 'Support to configure single priority value in ipv4-mixed-access-lists, such as Precedence, DSCP.' ;
  }

  feature ipv4-mixed-pri-range {
    description 'Support to configure single priority value or range in ipv4-mixed-access-lists, such as Precedence, DSCP.' ;
  }

  feature link-cos-value {
    description 'Support to configure single CoS(802.1p) value in link-access-lists.' ;
  }

  feature link-cos-range {
    description 'Support to configure single CoS(802.1p) value or range in link-access-lists.' ;
  }

  feature ipv4-mixed-cos-value {
    description 'Support to configure single CoS(802.1p) value in ipv4-mixed-access-lists.' ;
  }

  feature ipv4-mixed-cos-range {
    description 'Support to configure single CoS(802.1p) value or range in ipv4-mixed-access-lists.' ;
  }

  feature ipv6-mixed-log-config {
    description 'Support IPv6 mixed ACL log.' ;
  }

  feature l2-layer {
    description 'L2 information.' ;
    ncd:revise-date 2021-10-26 ;
  }

  feature none-rule-default-action {
    description 'Configure default action in empty ACL.' ;
    ncd:revise-date 2021-11-23 ;
  }

  feature port-pool {
    description 'Configure port-pool.' ;
    ncd:revise-date 2023-12-12 ;
  }

  feature prefix-list {
    description 'Match prefix-list Configuration.' ;
    ncd:revise-date 2023-12-12 ;
  }

  feature acl-if-application {
    description 'Support to configure ACL interface application.' ;
    ncd:revise-date 2024-01-16 ;
  }

  feature ip-flags-config {
    description 'Support to configure IP flags.' ;
    ncd:revise-date 2024-03-22 ;
  }

  feature vxlan-acl-tcp-flag {
    description 'Support to configure TCP flags in VXLAN ACL.' ;
    ncd:revise-date 2024-06-01 ;
  }

  feature link-acl-description {
    description 'Support to configure a description for a link ACL.' ;
    ncd:revise-date 2024-08-13 ;
  }

  feature port-pool-description {
    description 'Support to configure a description for a port pool.' ;
    ncd:revise-date 2024-08-13 ;
  }

  feature ipv4-mixed-vrf {
    description 'Support to configure VRF in an IPv4 mixed ACL.' ;
    ncd:revise-date 2024-12-10 ;
  }

  feature ipv6-mixed-vrf {
    description 'Support to configure VRF in an IPv6 mixed ACL.' ;
    ncd:revise-date 2024-12-10 ;
  }

  feature ipv6-mixed-label {
    description 'Support to configure the outermost label in an IPv6 mixed ACL.' ;
    ncd:revise-date 2024-12-10 ;
  }

  feature ipv6-mixed-label2 {
    description 'Support to configure the second-layer label in an IPv6 mixed ACL.' ;
    ncd:revise-date 2024-12-10 ;
  }

  typedef acl-name-type {
    type string {
      length 1..31 ;

    }

    description 'The definition of ACL name type, support 1-31 characters.' ;
  }

  typedef acl-port-range {
    type ncd:single-range {
      pattern "((([1-9][0-9]{1,3})|([1-9][0-9]{0,0})|0|([1-5][0-9]{4,4})|(6[0-4][0-9]{3,3})|(65[0-4][0-9]{2,2})|(655[0-2][0-9]{1,1})|(6553[0-4])|65535)(-(([1-9][0-9]{1,3})|([1-9][0-9]{0,0})|0|([1-5][0-9]{4,4})|(6[0-4][0-9]{3,3})|(65[0-4][0-9]{2,2})|(655[0-2][0-9]{1,1})|(6553[0-4])|65535)){0,1})" ;

    }

    description 'The definition of ACL port range, support <0-65535>-<0-65535>.' ;
  }

  typedef acl-vlan-range {
    type ncd:single-range {
      pattern "((([1-9][0-9]{1,2})|([2-9][0-9]{0,0})|1|([1-3][0-9]{3,3})|(40[0-8][0-9]{1,1})|(409[0-3])|4094)(-(([1-9][0-9]{1,2})|([2-9][0-9]{0,0})|1|([1-3][0-9]{3,3})|(40[0-8][0-9]{1,1})|(409[0-3])|4094)){0,1})" ;

    }

    description 'The definition of ACL VLAN range, support <1-4094>-<1-4094>.' ;
  }

  typedef acl-ttl-range {
    type ncd:single-range {
      pattern "((([1-9][0-9]{1,1})|([2-9][0-9]{0,0})|1|([1-1][0-9]{2,2})|(2[0-4][0-9]{1,1})|(25[0-4])|255)(-(([1-9][0-9]{1,1})|([2-9][0-9]{0,0})|1|([1-1][0-9]{2,2})|(2[0-4][0-9]{1,1})|(25[0-4])|255)){0,1})" ;

    }

    description 'The definition of ACL TTL range, support <1-255>-<1-255>.' ;
  }

  typedef acl-tcp-flag {
    type enumeration {
      enum - {
        value 0 ;
        description 'Match when the flag not set.' ;
      }

      enum "+" {
        value 1 ;
        description 'Match when the flag set.' ;
      }

    }

    description 'The definition of ACL TCP flag.' ;
  }

  typedef acl-prec-range {
    type ncd:single-range {
      pattern "((([0-7]-[0-7])|([0-7])){1,1})" ;

    }

    description 'The definition of ACL Precedence range, support <0-7>-<0-7>.' ;
  }

  typedef acl-dscp-range {
    type ncd:single-range {
      pattern "((((([1-9][0-9]{0,0})|0|([1-5][0-9]{1,1})|(6[0-2])|63)-(([1-9][0-9]{0,0})|0|([1-5][0-9]{1,1})|(6[0-2])|63))|(([1-9][0-9]{0,0})|0|([1-5][0-9]{1,1})|(6[0-2])|63)){1,1})" ;

    }

    description 'The definition of ACL DSCP range, support <0-63>-<0-63>.' ;
  }

  typedef acl-cos-range {
    type ncd:single-range {
      pattern "((([0-7]-[0-7])|([0-7])){1,1})" ;

    }

    description 'The definition of ACL CoS range, support <0-7>-<0-7>.' ;
  }

  typedef acl-if-direction {
    type enumeration {
      enum egress {
        value 0 ;
        description 'Direction egress.' ;
      }

      enum ingress {
        value 1 ;
        description 'Direction ingress.' ;
      }

    }

    description 'The definition of interface direction, as follows,
     egress  Direction egress
     ingress Direction ingress.' ;
  }

  typedef acl-vrf-name {
    type string {
      length 1..32 {
        description 'VPN Routing/Forwarding instance name, support 1-32 characters.' ;
      }

    }

    description 'VPN Routing/Forwarding instance name, support 1-32 characters.' ;
  }

  typedef acl-pktlen-opr {
    type enumeration {
      enum eq {
        value 1 ;
        description 'Match only packets on a given packet length.' ;
      }

      enum gt {
        value 4 ;
        description 'Match only packets with a greater packet length.' ;
      }

      enum lt {
        value 5 ;
        description 'Match only packets with a lower packet length.' ;
      }

      enum neq {
        value 6 ;
        description 'Match only packets not on a given packet length.' ;
      }

    }

    description 'Packet length operator, such as 
  eq   Match only packets on a given packet length
  gt   Match only packets with a greater packet length
  lt   Match only packets with a lower packet length
  neq  Match only packets not on a given packet length.' ;
  }

  typedef acl-pktlen-range {
    type ncd:single-range {
      pattern "((([1-9][0-9]{1,3})|([2-9][0-9]{0,0})|1|([1-5][0-9]{4,4})|(6[0-4][0-9]{3,3})|(65[0-4][0-9]{2,2})|(655[0-2][0-9]{1,1})|(6553[0-4])|65535)(-(([1-9][0-9]{1,3})|([2-9][0-9]{0,0})|1|([1-5][0-9]{4,4})|(6[0-4][0-9]{3,3})|(65[0-4][0-9]{2,2})|(655[0-2][0-9]{1,1})|(6553[0-4])|65535)){0,1})" ;

    }

    description 'Match only packets on a given packet length range, support <1-65535>-<1-65535>.' ;
  }

  typedef vxlan-head-type {
    type enumeration {
      enum outer-l2-head {
        value 1 ;
        description 'outer-l2-head' ;
      }

      enum vxlan-head {
        value 2 ;
        description 'vxlan-head' ;
      }

      enum vxlan-in-v4 {
        value 3 ;
        description 'vxlan-in-v4' ;
      }

      enum vxlan-in-v4-gre {
        value 4 ;
        description 'vxlan-in-v4-gre' ;
      }

    }

    description 'The definition of head type, as follows,  
  outer-l2-head    Outer-l2-head(1)
  vxlan-head       Vxlan-head(2)
  vxlan-in-v4      Vxlan-Inner-ipv4(3)
  vxlan-in-v4-gre  Vxlan-Inner-ipv4-gre(4)' ;
  }

  typedef general-template-head-type {
    type enumeration {
      enum l2-head {
        value 1 ;
        description 'Offset from L2-head' ;
      }

      enum l3-head {
        value 2 ;
        description 'Offset from L3-head' ;
      }

      enum l4-head {
        value 3 ;
        description 'Offset from L4-head' ;
      }

    }

    description 'The definition of head type, as follows,  
  l2-head    Offset from L2-head(1)
  l3-head    Offset from L3-head(2)
  l4-head    Offset from L4-head(3)' ;
  }

  typedef acl-port-pool-name {
    type string {
      length 1..31 ;

    }

    description 'The definition of ACL port pool name type, support 1-31 characters.' ;
  }

  typedef acl-if-application-mode-type {
    type enumeration {
      enum overwrite {
        value 1 ;
        description 'overwrite mode' ;
      }

    }

    description 'The definition of interface application mode type, as follows:
             overwrite(1) overwrite mode' ;
  }

  container configuration {
    description 'Configuration model.' ;
    container acl {
      description 'Configuration related to ACL.' ;
      container templates {
        if-feature udf-template-type ;

        description 'Configure user-defined template.' ;
        container udf-template-vxlans {
          if-feature udf-template-type ;

          description 'Configure VXLAN user-defined template.' ;
          list udf-template-vxlan {
            if-feature udf-template-type ;

            description 'Configure VXLAN user-defined template.' ;
            key template-name ;
            leaf template-name {
              description 'The template name of the VXLAN user-defined template.' ;
              type acl-name-type ;

            }

            container format {
              description 'Configure the format of the VXLAN user-defined template.' ;
              presence format ;
              container segment1 {
                description 'Configure the first segment of the VXLAN user-defined template.' ;
                presence segment1 ;
                leaf head-type1 {
                  description 'Configure the VXLAN packet header type.' ;
                  type vxlan-head-type ;

                  mandatory true ;
                }

                leaf offset1 {
                  description 'Configure the offset value.' ;
                  type uint8 {
                    range 0..77 ;

                  }

                  mandatory true ;
                }

                leaf matchlen1 {
                  description 'Configure the match length.' ;
                  type uint8 {
                    range 1..4 ;

                  }

                  default 2 ;
                }

              }

              container segment2 {
                description 'Configure the second segment of the VXLAN user-defined template.' ;
                presence segment2 ;
                leaf head-type2 {
                  description 'Configure the VXLAN packet header type.' ;
                  type vxlan-head-type ;

                  mandatory true ;
                }

                leaf offset2 {
                  description 'Configure the offset value.' ;
                  type uint8 {
                    range 0..77 ;

                  }

                  mandatory true ;
                }

                leaf matchlen2 {
                  description 'Configure the match length.' ;
                  type uint8 {
                    range 1..4 ;

                  }

                  default 2 ;
                }

              }

              container segment3 {
                description 'Configure the third segment of the VXLAN user-defined template.' ;
                presence segment3 ;
                leaf head-type3 {
                  description 'Configure the VXLAN packet header type.' ;
                  type vxlan-head-type ;

                  mandatory true ;
                }

                leaf offset3 {
                  description 'Configure the offset value.' ;
                  type uint8 {
                    range 0..77 ;

                  }

                  mandatory true ;
                }

                leaf matchlen3 {
                  description 'Configure the match length.' ;
                  type uint8 {
                    range 1..4 ;

                  }

                  default 2 ;
                }

              }

              container segment4 {
                description 'Configure the fourth segment of the VXLAN user-defined template.' ;
                presence segment4 ;
                leaf head-type4 {
                  description 'Configure the VXLAN packet header type.' ;
                  type vxlan-head-type ;

                  mandatory true ;
                }

                leaf offset4 {
                  description 'Configure the offset value.' ;
                  type uint8 {
                    range 0..77 ;

                  }

                  mandatory true ;
                }

                leaf matchlen4 {
                  description 'Configure the match length.' ;
                  type uint8 {
                    range 1..4 ;

                  }

                  default 2 ;
                }

              }

              container segment5 {
                description 'Configure the fifth segment of the VXLAN user-defined template.' ;
                presence segment5 ;
                leaf head-type5 {
                  description 'Configure the VXLAN packet header type.' ;
                  type vxlan-head-type ;

                  mandatory true ;
                }

                leaf offset5 {
                  description 'Configure the offset value.' ;
                  type uint8 {
                    range 0..77 ;

                  }

                  mandatory true ;
                }

                leaf matchlen5 {
                  description 'Configure the match length.' ;
                  type uint8 {
                    range 1..4 ;

                  }

                  default 2 ;
                }

              }

              container segment6 {
                description 'Configure the sixth segment of the VXLAN user-defined template.' ;
                presence segment6 ;
                leaf head-type6 {
                  description 'Configure the VXLAN packet header type.' ;
                  type vxlan-head-type ;

                  mandatory true ;
                }

                leaf offset6 {
                  description 'Configure the offset value.' ;
                  type uint8 {
                    range 0..77 ;

                  }

                  mandatory true ;
                }

                leaf matchlen6 {
                  description 'Configure the match length.' ;
                  type uint8 {
                    range 1..4 ;

                  }

                  default 2 ;
                }

              }

              container segment7 {
                description 'Configure the seventh segment of the VXLAN user-defined template.' ;
                presence segment7 ;
                leaf head-type7 {
                  description 'Configure the VXLAN packet header type.' ;
                  type vxlan-head-type ;

                  mandatory true ;
                }

                leaf offset7 {
                  description 'Configure the offset value.' ;
                  type uint8 {
                    range 0..77 ;

                  }

                  mandatory true ;
                }

                leaf matchlen7 {
                  description 'Configure the match length.' ;
                  type uint8 {
                    range 1..4 ;

                  }

                  default 2 ;
                }

              }

              container segment8 {
                description 'Configure the eighth segment of the VXLAN user-defined template.' ;
                presence segment8 ;
                leaf head-type8 {
                  description 'Configure the VXLAN packet header type.' ;
                  type vxlan-head-type ;

                  mandatory true ;
                }

                leaf offset8 {
                  description 'Configure the offset value.' ;
                  type uint8 {
                    range 0..77 ;

                  }

                  mandatory true ;
                }

                leaf matchlen8 {
                  description 'Configure the match length.' ;
                  type uint8 {
                    range 1..4 ;

                  }

                  default 2 ;
                }

              }

            }

          }

        }

        container udf-template-generals {
          description 'Configure general user-defined template.' ;
          list udf-template-general {
            description 'Configure general user-defined template.' ;
            key template-name ;
            leaf template-name {
              description 'The template name of the general user-defined template.' ;
              type acl-name-type ;

            }

            container format {
              description 'Configure the format of the general user-defined template.' ;
              presence format ;
              container segment1 {
                description 'Configure the first segment of the general user-defined template.' ;
                presence segment1 ;
                leaf head-type1 {
                  description 'Configure the general packet header type.' ;
                  type general-template-head-type ;

                  mandatory true ;
                }

                leaf offset1 {
                  description 'Configure the offset value.' ;
                  type uint8 {
                    range 0..77 ;

                  }

                  mandatory true ;
                }

                leaf matchlen1 {
                  description 'Configure the match length.' ;
                  type uint8 {
                    range 1..4 ;

                  }

                  default 2 ;
                }

              }

              container segment2 {
                description 'Configure the second segment of the general user-defined template.' ;
                presence segment2 ;
                leaf head-type2 {
                  description 'Configure the general packet header type.' ;
                  type general-template-head-type ;

                  mandatory true ;
                }

                leaf offset2 {
                  description 'Configure the offset value.' ;
                  type uint8 {
                    range 0..77 ;

                  }

                  mandatory true ;
                }

                leaf matchlen2 {
                  description 'Configure the match length.' ;
                  type uint8 {
                    range 1..4 ;

                  }

                  default 2 ;
                }

              }

              container segment3 {
                description 'Configure the third segment of the general user-defined template.' ;
                presence segment3 ;
                leaf head-type3 {
                  description 'Configure the general packet header type.' ;
                  type general-template-head-type ;

                  mandatory true ;
                }

                leaf offset3 {
                  description 'Configure the offset value.' ;
                  type uint8 {
                    range 0..77 ;

                  }

                  mandatory true ;
                }

                leaf matchlen3 {
                  description 'Configure the match length.' ;
                  type uint8 {
                    range 1..4 ;

                  }

                  default 2 ;
                }

              }

              container segment4 {
                description 'Configure the fourth segment of the general user-defined template.' ;
                presence segment4 ;
                leaf head-type4 {
                  description 'Configure the general packet header type.' ;
                  type general-template-head-type ;

                  mandatory true ;
                }

                leaf offset4 {
                  description 'Configure the offset value.' ;
                  type uint8 {
                    range 0..77 ;

                  }

                  mandatory true ;
                }

                leaf matchlen4 {
                  description 'Configure the match length.' ;
                  type uint8 {
                    range 1..4 ;

                  }

                  default 2 ;
                }

              }

              container segment5 {
                description 'Configure the fifth segment of the general user-defined template.' ;
                presence segment5 ;
                leaf head-type5 {
                  description 'Configure the general packet header type.' ;
                  type general-template-head-type ;

                  mandatory true ;
                }

                leaf offset5 {
                  description 'Configure the offset value.' ;
                  type uint8 {
                    range 0..77 ;

                  }

                  mandatory true ;
                }

                leaf matchlen5 {
                  description 'Configure the match length.' ;
                  type uint8 {
                    range 1..4 ;

                  }

                  default 2 ;
                }

              }

              container segment6 {
                description 'Configure the sixth segment of the general user-defined template.' ;
                presence segment6 ;
                leaf head-type6 {
                  description 'Configure the general packet header type.' ;
                  type general-template-head-type ;

                  mandatory true ;
                }

                leaf offset6 {
                  description 'Configure the offset value.' ;
                  type uint8 {
                    range 0..77 ;

                  }

                  mandatory true ;
                }

                leaf matchlen6 {
                  description 'Configure the match length.' ;
                  type uint8 {
                    range 1..4 ;

                  }

                  default 2 ;
                }

              }

              container segment7 {
                description 'Configure the seventh segment of the general user-defined template.' ;
                presence segment7 ;
                leaf head-type7 {
                  description 'Configure the general packet header type.' ;
                  type general-template-head-type ;

                  mandatory true ;
                }

                leaf offset7 {
                  description 'Configure the offset value.' ;
                  type uint8 {
                    range 0..77 ;

                  }

                  mandatory true ;
                }

                leaf matchlen7 {
                  description 'Configure the match length.' ;
                  type uint8 {
                    range 1..4 ;

                  }

                  default 2 ;
                }

              }

              container segment8 {
                description 'Configure the eighth segment of the general user-defined template.' ;
                presence segment8 ;
                leaf head-type8 {
                  description 'Configure the general packet header type.' ;
                  type general-template-head-type ;

                  mandatory true ;
                }

                leaf offset8 {
                  description 'Configure the offset value.' ;
                  type uint8 {
                    range 0..77 ;

                  }

                  mandatory true ;
                }

                leaf matchlen8 {
                  description 'Configure the match length.' ;
                  type uint8 {
                    range 1..4 ;

                  }

                  default 2 ;
                }

              }

            }

          }

          ncd:revise-date 2022-01-27 ;
        }

        ncd:revise-date 2017-05-08 ;
      }

      container port-pools {
        if-feature port-pool ;

        description 'Configure ACL port pools.' ;
        list port-pool {
          description 'Configure an ACL port pool.' ;
          key port-pool-name ;
          leaf port-pool-name {
            type acl-port-pool-name ;

            description 'Port pool name.' ;
          }

          container port-pool-items {
            container port-eq-items {
              list port-eq-item {
                description 'Configure a port EQ item.' ;
                key port-eq-value ;
                leaf port-eq-value {
                  type uint16 {
                    range 0..65535 ;

                  }

                  description 'Match packets on a given port number.' ;
                }

              }

              description 'Configure port EQ items.' ;
            }

            container port-ge-item {
              leaf port-ge-value {
                type uint16 {
                  range 0..65535 ;

                }

                description 'Match packets with a no lower port number.' ;
                mandatory true ;
              }

              description 'Configure a port GE item.' ;
              presence port-ge-value ;
            }

            container port-le-item {
              leaf port-le-value {
                type uint16 {
                  range 0..65535 ;

                }

                description 'Match packets with a no greater port number.' ;
                mandatory true ;
              }

              description 'Configure a port LE item.' ;
              presence port-le-value ;
            }

            container port-range-items {
              list port-range-item {
                leaf port-range {
                  type acl-port-range ;

                  description 'Match packets on a given port range.' ;
                }

                description 'Configure a port range item.' ;
                key port-range ;
              }

              description 'Configure port range items.' ;
            }

            description 'Configure port pool items.' ;
          }

          container port-pool-description {
            leaf description {
              type ncd:string-with-blank {
                length 1..79 {
                  description 'Description of an access control list, support 1-79 characters.' ;
                }

              }

              description 'The description of an ACL port pool.' ;
              mandatory true ;
            }

            description 'The description of an ACL port pool.' ;
            presence "Specify acl port pool description" ;
            if-feature port-pool-description ;

            ncd:revise-date 2024-08-13 ;
          }

        }

        ncd:revise-date 2023-12-12 ;
      }

      container access-list {
        description 'Configure the Access Control List (ACL).' ;
        list ipv4-access-list {
          if-feature ipv4-feature ;

          description 'Configure the IPv4 ACL.' ;
          key acl-name ;
          leaf acl-name {
            description 'Specify the ACL name.' ;
            type acl-name-type ;

          }

          list rule {
            description 'Configure an IPv4 ACL rule.' ;
            key ruleid ;
            leaf ruleid {
              description 'Specify the rule ID.' ;
              type uint32 {
                range 1..2147483644 ;

              }

            }

            choice permit-deny {
              description 'Specify the action as either permit or deny.' ;
              case deny {
                description 'Deny the packets that match the rule.' ;
                leaf deny {
                  description 'Deny the packets that match the rule.' ;
                  type empty ;

                  mandatory true ;
                }

              }

              case permit {
                description 'Permit the packets that match the rule.' ;
                leaf permit {
                  description 'Permit the packets that match the rule.' ;
                  type empty ;

                  mandatory true ;
                }

              }

            }

            choice src-addr {
              description 'Specify source IP address.' ;
              case src-ip-address {
                description 'Source IP address.' ;
                leaf src-address {
                  description 'Source IP address.' ;
                  type ncd:ipv4-address ;

                  mandatory true ;
                }

                leaf src-wildcard {
                  description 'Source IP address wildcard.' ;
                  type ncd:ipv4-address ;

                  mandatory true ;
                }

              }

              case src-any {
                description 'Any source IP address.' ;
                leaf src-any {
                  description 'Any source IP address.' ;
                  type empty ;

                  mandatory true ;
                }

              }

              case src-url {
                if-feature url-config ;

                description 'Source URL.' ;
                leaf src-url {
                  description 'Source URL.' ;
                  type ncd:url {
                    length 1..95 ;

                  }

                  mandatory true ;
                }

              }

              case src-prefix-list {
                container src-prefix-list {
                  leaf src-prefix-list {
                    type string {
                      length 1..169 {
                        description 'Prefix list name, support 1-169 characters.' ;
                      }

                    }

                    description 'Source prefix list.' ;
                    mandatory true ;
                  }

                  description 'Source prefix list.' ;
                }

                if-feature prefix-list ;

                description 'Source prefix list.' ;
                ncd:revise-date 2023-12-12 ;
              }

            }

            leaf log {
              if-feature log-config ;

              description 'Enable/Disable the function of counting matched packet data.' ;
              type boolean ;

              default false ;
            }

            leaf time-range {
              description 'The name of the time range referenced by the ACL rule.
The referenced time range must exist.' ;
              type string {
                length 1..31 ;

              }

            }

            choice rule-type {
              description 'Specify the rule type of an IPv4 ACL rule.' ;
              case std {
                description 'Standard rule type.' ;
                leaf ipv4-protocol-std {
                  description 'Standard rule type.' ;
                  type empty ;

                  mandatory true ;
                }

              }

              case extend {
                description 'Extended rule type.' ;
                container extended {
                  description 'Extended rule type.' ;
                  choice dest-addr {
                    description 'Specify destination IP address.' ;
                    mandatory true ;
                    case dest-ip-address {
                      description 'Destination IP address.' ;
                      leaf dest-address {
                        description 'Destination IP address.' ;
                        type ncd:ipv4-address ;

                        mandatory true ;
                      }

                      leaf dest-wildcard {
                        description 'Destination IP address wildcard.' ;
                        type ncd:ipv4-address ;

                        mandatory true ;
                      }

                    }

                    case dest-any {
                      description 'Any destination IP address.' ;
                      leaf dest-any {
                        description 'Any destination IP address.' ;
                        type empty ;

                      }

                    }

                    case dest-url {
                      if-feature url-config ;

                      description 'Destination URL.' ;
                      leaf dest-url {
                        description 'Destination URL.' ;
                        type ncd:url {
                          length 1..95 ;

                        }

                      }

                    }

                    case dest-prefix-list {
                      container dest-prefix-list {
                        leaf dest-prefix-list {
                          type string {
                            length 1..169 {
                              description 'Prefix list name, support 1-169 characters.' ;
                            }

                          }

                          description 'Destination prefix list.' ;
                          mandatory true ;
                        }

                        description 'Destination prefix list.' ;
                      }

                      if-feature prefix-list ;

                      description 'Destination prefix list.' ;
                      ncd:revise-date 2023-12-12 ;
                    }

                  }

                  choice priority {
                    description 'Specify the priority of packets.
This is an optional node.
If you set this node you can choose precedence, tos, or dscp.
None means all case is invalid, And the default state is none.' ;
                    case precedence {
                      if-feature pri-value-config ;

                      description 'Specify the precedence value.' ;
                      leaf precedence {
                        description 'Specify the precedence value.' ;
                        type uint8 {
                          range 0..7 ;

                        }

                      }

                    }

                    case prec-range {
                      if-feature pri-range-config ;

                      description 'Specify the precedence, supporting single value and range configuration.' ;
                      leaf prec-range {
                        description 'Specify the precedence, supporting single value and range configuration.' ;
                        type acl-prec-range ;

                      }

                      ncd:revise-date 2015-04-20 ;
                    }

                    case tos {
                      description 'Specify the TOS value.' ;
                      leaf tos {
                        description 'Specify the TOS value.' ;
                        type uint8 {
                          range 0..15 ;

                        }

                      }

                    }

                    case dscp {
                      if-feature pri-value-config ;

                      description 'Specify the DSCP value.' ;
                      leaf dscp {
                        description 'Specify the DSCP value.' ;
                        type uint8 {
                          range 0..63 ;

                        }

                      }

                    }

                    case dscp-range {
                      if-feature pri-range-config ;

                      description 'Specify the DSCP, supporting single value and range configuration.' ;
                      leaf dscp-range {
                        description 'Specify the DSCP, supporting single value and range configuration.' ;
                        type acl-dscp-range ;

                      }

                      ncd:revise-date 2015-04-20 ;
                    }

                  }

                  leaf fragment {
                    description 'Examine non-initial fragments of packet.' ;
                    type boolean ;

                    default false ;
                  }

                  choice ttl {
                    if-feature ttl-config ;

                    status obsolete {
                      ncd:revise-date 2017-07-20 ;
                    }

                    description 'Specify the TTL value
The operator value of TTL mean 
eq(1)   : Match only packets on a given ttl value
ge(2)   : Match only packets with a no lower ttl value
le(3)   : Match only packets with a no greater ttl value
neq(6)  : Match only packets with a no equeal ttl value
range(7): Match only packet on a given ttl value range.' ;
                    case ttl-value {
                      status obsolete {
                        ncd:revise-date 2017-07-20 ;
                      }

                      description 'Specify the TTL value.' ;
                      leaf ttl-value-operator {
                        status obsolete {
                          ncd:revise-date 2017-07-20 ;
                        }

                        description 'Operator type
eq(1)   : Match only packets on a given ttl value
ge(2)   : Match only packets with a no lower ttl value
le(3)   : Match only packets with a no greater ttl value
neq(6)  : Match only packets with a no equal ttl value.' ;
                        type enumeration {
                          enum eq {
                            value 1 ;
                            description 'Equal to.' ;
                          }

                          enum ge {
                            value 2 ;
                            description 'Great than or equal to.' ;
                          }

                          enum le {
                            value 3 ;
                            description 'Less than or equal to.' ;
                          }

                          enum neq {
                            value 6 ;
                            description 'Not equal to.' ;
                          }

                        }

                        mandatory true ;
                      }

                      leaf ttl-value {
                        status obsolete {
                          ncd:revise-date 2017-07-20 ;
                        }

                        description 'TTL value.' ;
                        type uint8 {
                          range 1..255 ;

                        }

                        mandatory true ;
                      }

                    }

                    case ttl-range {
                      status obsolete {
                        ncd:revise-date 2017-07-20 ;
                      }

                      description 'Specify the TTL range.' ;
                      leaf ttl-range-operator {
                        status obsolete {
                          ncd:revise-date 2017-07-20 ;
                        }

                        description 'Operator type
range(7): Match only packet on a given ttl value range.' ;
                        type empty ;

                        mandatory true ;
                      }

                      leaf ttl-range {
                        status obsolete {
                          ncd:revise-date 2017-07-20 ;
                        }

                        description 'TTL value range.' ;
                        type acl-ttl-range ;

                        mandatory true ;
                      }

                    }

                  }

                  container time-to-live {
                    if-feature ttl-config ;

                    description 'Specify the time to live (TTL).' ;
                    presence "Specify the TTL" ;
                    choice ttl {
                      description 'Specify the TTL value
The operator value of TTL mean 
eq(1)   : Match only packets on a given ttl value
ge(2)   : Match only packets with a no lower ttl value
le(3)   : Match only packets with a no greater ttl value
neq(6)  : Match only packets with a no equeal ttl value
range(7): Match only packet on a given ttl value range.' ;
                      mandatory true ;
                      case ttl-value {
                        description 'Specify the value of the TTL.' ;
                        container ttl-value {
                          description 'Specify the value of the TTL.' ;
                          presence "Specify the TTL value" ;
                          leaf ttl-operator {
                            description 'Specify the operation type of the TTL.' ;
                            type enumeration {
                              enum eq {
                                value 1 ;
                                description 'Equal to.' ;
                              }

                              enum ge {
                                value 2 ;
                                description 'Great than or equal to.' ;
                              }

                              enum le {
                                value 3 ;
                                description 'Less than or equal to.' ;
                              }

                              enum neq {
                                value 6 ;
                                description 'Not equal to.' ;
                              }

                            }

                            mandatory true ;
                          }

                          leaf ttl-value {
                            description 'Specify the value of the TTL.' ;
                            type uint8 {
                              range 1..255 {
                                description 'TTL value, support 1-255.' ;
                              }

                            }

                            mandatory true ;
                          }

                        }

                      }

                      case ttl-range {
                        description 'Specify the range of the TTL.' ;
                        container ttl-range {
                          description 'Specify the range of the TTL.' ;
                          presence "Specify the TTL range" ;
                          leaf ttl-operator {
                            description 'Specify the operation type of the TTL.' ;
                            type enumeration {
                              enum range {
                                value 7 ;
                                description 'Range.' ;
                              }

                            }

                            mandatory true ;
                          }

                          leaf ttl-range {
                            description 'Specify the range of the TTL.' ;
                            type acl-ttl-range ;

                            mandatory true ;
                          }

                        }

                      }

                    }

                    ncd:revise-date 2017-07-20 ;
                  }

                  choice ipv4-protocol-type {
                    description 'IPv4 protocol type.' ;
                    mandatory true ;
                    case udp-tcp {
                      description 'The protocol number is UDP or TCP.' ;
                      container udp-tcp {
                        description 'The protocol number is UDP or TCP.' ;
                        choice udpOrTcp {
                          description 'The protocol number is UDP or TCP.' ;
                          mandatory true ;
                          case udp {
                            description 'The protocol number is UDP.' ;
                            leaf ipv4-protocol-udp {
                              description 'The protocol number is UDP.' ;
                              type empty ;

                            }

                          }

                          case tcp {
                            description 'The protocol number is TCP.' ;
                            leaf ipv4-protocol-tcp {
                              description 'The protocol number is TCP.' ;
                              type empty ;

                              mandatory true ;
                            }

                            leaf established {
                              description 'Specify the flag that indicates whether the TCP protocol initiates a connection establishment.' ;
                              type boolean ;

                              default false ;
                            }

                            leaf rst {
                              description 'Specify the RST flag.' ;
                              type acl-tcp-flag ;

                            }

                            leaf ack {
                              description 'Specify the ACK flag.' ;
                              type acl-tcp-flag ;

                            }

                            leaf fin {
                              description 'Specify the FIN flag.' ;
                              type acl-tcp-flag ;

                            }

                            leaf syn {
                              description 'Specify the SYN flag.' ;
                              type acl-tcp-flag ;

                            }

                            leaf psh {
                              description 'Specify the PSH flag.' ;
                              type acl-tcp-flag ;

                            }

                            leaf urg {
                              description 'Specify the URG flag.' ;
                              type acl-tcp-flag ;

                            }

                          }

                        }

                        choice src-port {
                          status obsolete {
                            ncd:revise-date 2017-07-20 ;
                          }

                          description 'Specify source port.
When the value of operator is invalid, it means match all port range,
the other value of operator means
eq(1)   : match only packets on a given port number
ge(2)   : match only packets with a no lower port number
le(3)   : match only packets with a no greater port number
range(7): match only packet on a given port range.' ;
                          case src-value {
                            status obsolete {
                              ncd:revise-date 2017-07-20 ;
                            }

                            description 'Configure port number.' ;
                            leaf src-value-operator {
                              status obsolete {
                                ncd:revise-date 2017-07-20 ;
                              }

                              description 'Operator type
eq(1)   : match only packets on a given port number
ge(2)   : match only packets with a no lower port number
le(3)   : match only packets with a no greater port number.' ;
                              type enumeration {
                                enum eq {
                                  value 1 ;
                                  description 'Equal to.' ;
                                }

                                enum ge {
                                  value 2 ;
                                  description 'Great than or equal to.' ;
                                }

                                enum le {
                                  value 3 ;
                                  description 'Less than or equal to.' ;
                                }

                              }

                              mandatory true ;
                            }

                            leaf src-port-number {
                              status obsolete {
                                ncd:revise-date 2017-07-20 ;
                              }

                              description 'Port number.' ;
                              type uint16 {
                                range 0..65535 ;

                              }

                              mandatory true ;
                            }

                          }

                          case src-range {
                            status obsolete {
                              ncd:revise-date 2017-07-20 ;
                            }

                            description 'Configure port range.' ;
                            leaf src-range-operator {
                              status obsolete {
                                ncd:revise-date 2017-07-20 ;
                              }

                              description 'Operator type
range(7): match only packet on a given port range.' ;
                              type empty ;

                              mandatory true ;
                            }

                            leaf src-port-range {
                              status obsolete {
                                ncd:revise-date 2017-07-20 ;
                              }

                              description 'Port range.' ;
                              type acl-port-range ;

                              mandatory true ;
                            }

                          }

                        }

                        choice dest-port {
                          status obsolete {
                            ncd:revise-date 2017-07-20 ;
                          }

                          description 'Specify destination port.
When the value of operator is invalid, it means match all port range,
the other value of operator means
eq(1)   : match only packets on a given port number
ge(2)   : match only packets with a no lower port number
le(3)   : match only packets with a no greater port number
range(7): match only packet on a given port range.' ;
                          case dest-value {
                            status obsolete {
                              ncd:revise-date 2017-07-20 ;
                            }

                            description 'Configure port number.' ;
                            leaf dest-value-operator {
                              status obsolete {
                                ncd:revise-date 2017-07-20 ;
                              }

                              description 'Operator type
eq(1)   : match only packets on a given port number
ge(2)   : match only packets with a no lower port number
le(3)   : match only packets with a no greater port number.' ;
                              type enumeration {
                                enum eq {
                                  value 1 ;
                                  description 'Equal to.' ;
                                }

                                enum ge {
                                  value 2 ;
                                  description 'Great than or equal to.' ;
                                }

                                enum le {
                                  value 3 ;
                                  description 'Less than or equal to.' ;
                                }

                              }

                              mandatory true ;
                            }

                            leaf dest-port-number {
                              status obsolete {
                                ncd:revise-date 2017-07-20 ;
                              }

                              description 'Port number.' ;
                              type uint16 {
                                range 0..65535 ;

                              }

                              mandatory true ;
                            }

                          }

                          case dest-range {
                            status obsolete {
                              ncd:revise-date 2017-07-20 ;
                            }

                            description 'Configure port range.' ;
                            leaf dest-range-operator {
                              status obsolete {
                                ncd:revise-date 2017-07-20 ;
                              }

                              description 'Operator type
range(7): match only packet on a given port range.' ;
                              type empty ;

                              mandatory true ;
                            }

                            leaf dest-port-range {
                              status obsolete {
                                ncd:revise-date 2017-07-20 ;
                              }

                              description 'Port range.' ;
                              type acl-port-range ;

                              mandatory true ;
                            }

                          }

                        }

                        container source-port {
                          description 'Specify the source port.' ;
                          presence "Specify source port" ;
                          choice source-port {
                            description 'Specify the source port.' ;
                            mandatory true ;
                            case src-port-value {
                              description 'Specify the value of the source port number.' ;
                              container src-port-value {
                                description 'Specify the value of the source port number.' ;
                                presence "Configure port number" ;
                                leaf src-port-operator {
                                  description 'Specify the operation type of the source port number.' ;
                                  type enumeration {
                                    enum eq {
                                      value 1 ;
                                      description 'Equal to.' ;
                                    }

                                    enum ge {
                                      value 2 ;
                                      description 'Great than or equal to.' ;
                                    }

                                    enum le {
                                      value 3 ;
                                      description 'Less than or equal to.' ;
                                    }

                                  }

                                  mandatory true ;
                                }

                                leaf src-port-value {
                                  description 'Specify the value of the source port number.' ;
                                  type uint16 {
                                    range 0..65535 ;

                                  }

                                  mandatory true ;
                                }

                              }

                            }

                            case src-port-range {
                              description 'Specify the range of the source port number.' ;
                              container src-port-range {
                                description 'Specify the range of the source port number.' ;
                                presence "Configure port range" ;
                                leaf src-port-operator {
                                  description 'Specify the operation type of the source port number.' ;
                                  type enumeration {
                                    enum range {
                                      value 7 ;
                                      description 'Range.' ;
                                    }

                                  }

                                  mandatory true ;
                                }

                                leaf src-port-range {
                                  description 'Specify the range of the source port number.' ;
                                  type acl-port-range ;

                                  mandatory true ;
                                }

                              }

                            }

                            case src-port-pool {
                              container src-port-pool {
                                leaf port-pool-name {
                                  type acl-port-pool-name ;

                                  description 'Specify the name of the source port pool.
The referenced port pool must exist.' ;
                                  mandatory true ;
                                }

                                description 'Specify the source port pool.' ;
                                presence "Configure source port pool" ;
                              }

                              description 'Specify the source port pool.' ;
                              if-feature port-pool ;

                              ncd:revise-date 2023-12-12 ;
                            }

                          }

                          ncd:revise-date 2017-07-20 ;
                        }

                        container destination-port {
                          description 'Specify the destination port.' ;
                          presence "Specify destination port" ;
                          choice destination-port {
                            description 'Specify the destination port.' ;
                            mandatory true ;
                            case dst-port-value {
                              description 'Specify the value of the destination port number.' ;
                              container dst-port-value {
                                description 'Specify the value of the destination port number.' ;
                                presence "Configure port number" ;
                                leaf dst-port-operator {
                                  description 'Specify the operation type of the destination port number.' ;
                                  type enumeration {
                                    enum eq {
                                      value 1 ;
                                      description 'Equal to.' ;
                                    }

                                    enum ge {
                                      value 2 ;
                                      description 'Great than or equal to.' ;
                                    }

                                    enum le {
                                      value 3 ;
                                      description 'Less than or equal to.' ;
                                    }

                                  }

                                  mandatory true ;
                                }

                                leaf dst-port-value {
                                  description 'Specify the value of the destination port number.' ;
                                  type uint16 {
                                    range 0..65535 ;

                                  }

                                  mandatory true ;
                                }

                              }

                            }

                            case dst-port-range {
                              description 'Specify the range of the destination port number.' ;
                              container dst-port-range {
                                description 'Specify the range of the destination port number.' ;
                                presence "Configure port range" ;
                                leaf dst-port-operator {
                                  description 'Specify the operation type of the destination port number.' ;
                                  type enumeration {
                                    enum range {
                                      value 7 ;
                                      description 'Range.' ;
                                    }

                                  }

                                  mandatory true ;
                                }

                                leaf dst-port-range {
                                  description 'Specify the range of the destination port number.' ;
                                  type acl-port-range ;

                                  mandatory true ;
                                }

                              }

                            }

                            case dst-port-pool {
                              container dst-port-pool {
                                leaf port-pool-name {
                                  type acl-port-pool-name ;

                                  description 'Specify the name of the destination port pool.
The referenced port pool must exist.' ;
                                  mandatory true ;
                                }

                                description 'Specify the destination port pool.' ;
                                presence "Configure destination port pool" ;
                              }

                              description 'Specify the destination port pool.' ;
                              if-feature port-pool ;

                              ncd:revise-date 2023-12-12 ;
                            }

                          }

                          ncd:revise-date 2017-07-20 ;
                        }

                      }

                    }

                    case icmp {
                      description 'The protocol number is ICMP.' ;
                      leaf ipv4-protocol-icmp {
                        description 'The protocol number is ICMP.' ;
                        type empty ;

                        mandatory true ;
                      }

                      container icmp-conf {
                        description 'Specify the ICMP type and ICMP code.' ;
                        presence "config icmp type and code" ;
                        leaf icmp-type {
                          description 'Specify the ICMP type.' ;
                          type uint16 {
                            range 0..255 ;

                          }

                          mandatory true ;
                        }

                        leaf icmp-code {
                          description 'Specify the ICMP code.' ;
                          type uint16 {
                            range 0..255 ;

                          }

                        }

                      }

                      container icmp-port {
                        description 'Specify the port.' ;
                        choice src-port {
                          status obsolete {
                            ncd:revise-date 2017-07-20 ;
                          }

                          description 'Specify source port.
When the value of operator is invalid, it means match all port range,
the other value of operator means
eq(1)   : match only packets on a given port number
ge(2)   : match only packets with a no lower port number
le(3)   : match only packets with a no greater port number
range(7): match only packet on a given port range.' ;
                          case src-value {
                            status obsolete {
                              ncd:revise-date 2017-07-20 ;
                            }

                            description 'Configure port number.' ;
                            leaf src-value-operator {
                              status obsolete {
                                ncd:revise-date 2017-07-20 ;
                              }

                              description 'Operator type
eq(1)   : match only packets on a given port number
ge(2)   : match only packets with a no lower port number
le(3)   : match only packets with a no greater port number.' ;
                              type enumeration {
                                enum eq {
                                  value 1 ;
                                  description 'Equal to.' ;
                                }

                                enum ge {
                                  value 2 ;
                                  description 'Great than or equal to.' ;
                                }

                                enum le {
                                  value 3 ;
                                  description 'Less than or equal to.' ;
                                }

                              }

                              mandatory true ;
                            }

                            leaf src-port-number {
                              status obsolete {
                                ncd:revise-date 2017-07-20 ;
                              }

                              description 'Port number.' ;
                              type uint16 {
                                range 0..65535 ;

                              }

                              mandatory true ;
                            }

                          }

                          case src-range {
                            status obsolete {
                              ncd:revise-date 2017-07-20 ;
                            }

                            description 'Configure port range.' ;
                            leaf src-range-operator {
                              status obsolete {
                                ncd:revise-date 2017-07-20 ;
                              }

                              description 'Operator type
range(7): match only packet on a given port range.' ;
                              type empty ;

                              mandatory true ;
                            }

                            leaf src-port-range {
                              status obsolete {
                                ncd:revise-date 2017-07-20 ;
                              }

                              description 'Port range.' ;
                              type acl-port-range ;

                              mandatory true ;
                            }

                          }

                        }

                        choice dest-port {
                          status obsolete {
                            ncd:revise-date 2017-07-20 ;
                          }

                          description 'Specify destination port.
When the value of operator is invalid, it means match all port range,
the other value of operator means
eq(1)   : match only packets on a given port number
ge(2)   : match only packets with a no lower port number
le(3)   : match only packets with a no greater port number
range(7): match only packet on a given port range.' ;
                          case dest-value {
                            status obsolete {
                              ncd:revise-date 2017-07-20 ;
                            }

                            description 'Configure port number.' ;
                            leaf dest-value-operator {
                              status obsolete {
                                ncd:revise-date 2017-07-20 ;
                              }

                              description 'Operator type
eq(1)   : match only packets on a given port number
ge(2)   : match only packets with a no lower port number
le(3)   : match only packets with a no greater port number.' ;
                              type enumeration {
                                enum eq {
                                  value 1 ;
                                  description 'Equal to.' ;
                                }

                                enum ge {
                                  value 2 ;
                                  description 'Great than or equal to.' ;
                                }

                                enum le {
                                  value 3 ;
                                  description 'Less than or equal to.' ;
                                }

                              }

                              mandatory true ;
                            }

                            leaf dest-port-number {
                              status obsolete {
                                ncd:revise-date 2017-07-20 ;
                              }

                              description 'Port number.' ;
                              type uint16 {
                                range 0..65535 ;

                              }

                              mandatory true ;
                            }

                          }

                          case dest-range {
                            status obsolete {
                              ncd:revise-date 2017-07-20 ;
                            }

                            description 'Configure port range.' ;
                            leaf dest-range-operator {
                              status obsolete {
                                ncd:revise-date 2017-07-20 ;
                              }

                              description 'Operator type
range(7): match only packet on a given port range.' ;
                              type empty ;

                              mandatory true ;
                            }

                            leaf dest-port-range {
                              status obsolete {
                                ncd:revise-date 2017-07-20 ;
                              }

                              description 'Port range.' ;
                              type acl-port-range ;

                              mandatory true ;
                            }

                          }

                        }

                        container source-port {
                          description 'Specify the source port.' ;
                          presence "Specify source port" ;
                          choice source-port {
                            description 'Specify the source port.' ;
                            mandatory true ;
                            case src-port-value {
                              description 'Specify the value of the source port number.' ;
                              container src-port-value {
                                description 'Specify the value of the source port number.' ;
                                presence "Configure port number" ;
                                leaf src-port-operator {
                                  description 'Specify the operation type of the source port number.' ;
                                  type enumeration {
                                    enum eq {
                                      value 1 ;
                                      description 'Equal to.' ;
                                    }

                                    enum ge {
                                      value 2 ;
                                      description 'Great than or equal to.' ;
                                    }

                                    enum le {
                                      value 3 ;
                                      description 'Less than or equal to.' ;
                                    }

                                  }

                                  mandatory true ;
                                }

                                leaf src-port-value {
                                  description 'Specify the value of the source port number.' ;
                                  type uint16 {
                                    range 0..65535 ;

                                  }

                                  mandatory true ;
                                }

                              }

                            }

                            case src-port-range {
                              description 'Specify the range of the source port number.' ;
                              container src-port-range {
                                description 'Specify the range of the source port number.' ;
                                presence "Configure port range" ;
                                leaf src-port-operator {
                                  description 'Specify the operation type of the source port number.' ;
                                  type enumeration {
                                    enum range {
                                      value 7 ;
                                      description 'Range.' ;
                                    }

                                  }

                                  mandatory true ;
                                }

                                leaf src-port-range {
                                  description 'Specify the range of the source port number.' ;
                                  type acl-port-range ;

                                  mandatory true ;
                                }

                              }

                            }

                            case src-port-pool {
                              container src-port-pool {
                                leaf port-pool-name {
                                  type acl-port-pool-name ;

                                  description 'Specify the name of the source port pool.
The referenced port pool must exist.' ;
                                  mandatory true ;
                                }

                                description 'Specify the source port pool.' ;
                                presence "Configure source port pool" ;
                              }

                              description 'Specify the source port pool.' ;
                              if-feature port-pool ;

                              ncd:revise-date 2023-12-12 ;
                            }

                          }

                          ncd:revise-date 2017-07-20 ;
                        }

                        container destination-port {
                          description 'Specify the destination port.' ;
                          presence "Specify destination port" ;
                          choice destination-port {
                            description 'Specify the destination port.' ;
                            mandatory true ;
                            case dst-port-value {
                              description 'Specify the value of the destination port number.' ;
                              container dst-port-value {
                                description 'Specify the value of the destination port number.' ;
                                presence "Configure port number" ;
                                leaf dst-port-operator {
                                  description 'Specify the operation type of the destination port number.' ;
                                  type enumeration {
                                    enum eq {
                                      value 1 ;
                                      description 'Equal to.' ;
                                    }

                                    enum ge {
                                      value 2 ;
                                      description 'Great than or equal to.' ;
                                    }

                                    enum le {
                                      value 3 ;
                                      description 'Less than or equal to.' ;
                                    }

                                  }

                                  mandatory true ;
                                }

                                leaf dst-port-value {
                                  description 'Specify the value of the destination port number.' ;
                                  type uint16 {
                                    range 0..65535 ;

                                  }

                                  mandatory true ;
                                }

                              }

                            }

                            case dst-port-range {
                              description 'Specify the range of the destination port number.' ;
                              container dst-port-range {
                                description 'Specify the range of the destination port number.' ;
                                presence "Configure port range" ;
                                leaf dst-port-operator {
                                  description 'Specify the operation type of the destination port number.' ;
                                  type enumeration {
                                    enum range {
                                      value 7 ;
                                      description 'Range.' ;
                                    }

                                  }

                                  mandatory true ;
                                }

                                leaf dst-port-range {
                                  description 'Specify the range of the destination port number.' ;
                                  type acl-port-range ;

                                  mandatory true ;
                                }

                              }

                            }

                            case dst-port-pool {
                              container dst-port-pool {
                                leaf port-pool-name {
                                  type acl-port-pool-name ;

                                  description 'Specify the name of the destination port pool.
The referenced port pool must exist.' ;
                                  mandatory true ;
                                }

                                description 'Specify the destination port pool.' ;
                                presence "Configure destination port pool" ;
                              }

                              description 'Specify the destination port pool.' ;
                              if-feature port-pool ;

                              ncd:revise-date 2023-12-12 ;
                            }

                          }

                          ncd:revise-date 2017-07-20 ;
                        }

                        ncd:revise-date 2016-01-13 ;
                      }

                    }

                    case ip {
                      description 'The protocol number is a value excluding TCP, UDP, and ICMP.' ;
                      leaf ipv4-protocol {
                        description 'Specify the IP protocol type excluding TCP, UDP, and ICMP.' ;
                        type uint16 {
                          range "0 | 2..5 | 7..16 | 18..255 | 65535" ;

                        }

                        mandatory true ;
                      }

                      container port {
                        description 'Specify the port.' ;
                        choice src-port {
                          status obsolete {
                            ncd:revise-date 2017-07-20 ;
                          }

                          description 'Specify source port.
When the value of operator is invalid, it means match all port range,
the other value of operator means
eq(1)   : match only packets on a given port number
ge(2)   : match only packets with a no lower port number
le(3)   : match only packets with a no greater port number
range(7): match only packet on a given port range.' ;
                          case src-value {
                            status obsolete {
                              ncd:revise-date 2017-07-20 ;
                            }

                            description 'Configure port number.' ;
                            leaf src-value-operator {
                              status obsolete {
                                ncd:revise-date 2017-07-20 ;
                              }

                              description 'Operator type
eq(1)   : match only packets on a given port number
ge(2)   : match only packets with a no lower port number
le(3)   : match only packets with a no greater port number.' ;
                              type enumeration {
                                enum eq {
                                  value 1 ;
                                  description 'Equal to.' ;
                                }

                                enum ge {
                                  value 2 ;
                                  description 'Great than or equal to.' ;
                                }

                                enum le {
                                  value 3 ;
                                  description 'Less than or equal to.' ;
                                }

                              }

                              mandatory true ;
                            }

                            leaf src-port-number {
                              status obsolete {
                                ncd:revise-date 2017-07-20 ;
                              }

                              description 'Port number.' ;
                              type uint16 {
                                range 0..65535 ;

                              }

                              mandatory true ;
                            }

                          }

                          case src-range {
                            status obsolete {
                              ncd:revise-date 2017-07-20 ;
                            }

                            description 'Configure port range.' ;
                            leaf src-range-operator {
                              status obsolete {
                                ncd:revise-date 2017-07-20 ;
                              }

                              description 'Operator type
range(7): match only packet on a given port range.' ;
                              type empty ;

                              mandatory true ;
                            }

                            leaf src-port-range {
                              status obsolete {
                                ncd:revise-date 2017-07-20 ;
                              }

                              description 'Port range.' ;
                              type acl-port-range ;

                              mandatory true ;
                            }

                          }

                        }

                        choice dest-port {
                          status obsolete {
                            ncd:revise-date 2017-07-20 ;
                          }

                          description 'Specify destination port.
When the value of operator is invalid, it means match all port range,
the other value of operator means
eq(1)   : match only packets on a given port number
ge(2)   : match only packets with a no lower port number
le(3)   : match only packets with a no greater port number
range(7): match only packet on a given port range.' ;
                          case dest-value {
                            status obsolete {
                              ncd:revise-date 2017-07-20 ;
                            }

                            description 'Configure port number.' ;
                            leaf dest-value-operator {
                              status obsolete {
                                ncd:revise-date 2017-07-20 ;
                              }

                              description 'Operator type
eq(1)   : match only packets on a given port number
ge(2)   : match only packets with a no lower port number
le(3)   : match only packets with a no greater port number.' ;
                              type enumeration {
                                enum eq {
                                  value 1 ;
                                  description 'Equal to.' ;
                                }

                                enum ge {
                                  value 2 ;
                                  description 'Great than or equal to.' ;
                                }

                                enum le {
                                  value 3 ;
                                  description 'Less than or equal to.' ;
                                }

                              }

                              mandatory true ;
                            }

                            leaf dest-port-number {
                              status obsolete {
                                ncd:revise-date 2017-07-20 ;
                              }

                              description 'Port number.' ;
                              type uint16 {
                                range 0..65535 ;

                              }

                              mandatory true ;
                            }

                          }

                          case dest-range {
                            status obsolete {
                              ncd:revise-date 2017-07-20 ;
                            }

                            description 'Configure port range.' ;
                            leaf dest-range-operator {
                              status obsolete {
                                ncd:revise-date 2017-07-20 ;
                              }

                              description 'Operator type
range(7): match only packet on a given port range.' ;
                              type empty ;

                              mandatory true ;
                            }

                            leaf dest-port-range {
                              status obsolete {
                                ncd:revise-date 2017-07-20 ;
                              }

                              description 'Port range.' ;
                              type acl-port-range ;

                              mandatory true ;
                            }

                          }

                        }

                        container source-port {
                          description 'Specify the source port.' ;
                          presence "Specify source port" ;
                          choice source-port {
                            description 'Specify the source port.' ;
                            mandatory true ;
                            case src-port-value {
                              description 'Specify the value of the source port number.' ;
                              container src-port-value {
                                description 'Specify the value of the source port number.' ;
                                presence "Configure port number" ;
                                leaf src-port-operator {
                                  description 'Specify the operation type of the source port number.' ;
                                  type enumeration {
                                    enum eq {
                                      value 1 ;
                                      description 'Equal to.' ;
                                    }

                                    enum ge {
                                      value 2 ;
                                      description 'Great than or equal to.' ;
                                    }

                                    enum le {
                                      value 3 ;
                                      description 'Less than or equal to.' ;
                                    }

                                  }

                                  mandatory true ;
                                }

                                leaf src-port-value {
                                  description 'Specify the value of the source port number.' ;
                                  type uint16 {
                                    range 0..65535 ;

                                  }

                                  mandatory true ;
                                }

                              }

                            }

                            case src-port-range {
                              description 'Specify the range of the source port number.' ;
                              container src-port-range {
                                description 'Specify the range of the source port number.' ;
                                presence "Configure port range" ;
                                leaf src-port-operator {
                                  description 'Specify the operation type of the source port number.' ;
                                  type enumeration {
                                    enum range {
                                      value 7 ;
                                      description 'Range.' ;
                                    }

                                  }

                                  mandatory true ;
                                }

                                leaf src-port-range {
                                  description 'Specify the range of the source port number.' ;
                                  type acl-port-range ;

                                  mandatory true ;
                                }

                              }

                            }

                            case src-port-pool {
                              container src-port-pool {
                                leaf port-pool-name {
                                  type acl-port-pool-name ;

                                  description 'Specify the name of the source port pool.
The referenced port pool must exist.' ;
                                  mandatory true ;
                                }

                                description 'Specify the source port pool.' ;
                                presence "Configure source port pool" ;
                              }

                              description 'Specify the source port pool.' ;
                              if-feature port-pool ;

                              ncd:revise-date 2023-12-12 ;
                            }

                          }

                          ncd:revise-date 2017-07-20 ;
                        }

                        container destination-port {
                          description 'Specify the destination port.' ;
                          presence "Specify destination port" ;
                          choice destination-port {
                            description 'Specify the destination port.' ;
                            mandatory true ;
                            case dst-port-value {
                              description 'Specify the value of the destination port number.' ;
                              container dst-port-value {
                                description 'Specify the value of the destination port number.' ;
                                presence "Configure port number" ;
                                leaf dst-port-operator {
                                  description 'Specify the operation type of the destination port number.' ;
                                  type enumeration {
                                    enum eq {
                                      value 1 ;
                                      description 'Equal to.' ;
                                    }

                                    enum ge {
                                      value 2 ;
                                      description 'Great than or equal to.' ;
                                    }

                                    enum le {
                                      value 3 ;
                                      description 'Less than or equal to.' ;
                                    }

                                  }

                                  mandatory true ;
                                }

                                leaf dst-port-value {
                                  description 'Specify the value of the destination port number.' ;
                                  type uint16 {
                                    range 0..65535 ;

                                  }

                                  mandatory true ;
                                }

                              }

                            }

                            case dst-port-range {
                              description 'Specify the range of the destination port number.' ;
                              container dst-port-range {
                                description 'Specify the range of the destination port number.' ;
                                presence "Configure port range" ;
                                leaf dst-port-operator {
                                  description 'Specify the operation type of the destination port number.' ;
                                  type enumeration {
                                    enum range {
                                      value 7 ;
                                      description 'Range.' ;
                                    }

                                  }

                                  mandatory true ;
                                }

                                leaf dst-port-range {
                                  description 'Specify the range of the destination port number.' ;
                                  type acl-port-range ;

                                  mandatory true ;
                                }

                              }

                            }

                            case dst-port-pool {
                              container dst-port-pool {
                                leaf port-pool-name {
                                  type acl-port-pool-name ;

                                  description 'Specify the name of the destination port pool.
The referenced port pool must exist.' ;
                                  mandatory true ;
                                }

                                description 'Specify the destination port pool.' ;
                                presence "Configure destination port pool" ;
                              }

                              description 'Specify the destination port pool.' ;
                              if-feature port-pool ;

                              ncd:revise-date 2023-12-12 ;
                            }

                          }

                          ncd:revise-date 2017-07-20 ;
                        }

                        ncd:revise-date 2016-01-13 ;
                      }

                    }

                  }

                  container packet-length {
                    description 'Specify the packet length.' ;
                    presence "Configure packet length" ;
                    choice packet-length {
                      description 'Specify the packet length.' ;
                      mandatory true ;
                      case packet-length-value {
                        description 'Specify the value of the packet length.' ;
                        container packet-length-value {
                          description 'Specify the value of the packet length.' ;
                          presence "Configure packet length" ;
                          leaf packet-length-oper {
                            description 'Specify the operation type of the packet length.' ;
                            type acl-pktlen-opr ;

                            mandatory true ;
                          }

                          leaf packet-length-value {
                            description 'Specify the value of the packet length.' ;
                            type uint16 {
                              range 1..65535 {
                                description 'Packet length value, support 1-65535.' ;
                              }

                            }

                            mandatory true ;
                          }

                        }

                      }

                      case packet-length-range {
                        description 'Specify the range of the packet length.' ;
                        container packet-length-range {
                          description 'Specify the range of the packet length.' ;
                          presence "Configure packet length" ;
                          leaf packet-length-oper {
                            description 'Specify the operation type of the packet length.' ;
                            type enumeration {
                              enum range {
                                value 7 ;
                                description 'Match only packets on a given packet length range.' ;
                              }

                            }

                            mandatory true ;
                          }

                          leaf packet-length-range {
                            description 'Specify the range of the packet length.' ;
                            type acl-pktlen-range ;

                            mandatory true ;
                          }

                        }

                      }

                    }

                    ncd:revise-date 2017-06-20 ;
                  }

                  leaf monitor-group-id {
                    description 'Specify the monitor group ID.' ;
                    type uint8 {
                      range 1..63 ;

                    }

                    ncd:revise-date 2019-11-26 ;
                  }

                  leaf source-monitor-group-id {
                    description 'Specify the source monitor group ID.' ;
                    type uint8 {
                      range 1..63 ;

                    }

                    ncd:revise-date 2019-12-11 ;
                  }

                }

              }

            }

            leaf description {
              description 'The description of the rule.' ;
              type ncd:string-with-blank {
                length 1..70 {
                  description 'Direction for use, support 1-70 characters.' ;
                }

              }

              ncd:revise-date 2016-08-18 ;
            }

            choice vrf-config {
              description 'VPN Routing/Forwarding instance.' ;
              case vrf-config-choice-clear {
                description 'Remove value of any entities which belong to any case within this choice.' ;
                container vrf-config-all-clear {
                  description 'Remove this entity means to remove value of any entities which belong to any case within this choice.' ;
                  presence vrf-config-all-clear ;
                }

                ncd:revise-date 2020-08-17 ;
              }

              case vrf {
                description 'Specify the VRF instance name.' ;
                leaf vrf {
                  description 'Specify the VRF instance name.
The referenced VRF must exist.' ;
                  type acl-vrf-name ;

                }

              }

              case vrf-dcn {
                description 'Specify it for DCN VRF.' ;
                leaf vrf-dcn {
                  description 'Specify it for DCN VRF.' ;
                  type empty ;

                }

                ncd:revise-date 2020-08-17 ;
              }

              ncd:revise-date 2017-06-20 ;
            }

            container policy-route-id {
              description 'Specify the policy route ID.' ;
              presence "Specify the policy route id" ;
              choice policy-route-id {
                description 'Policy route ID, including source policy route ID and destination policy route ID.' ;
                mandatory true ;
                case src {
                  description 'Source policy route ID.' ;
                  container source {
                    description 'Specify the source policy route ID.' ;
                    presence "Specify the source policy route id" ;
                    leaf src-policy-route-id {
                      description 'Specify the source policy route ID.' ;
                      type uint8 {
                        range 1..63 ;

                      }

                      mandatory true ;
                    }

                  }

                }

                case dest {
                  description 'Destination policy route ID.' ;
                  container destination {
                    description 'Specify the destination policy route ID.' ;
                    presence "Specify the destination policy route id" ;
                    leaf dest-policy-route-id {
                      description 'Specify the destination policy route ID.' ;
                      type uint8 {
                        range 1..63 ;

                      }

                      mandatory true ;
                    }

                  }

                }

              }

              ncd:revise-date 2019-09-10 ;
            }

          }

          container acl-description {
            description 'The description of the ACL.' ;
            presence "Specify acl description" ;
            leaf acl-description {
              description 'The description of the ACL.' ;
              type ncd:string-with-blank {
                length 1..79 {
                  description 'Description of an access control list, support 1-79 characters.' ;
                }

              }

              mandatory true ;
            }

            ncd:revise-date 2020-06-18 ;
          }

        }

        list ipv4-mixed-access-list {
          if-feature ipv4-mixed-feature ;

          description 'Configure the IPv4 mixed ACL.' ;
          key acl-name ;
          leaf acl-name {
            description 'Specify the ACL name.' ;
            type acl-name-type ;

          }

          list rule {
            description 'Configure an IPv4 mixed ACL rule.' ;
            key ruleid ;
            leaf ruleid {
              description 'Specify the rule ID.' ;
              type uint32 {
                range 1..2147483644 ;

              }

            }

            choice link-prot {
              description 'Specify the link protocol type.' ;
              case link-protocol {
                description 'Specify the link protocol type.' ;
                leaf link-protocol {
                  description 'Specify the link protocol type.' ;
                  type uint32 {
                    range 1536..65535 ;

                  }

                }

              }

              case link-protocol-hex {
                if-feature link-prot-hex-config ;

                status obsolete {
                  ncd:revise-date 2017-01-04 ;
                }

                description 'Specify the link protocol in hexadecimal format.' ;
                leaf link-protocol-hex {
                  description 'Specify the link protocol in hexadecimal format.
' ;
                  type ncd:hex ;

                }

              }

              case sap {
                if-feature sap-feature ;

                description 'Specify the Service Access Point (SAP).' ;
                container dsap-ssap {
                  description 'Specify the Destination Service Access Point (DSAP) and the Source Service Access Point (SSAP).' ;
                  presence "config dsap and ssap" ;
                  leaf dsap {
                    description 'Specify the DSAP.' ;
                    type uint16 {
                      range 0..255 ;

                    }

                    mandatory true ;
                  }

                  leaf ssap {
                    description 'Specify the SSAP.' ;
                    type uint16 {
                      range 0..255 ;

                    }

                    mandatory true ;
                  }

                }

                ncd:revise-date 2017-07-12 ;
              }

            }

            choice src-mac-addr {
              description 'Specify source MAC address.' ;
              case src-mac-addr {
                description 'Source MAC address.' ;
                leaf src-mac-address {
                  description 'Source MAC address.' ;
                  type ncd:mac-address ;

                  mandatory true ;
                }

                leaf src-mac-wildcard {
                  description 'Source MAC address wildcard.' ;
                  type ncd:mac-address ;

                  mandatory true ;
                }

              }

              case src-mac-any {
                description 'Any source MAC address.' ;
                leaf src-mac-any {
                  description 'Any source MAC address.' ;
                  type empty ;

                }

              }

              case src-mac-range {
                if-feature mac-range-config ;

                description 'Source MAC address range.' ;
                leaf src-mac-from1 {
                  description 'The starting value of the first range of source MAC address.' ;
                  type ncd:mac-address ;

                  mandatory true ;
                }

                leaf src-mac-to1 {
                  description 'The ending value of the first range of source MAC address.' ;
                  type ncd:mac-address ;

                  mandatory true ;
                }

                container src-mac-range2 {
                  description 'The second range of source MAC address.' ;
                  presence "config second source mac range" ;
                  leaf src-mac-from2 {
                    description 'The starting value of the second range of source MAC address.' ;
                    type ncd:mac-address ;

                    mandatory true ;
                  }

                  leaf src-mac-to2 {
                    description 'The ending value of the second range of source MAC address.' ;
                    type ncd:mac-address ;

                    mandatory true ;
                  }

                }

              }

            }

            choice dest-mac-addr {
              description 'Specify destination MAC address.' ;
              case dest-mac-addr {
                description 'Destination MAC address.' ;
                leaf dest-mac-address {
                  description 'Destination MAC address.' ;
                  type ncd:mac-address ;

                  mandatory true ;
                }

                leaf dest-mac-wildcard {
                  description 'Destination MAC address wildcard.' ;
                  type ncd:mac-address ;

                  mandatory true ;
                }

              }

              case dest-mac-any {
                description 'Any destination MAC address.' ;
                leaf dest-mac-any {
                  description 'Any destination MAC address.' ;
                  type empty ;

                }

              }

              case dest-mac-range {
                if-feature mac-range-config ;

                description 'Destination MAC address range.' ;
                leaf dest-mac-from1 {
                  description 'The starting value of the first range of destination MAC address.' ;
                  type ncd:mac-address ;

                  mandatory true ;
                }

                leaf dest-mac-to1 {
                  description 'The ending value of the first range of destination MAC address.' ;
                  type ncd:mac-address ;

                  mandatory true ;
                }

                container dest-mac-range2 {
                  description 'The second range of destination MAC address.' ;
                  presence "config second destination mac range" ;
                  leaf dest-mac-from2 {
                    description 'The starting value of the second range of destination MAC address.' ;
                    type ncd:mac-address ;

                    mandatory true ;
                  }

                  leaf dest-mac-to2 {
                    description 'The ending value of the second range of destination MAC address.' ;
                    type ncd:mac-address ;

                    mandatory true ;
                  }

                }

              }

            }

            leaf inner-cos {
              if-feature ipv4-mixed-cos-value ;

              description 'Specify the inner-layer CoS value.' ;
              type uint8 {
                range 0..7 ;

              }

            }

            leaf inner-cos-range {
              if-feature ipv4-mixed-cos-range ;

              description 'Specify the range of inner-layer CoS, supporting single value and range configuration.' ;
              type acl-cos-range ;

              ncd:revise-date 2015-04-20 ;
            }

            leaf outer-cos {
              if-feature ipv4-mixed-cos-value ;

              description 'Specify the outer-layer CoS value.' ;
              type uint8 {
                range 0..7 ;

              }

            }

            leaf outer-cos-range {
              if-feature ipv4-mixed-cos-range ;

              description 'Specify the range of outer-layer CoS, supporting single value and range configuration.' ;
              type acl-cos-range ;

              ncd:revise-date 2015-04-20 ;
            }

            choice vlan-conf {
              description 'Specify VLAN.' ;
              case vlan-value {
                if-feature vlan-value-config ;

                description 'Specify the VLAN value.' ;
                leaf inne-vlan-value {
                  description 'Specify the inner-layer VLAN value.' ;
                  type uint16 {
                    range 1..4094 ;

                  }

                }

                leaf outer-vlan-value {
                  description 'Specify the outer-layer VLAN value.' ;
                  type uint16 {
                    range 1..4094 ;

                  }

                }

              }

              case vlan-range {
                if-feature vlan-range-config ;

                description 'Specify the VLAN range.' ;
                leaf inner-vlan-range {
                  description 'Specify the range of the inner-layer VLAN.' ;
                  type acl-vlan-range ;

                }

                leaf cfi {
                  description 'Specify the CFI.' ;
                  type enumeration {
                    enum set {
                      value 1 ;
                      description 'Match when the flag is set.' ;
                    }

                    enum unset {
                      value 0 ;
                      description 'Match when the flag is not set.' ;
                    }

                  }

                  ncd:revise-date 2017-06-20 ;
                }

                leaf outer-vlan-range {
                  description 'Specify the range of the outer-layer VLAN.' ;
                  type acl-vlan-range ;

                }

                leaf dei {
                  description 'Specify the DEI.' ;
                  type enumeration {
                    enum set {
                      value 1 ;
                      description 'Match when the flag is set.' ;
                    }

                    enum unset {
                      value 0 ;
                      description 'Match when the flag is not set.' ;
                    }

                  }

                  ncd:revise-date 2017-06-20 ;
                }

              }

            }

            choice permit-deny {
              description 'Specify the action as either permit or deny.' ;
              case deny {
                description 'Deny the packets that match the rule.' ;
                leaf deny {
                  description 'Deny the packets that match the rule.' ;
                  type empty ;

                }

              }

              case permit {
                description 'Permit the packets that match the rule.' ;
                leaf permit {
                  description 'Permit the packets that match the rule.' ;
                  type empty ;

                }

              }

            }

            choice src-addr {
              description 'Specify source IP address.' ;
              case src-ip-address {
                description 'Source IP address.' ;
                leaf src-address {
                  description 'Source IP address.' ;
                  type ncd:ipv4-address ;

                  mandatory true ;
                }

                leaf src-wildcard {
                  description 'Source IP address wildcard.' ;
                  type ncd:ipv4-address ;

                  mandatory true ;
                }

              }

              case src-any {
                description 'Any source IP address.' ;
                leaf src-any {
                  description 'Any source IP address.' ;
                  type empty ;

                }

              }

            }

            leaf time-range {
              description 'The name of the time range referenced by the ACL rule.
The referenced time range must exist.' ;
              type string {
                length 1..31 ;

              }

            }

            choice rule-type {
              description 'Specify the rule type of an IPv4 mixed ACL rule.' ;
              case std {
                description 'Standard rule type.' ;
                leaf ipv4-protocol-std {
                  description 'Standard rule type.' ;
                  type empty ;

                }

              }

              case extend {
                description 'Extended rule type.' ;
                container extended {
                  description 'Extended rule type.' ;
                  choice dest-addr {
                    description 'Specify destination IP address.' ;
                    mandatory true ;
                    case dest-ip-address {
                      description 'Destination IP address.' ;
                      leaf dest-address {
                        description 'Destination IP address.' ;
                        type ncd:ipv4-address ;

                        mandatory true ;
                      }

                      leaf dest-wildcard {
                        description 'Destination IP address wildcard.' ;
                        type ncd:ipv4-address ;

                        mandatory true ;
                      }

                    }

                    case dest-any {
                      description 'Any destination IP address.' ;
                      leaf dest-any {
                        description 'Any destination IP address.' ;
                        type empty ;

                      }

                    }

                  }

                  choice priority {
                    description 'Specify the priority of packets.
This is an optional node.
If you set this node you can choose precedence, tos, or dscp.
None means all case is invalid, And the default state is none.' ;
                    case precedence {
                      if-feature ipv4-mixed-pri-value ;

                      description 'Specify the precedence value.' ;
                      leaf precedence {
                        description 'Specify the precedence value.' ;
                        type uint8 {
                          range 0..7 ;

                        }

                      }

                    }

                    case prec-range {
                      if-feature ipv4-mixed-pri-range ;

                      description 'Specify the precedence, supporting single value and range configuration.' ;
                      leaf prec-range {
                        description 'Specify the precedence, supporting single value and range configuration.' ;
                        type acl-prec-range ;

                      }

                      ncd:revise-date 2015-04-20 ;
                    }

                    case tos {
                      description 'Specify the TOS value.' ;
                      leaf tos {
                        description 'Specify the TOS value.' ;
                        type uint8 {
                          range 0..15 ;

                        }

                      }

                    }

                    case dscp {
                      if-feature ipv4-mixed-pri-value ;

                      description 'Specify the DSCP value.' ;
                      leaf dscp {
                        description 'Specify the DSCP value.' ;
                        type uint8 {
                          range 0..63 ;

                        }

                      }

                    }

                    case dscp-range {
                      if-feature ipv4-mixed-pri-range ;

                      description 'Specify the DSCP, supporting single value and range configuration.' ;
                      leaf dscp-range {
                        description 'Specify the DSCP, supporting single value and range configuration.' ;
                        type acl-dscp-range ;

                      }

                      ncd:revise-date 2015-04-20 ;
                    }

                  }

                  leaf fragment {
                    description 'Examine non-initial fragments of packet.' ;
                    type boolean ;

                    default false ;
                  }

                  choice ipv4-protocol-type {
                    description 'IPv4 protocol type.' ;
                    mandatory true ;
                    case udp-tcp {
                      description 'The protocol number is UDP or TCP.' ;
                      container udp-tcp {
                        description 'The protocol number is UDP or TCP.' ;
                        choice udpOrTcp {
                          description 'The protocol number is UDP or TCP.' ;
                          mandatory true ;
                          case udp {
                            description 'The protocol number is UDP.' ;
                            leaf ipv4-protocol-udp {
                              description 'The protocol number is UDP.' ;
                              type empty ;

                            }

                          }

                          case tcp {
                            description 'The protocol number is TCP.' ;
                            leaf ipv4-protocol-tcp {
                              description 'The protocol number is TCP.' ;
                              type empty ;

                              mandatory true ;
                            }

                            leaf established {
                              description 'Specify the flag that indicates whether the TCP protocol initiates a connection establishment.' ;
                              type boolean ;

                              default false ;
                            }

                            leaf rst {
                              description 'Specify the RST flag.' ;
                              type acl-tcp-flag ;

                            }

                            leaf ack {
                              description 'Specify the ACK flag.' ;
                              type acl-tcp-flag ;

                            }

                            leaf fin {
                              description 'Specify the FIN flag.' ;
                              type acl-tcp-flag ;

                            }

                            leaf syn {
                              description 'Specify the SYN flag.' ;
                              type acl-tcp-flag ;

                            }

                            leaf psh {
                              description 'Specify the PSH flag.' ;
                              type acl-tcp-flag ;

                            }

                            leaf urg {
                              description 'Specify the URG flag.' ;
                              type acl-tcp-flag ;

                            }

                          }

                        }

                        choice src-port {
                          status obsolete {
                            ncd:revise-date 2017-07-20 ;
                          }

                          description 'Specify source port.
When the value of operator is invalid, it means match all port range,
the other value of operator means
eq(1)   : match only packets on a given port number
ge(2)   : match only packets with a no lower port number
le(3)   : match only packets with a no greater port number
range(7): match only packet on a given port range.' ;
                          case src-value {
                            status obsolete {
                              ncd:revise-date 2017-07-20 ;
                            }

                            description 'Configure port number.' ;
                            leaf src-value-operator {
                              status obsolete {
                                ncd:revise-date 2017-07-20 ;
                              }

                              description 'Operator type
eq(1)   : match only packets on a given port number
ge(2)   : match only packets with a no lower port number
le(3)   : match only packets with a no greater port number.' ;
                              type enumeration {
                                enum eq {
                                  value 1 ;
                                  description 'Equal to.' ;
                                }

                                enum ge {
                                  value 2 ;
                                  description 'Great than or equal to.' ;
                                }

                                enum le {
                                  value 3 ;
                                  description 'Less than or equal to.' ;
                                }

                              }

                              mandatory true ;
                            }

                            leaf src-port-number {
                              status obsolete {
                                ncd:revise-date 2017-07-20 ;
                              }

                              description 'Port number.' ;
                              type uint16 {
                                range 0..65535 ;

                              }

                              mandatory true ;
                            }

                          }

                          case src-range {
                            status obsolete {
                              ncd:revise-date 2017-07-20 ;
                            }

                            description 'Configure port range.' ;
                            leaf src-range-operator {
                              status obsolete {
                                ncd:revise-date 2017-07-20 ;
                              }

                              description 'Operator type
range(7): match only packet on a given port range.' ;
                              type empty ;

                              mandatory true ;
                            }

                            leaf src-port-range {
                              status obsolete {
                                ncd:revise-date 2017-07-20 ;
                              }

                              description 'Port range.' ;
                              type acl-port-range ;

                              mandatory true ;
                            }

                          }

                        }

                        choice dest-port {
                          status obsolete {
                            ncd:revise-date 2017-07-20 ;
                          }

                          description 'Specify destination port.
When the value of operator is invalid, it means match all port range,
the other value of operator means
eq(1)   : match only packets on a given port number
ge(2)   : match only packets with a no lower port number
le(3)   : match only packets with a no greater port number
range(7): match only packet on a given port range.' ;
                          case dest-value {
                            status obsolete {
                              ncd:revise-date 2017-07-20 ;
                            }

                            description 'Configure port number.' ;
                            leaf dest-value-operator {
                              status obsolete {
                                ncd:revise-date 2017-07-20 ;
                              }

                              description 'Operator type
eq(1)   : match only packets on a given port number
ge(2)   : match only packets with a no lower port number
le(3)   : match only packets with a no greater port number.' ;
                              type enumeration {
                                enum eq {
                                  value 1 ;
                                  description 'Equal to.' ;
                                }

                                enum ge {
                                  value 2 ;
                                  description 'Great than or equal to.' ;
                                }

                                enum le {
                                  value 3 ;
                                  description 'Less than or equal to.' ;
                                }

                              }

                              mandatory true ;
                            }

                            leaf dest-port-number {
                              status obsolete {
                                ncd:revise-date 2017-07-20 ;
                              }

                              description 'Port number.' ;
                              type uint16 {
                                range 0..65535 ;

                              }

                              mandatory true ;
                            }

                          }

                          case dest-range {
                            status obsolete {
                              ncd:revise-date 2017-07-20 ;
                            }

                            description 'Configure port range.' ;
                            leaf dest-range-operator {
                              status obsolete {
                                ncd:revise-date 2017-07-20 ;
                              }

                              description 'Operator type
range(7): match only packet on a given port range.' ;
                              type empty ;

                              mandatory true ;
                            }

                            leaf dest-port-range {
                              status obsolete {
                                ncd:revise-date 2017-07-20 ;
                              }

                              description 'Port range.' ;
                              type acl-port-range ;

                              mandatory true ;
                            }

                          }

                        }

                        container source-port {
                          description 'Specify the source port.' ;
                          presence "Specify source port" ;
                          choice source-port {
                            description 'Specify the source port.' ;
                            mandatory true ;
                            case src-port-value {
                              description 'Specify the value of the source port number.' ;
                              container src-port-value {
                                description 'Specify the value of the source port number.' ;
                                presence "Configure port number" ;
                                leaf src-port-operator {
                                  description 'Specify the operation type of the source port number.' ;
                                  type enumeration {
                                    enum eq {
                                      value 1 ;
                                      description 'Equal to.' ;
                                    }

                                    enum ge {
                                      value 2 ;
                                      description 'Great than or equal to.' ;
                                    }

                                    enum le {
                                      value 3 ;
                                      description 'Less than or equal to.' ;
                                    }

                                  }

                                  mandatory true ;
                                }

                                leaf src-port-value {
                                  description 'Specify the value of the source port number.' ;
                                  type uint16 {
                                    range 0..65535 ;

                                  }

                                  mandatory true ;
                                }

                              }

                            }

                            case src-port-range {
                              description 'Specify the range of the source port number.' ;
                              container src-port-range {
                                description 'Specify the range of the source port number.' ;
                                presence "Configure port range" ;
                                leaf src-port-operator {
                                  description 'Specify the operation type of the source port number.' ;
                                  type enumeration {
                                    enum range {
                                      value 7 ;
                                      description 'Range.' ;
                                    }

                                  }

                                  mandatory true ;
                                }

                                leaf src-port-range {
                                  description 'Specify the range of the source port number.' ;
                                  type acl-port-range ;

                                  mandatory true ;
                                }

                              }

                            }

                          }

                          ncd:revise-date 2017-07-20 ;
                        }

                        container destination-port {
                          description 'Specify the destination port.' ;
                          presence "Specify destination port" ;
                          choice destination-port {
                            description 'Specify the destination port.' ;
                            mandatory true ;
                            case dst-port-value {
                              description 'Specify the value of the destination port number.' ;
                              container dst-port-value {
                                description 'Specify the value of the destination port number.' ;
                                presence "Configure port number" ;
                                leaf dst-port-operator {
                                  description 'Specify the operation type of the destination port number.' ;
                                  type enumeration {
                                    enum eq {
                                      value 1 ;
                                      description 'Equal to.' ;
                                    }

                                    enum ge {
                                      value 2 ;
                                      description 'Great than or equal to.' ;
                                    }

                                    enum le {
                                      value 3 ;
                                      description 'Less than or equal to.' ;
                                    }

                                  }

                                  mandatory true ;
                                }

                                leaf dst-port-value {
                                  description 'Specify the value of the destination port number.' ;
                                  type uint16 {
                                    range 0..65535 ;

                                  }

                                  mandatory true ;
                                }

                              }

                            }

                            case dst-port-range {
                              description 'Specify the range of the destination port number.' ;
                              container dst-port-range {
                                description 'Specify the range of the destination port number.' ;
                                presence "Configure port range" ;
                                leaf dst-port-operator {
                                  description 'Specify the operation type of the destination port number.' ;
                                  type enumeration {
                                    enum range {
                                      value 7 ;
                                      description 'Range.' ;
                                    }

                                  }

                                  mandatory true ;
                                }

                                leaf dst-port-range {
                                  description 'Specify the range of the destination port number.' ;
                                  type acl-port-range ;

                                  mandatory true ;
                                }

                              }

                            }

                          }

                          ncd:revise-date 2017-07-20 ;
                        }

                      }

                    }

                    case icmp {
                      description 'The protocol number is ICMP.' ;
                      leaf ipv4-protocol-icmp {
                        description 'The protocol number is ICMP.' ;
                        type empty ;

                        mandatory true ;
                      }

                      container icmp-conf {
                        description 'Specify the ICMP type and ICMP code.' ;
                        presence "config icmp type and code" ;
                        leaf icmp-type {
                          description 'Specify the ICMP type.' ;
                          type uint16 {
                            range 0..255 ;

                          }

                          mandatory true ;
                        }

                        leaf icmp-code {
                          description 'Specify the ICMP code.' ;
                          type uint16 {
                            range 0..255 ;

                          }

                        }

                      }

                    }

                    case ip {
                      description 'The protocol number is a value excluding TCP, UDP, and ICMP.' ;
                      leaf ipv4-protocol {
                        description 'Specify the IP protocol type excluding TCP, UDP, and ICMP.' ;
                        mandatory true ;
                        type uint16 {
                          range "0 | 2..5 | 7..16 | 18..255 | 65535" ;

                        }

                      }

                      container port {
                        container source-port {
                          choice source-port {
                            case src-port-value {
                              container src-port-value {
                                leaf src-port-operator {
                                  type enumeration {
                                    enum eq {
                                      value 1 ;
                                      description 'Equal to.' ;
                                    }

                                    enum ge {
                                      value 2 ;
                                      description 'Great than or equal to.' ;
                                    }

                                    enum le {
                                      value 3 ;
                                      description 'Less than or equal to.' ;
                                    }

                                  }

                                  description 'Specify the operation type of the source port number.' ;
                                  mandatory true ;
                                }

                                leaf src-port-value {
                                  type uint16 {
                                    range 0..65535 ;

                                  }

                                  description 'Specify the value of the source port number.' ;
                                  mandatory true ;
                                }

                                description 'Specify the value of the source port number.' ;
                                presence "Configure port number" ;
                              }

                              description 'Specify the value of the source port number.' ;
                            }

                            case src-port-range {
                              container src-port-range {
                                leaf src-port-operator {
                                  type enumeration {
                                    enum range {
                                      value 7 ;
                                      description 'Range.' ;
                                    }

                                  }

                                  description 'Specify the operation type of the source port number.' ;
                                  mandatory true ;
                                }

                                leaf src-port-range {
                                  type acl-port-range ;

                                  description 'Specify the range of the source port number.' ;
                                  mandatory true ;
                                }

                                description 'Specify the range of the source port number.' ;
                                presence "Configure port range" ;
                              }

                              description 'Specify the range of the source port number.' ;
                            }

                            description 'Specify the source port.' ;
                            mandatory true ;
                          }

                          description 'Specify the source port.' ;
                          presence "Specify source port" ;
                        }

                        container destination-port {
                          choice destination-port {
                            case dst-port-value {
                              container dst-port-value {
                                leaf dst-port-operator {
                                  type enumeration {
                                    enum eq {
                                      value 1 ;
                                      description 'Equal to.' ;
                                    }

                                    enum ge {
                                      value 2 ;
                                      description 'Great than or equal to.' ;
                                    }

                                    enum le {
                                      value 3 ;
                                      description 'Less than or equal to.' ;
                                    }

                                  }

                                  description 'Specify the operation type of the destination port number.' ;
                                  mandatory true ;
                                }

                                leaf dst-port-value {
                                  type uint16 {
                                    range 0..65535 ;

                                  }

                                  description 'Specify the value of the destination port number.' ;
                                  mandatory true ;
                                }

                                description 'Specify the value of the destination port number.' ;
                                presence "Configure port number" ;
                              }

                              description 'Specify the value of the destination port number.' ;
                            }

                            case dst-port-range {
                              container dst-port-range {
                                leaf dst-port-operator {
                                  type enumeration {
                                    enum range {
                                      value 7 ;
                                      description 'Range.' ;
                                    }

                                  }

                                  description 'Specify the operation type of the destination port number.' ;
                                  mandatory true ;
                                }

                                leaf dst-port-range {
                                  type acl-port-range ;

                                  description 'Specify the range of the destination port number.' ;
                                  mandatory true ;
                                }

                                description 'Specify the range of the destination port number.' ;
                                presence "Configure port range" ;
                              }

                              description 'Specify the range of the destination port number.' ;
                            }

                            description 'Specify the destination port.' ;
                            mandatory true ;
                          }

                          description 'Specify the destination port.' ;
                          presence "Specify destination port" ;
                        }

                        description 'Specify the port. The port is valid when the protocol number is 132.' ;
                        ncd:revise-date 2024-02-27 ;
                      }

                    }

                  }

                  leaf source-monitor-group-id {
                    description 'Specify the source monitor group ID.' ;
                    type uint8 {
                      range 1..63 ;

                    }

                    ncd:revise-date 2020-07-13 ;
                  }

                  leaf destination-monitor-group-id {
                    description 'Specify the destination monitor group ID.' ;
                    type uint8 {
                      range 1..63 ;

                    }

                    ncd:revise-date 2020-07-13 ;
                  }

                }

              }

            }

            leaf exp {
              description 'Specify the MPLS EXP value.' ;
              type uint8 {
                range 0..7 {
                  description 'Value of exp, support 0-7.' ;
                }

              }

              ncd:revise-date 2019-10-08 ;
            }

            leaf label {
              description 'Specify the outermost label value.' ;
              type uint32 {
                range 1..1048575 ;

              }

              ncd:revise-date 2019-10-08 ;
            }

            leaf label2 {
              description 'Specify the second-layer label value.' ;
              type uint32 {
                range 1..1048575 ;

              }

              ncd:revise-date 2019-10-08 ;
            }

            leaf log {
              if-feature ipv4-mixed-log-config ;

              description 'Enable/Disable the function of counting matched packet data.' ;
              type boolean ;

              default false ;
              ncd:revise-date 2019-10-08 ;
            }

            leaf v4mix-desc {
              description 'The description of the rule.' ;
              type ncd:string-with-blank {
                length 1..70 {
                  description 'Direction for use, support 1-70 characters.' ;
                }

              }

              ncd:revise-date 2019-12-06 ;
            }

            container policy-route-id {
              description 'Specify the policy route ID.' ;
              presence "Specify the policy route id" ;
              choice policy-route-id {
                description 'Policy route ID, including source policy route ID and destination policy route ID.' ;
                mandatory true ;
                case src {
                  description 'Source policy route ID.' ;
                  container source {
                    description 'Specify the source policy route ID.' ;
                    presence "Specify the source policy route id" ;
                    leaf src-policy-route-id {
                      description 'Specify the source policy route ID.' ;
                      type uint8 {
                        range 1..63 ;

                      }

                      mandatory true ;
                    }

                  }

                }

                case dest {
                  description 'Destination policy route ID.' ;
                  container destination {
                    description 'Specify the destination policy route ID.' ;
                    presence "Specify the destination policy route id" ;
                    leaf dest-policy-route-id {
                      description 'Specify the destination policy route ID.' ;
                      type uint8 {
                        range 1..63 ;

                      }

                      mandatory true ;
                    }

                  }

                }

              }

              ncd:revise-date 2020-07-13 ;
            }

            leaf vrf {
              type acl-vrf-name {
                length 1..32 {
                  description 'VPN Routing/Forwarding instance name, support 1-32 characters.' ;
                }

              }

              if-feature ipv4-mixed-vrf ;

              description 'Specify the VRF instance name.
The referenced VRF must exist.' ;
              ncd:revise-date 2024-12-10 ;
            }

          }

          container acl-description {
            description 'The description of the ACL.' ;
            presence "Specify acl description" ;
            leaf acl-description {
              description 'The description of the ACL.' ;
              type ncd:string-with-blank {
                length 1..79 {
                  description 'Description of an access control list, support 1-79 characters.' ;
                }

              }

              mandatory true ;
            }

            ncd:revise-date 2020-06-18 ;
          }

        }

        list ipv6-access-list {
          if-feature ipv6-feature ;

          description 'Configure the IPv6 ACL.' ;
          key acl-name ;
          leaf acl-name {
            description 'Specify the ACL name.' ;
            type acl-name-type ;

          }

          list rule {
            description 'Configure an IPv6 ACL rule.' ;
            key ruleid ;
            leaf ruleid {
              description 'Specify the rule ID.' ;
              type uint32 {
                range 1..2147483644 ;

              }

            }

            choice permit-deny {
              description 'Specify the action as either permit or deny.' ;
              case deny {
                description 'Deny the packets that match the rule.' ;
                leaf deny {
                  description 'Deny the packets that match the rule.' ;
                  type empty ;

                  mandatory true ;
                }

              }

              case permit {
                description 'Permit the packets that match the rule.' ;
                leaf permit {
                  description 'Permit the packets that match the rule.' ;
                  type empty ;

                  mandatory true ;
                }

              }

            }

            leaf flowlabel {
              description 'Specify the flow label.' ;
              type uint32 {
                range 0..1048575 ;

              }

            }

            choice src-addr {
              description 'Specify source IPv6 address.' ;
              case src-ip-address {
                description 'Source IPv6 address.' ;
                leaf src-address {
                  description 'Source IPv6 address.' ;
                  type ncd:ipv6-address ;

                  mandatory true ;
                }

                choice src-wildcard-type {
                  description 'Source IPv6 address wildcard.' ;
                  case wildcard-len {
                    description 'Source IPv6 address prefix length.' ;
                    leaf src-wildcard {
                      description 'Source IPv6 address prefix length.' ;
                      type ncd:ipv6-mask-length ;

                      mandatory true ;
                    }

                  }

                  case wildcard-bits {
                    description 'Source IPv6 address wildcard.' ;
                    leaf src-wildcard-bits {
                      description 'Source IPv6 address wildcard.' ;
                      type ncd:ipv6-address ;

                      mandatory true ;
                    }

                    ncd:revise-date 2021-08-09 ;
                  }

                }

              }

              case src-any {
                description 'Any source IPv6 address.' ;
                leaf src-any {
                  description 'Any source IPv6 address.' ;
                  type empty ;

                  mandatory true ;
                }

              }

              case src-url {
                if-feature url-config ;

                description 'Source URL.' ;
                leaf src-url {
                  description 'Source URL.' ;
                  type ncd:url {
                    length 1..95 ;

                  }

                  mandatory true ;
                }

              }

              case src-prefix-list {
                container src-prefix-list {
                  leaf src-prefix-list {
                    type string {
                      length 1..169 {
                        description 'Prefix list name, support 1-169 characters.' ;
                      }

                    }

                    description 'Source prefix list.' ;
                    mandatory true ;
                  }

                  description 'Source prefix list.' ;
                }

                if-feature prefix-list ;

                description 'Source prefix list.' ;
                ncd:revise-date 2023-12-12 ;
              }

            }

            choice dest-addr {
              description 'Specify destination IPv6 address.' ;
              case dest-ip-address {
                description 'Destination IPv6 address.' ;
                leaf dest-address {
                  description 'Destination IPv6 address.' ;
                  type ncd:ipv6-address ;

                  mandatory true ;
                }

                choice dest-wildcard-type {
                  description 'Destination IPv6 address wildcard.' ;
                  case wildcard-len {
                    description 'Destination IPv6 address prefix length.' ;
                    leaf dest-wildcard {
                      description 'Destination IPv6 address prefix length.' ;
                      type ncd:ipv6-mask-length ;

                      mandatory true ;
                    }

                  }

                  case wildcard-bits {
                    description 'Destination IPv6 address wildcard.' ;
                    leaf dest-wildcard-bits {
                      description 'Destination IPv6 address wildcard.' ;
                      type ncd:ipv6-address ;

                      mandatory true ;
                    }

                    ncd:revise-date 2021-08-09 ;
                  }

                }

              }

              case dest-any {
                description 'Any destination IPv6 address.' ;
                leaf dest-any {
                  description 'Any destination IPv6 address.' ;
                  type empty ;

                  mandatory true ;
                }

              }

              case dest-url {
                if-feature url-config ;

                description 'Destination URL.' ;
                leaf dest-url {
                  description 'Destination URL.' ;
                  type ncd:url {
                    length 1..95 ;

                  }

                  mandatory true ;
                }

              }

              case dest-prefix-list {
                container dest-prefix-list {
                  leaf dest-prefix-list {
                    type string {
                      length 1..169 {
                        description 'Prefix list name, support 1-169 characters.' ;
                      }

                    }

                    description 'Destination prefix list.' ;
                    mandatory true ;
                  }

                  description 'Destination prefix list.' ;
                }

                if-feature prefix-list ;

                description 'Destination prefix list.' ;
                ncd:revise-date 2023-12-12 ;
              }

            }

            leaf log {
              if-feature ipv6-log-config ;

              description 'Enable/Disable the function of counting matched packet data.' ;
              type boolean ;

              default false ;
              ncd:revise-date 2015-04-20 ;
            }

            leaf time-range {
              description 'The name of the time range referenced by the ACL rule.
The referenced time range must exist.' ;
              type string {
                length 1..31 ;

              }

            }

            leaf routing {
              description 'Specify the routing header.' ;
              type boolean ;

              default false ;
            }

            leaf authen {
              description 'Specify the authentication header.' ;
              type boolean ;

              default false ;
            }

            leaf destopts {
              description 'Specify the destination options header.' ;
              type boolean ;

              default false ;
            }

            leaf fragment {
              description 'Specify the fragment header.' ;
              type boolean ;

              default false ;
            }

            leaf hop-by-hop {
              description 'Specify the hop-by-hop options header.' ;
              type boolean ;

              default false ;
            }

            leaf esp {
              description 'Specify the encapsulated security payload header.' ;
              type boolean ;

              default false ;
            }

            choice dscp-tc {
              description 'Specify the DSCP or traffic class.' ;
              case dscp {
                description 'Specify the DSCP.' ;
                leaf dscp {
                  description 'Specify the DSCP value.' ;
                  type uint8 {
                    range 0..63 ;

                  }

                }

                leaf dscp-range {
                  if-feature ipv6-dscp-range-config ;

                  description 'Specify the DSCP, supporting single-value and range configuration.' ;
                  type acl-dscp-range ;

                  ncd:revise-date 2020-08-21 ;
                }

              }

              case tc {
                description 'Specify the traffic class.' ;
                leaf traffic-class {
                  description 'Specify the traffic class.' ;
                  type uint16 {
                    range 0..255 ;

                  }

                }

              }

            }

            choice rule-type {
              description 'Specify the rule type of an IPv6 ACL rule.' ;
              case udp-tcp {
                description 'The protocol number is UDP or TCP.' ;
                container udp-tcp {
                  description 'The protocol number is UDP or TCP.' ;
                  choice udpOrTcp {
                    description 'The protocol number is UDP or TCP.' ;
                    mandatory true ;
                    case udp {
                      description 'The protocol number is UDP.' ;
                      leaf ipv6-protocol-udp {
                        description 'The protocol number is UDP.' ;
                        type empty ;

                      }

                    }

                    case tcp {
                      description 'The protocol number is TCP.' ;
                      leaf ipv6-protocol-tcp {
                        description 'The protocol number is TCP.' ;
                        type empty ;

                        mandatory true ;
                      }

                      leaf established {
                        description 'Specify the flag that indicates whether the TCP protocol initiates a connection establishment.' ;
                        type boolean ;

                        default false ;
                      }

                      leaf rst {
                        description 'Specify the RST flag.' ;
                        type acl-tcp-flag ;

                      }

                      leaf ack {
                        description 'Specify the ACK flag.' ;
                        type acl-tcp-flag ;

                      }

                      leaf fin {
                        description 'Specify the FIN flag.' ;
                        type acl-tcp-flag ;

                      }

                      leaf syn {
                        description 'Specify the SYN flag.' ;
                        type acl-tcp-flag ;

                      }

                      leaf psh {
                        description 'Specify the PSH flag.' ;
                        type acl-tcp-flag ;

                      }

                      leaf urg {
                        description 'Specify the URG flag.' ;
                        type acl-tcp-flag ;

                      }

                    }

                  }

                  choice src-port {
                    status obsolete {
                      ncd:revise-date 2017-07-20 ;
                    }

                    description 'Specify source port.
When the value of operator is invalid, it means match all port range,
the other value of operator means
eq(1)   : match only packets on a given port number
ge(2)   : match only packets with a no lower port number
le(3)   : match only packets with a no greater port number
range(7): match only packet on a given port range.' ;
                    case src-value {
                      status obsolete {
                        ncd:revise-date 2017-07-20 ;
                      }

                      description 'Configure port number.' ;
                      leaf src-value-operator {
                        status obsolete {
                          ncd:revise-date 2017-07-20 ;
                        }

                        description 'Operator type
eq(1)   : match only packets on a given port number
ge(2)   : match only packets with a no lower port number
le(3)   : match only packets with a no greater port number.' ;
                        type enumeration {
                          enum eq {
                            value 1 ;
                            description 'Equal to.' ;
                          }

                          enum ge {
                            value 2 ;
                            description 'Great than or equal to.' ;
                          }

                          enum le {
                            value 3 ;
                            description 'Less than or equal to.' ;
                          }

                        }

                        mandatory true ;
                      }

                      leaf src-port-number {
                        status obsolete {
                          ncd:revise-date 2017-07-20 ;
                        }

                        description 'Port number.' ;
                        type uint16 {
                          range 0..65535 ;

                        }

                        mandatory true ;
                      }

                    }

                    case src-range {
                      status obsolete {
                        ncd:revise-date 2017-07-20 ;
                      }

                      description 'Configure port range.' ;
                      leaf src-range-operator {
                        status obsolete {
                          ncd:revise-date 2017-07-20 ;
                        }

                        description 'Operator type
range(7): match only packet on a given port range.' ;
                        type empty ;

                        mandatory true ;
                      }

                      leaf src-port-range {
                        status obsolete {
                          ncd:revise-date 2017-07-20 ;
                        }

                        description 'Port range.' ;
                        type acl-port-range ;

                        mandatory true ;
                      }

                    }

                  }

                  choice dest-port {
                    status obsolete {
                      ncd:revise-date 2017-07-20 ;
                    }

                    description 'Specify destination port.
When the value of operator is invalid, it means match all port range,
the other value of operator means
eq(1)   : match only packets on a given port number
ge(2)   : match only packets with a no lower port number
le(3)   : match only packets with a no greater port number
range(7): match only packet on a given port range.' ;
                    case dest-value {
                      status obsolete {
                        ncd:revise-date 2017-07-20 ;
                      }

                      description 'Configure port number.' ;
                      leaf dest-value-operator {
                        status obsolete {
                          ncd:revise-date 2017-07-20 ;
                        }

                        description 'Operator type
eq(1)   : match only packets on a given port number
ge(2)   : match only packets with a no lower port number
le(3)   : match only packets with a no greater port number.' ;
                        type enumeration {
                          enum eq {
                            value 1 ;
                            description 'Equal to.' ;
                          }

                          enum ge {
                            value 2 ;
                            description 'Great than or equal to.' ;
                          }

                          enum le {
                            value 3 ;
                            description 'Less than or equal to.' ;
                          }

                        }

                        mandatory true ;
                      }

                      leaf dest-port-number {
                        status obsolete {
                          ncd:revise-date 2017-07-20 ;
                        }

                        description 'Port number.' ;
                        type uint16 {
                          range 0..65535 ;

                        }

                        mandatory true ;
                      }

                    }

                    case dest-range {
                      status obsolete {
                        ncd:revise-date 2017-07-20 ;
                      }

                      description 'Configure port range.' ;
                      leaf dest-range-operator {
                        status obsolete {
                          ncd:revise-date 2017-07-20 ;
                        }

                        description 'Operator type
range(7): match only packet on a given port range.' ;
                        type empty ;

                        mandatory true ;
                      }

                      leaf dest-port-range {
                        status obsolete {
                          ncd:revise-date 2017-07-20 ;
                        }

                        description 'Port range.' ;
                        type acl-port-range ;

                        mandatory true ;
                      }

                    }

                  }

                  container source-port {
                    description 'Specify the source port.' ;
                    presence "Specify source port" ;
                    choice source-port {
                      description 'Specify the source port.' ;
                      mandatory true ;
                      case src-port-value {
                        description 'Specify the value of the source port number.' ;
                        container src-port-value {
                          description 'Specify the value of the source port number.' ;
                          presence "Configure port number" ;
                          leaf src-port-operator {
                            description 'Specify the operation type of the source port number.' ;
                            type enumeration {
                              enum eq {
                                value 1 ;
                                description 'Equal to.' ;
                              }

                              enum ge {
                                value 2 ;
                                description 'Great than or equal to.' ;
                              }

                              enum le {
                                value 3 ;
                                description 'Less than or equal to.' ;
                              }

                            }

                            mandatory true ;
                          }

                          leaf src-port-value {
                            description 'Specify the value of the source port number.' ;
                            type uint16 {
                              range 0..65535 ;

                            }

                            mandatory true ;
                          }

                        }

                      }

                      case src-port-range {
                        description 'Specify the range of the source port number.' ;
                        container src-port-range {
                          description 'Specify the range of the source port number.' ;
                          presence "Configure port range" ;
                          leaf src-port-operator {
                            description 'Specify the operation type of the source port number.' ;
                            type enumeration {
                              enum range {
                                value 7 ;
                                description 'Range.' ;
                              }

                            }

                            mandatory true ;
                          }

                          leaf src-port-range {
                            description 'Specify the range of the source port number.' ;
                            type acl-port-range ;

                            mandatory true ;
                          }

                        }

                      }

                      case src-port-pool {
                        container src-port-pool {
                          leaf port-pool-name {
                            type acl-port-pool-name ;

                            description 'Specify the name of the source port pool.
The referenced port pool must exist.' ;
                            mandatory true ;
                          }

                          description 'Specify the source port pool.' ;
                          presence "Configure source port pool" ;
                        }

                        description 'Specify the source port pool.' ;
                        if-feature port-pool ;

                        ncd:revise-date 2023-12-12 ;
                      }

                    }

                    ncd:revise-date 2017-07-20 ;
                  }

                  container destination-port {
                    description 'Specify the destination port.' ;
                    presence "Specify destination port" ;
                    choice destination-port {
                      description 'Specify the destination port.' ;
                      mandatory true ;
                      case dst-port-value {
                        description 'Specify the value of the destination port number.' ;
                        container dst-port-value {
                          description 'Specify the value of the destination port number.' ;
                          presence "Configure port number" ;
                          leaf dst-port-operator {
                            description 'Specify the operation type of the destination port number.' ;
                            type enumeration {
                              enum eq {
                                value 1 ;
                                description 'Equal to.' ;
                              }

                              enum ge {
                                value 2 ;
                                description 'Great than or equal to.' ;
                              }

                              enum le {
                                value 3 ;
                                description 'Less than or equal to.' ;
                              }

                            }

                            mandatory true ;
                          }

                          leaf dst-port-value {
                            description 'Specify the value of the destination port number.' ;
                            type uint16 {
                              range 0..65535 ;

                            }

                            mandatory true ;
                          }

                        }

                      }

                      case dst-port-range {
                        description 'Specify the range of the destination port number.' ;
                        container dst-port-range {
                          description 'Specify the range of the destination port number.' ;
                          presence "Configure port range" ;
                          leaf dst-port-operator {
                            description 'Specify the operation type of the destination port number.' ;
                            type enumeration {
                              enum range {
                                value 7 ;
                                description 'Range.' ;
                              }

                            }

                            mandatory true ;
                          }

                          leaf dst-port-range {
                            description 'Specify the range of the destination port number.' ;
                            type acl-port-range ;

                            mandatory true ;
                          }

                        }

                      }

                      case dst-port-pool {
                        container dst-port-pool {
                          leaf port-pool-name {
                            type acl-port-pool-name ;

                            description 'Specify the name of the destination port pool.
The referenced port pool must exist.' ;
                            mandatory true ;
                          }

                          description 'Specify the destination port pool.' ;
                          presence "Configure destination port pool" ;
                        }

                        description 'Specify the destination port pool.' ;
                        if-feature port-pool ;

                        ncd:revise-date 2023-12-12 ;
                      }

                    }

                    ncd:revise-date 2017-07-20 ;
                  }

                }

              }

              case icmp {
                description 'The protocol number is ICMP.' ;
                leaf ipv6-protocol-icmp {
                  description 'The protocol number is ICMP.' ;
                  type empty ;

                  mandatory true ;
                }

                container icmp-conf {
                  description 'Specify the ICMP type and ICMP code.' ;
                  presence "config icmp type and code" ;
                  leaf icmp-type {
                    description 'Specify the ICMP type.' ;
                    type uint16 {
                      range 0..255 ;

                    }

                    mandatory true ;
                  }

                  leaf icmp-code {
                    description 'Specify the ICMP code.' ;
                    type uint16 {
                      range 0..255 ;

                    }

                  }

                }

                container icmp-port {
                  description 'Specify the port.' ;
                  choice src-port {
                    status obsolete {
                      ncd:revise-date 2017-07-20 ;
                    }

                    description 'Specify source port.
When the value of operator is invalid, it means match all port range,
the other value of operator means
eq(1)   : match only packets on a given port number
ge(2)   : match only packets with a no lower port number
le(3)   : match only packets with a no greater port number
range(7): match only packet on a given port range.' ;
                    case src-value {
                      status obsolete {
                        ncd:revise-date 2017-07-20 ;
                      }

                      description 'Configure port number.' ;
                      leaf src-value-operator {
                        status obsolete {
                          ncd:revise-date 2017-07-20 ;
                        }

                        description 'Operator type
eq(1)   : match only packets on a given port number
ge(2)   : match only packets with a no lower port number
le(3)   : match only packets with a no greater port number.' ;
                        type enumeration {
                          enum eq {
                            value 1 ;
                            description 'Equal to.' ;
                          }

                          enum ge {
                            value 2 ;
                            description 'Great than or equal to.' ;
                          }

                          enum le {
                            value 3 ;
                            description 'Less than or equal to.' ;
                          }

                        }

                        mandatory true ;
                      }

                      leaf src-port-number {
                        status obsolete {
                          ncd:revise-date 2017-07-20 ;
                        }

                        description 'Port number.' ;
                        type uint16 {
                          range 0..65535 ;

                        }

                        mandatory true ;
                      }

                    }

                    case src-range {
                      status obsolete {
                        ncd:revise-date 2017-07-20 ;
                      }

                      description 'Configure port range.' ;
                      leaf src-range-operator {
                        status obsolete {
                          ncd:revise-date 2017-07-20 ;
                        }

                        description 'Operator type
range(7): match only packet on a given port range.' ;
                        type empty ;

                        mandatory true ;
                      }

                      leaf src-port-range {
                        status obsolete {
                          ncd:revise-date 2017-07-20 ;
                        }

                        description 'Port range.' ;
                        type acl-port-range ;

                        mandatory true ;
                      }

                    }

                  }

                  choice dest-port {
                    status obsolete {
                      ncd:revise-date 2017-07-20 ;
                    }

                    description 'Specify destination port.
When the value of operator is invalid, it means match all port range,
the other value of operator means
eq(1)   : match only packets on a given port number
ge(2)   : match only packets with a no lower port number
le(3)   : match only packets with a no greater port number
range(7): match only packet on a given port range.' ;
                    case dest-value {
                      status obsolete {
                        ncd:revise-date 2017-07-20 ;
                      }

                      description 'Configure port number.' ;
                      leaf dest-value-operator {
                        status obsolete {
                          ncd:revise-date 2017-07-20 ;
                        }

                        description 'Operator type
eq(1)   : match only packets on a given port number
ge(2)   : match only packets with a no lower port number
le(3)   : match only packets with a no greater port number.' ;
                        type enumeration {
                          enum eq {
                            value 1 ;
                            description 'Equal to.' ;
                          }

                          enum ge {
                            value 2 ;
                            description 'Great than or equal to.' ;
                          }

                          enum le {
                            value 3 ;
                            description 'Less than or equal to.' ;
                          }

                        }

                        mandatory true ;
                      }

                      leaf dest-port-number {
                        status obsolete {
                          ncd:revise-date 2017-07-20 ;
                        }

                        description 'Port number.' ;
                        type uint16 {
                          range 0..65535 ;

                        }

                        mandatory true ;
                      }

                    }

                    case dest-range {
                      status obsolete {
                        ncd:revise-date 2017-07-20 ;
                      }

                      description 'Configure port range.' ;
                      leaf dest-range-operator {
                        status obsolete {
                          ncd:revise-date 2017-07-20 ;
                        }

                        description 'Operator type
range(7): match only packet on a given port range.' ;
                        type empty ;

                        mandatory true ;
                      }

                      leaf dest-port-range {
                        status obsolete {
                          ncd:revise-date 2017-07-20 ;
                        }

                        description 'Port range.' ;
                        type acl-port-range ;

                        mandatory true ;
                      }

                    }

                  }

                  container source-port {
                    description 'Specify the source port.' ;
                    presence "Specify source port" ;
                    choice source-port {
                      description 'Specify the source port.' ;
                      mandatory true ;
                      case src-port-value {
                        description 'Specify the value of the source port number.' ;
                        container src-port-value {
                          description 'Specify the value of the source port number.' ;
                          presence "Configure port number" ;
                          leaf src-port-operator {
                            description 'Specify the operation type of the source port number.' ;
                            type enumeration {
                              enum eq {
                                value 1 ;
                                description 'Equal to.' ;
                              }

                              enum ge {
                                value 2 ;
                                description 'Great than or equal to.' ;
                              }

                              enum le {
                                value 3 ;
                                description 'Less than or equal to.' ;
                              }

                            }

                            mandatory true ;
                          }

                          leaf src-port-value {
                            description 'Specify the value of the source port number.' ;
                            type uint16 {
                              range 0..65535 ;

                            }

                            mandatory true ;
                          }

                        }

                      }

                      case src-port-range {
                        description 'Specify the range of the source port number.' ;
                        container src-port-range {
                          description 'Specify the range of the source port number.' ;
                          presence "Configure port range" ;
                          leaf src-port-operator {
                            description 'Specify the operation type of the source port number.' ;
                            type enumeration {
                              enum range {
                                value 7 ;
                                description 'Range.' ;
                              }

                            }

                            mandatory true ;
                          }

                          leaf src-port-range {
                            description 'Specify the range of the source port number.' ;
                            type acl-port-range ;

                            mandatory true ;
                          }

                        }

                      }

                      case src-port-pool {
                        container src-port-pool {
                          leaf port-pool-name {
                            type acl-port-pool-name ;

                            description 'Specify the name of the source port pool.
The referenced port pool must exist.' ;
                            mandatory true ;
                          }

                          description 'Specify the source port pool.' ;
                          presence "Configure source port pool" ;
                        }

                        description 'Specify the source port pool.' ;
                        if-feature port-pool ;

                        ncd:revise-date 2023-12-12 ;
                      }

                    }

                    ncd:revise-date 2017-07-20 ;
                  }

                  container destination-port {
                    description 'Specify the destination port.' ;
                    presence "Specify destination port" ;
                    choice destination-port {
                      description 'Specify the destination port.' ;
                      mandatory true ;
                      case dst-port-value {
                        description 'Specify the value of the destination port number.' ;
                        container dst-port-value {
                          description 'Specify the value of the destination port number.' ;
                          presence "Configure port number" ;
                          leaf dst-port-operator {
                            description 'Specify the operation type of the destination port number.' ;
                            type enumeration {
                              enum eq {
                                value 1 ;
                                description 'Equal to.' ;
                              }

                              enum ge {
                                value 2 ;
                                description 'Great than or equal to.' ;
                              }

                              enum le {
                                value 3 ;
                                description 'Less than or equal to.' ;
                              }

                            }

                            mandatory true ;
                          }

                          leaf dst-port-value {
                            description 'Specify the value of the destination port number.' ;
                            type uint16 {
                              range 0..65535 ;

                            }

                            mandatory true ;
                          }

                        }

                      }

                      case dst-port-range {
                        description 'Specify the range of the destination port number.' ;
                        container dst-port-range {
                          description 'Specify the range of the destination port number.' ;
                          presence "Configure port range" ;
                          leaf dst-port-operator {
                            description 'Specify the operation type of the destination port number.' ;
                            type enumeration {
                              enum range {
                                value 7 ;
                                description 'Range.' ;
                              }

                            }

                            mandatory true ;
                          }

                          leaf dst-port-range {
                            description 'Specify the range of the destination port number.' ;
                            type acl-port-range ;

                            mandatory true ;
                          }

                        }

                      }

                      case dst-port-pool {
                        container dst-port-pool {
                          leaf port-pool-name {
                            type acl-port-pool-name ;

                            description 'Specify the name of the destination port pool.
The referenced port pool must exist.' ;
                            mandatory true ;
                          }

                          description 'Specify the destination port pool.' ;
                          presence "Configure destination port pool" ;
                        }

                        description 'Specify the destination port pool.' ;
                        if-feature port-pool ;

                        ncd:revise-date 2023-12-12 ;
                      }

                    }

                    ncd:revise-date 2017-07-20 ;
                  }

                  ncd:revise-date 2016-01-13 ;
                }

              }

              case ip {
                description 'The protocol number is a value excluding TCP, UDP, and ICMP.' ;
                leaf ipv6-protocol {
                  description 'Specify the IPv6 protocol type excluding TCP, UDP, and ICMP.' ;
                  type uint16 {
                    range "0..5 | 7..16 | 18..57 | 59..255 | 65535" ;

                  }

                  mandatory true ;
                }

                container port {
                  description 'Specify the port.' ;
                  choice src-port {
                    status obsolete {
                      ncd:revise-date 2017-07-20 ;
                    }

                    description 'Specify source port.
When the value of operator is invalid, it means match all port range,
the other value of operator means
eq(1)   : match only packets on a given port number
ge(2)   : match only packets with a no lower port number
le(3)   : match only packets with a no greater port number
range(7): match only packet on a given port range.' ;
                    case src-value {
                      status obsolete {
                        ncd:revise-date 2017-07-20 ;
                      }

                      description 'Configure port number.' ;
                      leaf src-value-operator {
                        status obsolete {
                          ncd:revise-date 2017-07-20 ;
                        }

                        description 'Operator type
eq(1)   : match only packets on a given port number
ge(2)   : match only packets with a no lower port number
le(3)   : match only packets with a no greater port number.' ;
                        type enumeration {
                          enum eq {
                            value 1 ;
                            description 'Equal to.' ;
                          }

                          enum ge {
                            value 2 ;
                            description 'Great than or equal to.' ;
                          }

                          enum le {
                            value 3 ;
                            description 'Less than or equal to.' ;
                          }

                        }

                        mandatory true ;
                      }

                      leaf src-port-number {
                        status obsolete {
                          ncd:revise-date 2017-07-20 ;
                        }

                        description 'Port number.' ;
                        type uint16 {
                          range 0..65535 ;

                        }

                        mandatory true ;
                      }

                    }

                    case src-range {
                      status obsolete {
                        ncd:revise-date 2017-07-20 ;
                      }

                      description 'Configure port range.' ;
                      leaf src-range-operator {
                        status obsolete {
                          ncd:revise-date 2017-07-20 ;
                        }

                        description 'Operator type
range(7): match only packet on a given port range.' ;
                        type empty ;

                        mandatory true ;
                      }

                      leaf src-port-range {
                        status obsolete {
                          ncd:revise-date 2017-07-20 ;
                        }

                        description 'Port range.' ;
                        type acl-port-range ;

                        mandatory true ;
                      }

                    }

                  }

                  choice dest-port {
                    status obsolete {
                      ncd:revise-date 2017-07-20 ;
                    }

                    description 'Specify destination port.
When the value of operator is invalid, it means match all port range,
the other value of operator means
eq(1)   : match only packets on a given port number
ge(2)   : match only packets with a no lower port number
le(3)   : match only packets with a no greater port number
range(7): match only packet on a given port range.' ;
                    case dest-value {
                      status obsolete {
                        ncd:revise-date 2017-07-20 ;
                      }

                      description 'Configure port number.' ;
                      leaf dest-value-operator {
                        status obsolete {
                          ncd:revise-date 2017-07-20 ;
                        }

                        description 'Operator type
eq(1)   : match only packets on a given port number
ge(2)   : match only packets with a no lower port number
le(3)   : match only packets with a no greater port number.' ;
                        type enumeration {
                          enum eq {
                            value 1 ;
                            description 'Equal to.' ;
                          }

                          enum ge {
                            value 2 ;
                            description 'Great than or equal to.' ;
                          }

                          enum le {
                            value 3 ;
                            description 'Less than or equal to.' ;
                          }

                        }

                        mandatory true ;
                      }

                      leaf dest-port-number {
                        status obsolete {
                          ncd:revise-date 2017-07-20 ;
                        }

                        description 'Port number.' ;
                        type uint16 {
                          range 0..65535 ;

                        }

                        mandatory true ;
                      }

                    }

                    case dest-range {
                      status obsolete {
                        ncd:revise-date 2017-07-20 ;
                      }

                      description 'Configure port range.' ;
                      leaf dest-range-operator {
                        status obsolete {
                          ncd:revise-date 2017-07-20 ;
                        }

                        description 'Operator type
range(7): match only packet on a given port range.' ;
                        type empty ;

                        mandatory true ;
                      }

                      leaf dest-port-range {
                        status obsolete {
                          ncd:revise-date 2017-07-20 ;
                        }

                        description 'Port range.' ;
                        type acl-port-range ;

                        mandatory true ;
                      }

                    }

                  }

                  container source-port {
                    description 'Specify the source port.' ;
                    presence "Specify source port" ;
                    choice source-port {
                      description 'Specify the source port.' ;
                      mandatory true ;
                      case src-port-value {
                        description 'Specify the value of the source port number.' ;
                        container src-port-value {
                          description 'Specify the value of the source port number.' ;
                          presence "Configure port number" ;
                          leaf src-port-operator {
                            description 'Specify the operation type of the source port number.' ;
                            type enumeration {
                              enum eq {
                                value 1 ;
                                description 'Equal to.' ;
                              }

                              enum ge {
                                value 2 ;
                                description 'Great than or equal to.' ;
                              }

                              enum le {
                                value 3 ;
                                description 'Less than or equal to.' ;
                              }

                            }

                            mandatory true ;
                          }

                          leaf src-port-value {
                            description 'Specify the value of the source port number.' ;
                            type uint16 {
                              range 0..65535 ;

                            }

                            mandatory true ;
                          }

                        }

                      }

                      case src-port-range {
                        description 'Specify the range of the source port number.' ;
                        container src-port-range {
                          description 'Specify the range of the source port number.' ;
                          presence "Configure port range" ;
                          leaf src-port-operator {
                            description 'Specify the operation type of the source port number.' ;
                            type enumeration {
                              enum range {
                                value 7 ;
                                description 'Range.' ;
                              }

                            }

                            mandatory true ;
                          }

                          leaf src-port-range {
                            description 'Specify the range of the source port number.' ;
                            type acl-port-range ;

                            mandatory true ;
                          }

                        }

                      }

                      case src-port-pool {
                        container src-port-pool {
                          leaf port-pool-name {
                            type acl-port-pool-name ;

                            description 'Specify the name of the source port pool.
The referenced port pool must exist.' ;
                            mandatory true ;
                          }

                          description 'Specify the source port pool.' ;
                          presence "Configure source port pool" ;
                        }

                        description 'Specify the source port pool.' ;
                        if-feature port-pool ;

                        ncd:revise-date 2023-12-12 ;
                      }

                    }

                    ncd:revise-date 2017-07-20 ;
                  }

                  container destination-port {
                    description 'Specify the destination port.' ;
                    presence "Specify destination port" ;
                    choice destination-port {
                      description 'Specify the destination port.' ;
                      mandatory true ;
                      case dst-port-value {
                        description 'Specify the value of the destination port number.' ;
                        container dst-port-value {
                          description 'Specify the value of the destination port number.' ;
                          presence "Configure port number" ;
                          leaf dst-port-operator {
                            description 'Specify the operation type of the destination port number.' ;
                            type enumeration {
                              enum eq {
                                value 1 ;
                                description 'Equal to.' ;
                              }

                              enum ge {
                                value 2 ;
                                description 'Great than or equal to.' ;
                              }

                              enum le {
                                value 3 ;
                                description 'Less than or equal to.' ;
                              }

                            }

                            mandatory true ;
                          }

                          leaf dst-port-value {
                            description 'Specify the value of the destination port number.' ;
                            type uint16 {
                              range 0..65535 ;

                            }

                            mandatory true ;
                          }

                        }

                      }

                      case dst-port-range {
                        description 'Specify the range of the destination port number.' ;
                        container dst-port-range {
                          description 'Specify the range of the destination port number.' ;
                          presence "Configure port range" ;
                          leaf dst-port-operator {
                            description 'Specify the operation type of the destination port number.' ;
                            type enumeration {
                              enum range {
                                value 7 ;
                                description 'Range.' ;
                              }

                            }

                            mandatory true ;
                          }

                          leaf dst-port-range {
                            description 'Specify the range of the destination port number.' ;
                            type acl-port-range ;

                            mandatory true ;
                          }

                        }

                      }

                      case dst-port-pool {
                        container dst-port-pool {
                          leaf port-pool-name {
                            type acl-port-pool-name ;

                            description 'Specify the name of the destination port pool.
The referenced port pool must exist.' ;
                            mandatory true ;
                          }

                          description 'Specify the destination port pool.' ;
                          presence "Configure destination port pool" ;
                        }

                        description 'Specify the destination port pool.' ;
                        if-feature port-pool ;

                        ncd:revise-date 2023-12-12 ;
                      }

                    }

                    ncd:revise-date 2017-07-20 ;
                  }

                  ncd:revise-date 2016-01-13 ;
                }

              }

            }

            leaf description {
              description 'The description of the rule.' ;
              type ncd:string-with-blank {
                length 1..70 {
                  description 'Direction for use, support 1-70 characters.' ;
                }

              }

              ncd:revise-date 2016-08-18 ;
            }

            choice vrf-config {
              description 'VPN Routing/Forwarding instance.' ;
              case vrf-config-choice-clear {
                description 'Remove value of any entities which belong to any case within this choice.' ;
                container vrf-config-all-clear {
                  description 'Remove this entity means to remove value of any entities which belong to any case within this choice.' ;
                  presence vrf-config-all-clear ;
                }

                ncd:revise-date 2020-08-17 ;
              }

              case vrf {
                description 'Specify the VRF instance name.' ;
                leaf vrf {
                  description 'Specify the VRF instance name.
The referenced VRF must exist.' ;
                  type acl-vrf-name ;

                }

              }

              case vrf-dcn {
                description 'Specify it for DCN VRF.' ;
                leaf vrf-dcn {
                  description 'Specify it for DCN VRF.' ;
                  type empty ;

                }

                ncd:revise-date 2020-08-17 ;
              }

              ncd:revise-date 2017-06-20 ;
            }

            container packet-length {
              description 'Specify the packet length.' ;
              presence "Configure packet length" ;
              choice packet-length {
                description 'Specify the packet length.' ;
                mandatory true ;
                case packet-length-value {
                  description 'Specify the value of the packet length.' ;
                  container packet-length-value {
                    description 'Specify the value of the packet length.' ;
                    presence "Configure packet length" ;
                    leaf packet-length-oper {
                      description 'Specify the operation type of the packet length.' ;
                      type acl-pktlen-opr ;

                      mandatory true ;
                    }

                    leaf packet-length-value {
                      description 'Specify the value of the packet length.' ;
                      type uint16 {
                        range 1..65535 {
                          description 'Packet length value, support 1-65535.' ;
                        }

                      }

                      mandatory true ;
                    }

                  }

                }

                case packet-length-range {
                  description 'Specify the range of the packet length.' ;
                  container packet-length-range {
                    description 'Specify the range of the packet length.' ;
                    presence "Configure packet length" ;
                    leaf packet-length-oper {
                      description 'Specify the operation type of the packet length.' ;
                      type enumeration {
                        enum range {
                          value 7 ;
                          description 'Match only packets on a given packet length range.' ;
                        }

                      }

                      mandatory true ;
                    }

                    leaf packet-length-range {
                      description 'Specify the range of the packet length.' ;
                      type acl-pktlen-range ;

                      mandatory true ;
                    }

                  }

                }

              }

              ncd:revise-date 2017-06-20 ;
            }

            container policy-route-id {
              description 'Specify the policy route ID.' ;
              presence "Specify the policy route id" ;
              choice policy-route-id {
                description 'Policy route ID, including source policy route ID and destination policy route ID.' ;
                mandatory true ;
                case src {
                  description 'Source policy route ID.' ;
                  container source {
                    description 'Specify the source policy route ID.' ;
                    presence "Specify the source policy route id" ;
                    leaf src-policy-route-id {
                      description 'Specify the source policy route ID.' ;
                      type uint8 {
                        range 1..63 ;

                      }

                      mandatory true ;
                    }

                  }

                }

                case dest {
                  description 'Destination policy route ID.' ;
                  container destination {
                    description 'Specify the destination policy route ID.' ;
                    presence "Specify the destination policy route id" ;
                    leaf dest-policy-route-id {
                      description 'Specify the destination policy route ID.' ;
                      type uint8 {
                        range 1..63 ;

                      }

                      mandatory true ;
                    }

                  }

                }

              }

              ncd:revise-date 2019-09-10 ;
            }

            leaf monitor-group-id {
              description 'Specify the monitor group ID.' ;
              type uint8 {
                range 1..63 ;

              }

              ncd:revise-date 2019-11-26 ;
            }

            leaf source-monitor-group-id {
              description 'Specify the source monitor group ID.' ;
              type uint8 {
                range 1..63 ;

              }

              ncd:revise-date 2019-12-11 ;
            }

            container time-to-live {
              if-feature ipv6-ttl-config ;

              description 'Specify the time to live (TTL).' ;
              presence "Specify the TTL" ;
              choice ttl {
                description 'Specify the TTL value
The operator value of TTL mean 
eq(1)   : Match only packets on a given ttl value
ge(2)   : Match only packets with a no lower ttl value
le(3)   : Match only packets with a no greater ttl value
neq(6)  : Match only packets with a no equeal ttl value
range(7): Match only packet on a given ttl value range.' ;
                mandatory true ;
                case ttl-value {
                  description 'Specify the value of the TTL.' ;
                  container ttl-value {
                    description 'Specify the value of the TTL.' ;
                    presence "Specify the TTL value" ;
                    leaf ttl-operator {
                      description 'Specify the operation type of the TTL.' ;
                      type enumeration {
                        enum eq {
                          value 1 ;
                          description 'Equal to.' ;
                        }

                        enum ge {
                          value 2 ;
                          description 'Great than or equal to.' ;
                        }

                        enum le {
                          value 3 ;
                          description 'Less than or equal to.' ;
                        }

                        enum neq {
                          value 6 ;
                          description 'Not equal to.' ;
                        }

                      }

                      mandatory true ;
                    }

                    leaf ttl-value {
                      description 'Specify the value of the TTL.' ;
                      type uint8 {
                        range 1..255 {
                          description 'TTL value, support 1-255.' ;
                        }

                      }

                      mandatory true ;
                    }

                  }

                }

                case ttl-range {
                  description 'Specify the range of the TTL.' ;
                  container ttl-range {
                    description 'Specify the range of the TTL.' ;
                    presence "Specify the TTL range" ;
                    leaf ttl-operator {
                      description 'Specify the operation type of the TTL.' ;
                      type enumeration {
                        enum range {
                          value 7 ;
                          description 'Range.' ;
                        }

                      }

                      mandatory true ;
                    }

                    leaf ttl-range {
                      description 'Specify the range of the TTL.' ;
                      type acl-ttl-range ;

                      mandatory true ;
                    }

                  }

                }

              }

              ncd:revise-date 2020-03-23 ;
            }

          }

          container acl-description {
            description 'The description of the ACL.' ;
            presence "Specify acl description" ;
            leaf acl-description {
              description 'The description of the ACL.' ;
              type ncd:string-with-blank {
                length 1..79 {
                  description 'Description of an access control list, support 1-79 characters.' ;
                }

              }

              mandatory true ;
            }

            ncd:revise-date 2020-06-18 ;
          }

        }

        list ipv6-mixed-access-list {
          if-feature ipv6-mixed-feature ;

          description 'Configure the IPv6 mixed ACL.' ;
          key acl-name ;
          leaf acl-name {
            description 'Specify the ACL name.' ;
            type acl-name-type ;

          }

          list rule {
            description 'Configure an IPv6 mixed ACL rule.' ;
            key ruleid ;
            leaf ruleid {
              description 'Specify the rule ID.' ;
              type uint32 {
                range 1..2147483644 ;

              }

            }

            choice link-prot {
              description 'Specify the link protocol type.' ;
              case link-protocol {
                description 'Specify the link protocol type.' ;
                leaf link-protocol {
                  description 'Specify the link protocol type.' ;
                  type uint32 {
                    range 1536..65535 ;

                  }

                }

              }

              case link-protocol-hex {
                if-feature link-prot-hex-config ;

                status obsolete {
                  ncd:revise-date 2017-01-04 ;
                }

                description 'Specify the link protocol in hexadecimal format.' ;
                leaf link-protocol-hex {
                  description 'Specify the link protocol in hexadecimal format.' ;
                  type ncd:hex ;

                }

              }

              case sap {
                if-feature sap-feature ;

                description 'Specify the Service Access Point (SAP).' ;
                container dsap-ssap {
                  description 'Specify the Destination Service Access Point (DSAP) and the Source Service Access Point (SSAP).' ;
                  presence "config dsap and ssap" ;
                  leaf dsap {
                    description 'Specify the DSAP.' ;
                    type uint16 {
                      range 0..255 ;

                    }

                    mandatory true ;
                  }

                  leaf ssap {
                    description 'Specify the SSAP.' ;
                    type uint16 {
                      range 0..255 ;

                    }

                    mandatory true ;
                  }

                }

                ncd:revise-date 2017-07-12 ;
              }

            }

            choice src-mac-addr {
              description 'Specify source MAC address.' ;
              case src-mac-addr {
                description 'Source MAC address.' ;
                leaf src-mac-address {
                  description 'Source MAC address.' ;
                  type ncd:mac-address ;

                  mandatory true ;
                }

                leaf src-mac-wildcard {
                  description 'Source MAC address wildcard.' ;
                  type ncd:mac-address ;

                  mandatory true ;
                }

              }

              case src-mac-any {
                description 'Any source MAC address.' ;
                leaf src-mac-any {
                  description 'Any source MAC address.' ;
                  type empty ;

                }

              }

              case src-mac-range {
                if-feature mac-range-config ;

                description 'Source MAC address range.' ;
                leaf src-mac-from1 {
                  description 'The starting value of the first range of source MAC address.' ;
                  type ncd:mac-address ;

                  mandatory true ;
                }

                leaf src-mac-to1 {
                  description 'The ending value of the first range of source MAC address.' ;
                  type ncd:mac-address ;

                  mandatory true ;
                }

                container src-mac-range2 {
                  description 'The second range of source MAC address.' ;
                  presence "config second source mac range" ;
                  leaf src-mac-from2 {
                    description 'The starting value of the second range of source MAC address.' ;
                    type ncd:mac-address ;

                    mandatory true ;
                  }

                  leaf src-mac-to2 {
                    description 'The ending value of the second range of source MAC address.' ;
                    type ncd:mac-address ;

                    mandatory true ;
                  }

                }

              }

            }

            choice dest-mac-addr {
              description 'Specify destination MAC address.' ;
              case dest-mac-addr {
                description 'Destination MAC address.' ;
                leaf dest-mac-address {
                  description 'Destination MAC address.' ;
                  type ncd:mac-address ;

                  mandatory true ;
                }

                leaf dest-mac-wildcard {
                  description 'Destination MAC address wildcard.' ;
                  type ncd:mac-address ;

                  mandatory true ;
                }

              }

              case dest-mac-any {
                description 'Any destination MAC address.' ;
                leaf dest-mac-any {
                  description 'Any destination MAC address.' ;
                  type empty ;

                }

              }

              case dest-mac-range {
                if-feature mac-range-config ;

                description 'Destination MAC address range.' ;
                leaf dest-mac-from1 {
                  description 'The starting value of the first range of destination MAC address.' ;
                  type ncd:mac-address ;

                  mandatory true ;
                }

                leaf dest-mac-to1 {
                  description 'The ending value of the first range of destination MAC address.' ;
                  type ncd:mac-address ;

                  mandatory true ;
                }

                container dest-mac-range2 {
                  description 'The second range of destination MAC address.' ;
                  presence "config second destination mac range" ;
                  leaf dest-mac-from2 {
                    description 'The starting value of the second range of destination MAC address.' ;
                    type ncd:mac-address ;

                    mandatory true ;
                  }

                  leaf dest-mac-to2 {
                    description 'The ending value of the second range of destination MAC address.' ;
                    type ncd:mac-address ;

                    mandatory true ;
                  }

                }

              }

            }

            leaf inner-cos {
              description 'Specify the inner-layer CoS value.' ;
              type uint8 {
                range 0..7 ;

              }

            }

            leaf inner-cos-range {
              if-feature ipv6-cos-range-config ;

              description 'Specify the range of inner-layer CoS, supporting single value and range configuration.' ;
              type acl-cos-range ;

              ncd:revise-date 2020-08-21 ;
            }

            leaf outer-cos {
              description 'Specify the outer-layer CoS value.' ;
              type uint8 {
                range 0..7 ;

              }

            }

            leaf outer-cos-range {
              if-feature ipv6-cos-range-config ;

              description 'Specify the range of outer-layer CoS, supporting single value and range configuration.' ;
              type acl-cos-range ;

              ncd:revise-date 2020-08-21 ;
            }

            choice vlan-conf {
              description 'Specify VLAN.' ;
              case vlan-value {
                if-feature vlan-value-config ;

                description 'Specify the VLAN value.' ;
                leaf inne-vlan-value {
                  description 'Specify the inner-layer VLAN value.' ;
                  type uint16 {
                    range 1..4094 ;

                  }

                }

                leaf outer-vlan-value {
                  description 'Specify the outer-layer VLAN value.' ;
                  type uint16 {
                    range 1..4094 ;

                  }

                }

              }

              case vlan-range {
                if-feature vlan-range-config ;

                description 'Specify the VLAN range.' ;
                leaf inner-vlan-range {
                  description 'Specify the range of the inner-layer VLAN.' ;
                  type acl-vlan-range ;

                }

                leaf outer-vlan-range {
                  description 'Specify the range of the outer-layer VLAN.' ;
                  type acl-vlan-range ;

                }

              }

            }

            choice permit-deny {
              description 'Specify the action as either permit or deny.' ;
              case deny {
                description 'Deny the packets that match the rule.' ;
                leaf deny {
                  description 'Deny the packets that match the rule.' ;
                  type empty ;

                }

              }

              case permit {
                description 'Permit the packets that match the rule.' ;
                leaf permit {
                  description 'Permit the packets that match the rule.' ;
                  type empty ;

                }

              }

            }

            leaf flowlabel {
              description 'Specify the flow label.' ;
              type uint32 {
                range 0..1048575 ;

              }

            }

            choice src-addr {
              description 'Specify source IPv6 address.' ;
              case src-ip-address {
                description 'Source IPv6 address.' ;
                leaf src-address {
                  description 'Source IPv6 address.' ;
                  type ncd:ipv6-address ;

                  mandatory true ;
                }

                choice src-wildcard-type {
                  description 'Source IPv6 address wildcard.' ;
                  case wildcard-len {
                    description 'Source IPv6 address prefix length.' ;
                    leaf src-wildcard {
                      description 'Source IPv6 address prefix length.' ;
                      type ncd:ipv6-mask-length ;

                      mandatory true ;
                    }

                  }

                  case wildcard-bits {
                    description 'Source IPv6 address wildcard.' ;
                    leaf src-wildcard-bits {
                      description 'Source IPv6 address wildcard.' ;
                      type ncd:ipv6-address ;

                      mandatory true ;
                    }

                    ncd:revise-date 2021-08-09 ;
                  }

                }

              }

              case src-any {
                description 'Any source IPv6 address.' ;
                leaf src-any {
                  description 'Any source IPv6 address.' ;
                  type empty ;

                }

              }

            }

            choice dest-addr {
              description 'Specify destination IPv6 address.' ;
              case dest-ip-address {
                description 'Destination IPv6 address.' ;
                leaf dest-address {
                  description 'Destination IPv6 address.' ;
                  type ncd:ipv6-address ;

                  mandatory true ;
                }

                choice dest-wildcard-type {
                  description 'Destination IPv6 address wildcard.' ;
                  case wildcard-len {
                    description 'Destination IPv6 address prefix length.' ;
                    leaf dest-wildcard {
                      description 'Destination IPv6 address prefix length.' ;
                      type ncd:ipv6-mask-length ;

                      mandatory true ;
                    }

                  }

                  case wildcard-bits {
                    description 'Destination IPv6 address wildcard.' ;
                    leaf dest-wildcard-bits {
                      description 'Destination IPv6 address wildcard.' ;
                      type ncd:ipv6-address ;

                      mandatory true ;
                    }

                    ncd:revise-date 2021-08-09 ;
                  }

                }

              }

              case dest-any {
                description 'Any destination IPv6 address.' ;
                leaf dest-any {
                  description 'Any destination IPv6 address.' ;
                  type empty ;

                }

              }

            }

            leaf time-range {
              description 'The name of the time range referenced by the ACL rule.
The referenced time range must exist.' ;
              type string {
                length 1..31 ;

              }

            }

            leaf routing {
              description 'Specify the routing header.' ;
              type boolean ;

              default false ;
            }

            leaf authen {
              description 'Specify the authentication header.' ;
              type boolean ;

              default false ;
            }

            leaf destopts {
              description 'Specify the destination options header.' ;
              type boolean ;

              default false ;
            }

            leaf fragment {
              description 'Specify the fragment header.' ;
              type boolean ;

              default false ;
            }

            leaf hop-by-hop {
              description 'Specify the hop-by-hop options header.' ;
              type boolean ;

              default false ;
            }

            leaf esp {
              description 'Specify the encapsulated security payload header.' ;
              type boolean ;

              default false ;
            }

            choice dscp-tc {
              description 'Specify the DSCP or traffic class.' ;
              case dscp {
                description 'Specify the DSCP.' ;
                leaf dscp {
                  description 'Specify the DSCP value.' ;
                  type uint8 {
                    range 0..63 ;

                  }

                }

                leaf dscp-range {
                  if-feature ipv6-dscp-range-config ;

                  description 'Specify the DSCP, supporting single-value and range configuration.' ;
                  type acl-dscp-range ;

                  ncd:revise-date 2020-08-21 ;
                }

              }

              case tc {
                description 'Specify the traffic class.' ;
                leaf traffic-class {
                  description 'Specify the traffic class.' ;
                  type uint16 {
                    range 0..255 ;

                  }

                }

              }

            }

            choice rule-type {
              description 'Specify the rule type of an IPv6 mixed ACL rule.' ;
              case udp-tcp {
                description 'The protocol number is UDP or TCP.' ;
                container udp-tcp {
                  description 'The protocol number is UDP or TCP.' ;
                  choice udpOrTcp {
                    description 'The protocol number is UDP or TCP.' ;
                    mandatory true ;
                    case udp {
                      description 'The protocol number is UDP.' ;
                      leaf ipv6-protocol-udp {
                        description 'The protocol number is UDP.' ;
                        type empty ;

                      }

                    }

                    case tcp {
                      description 'The protocol number is TCP.' ;
                      leaf ipv6-protocol-tcp {
                        description 'The protocol number is TCP.' ;
                        type empty ;

                        mandatory true ;
                      }

                      leaf established {
                        description 'Specify the flag that indicates whether the TCP protocol initiates a connection establishment.' ;
                        type boolean ;

                        default false ;
                      }

                      leaf rst {
                        description 'Specify the RST flag.' ;
                        type acl-tcp-flag ;

                      }

                      leaf ack {
                        description 'Specify the ACK flag.' ;
                        type acl-tcp-flag ;

                      }

                      leaf fin {
                        description 'Specify the FIN flag.' ;
                        type acl-tcp-flag ;

                      }

                      leaf syn {
                        description 'Specify the SYN flag.' ;
                        type acl-tcp-flag ;

                      }

                      leaf psh {
                        description 'Specify the PSH flag.' ;
                        type acl-tcp-flag ;

                      }

                      leaf urg {
                        description 'Specify the URG flag.' ;
                        type acl-tcp-flag ;

                      }

                    }

                  }

                  choice src-port {
                    status obsolete {
                      ncd:revise-date 2017-07-20 ;
                    }

                    description 'Specify source port.
When the value of operator is invalid, it means match all port range,
the other value of operator means
eq(1)   : match only packets on a given port number
ge(2)   : match only packets with a no lower port number
le(3)   : match only packets with a no greater port number
range(7): match only packet on a given port range.' ;
                    case src-value {
                      status obsolete {
                        ncd:revise-date 2017-07-20 ;
                      }

                      description 'Configure port number.' ;
                      leaf src-value-operator {
                        status obsolete {
                          ncd:revise-date 2017-07-20 ;
                        }

                        description 'Operator type
eq(1)   : match only packets on a given port number
ge(2)   : match only packets with a no lower port number
le(3)   : match only packets with a no greater port number.' ;
                        type enumeration {
                          enum eq {
                            value 1 ;
                            description 'Equal to.' ;
                          }

                          enum ge {
                            value 2 ;
                            description 'Great than or equal to.' ;
                          }

                          enum le {
                            value 3 ;
                            description 'Less than or equal to.' ;
                          }

                        }

                        mandatory true ;
                      }

                      leaf src-port-number {
                        status obsolete {
                          ncd:revise-date 2017-07-20 ;
                        }

                        description 'Port number.' ;
                        type uint16 {
                          range 0..65535 ;

                        }

                        mandatory true ;
                      }

                    }

                    case src-range {
                      status obsolete {
                        ncd:revise-date 2017-07-20 ;
                      }

                      description 'Configure port range.' ;
                      leaf src-range-operator {
                        status obsolete {
                          ncd:revise-date 2017-07-20 ;
                        }

                        description 'Operator type
range(7): match only packet on a given port range.' ;
                        type empty ;

                        mandatory true ;
                      }

                      leaf src-port-range {
                        status obsolete {
                          ncd:revise-date 2017-07-20 ;
                        }

                        description 'Port range.' ;
                        type acl-port-range ;

                        mandatory true ;
                      }

                    }

                  }

                  choice dest-port {
                    status obsolete {
                      ncd:revise-date 2017-07-20 ;
                    }

                    description 'Specify destination port.
When the value of operator is invalid, it means match all port range,
the other value of operator means
eq(1)   : match only packets on a given port number
ge(2)   : match only packets with a no lower port number
le(3)   : match only packets with a no greater port number
range(7): match only packet on a given port range.' ;
                    case dest-value {
                      status obsolete {
                        ncd:revise-date 2017-07-20 ;
                      }

                      description 'Configure port number.' ;
                      leaf dest-value-operator {
                        status obsolete {
                          ncd:revise-date 2017-07-20 ;
                        }

                        description 'Operator type
eq(1)   : match only packets on a given port number
ge(2)   : match only packets with a no lower port number
le(3)   : match only packets with a no greater port number.' ;
                        type enumeration {
                          enum eq {
                            value 1 ;
                            description 'Equal to.' ;
                          }

                          enum ge {
                            value 2 ;
                            description 'Great than or equal to.' ;
                          }

                          enum le {
                            value 3 ;
                            description 'Less than or equal to.' ;
                          }

                        }

                        mandatory true ;
                      }

                      leaf dest-port-number {
                        status obsolete {
                          ncd:revise-date 2017-07-20 ;
                        }

                        description 'Port number.' ;
                        type uint16 {
                          range 0..65535 ;

                        }

                        mandatory true ;
                      }

                    }

                    case dest-range {
                      status obsolete {
                        ncd:revise-date 2017-07-20 ;
                      }

                      description 'Configure port range.' ;
                      leaf dest-range-operator {
                        status obsolete {
                          ncd:revise-date 2017-07-20 ;
                        }

                        description 'Operator type
range(7): match only packet on a given port range.' ;
                        type empty ;

                        mandatory true ;
                      }

                      leaf dest-port-range {
                        status obsolete {
                          ncd:revise-date 2017-07-20 ;
                        }

                        description 'Port range.' ;
                        type acl-port-range ;

                        mandatory true ;
                      }

                    }

                  }

                  container source-port {
                    description 'Specify the source port.' ;
                    presence "Specify source port" ;
                    choice source-port {
                      description 'Specify the source port.' ;
                      mandatory true ;
                      case src-port-value {
                        description 'Specify the value of the source port number.' ;
                        container src-port-value {
                          description 'Specify the value of the source port number.' ;
                          presence "Configure port number" ;
                          leaf src-port-operator {
                            description 'Specify the operation type of the source port number.' ;
                            type enumeration {
                              enum eq {
                                value 1 ;
                                description 'Equal to.' ;
                              }

                              enum ge {
                                value 2 ;
                                description 'Great than or equal to.' ;
                              }

                              enum le {
                                value 3 ;
                                description 'Less than or equal to.' ;
                              }

                            }

                            mandatory true ;
                          }

                          leaf src-port-value {
                            description 'Specify the value of the source port number.' ;
                            type uint16 {
                              range 0..65535 ;

                            }

                            mandatory true ;
                          }

                        }

                      }

                      case src-port-range {
                        description 'Specify the range of the source port number.' ;
                        container src-port-range {
                          description 'Specify the range of the source port number.' ;
                          presence "Configure port range" ;
                          leaf src-port-operator {
                            description 'Specify the operation type of the source port number.' ;
                            type enumeration {
                              enum range {
                                value 7 ;
                                description 'Range.' ;
                              }

                            }

                            mandatory true ;
                          }

                          leaf src-port-range {
                            description 'Specify the range of the source port number.' ;
                            type acl-port-range ;

                            mandatory true ;
                          }

                        }

                      }

                    }

                    ncd:revise-date 2017-07-20 ;
                  }

                  container destination-port {
                    description 'Specify the destination port.' ;
                    presence "Specify destination port" ;
                    choice destination-port {
                      description 'Specify the destination port.' ;
                      mandatory true ;
                      case dst-port-value {
                        description 'Specify the value of the destination port number.' ;
                        container dst-port-value {
                          description 'Specify the value of the destination port number.' ;
                          presence "Configure port number" ;
                          leaf dst-port-operator {
                            description 'Specify the operation type of the destination port number.' ;
                            type enumeration {
                              enum eq {
                                value 1 ;
                                description 'Equal to.' ;
                              }

                              enum ge {
                                value 2 ;
                                description 'Great than or equal to.' ;
                              }

                              enum le {
                                value 3 ;
                                description 'Less than or equal to.' ;
                              }

                            }

                            mandatory true ;
                          }

                          leaf dst-port-value {
                            description 'Specify the value of the destination port number.' ;
                            type uint16 {
                              range 0..65535 ;

                            }

                            mandatory true ;
                          }

                        }

                      }

                      case dst-port-range {
                        description 'Specify the range of the destination port number.' ;
                        container dst-port-range {
                          description 'Specify the range of the destination port number.' ;
                          presence "Configure port range" ;
                          leaf dst-port-operator {
                            description 'Specify the operation type of the destination port number.' ;
                            type enumeration {
                              enum range {
                                value 7 ;
                                description 'Range.' ;
                              }

                            }

                            mandatory true ;
                          }

                          leaf dst-port-range {
                            description 'Specify the range of the destination port number.' ;
                            type acl-port-range ;

                            mandatory true ;
                          }

                        }

                      }

                    }

                    ncd:revise-date 2017-07-20 ;
                  }

                }

              }

              case icmp {
                description 'The protocol number is ICMP.' ;
                leaf ipv6-protocol-icmp {
                  description 'The protocol number is ICMP.' ;
                  type empty ;

                  mandatory true ;
                }

                container icmp-conf {
                  description 'Specify the ICMP type and ICMP code.' ;
                  presence "config icmp type and code" ;
                  leaf icmp-type {
                    description 'Specify the ICMP type.' ;
                    type uint16 {
                      range 0..255 ;

                    }

                    mandatory true ;
                  }

                  leaf icmp-code {
                    description 'Specify the ICMP code.' ;
                    type uint16 {
                      range 0..255 ;

                    }

                  }

                }

              }

              case ip {
                description 'The protocol number is a value excluding TCP, UDP, and ICMP.' ;
                leaf ipv6-protocol {
                  description 'Specify the IPv6 protocol type excluding TCP, UDP, and ICMP.' ;
                  mandatory true ;
                  type uint16 {
                    range "0..5 | 7..16 | 18..57 | 59..255 | 65535" ;

                  }

                }

                container port {
                  description 'Specify the port. The port is valid when the protocol number is 132.' ;
                  container source-port {
                    description 'Specify the source port.' ;
                    presence "Specify source port" ;
                    choice source-port {
                      description 'Specify the source port.' ;
                      mandatory true ;
                      case src-port-value {
                        description 'Specify the value of the source port number.' ;
                        container src-port-value {
                          description 'Specify the value of the source port number.' ;
                          presence "Configure port number" ;
                          leaf src-port-operator {
                            description 'Specify the operation type of the source port number.' ;
                            type enumeration {
                              enum eq {
                                value 1 ;
                                description 'Equal to.' ;
                              }

                              enum ge {
                                value 2 ;
                                description 'Great than or equal to.' ;
                              }

                              enum le {
                                value 3 ;
                                description 'Less than or equal to.' ;
                              }

                            }

                            mandatory true ;
                          }

                          leaf src-port-value {
                            description 'Specify the value of the source port number.' ;
                            type uint16 {
                              range 0..65535 ;

                            }

                            mandatory true ;
                          }

                        }

                      }

                      case src-port-range {
                        description 'Specify the range of the source port number.' ;
                        container src-port-range {
                          description 'Specify the range of the source port number.' ;
                          presence "Configure port range" ;
                          leaf src-port-operator {
                            description 'Specify the operation type of the source port number.' ;
                            type enumeration {
                              enum range {
                                value 7 ;
                                description 'Range.' ;
                              }

                            }

                            mandatory true ;
                          }

                          leaf src-port-range {
                            description 'Specify the range of the source port number.' ;
                            type acl-port-range ;

                            mandatory true ;
                          }

                        }

                      }

                    }

                  }

                  container destination-port {
                    description 'Specify the destination port.' ;
                    presence "Specify destination port" ;
                    choice destination-port {
                      description 'Specify the destination port.' ;
                      mandatory true ;
                      case dst-port-value {
                        description 'Specify the value of the destination port number.' ;
                        container dst-port-value {
                          description 'Specify the value of the destination port number.' ;
                          presence "Configure port number" ;
                          leaf dst-port-operator {
                            description 'Specify the operation type of the destination port number.' ;
                            type enumeration {
                              enum eq {
                                value 1 ;
                                description 'Equal to.' ;
                              }

                              enum ge {
                                value 2 ;
                                description 'Great than or equal to.' ;
                              }

                              enum le {
                                value 3 ;
                                description 'Less than or equal to.' ;
                              }

                            }

                            mandatory true ;
                          }

                          leaf dst-port-value {
                            description 'Specify the value of the destination port number.' ;
                            type uint16 {
                              range 0..65535 ;

                            }

                            mandatory true ;
                          }

                        }

                      }

                      case dst-port-range {
                        description 'Specify the range of the destination port number.' ;
                        container dst-port-range {
                          description 'Specify the range of the destination port number.' ;
                          presence "Configure port range" ;
                          leaf dst-port-operator {
                            description 'Specify the operation type of the destination port number.' ;
                            type enumeration {
                              enum range {
                                value 7 ;
                                description 'Range.' ;
                              }

                            }

                            mandatory true ;
                          }

                          leaf dst-port-range {
                            description 'Specify the range of the destination port number.' ;
                            type acl-port-range ;

                            mandatory true ;
                          }

                        }

                      }

                    }

                  }

                  ncd:revise-date 2024-02-27 ;
                }

              }

            }

            leaf v6mix-desc {
              description 'The description of the rule.' ;
              type ncd:string-with-blank {
                length 1..70 {
                  description 'Direction for use, support 1-70 characters.' ;
                }

              }

              ncd:revise-date 2019-12-06 ;
            }

            leaf log {
              if-feature ipv6-mixed-log-config ;

              description 'Enable/Disable the function of counting matched packet data.' ;
              type boolean ;

              default false ;
              ncd:revise-date 2021-06-03 ;
            }

            leaf exp {
              description 'Specify the MPLS EXP value.' ;
              type uint8 {
                range 0..7 {
                  description 'Value of exp, support 0-7.' ;
                }

              }

              ncd:revise-date 2021-08-04 ;
            }

            leaf label {
              type uint32 {
                range 1..1048575 ;

              }

              if-feature ipv6-mixed-label ;

              description 'Specify the outermost label value.' ;
              ncd:revise-date 2024-12-10 ;
            }

            leaf label2 {
              type uint32 {
                range 1..1048575 ;

              }

              if-feature ipv6-mixed-label2 ;

              description 'Specify the second-layer label value.' ;
              ncd:revise-date 2024-12-10 ;
            }

            leaf vrf {
              type acl-vrf-name {
                length 1..32 {
                  description 'VPN Routing/Forwarding instance name, support 1-32 characters.' ;
                }

              }

              if-feature ipv6-mixed-vrf ;

              description 'Specify the VRF instance name.
The referenced VRF must exist.' ;
              ncd:revise-date 2024-12-10 ;
            }

          }

          container acl-description {
            description 'The description of the ACL.' ;
            presence "Specify acl description" ;
            leaf acl-description {
              description 'The description of the ACL.' ;
              type ncd:string-with-blank {
                length 1..79 {
                  description 'Description of an access control list, support 1-79 characters.' ;
                }

              }

              mandatory true ;
            }

            ncd:revise-date 2020-06-29 ;
          }

        }

        list link-access-list {
          if-feature link-feature ;

          description 'Configure the link ACL.' ;
          key acl-name ;
          leaf acl-name {
            description 'Specify the ACL name.' ;
            type acl-name-type ;

          }

          list rule {
            description 'Configure a link ACL rule.' ;
            key ruleid ;
            leaf ruleid {
              description 'Specify the rule ID.' ;
              type uint32 {
                range 1..2147483644 ;

              }

            }

            choice permit-deny {
              description 'Specify the action as either permit or deny.' ;
              case deny {
                description 'Deny the packets that match the rule.' ;
                leaf deny {
                  description 'Deny the packets that match the rule.' ;
                  type empty ;

                  mandatory true ;
                }

              }

              case permit {
                description 'Permit the packets that match the rule.' ;
                leaf permit {
                  description 'Permit the packets that match the rule.' ;
                  type empty ;

                  mandatory true ;
                }

              }

            }

            choice link-prot {
              description 'Specify the link protocol type.' ;
              case link-protocol {
                description 'Specify the link protocol type.' ;
                leaf link-protocol {
                  description 'Specify the link protocol type.' ;
                  type uint32 {
                    range 1536..65535 ;

                  }

                }

                leaf link-protocol-mask {
                  description 'Specify the link protocol mask in hexadecimal format.' ;
                  type ncd:hex {
                    length 3..6 ;

                  }

                  ncd:revise-date 2017-06-02 ;
                }

              }

              case link-protocol-hex {
                if-feature link-prot-hex-config ;

                description 'Specify the link protocol in hexadecimal format.' ;
                leaf link-protocol-hex {
                  description 'Specify the link protocol in hexadecimal format.' ;
                  type ncd:hex ;

                }

                leaf link-protocol-hex-mask {
                  description 'Specify the link protocol mask in hexadecimal format.' ;
                  type ncd:hex {
                    length 3..6 ;

                  }

                  ncd:revise-date 2017-06-02 ;
                }

              }

              case sap {
                if-feature sap-feature ;

                description 'Specify the Service Access Point (SAP).' ;
                container dsap-ssap {
                  description 'Specify the Destination Service Access Point (DSAP) and the Source Service Access Point (SSAP).' ;
                  presence "config dsap and ssap" ;
                  leaf dsap {
                    description 'Specify the DSAP.' ;
                    type uint16 {
                      range 0..255 ;

                    }

                    mandatory true ;
                  }

                  leaf ssap {
                    description 'Specify the SSAP.' ;
                    type uint16 {
                      range 0..255 ;

                    }

                    mandatory true ;
                  }

                }

                ncd:revise-date 2017-07-12 ;
              }

            }

            choice src-mac-addr {
              description 'Specify source MAC address.' ;
              case src-mac-addr {
                description 'Source MAC address.' ;
                leaf src-mac-address {
                  description 'Source MAC address.' ;
                  type ncd:mac-address ;

                  mandatory true ;
                }

                leaf src-mac-wildcard {
                  description 'Source MAC address wildcard.' ;
                  type ncd:mac-address ;

                  mandatory true ;
                }

              }

              case src-mac-any {
                description 'Any source MAC address.' ;
                leaf src-mac-any {
                  description 'Any source MAC address.' ;
                  type empty ;

                  mandatory true ;
                }

              }

              case src-mac-range {
                if-feature mac-range-config ;

                description 'Source MAC address range.' ;
                leaf src-mac-from1 {
                  description 'The starting value of the first range of source MAC address.' ;
                  type ncd:mac-address ;

                  mandatory true ;
                }

                leaf src-mac-to1 {
                  description 'The ending value of the first range of source MAC address.' ;
                  type ncd:mac-address ;

                  mandatory true ;
                }

                container src-mac-range2 {
                  description 'The second range of source MAC address.' ;
                  presence "config second source mac range" ;
                  leaf src-mac-from2 {
                    description 'The starting value of the second range of source MAC address.' ;
                    type ncd:mac-address ;

                    mandatory true ;
                  }

                  leaf src-mac-to2 {
                    description 'The ending value of the second range of source MAC address.' ;
                    type ncd:mac-address ;

                    mandatory true ;
                  }

                }

              }

            }

            choice dest-mac-addr {
              description 'Specify destination MAC address.' ;
              case dest-mac-addr {
                description 'Destination MAC address.' ;
                leaf dest-mac-address {
                  description 'Destination MAC address.' ;
                  type ncd:mac-address ;

                  mandatory true ;
                }

                leaf dest-mac-wildcard {
                  description 'Destination MAC address wildcard.' ;
                  type ncd:mac-address ;

                  mandatory true ;
                }

              }

              case dest-mac-any {
                description 'Any destination MAC address.' ;
                leaf dest-mac-any {
                  description 'Any destination MAC address.' ;
                  type empty ;

                  mandatory true ;
                }

              }

              case dest-mac-range {
                if-feature mac-range-config ;

                description 'Destination MAC address range.' ;
                leaf dest-mac-from1 {
                  description 'The starting value of the first range of destination MAC address.' ;
                  type ncd:mac-address ;

                  mandatory true ;
                }

                leaf dest-mac-to1 {
                  description 'The ending value of the first range of destination MAC address.' ;
                  type ncd:mac-address ;

                  mandatory true ;
                }

                container dest-mac-range2 {
                  description 'The second range of destination MAC address.' ;
                  presence "config second destination mac range" ;
                  leaf dest-mac-from2 {
                    description 'The starting value of the second range of destination MAC address.' ;
                    type ncd:mac-address ;

                    mandatory true ;
                  }

                  leaf dest-mac-to2 {
                    description 'The ending value of the second range of destination MAC address.' ;
                    type ncd:mac-address ;

                    mandatory true ;
                  }

                }

              }

            }

            leaf inner-cos {
              if-feature link-cos-value ;

              description 'Specify the inner-layer CoS value.' ;
              type uint8 {
                range 0..7 ;

              }

            }

            leaf inner-cos-range {
              if-feature link-cos-range ;

              description 'Specify the range of inner-layer CoS, supporting single value and range configuration.' ;
              type acl-cos-range ;

              ncd:revise-date 2015-04-20 ;
            }

            leaf outer-cos {
              if-feature link-cos-value ;

              description 'Specify the outer-layer CoS value.' ;
              type uint8 {
                range 0..7 ;

              }

            }

            leaf outer-cos-range {
              if-feature link-cos-range ;

              description 'Specify the range of outer-layer CoS, supporting single value and range configuration.' ;
              type acl-cos-range ;

              ncd:revise-date 2015-04-20 ;
            }

            choice vlan-conf {
              description 'Specify VLAN.' ;
              case vlan-value {
                if-feature vlan-value-config ;

                description 'Specify the VLAN value.' ;
                leaf inne-vlan-value {
                  description 'Specify the inner-layer VLAN value.' ;
                  type uint16 {
                    range 1..4094 ;

                  }

                }

                leaf outer-vlan-value {
                  description 'Specify the outer-layer VLAN value.' ;
                  type uint16 {
                    range 1..4094 ;

                  }

                }

              }

              case vlan-range {
                if-feature vlan-range-config ;

                description 'Specify the VLAN range.' ;
                leaf inner-vlan-range {
                  description 'Specify the range of the inner-layer VLAN.' ;
                  type acl-vlan-range ;

                }

                leaf cfi {
                  description 'Specify the CFI.' ;
                  type enumeration {
                    enum set {
                      value 1 ;
                      description 'Match when the flag is set.' ;
                    }

                    enum unset {
                      value 0 ;
                      description 'Match when the flag is not set.' ;
                    }

                  }

                  ncd:revise-date 2017-06-20 ;
                }

                leaf outer-vlan-range {
                  description 'Specify the range of the outer-layer VLAN.' ;
                  type acl-vlan-range ;

                }

                leaf dei {
                  description 'Specify the DEI.' ;
                  type enumeration {
                    enum set {
                      value 1 ;
                      description 'Match when the flag is set.' ;
                    }

                    enum unset {
                      value 0 ;
                      description 'Match when the flag is not set.' ;
                    }

                  }

                  ncd:revise-date 2017-06-20 ;
                }

              }

            }

            leaf time-range {
              description 'The name of the time range referenced by the ACL rule.
The referenced time range must exist.' ;
              type string {
                length 1..31 ;

              }

            }

            leaf log {
              if-feature link-log-config ;

              description 'Enable/Disable the function of counting matched packet data.' ;
              type boolean ;

              default false ;
              ncd:revise-date 2015-04-20 ;
            }

            leaf description {
              description 'The description of the rule.' ;
              type ncd:string-with-blank {
                length 1..70 {
                  description 'Direction for use, support 1-70 characters.' ;
                }

              }

              ncd:revise-date 2016-08-18 ;
            }

            leaf vrf {
              description 'Specify the VRF instance name.
The referenced VRF must exist.' ;
              type acl-vrf-name {
                length 1..32 {
                  description 'VPN Routing/Forwarding instance name, support 1-32 characters.' ;
                }

              }

              ncd:revise-date 2017-06-20 ;
            }

            leaf exp {
              description 'Specify the MPLS EXP value.' ;
              type uint8 {
                range 0..7 {
                  description 'Value of exp, support 0-7.' ;
                }

              }

              ncd:revise-date 2017-06-20 ;
            }

            leaf label {
              description 'Specify the outermost label value.' ;
              type uint32 {
                range 1..1048575 ;

              }

              ncd:revise-date 2019-06-18 ;
            }

            leaf label2 {
              description 'Specify the second-layer label value.' ;
              type uint32 {
                range 1..1048575 ;

              }

              ncd:revise-date 2019-06-18 ;
            }

          }

          container acl-description {
            leaf acl-description {
              type ncd:string-with-blank {
                length 1..79 {
                  description 'Description of an access control list, support 1-79 characters.' ;
                }

              }

              description 'The description of the ACL.' ;
              mandatory true ;
            }

            description 'The description of the ACL.' ;
            presence "Specify acl description" ;
            if-feature link-acl-description ;

            ncd:revise-date 2024-08-13 ;
          }

        }

        list user-protocol-access-list {
          if-feature user-protocol-feature ;

          description 'Configure the user protocol ACL.' ;
          key acl-name ;
          leaf acl-name {
            description 'Specify the ACL name.' ;
            type acl-name-type ;

          }

          list rule {
            description 'Configure a user protocol ACL rule.' ;
            key ruleid ;
            leaf ruleid {
              description 'Specify the rule ID.' ;
              type uint32 {
                range 1..2147483644 ;

              }

            }

            choice ethernet-type {
              description 'Specify the ethernet protocol type or any ethernet protocol type.' ;
              mandatory true ;
              case any-ethernet-type {
                description 'Any ethernet protocol type.' ;
                leaf any {
                  description 'Any ethernet protocol type.' ;
                  type empty ;

                }

              }

              case ethernet-type-value {
                description 'Specify the ethernet protocol type.' ;
                leaf ether-type {
                  description 'Specify the ethernet protocol type.' ;
                  type ncd:hex {
                    pattern "((0x){1}([1-9]|[a-f]|[A-F]){1}([0-9]|[a-f]|[A-F]){0,3})" ;

                  }

                }

              }

            }

            leaf destination-mac {
              description 'Destination MAC address.' ;
              type ncd:mac-address ;

              mandatory true ;
            }

            leaf destination-mac-wildcard {
              description 'Destination MAC address wildcard.' ;
              type ncd:mac-address ;

              mandatory true ;
            }

          }

          ncd:revise-date 2015-11-04 ;
        }

        list user-defined-list {
          if-feature user-defined-feature ;

          description 'Configure the user-defined ACL.' ;
          key acl-name ;
          leaf acl-name {
            description 'Specify the ACL name.' ;
            type acl-name-type ;

          }

          list rule {
            description 'Configure a user-defined ACL rule.' ;
            key ruleid ;
            leaf ruleid {
              description 'Specify the rule ID.' ;
              type uint32 {
                range 1..2147483644 ;

              }

            }

            choice permit-deny {
              description 'Specify the action as either permit or deny.' ;
              mandatory true ;
              case deny {
                description 'Deny the packets that match the rule.' ;
                leaf deny {
                  description 'Deny the packets that match the rule.' ;
                  type empty ;

                }

              }

              case permit {
                description 'Permit the packets that match the rule.' ;
                leaf permit {
                  description 'Permit the packets that match the rule.' ;
                  type empty ;

                  mandatory true ;
                }

              }

            }

            leaf frame-type {
              description 'Specify the ethernet frame type.' ;
              type enumeration {
                enum any {
                  value 4 ;
                  description 'Any frame.' ;
                }

                enum ethernet2 {
                  value 1 ;
                  description 'Ethernet version II frame.' ;
                }

                enum llc-snap {
                  value 2 ;
                  description 'LLC/SNAP frame in IEEE802.3.' ;
                }

                enum sap {
                  value 3 ;
                  description 'SAP frame in IEEE802.3.' ;
                }

              }

              mandatory true ;
            }

            leaf tag-status {
              description 'Specify the status of the VLAN tag.' ;
              type enumeration {
                enum untag {
                  value 1 ;
                  description 'Status with no VLAN tag.' ;
                }

                enum single-tag {
                  value 2 ;
                  description 'Status with VLAN tag.' ;
                }

                enum double-tag {
                  value 3 ;
                  description 'Status with outer and inner VLAN tag.' ;
                }

                enum any {
                  value 4 ;
                  description 'Any status with VLAN tag.' ;
                }

              }

              mandatory true ;
            }

            leaf ip-flag {
              description 'Specify the type of IP packet header.' ;
              type enumeration {
                enum ip4-hdr-only {
                  value 1 ;
                  description 'Segment of only IPv4 header.' ;
                }

                enum ip6-hdr-only {
                  value 2 ;
                  description 'Segment of only IPv6 header.' ;
                }

                enum ip6-fragment {
                  value 3 ;
                  description 'Segment of IPv6 fragment.' ;
                }

                enum ip4-over-ip4 {
                  value 4 ;
                  description 'Segment of IPv4 datagram over IPv4.' ;
                }

                enum ip6-over-ip4 {
                  value 5 ;
                  description 'Segment of IPv6 datagram over IPv4' ;
                }

                enum ip6-fragment-over-ip4 {
                  value 6 ;
                  description 'Segment of IPv6 fragment datagram over IPv4.' ;
                }

                enum ip4-over-ip6 {
                  value 7 ;
                  description 'Segment of IPv4 datagram over IPv6.' ;
                }

                enum ip6-over-ip6 {
                  value 8 ;
                  description 'Segment of IPv6 datagram over IPv6.' ;
                }

                enum gre-ip4-over-ip4 {
                  value 9 ;
                  description 'Segment of IPv4 datagram over IPv4 by GRE.' ;
                }

                enum gre-ip6-over-ip4 {
                  value 10 ;
                  description 'Segment of IPv6 datagram over IPv4 by GRE.' ;
                }

                enum gre-ip4-over-ip6 {
                  value 11 ;
                  description 'Segment of IPv4 datagram over IPv6 by GRE.' ;
                }

                enum gre-ip6-over-ip6 {
                  value 12 ;
                  description 'Segment of IPv6 datagram over IPv6 by GRE.' ;
                }

                enum ip-unused {
                  value 13 ;
                  description 'None IP format datagram.' ;
                }

                enum one-mpls-label {
                  value 14 ;
                  description 'Segment of the first label out of tunnel.' ;
                }

                enum two-mpls-labels {
                  value 15 ;
                  description 'Segment of the second label in tunnel.' ;
                }

                enum any-mpls-labels {
                  value 16 ;
                  description 'Segment of any or multiple MPLS label.' ;
                }

                enum any {
                  value 17 ;
                  description 'Any segment' ;
                }

              }

              mandatory true ;
            }

            choice segment-type {
              description 'Type of the rule segment.' ;
              mandatory true ;
              case any-segment {
                description 'Any rule segment.' ;
                leaf any {
                  description 'Any rule segment.' ;
                  type empty ;

                  mandatory true ;
                }

              }

              case segment {
                description 'Configure the rule segment.' ;
                container segment1 {
                  description 'Configure the first segment.' ;
                  leaf offset {
                    description 'The first match field offset.' ;
                    type uint32 {
                      range 2..126 ;

                    }

                    mandatory true ;
                  }

                  leaf rule-string {
                    description 'The first match field value.' ;
                    type string {
                      length 10 {
                        description 'User defined hexadecimal string,as follows:
0x00000000-0xffffffff.' ;
                      }

                    }

                    mandatory true ;
                  }

                  leaf rule-mask {
                    description 'The first match field mask.' ;
                    type string {
                      length 10 {
                        description 'User defined hexadecimal string mask,as follows:
0x00000000-0xffffffff.' ;
                      }

                    }

                    mandatory true ;
                  }

                  container segment2 {
                    description 'Configure the second segment.' ;
                    presence segment2 ;
                    leaf offset {
                      description 'The second match field offset.' ;
                      type uint32 {
                        range 2..126 ;

                      }

                      mandatory true ;
                    }

                    leaf rule-string {
                      description 'The second match field value.' ;
                      type string {
                        length 10 {
                          description 'User defined hexadecimal string,as follows:
0x00000000-0xffffffff.' ;
                        }

                      }

                      mandatory true ;
                    }

                    leaf rule-mask {
                      description 'The second match field mask.' ;
                      type string {
                        length 10 {
                          description 'User defined hexadecimal string mask,as follows:
0x00000000-0xffffffff.' ;
                        }

                      }

                      mandatory true ;
                    }

                    container segment3 {
                      description 'Configure the third segment.' ;
                      presence segment3 ;
                      leaf offset {
                        description 'The third match field offset.' ;
                        type uint32 {
                          range 2..126 ;

                        }

                        mandatory true ;
                      }

                      leaf rule-string {
                        description 'The third match field value.' ;
                        type string {
                          length 10 {
                            description 'User defined hexadecimal string,as follows:
0x00000000-0xffffffff.' ;
                          }

                        }

                        mandatory true ;
                      }

                      leaf rule-mask {
                        description 'The third match field mask.' ;
                        type string {
                          length 10 {
                            description 'User defined hexadecimal string mask,as follows:
0x00000000-0xffffffff.' ;
                          }

                        }

                        mandatory true ;
                      }

                      container segment4 {
                        description 'Configure the fourth segment.' ;
                        presence segment4 ;
                        leaf offset {
                          description 'The fourth match field offset.' ;
                          type uint32 {
                            range 2..126 ;

                          }

                          mandatory true ;
                        }

                        leaf rule-string {
                          description 'The fourth match field value.' ;
                          type string {
                            length 10 {
                              description 'User defined hexadecimal string,as follows:
0x00000000-0xffffffff.' ;
                            }

                          }

                          mandatory true ;
                        }

                        leaf rule-mask {
                          description 'The fourth match field mask.' ;
                          type string {
                            length 10 {
                              description 'User defined hexadecimal string mask,as follows:
0x00000000-0xffffffff.' ;
                            }

                          }

                          mandatory true ;
                        }

                      }

                    }

                  }

                }

              }

            }

            leaf time-range {
              description 'The name of the time range referenced by the ACL rule.
The referenced time range must exist.' ;
              type string {
                length 1..31 ;

              }

            }

          }

          ncd:revise-date 2015-12-23 ;
        }

        container ipv4-vxlan-access-lists {
          description 'Configure the IPv4 VXLAN ACL.' ;
          list ipv4-vxlan-access-list {
            if-feature ipv4-vxlan-feature ;

            description 'Configure the IPv4 VXLAN ACL.' ;
            key acl-name ;
            leaf acl-name {
              description 'Specify the ACL name.' ;
              type acl-name-type ;

            }

            leaf without-vni {
              description 'Configure rules without virtual network ID.' ;
              type empty ;

            }

            leaf mode-type {
              description 'Mode type of the IPv4 VXLAN ACL.' ;
              type enumeration {
                enum transit-inner {
                  value 1 ;
                  description 'Transit node match VXLAN inner layer' ;
                }

                enum transit-outer {
                  value 2 ;
                  description 'Transit node match VXLAN outer layer' ;
                }

                enum vtep-inner {
                  value 3 ;
                  description 'VTEP node match VXLAN inner layer' ;
                }

                enum vtep-outer {
                  value 4 ;
                  description 'VTEP node match VXLAN outer layer' ;
                }

                enum outer-v4-transit-inner {
                  value 5 ;
                  description 'Transit node match VXLAN inner layer whose underlay is IPv4' ;
                }

                enum outer-v6-transit-inner {
                  value 6 ;
                  description 'Transit node match VXLAN inner layer whose underlay is IPv6' ;
                }

                enum outer-v4-vtep-inner {
                  value 7 ;
                  description 'VTEP node match VXLAN inner layer whose underlay is IPv4' ;
                }

                enum outer-v6-vtep-inner {
                  description 'VTEP node match VXLAN inner layer whose underlay is IPv6' ;
                  value 8 ;
                }

              }

              ncd:revise-date 2018-09-17 ;
            }

            container rules {
              description 'Configure the IPv4 VXLAN ACL rules in default mode.
An IPv4 VXLAN ACL without a mode type must be configured first.' ;
              list rule {
                description 'Configure an IPv4 VXLAN ACL rule in default mode.' ;
                key ruleid ;
                leaf ruleid {
                  description 'Specify the rule ID.' ;
                  type uint32 {
                    range 1..2147483644 ;

                  }

                }

                choice permit-deny {
                  description 'Specify the action as either permit or deny.' ;
                  mandatory true ;
                  case deny {
                    description 'Deny the packets that match the rule.' ;
                    leaf deny {
                      description 'Deny the packets that match the rule.' ;
                      type empty ;

                      mandatory true ;
                    }

                  }

                  case permit {
                    description 'Permit the packets that match the rule.' ;
                    leaf permit {
                      description 'Permit the packets that match the rule.' ;
                      type empty ;

                      mandatory true ;
                    }

                  }

                }

                container inner-layer {
                  description 'The inner-layer protocol of VXLAN.' ;
                  choice protocol-type {
                    description 'IPv4 protocol type.' ;
                    mandatory true ;
                    case tcp-udp {
                      description 'The protocol number is UDP or TCP.' ;
                      container tcp-udp {
                        description 'The protocol number is UDP or TCP.' ;
                        leaf tcp-udp {
                          description 'The protocol number is UDP or TCP.' ;
                          type enumeration {
                            enum tcp {
                              value 6 ;
                              description 'Transmission Control Protocol(6)' ;
                            }

                            enum udp {
                              value 17 ;
                              description 'User Datagram Protocol(17)' ;
                            }

                          }

                          mandatory true ;
                        }

                        choice src-addr {
                          description 'Specify source IP address.' ;
                          mandatory true ;
                          case addr-type {
                            description 'Source IP address.' ;
                            leaf src-address {
                              description 'Source IP address.' ;
                              type ncd:ipv4-address ;

                              mandatory true ;
                            }

                            leaf src-wildcard {
                              description 'Source IP address wildcard.' ;
                              type ncd:ipv4-address ;

                              mandatory true ;
                            }

                          }

                          case any-type {
                            description 'Any source IP address.' ;
                            leaf src-any-addr {
                              description 'Any source IP address.' ;
                              type empty ;

                              mandatory true ;
                            }

                          }

                        }

                        choice src-port {
                          status obsolete {
                            ncd:revise-date 2017-07-20 ;
                          }

                          description 'Configure source port.' ;
                          case src-oper {
                            status obsolete {
                              ncd:revise-date 2017-07-20 ;
                            }

                            description 'Configure source port.' ;
                            leaf src-oper {
                              status obsolete {
                                ncd:revise-date 2017-07-20 ;
                              }

                              description 'source port operator.
Operator type
eq(1)   : match only packets on a given port number
ge(2)   : match only packets with a no lower port number
le(3)   : match only packets with a no greater port number.' ;
                              type enumeration {
                                enum eq {
                                  value 1 ;
                                  description 'Match only packets on a given port number.' ;
                                }

                                enum ge {
                                  value 2 ;
                                  description 'Match only packets with a no lower port number.' ;
                                }

                                enum le {
                                  value 3 ;
                                  description 'Match only packets with a no greater port number.' ;
                                }

                              }

                              mandatory true ;
                            }

                            leaf src-port-number {
                              status obsolete {
                                ncd:revise-date 2017-07-20 ;
                              }

                              description 'Configure port number from 0 to 65535.' ;
                              type uint16 {
                                range 0..65535 ;

                              }

                              mandatory true ;
                            }

                          }

                          case src-range {
                            status obsolete {
                              ncd:revise-date 2017-07-20 ;
                            }

                            description 'configure range type source port.' ;
                            leaf src-range {
                              status obsolete {
                                ncd:revise-date 2017-07-20 ;
                              }

                              description 'configure range type source port.' ;
                              type empty ;

                              mandatory true ;
                            }

                            leaf src-range-value {
                              status obsolete {
                                ncd:revise-date 2017-07-20 ;
                              }

                              description 'Port range.' ;
                              type acl-port-range ;

                              mandatory true ;
                            }

                          }

                        }

                        container source-port {
                          description 'Specify the source port.' ;
                          presence "Specify source port" ;
                          choice source-port {
                            description 'Specify the source port.' ;
                            mandatory true ;
                            case src-port-value {
                              description 'Specify the value of the source port number.' ;
                              container src-port-value {
                                description 'Specify the value of the source port number.' ;
                                presence "Configure port number" ;
                                leaf src-port-operator {
                                  description 'Specify the operation type of the source port number.' ;
                                  type enumeration {
                                    enum eq {
                                      value 1 ;
                                      description 'Equal to.' ;
                                    }

                                    enum ge {
                                      value 2 ;
                                      description 'Great than or equal to.' ;
                                    }

                                    enum le {
                                      value 3 ;
                                      description 'Less than or equal to.' ;
                                    }

                                  }

                                  mandatory true ;
                                }

                                leaf src-port-value {
                                  description 'Specify the value of the source port number.' ;
                                  type uint16 {
                                    range 0..65535 ;

                                  }

                                  mandatory true ;
                                }

                              }

                            }

                            case src-port-range {
                              description 'Specify the range of the source port number.' ;
                              container src-port-range {
                                description 'Specify the range of the source port number.' ;
                                presence "Configure port range" ;
                                leaf src-port-operator {
                                  description 'Specify the operation type of the source port number.' ;
                                  type enumeration {
                                    enum range {
                                      value 7 ;
                                      description 'Range.' ;
                                    }

                                  }

                                  mandatory true ;
                                }

                                leaf src-port-range {
                                  description 'Specify the range of the source port number.' ;
                                  type acl-port-range ;

                                  mandatory true ;
                                }

                              }

                            }

                          }

                          ncd:revise-date 2017-07-20 ;
                        }

                        choice dst-addr {
                          description 'Specify destination IP address.' ;
                          mandatory true ;
                          case addr-type {
                            description 'Destination IP address.' ;
                            leaf dst-address {
                              description 'Destination IP address.' ;
                              type ncd:ipv4-address ;

                              mandatory true ;
                            }

                            leaf dst-wildcard {
                              description 'Destination IP address wildcard.' ;
                              type ncd:ipv4-address ;

                              mandatory true ;
                            }

                          }

                          case any-type {
                            description 'Any destination IP address.' ;
                            leaf dst-any-addr {
                              description 'Any destination IP address.' ;
                              type empty ;

                              mandatory true ;
                            }

                          }

                        }

                        choice dst-port {
                          status obsolete {
                            ncd:revise-date 2017-07-20 ;
                          }

                          description 'Configure destination port.' ;
                          case dst-oper {
                            status obsolete {
                              ncd:revise-date 2017-07-20 ;
                            }

                            description 'Configure destination port with operator flag.' ;
                            leaf dst-oper {
                              status obsolete {
                                ncd:revise-date 2017-07-20 ;
                              }

                              description 'Operator type
eq(1)   : match only packets on a given port number
ge(2)   : match only packets with a no lower port number
le(3)   : match only packets with a no greater port number.' ;
                              type enumeration {
                                enum eq {
                                  value 1 ;
                                  description 'Match only packets on a given port number.' ;
                                }

                                enum ge {
                                  value 2 ;
                                  description 'Match only packets with a no lower port number.' ;
                                }

                                enum le {
                                  value 3 ;
                                  description 'Match only packets with a no greater port number.' ;
                                }

                              }

                              mandatory true ;
                            }

                            leaf dst-port-number {
                              status obsolete {
                                ncd:revise-date 2017-07-20 ;
                              }

                              description 'Configure port number from 0 to 65535.' ;
                              type uint16 {
                                range 0..65535 ;

                              }

                              mandatory true ;
                            }

                          }

                          case dst-range {
                            status obsolete {
                              ncd:revise-date 2017-07-20 ;
                            }

                            description 'Configure destination port in range type.' ;
                            leaf dst-range {
                              status obsolete {
                                ncd:revise-date 2017-07-20 ;
                              }

                              description 'Range operator.' ;
                              type empty ;

                              mandatory true ;
                            }

                            leaf dst-range-value {
                              status obsolete {
                                ncd:revise-date 2017-07-20 ;
                              }

                              description 'Destination port range.' ;
                              type acl-port-range ;

                              mandatory true ;
                            }

                          }

                        }

                        container destination-port {
                          description 'Specify the destination port.' ;
                          presence "Specify destination port" ;
                          choice destination-port {
                            description 'Specify the destination port.' ;
                            mandatory true ;
                            case dst-port-value {
                              description 'Specify the value of the destination port number.' ;
                              container dst-port-value {
                                description 'Specify the value of the destination port number.' ;
                                presence "Configure port number" ;
                                leaf dst-port-operator {
                                  description 'Specify the operation type of the destination port number.' ;
                                  type enumeration {
                                    enum eq {
                                      value 1 ;
                                      description 'Equal to.' ;
                                    }

                                    enum ge {
                                      value 2 ;
                                      description 'Great than or equal to.' ;
                                    }

                                    enum le {
                                      value 3 ;
                                      description 'Less than or equal to.' ;
                                    }

                                  }

                                  mandatory true ;
                                }

                                leaf dst-port-value {
                                  description 'Specify the value of the destination port number.' ;
                                  type uint16 {
                                    range 0..65535 ;

                                  }

                                  mandatory true ;
                                }

                              }

                            }

                            case dst-port-range {
                              description 'Specify the range of the destination port number.' ;
                              container dst-port-range {
                                description 'Specify the range of the destination port number.' ;
                                presence "Configure port range" ;
                                leaf dst-port-operator {
                                  description 'Specify the operation type of the destination port number.' ;
                                  type enumeration {
                                    enum range {
                                      value 7 ;
                                      description 'Range.' ;
                                    }

                                  }

                                  mandatory true ;
                                }

                                leaf dst-port-range {
                                  description 'Specify the range of the destination port number.' ;
                                  type acl-port-range ;

                                  mandatory true ;
                                }

                              }

                            }

                          }

                          ncd:revise-date 2017-07-20 ;
                        }

                        leaf rst {
                          type acl-tcp-flag ;

                          description 'Specify the RST flag.
When the value of tcp-udp is tcp, the node is valid.' ;
                          if-feature vxlan-acl-tcp-flag ;

                          ncd:revise-date 2024-06-01 ;
                        }

                        leaf ack {
                          type acl-tcp-flag ;

                          description 'Specify the ACK flag.
When the value of tcp-udp is tcp, the node is valid.' ;
                          if-feature vxlan-acl-tcp-flag ;

                          ncd:revise-date 2024-06-01 ;
                        }

                        leaf fin {
                          type acl-tcp-flag ;

                          description 'Specify the FIN flag.
When the value of tcp-udp is tcp, the node is valid.' ;
                          if-feature vxlan-acl-tcp-flag ;

                          ncd:revise-date 2024-06-01 ;
                        }

                        leaf syn {
                          type acl-tcp-flag ;

                          description 'Specify the SYN flag.
When the value of tcp-udp is tcp, the node is valid.' ;
                          if-feature vxlan-acl-tcp-flag ;

                          ncd:revise-date 2024-06-01 ;
                        }

                        leaf psh {
                          type acl-tcp-flag ;

                          description 'Specify the PSH flag.
When the value of tcp-udp is tcp, the node is valid.' ;
                          if-feature vxlan-acl-tcp-flag ;

                          ncd:revise-date 2024-06-01 ;
                        }

                        leaf urg {
                          type acl-tcp-flag ;

                          description 'Specify the URG flag.
When the value of tcp-udp is tcp, the node is valid.' ;
                          if-feature vxlan-acl-tcp-flag ;

                          ncd:revise-date 2024-06-01 ;
                        }

                      }

                    }

                    case ip {
                      description 'The protocol number is a value excluding TCP and UDP.' ;
                      container ipv4-protocol {
                        description 'The protocol number is a value excluding TCP and UDP.' ;
                        leaf protocol-type {
                          description 'Specify the IP protocol type excluding TCP and UDP.' ;
                          type uint16 {
                            range "0..5 | 7..16 | 18..255 | 65535" ;

                          }

                          mandatory true ;
                        }

                        choice src-addr {
                          description 'Specify source IP address.' ;
                          mandatory true ;
                          case addr-type {
                            description 'Source IP address.' ;
                            leaf src-address {
                              description 'Source IP address.' ;
                              type ncd:ipv4-address ;

                              mandatory true ;
                            }

                            leaf src-wildcard {
                              description 'Source IP address wildcard.' ;
                              type ncd:ipv4-address ;

                              mandatory true ;
                            }

                          }

                          case any-type {
                            description 'Any source IP address.' ;
                            leaf src-any-addr {
                              description 'Any source IP address.' ;
                              type empty ;

                              mandatory true ;
                            }

                          }

                        }

                        choice dst-addr {
                          description 'Specify destination IP address.' ;
                          mandatory true ;
                          case addr-type {
                            description 'Destination IP address.' ;
                            leaf dst-address {
                              description 'Destination IP address.' ;
                              type ncd:ipv4-address ;

                              mandatory true ;
                            }

                            leaf dst-wildcard {
                              description 'Destination IP address wildcard.' ;
                              type ncd:ipv4-address ;

                              mandatory true ;
                            }

                          }

                          case any-type {
                            description 'Any destination IP address.' ;
                            leaf dst-any-addr {
                              description 'Any destination IP address.' ;
                              type empty ;

                              mandatory true ;
                            }

                          }

                        }

                      }

                    }

                  }

                  choice priority {
                    description 'Configure precedence or TOS or DSCP.' ;
                    case dscp {
                      description 'Specify the DSCP value.' ;
                      leaf dscp {
                        description 'Specify the DSCP value.' ;
                        type uint8 {
                          range 0..63 ;

                        }

                      }

                    }

                    case precedence {
                      description 'Specify the precedence value.' ;
                      leaf precedence {
                        description 'Specify the precedence value.' ;
                        type uint8 {
                          range 0..7 ;

                        }

                      }

                    }

                    case tos {
                      description 'Specify the TOS value.' ;
                      leaf tos {
                        description 'Specify the TOS value.' ;
                        type uint8 {
                          range 0..15 ;

                        }

                      }

                    }

                  }

                  leaf ip-flags {
                    type string {
                      length 3 {
                        description 'The binary form value of IP flags, ranging from 000 to 011.' ;
                      }

                    }

                    description 'The binary value of the IP flags, ranging from 000 to 011.' ;
                    if-feature ip-flags-config ;

                    ncd:revise-date 2024-03-22 ;
                  }

                }

                container vni {
                  description 'VXLAN ID.' ;
                  presence vni ;
                  leaf vxlan-id {
                    description 'VXLAN ID.' ;
                    type uint32 {
                      range 1..16777215 ;

                    }

                    mandatory true ;
                  }

                }

                container sgt {
                  description 'Security group tag.' ;
                  presence sgt ;
                  leaf sgt-value {
                    description 'The security group tag value.' ;
                    type uint16 ;

                    mandatory true ;
                  }

                  ncd:revise-date 2019-08-14 ;
                }

                container outer-layer {
                  description 'The outer-layer protocol of VXLAN.' ;
                  presence outer-layer ;
                  leaf udp {
                    description 'The protocol number is UDP.' ;
                    type empty ;

                    mandatory true ;
                  }

                  choice src-addr {
                    description 'Specify source IP address.' ;
                    mandatory true ;
                    case addr-type {
                      description 'Source IP address.' ;
                      leaf src-address {
                        description 'Source IP address.' ;
                        type ncd:ipv4-address ;

                        mandatory true ;
                      }

                      leaf src-wildcard {
                        description 'Source IP address wildcard.' ;
                        type ncd:ipv4-address ;

                        mandatory true ;
                      }

                    }

                    case any-type {
                      description 'Any source IP address.' ;
                      leaf src-any-addr {
                        description 'Any source IP address.' ;
                        type empty ;

                        mandatory true ;
                      }

                    }

                  }

                  choice src-port {
                    status obsolete {
                      ncd:revise-date 2017-07-20 ;
                    }

                    description 'Configure source port.' ;
                    case src-oper {
                      status obsolete {
                        ncd:revise-date 2017-07-20 ;
                      }

                      description 'Configure source port.' ;
                      leaf src-oper {
                        status obsolete {
                          ncd:revise-date 2017-07-20 ;
                        }

                        description 'source port operator.
Operator type
eq(1)   : match only packets on a given port number
ge(2)   : match only packets with a no lower port number
le(3)   : match only packets with a no greater port number.' ;
                        type enumeration {
                          enum eq {
                            value 1 ;
                            description 'Match only packets on a given port number.' ;
                          }

                          enum ge {
                            value 2 ;
                            description 'Match only packets with a no lower port number.' ;
                          }

                          enum le {
                            value 3 ;
                            description 'Match only packets with a no greater port number.' ;
                          }

                        }

                        mandatory true ;
                      }

                      leaf src-port-number {
                        status obsolete {
                          ncd:revise-date 2017-07-20 ;
                        }

                        description 'Port number.' ;
                        type uint16 {
                          range 0..65535 ;

                        }

                        mandatory true ;
                      }

                    }

                    case src-range {
                      status obsolete {
                        ncd:revise-date 2017-07-20 ;
                      }

                      description 'configure range type source port.' ;
                      leaf src-range {
                        status obsolete {
                          ncd:revise-date 2017-07-20 ;
                        }

                        description 'configure range type source port.' ;
                        type empty ;

                        mandatory true ;
                      }

                      leaf src-range-value {
                        status obsolete {
                          ncd:revise-date 2017-07-20 ;
                        }

                        description 'Port range.' ;
                        type acl-port-range ;

                        mandatory true ;
                      }

                    }

                  }

                  container source-port {
                    description 'Specify the source port.' ;
                    presence "Specify source port" ;
                    choice source-port {
                      description 'Specify the source port.' ;
                      mandatory true ;
                      case src-port-value {
                        description 'Specify the value of the source port number.' ;
                        container src-port-value {
                          description 'Specify the value of the source port number.' ;
                          presence "Configure port number" ;
                          leaf src-port-operator {
                            description 'Specify the operation type of the source port number.' ;
                            type enumeration {
                              enum eq {
                                value 1 ;
                                description 'Equal to.' ;
                              }

                              enum ge {
                                value 2 ;
                                description 'Great than or equal to.' ;
                              }

                              enum le {
                                value 3 ;
                                description 'Less than or equal to.' ;
                              }

                            }

                            mandatory true ;
                          }

                          leaf src-port-value {
                            description 'Specify the value of the source port number.' ;
                            type uint16 {
                              range 0..65535 ;

                            }

                            mandatory true ;
                          }

                        }

                      }

                      case src-port-range {
                        description 'Specify the range of the source port number.' ;
                        container src-port-range {
                          description 'Specify the range of the source port number.' ;
                          presence "Configure port range" ;
                          leaf src-port-operator {
                            description 'Specify the operation type of the source port number.' ;
                            type enumeration {
                              enum range {
                                value 7 ;
                                description 'Range.' ;
                              }

                            }

                            mandatory true ;
                          }

                          leaf src-port-range {
                            description 'Specify the range of the source port number.' ;
                            type acl-port-range ;

                            mandatory true ;
                          }

                        }

                      }

                    }

                    ncd:revise-date 2017-07-20 ;
                  }

                  choice dst-addr {
                    description 'Specify destination IP address.' ;
                    mandatory true ;
                    case addr-type {
                      description 'Destination IP address.' ;
                      leaf dst-address {
                        description 'Destination IP address.' ;
                        type ncd:ipv4-address ;

                        mandatory true ;
                      }

                      leaf dst-wildcard {
                        description 'Destination IP address wildcard.' ;
                        type ncd:ipv4-address ;

                        mandatory true ;
                      }

                    }

                    case any-type {
                      description 'Any Destination IP address.' ;
                      leaf dst-any-addr {
                        description 'Any Destination IP address.' ;
                        type empty ;

                        mandatory true ;
                      }

                    }

                  }

                  choice dst-port {
                    status obsolete {
                      ncd:revise-date 2017-07-20 ;
                    }

                    description 'Configure destination port.' ;
                    case dst-oper {
                      status obsolete {
                        ncd:revise-date 2017-07-20 ;
                      }

                      description 'Configure destination port with operator flag.' ;
                      leaf dst-oper {
                        status obsolete {
                          ncd:revise-date 2017-07-20 ;
                        }

                        description 'Operator type
eq(1)   : match only packets on a given port number
ge(2)   : match only packets with a no lower port number
le(3)   : match only packets with a no greater port number.' ;
                        type enumeration {
                          enum eq {
                            value 1 ;
                            description 'Match only packets on a given port number.' ;
                          }

                          enum ge {
                            value 2 ;
                            description 'Match only packets with a no lower port number.' ;
                          }

                          enum le {
                            value 3 ;
                            description 'Match only packets with a no greater port number.' ;
                          }

                        }

                        mandatory true ;
                      }

                      leaf dst-port-number {
                        status obsolete {
                          ncd:revise-date 2017-07-20 ;
                        }

                        description 'Port number.' ;
                        type uint16 {
                          range 0..65535 ;

                        }

                        mandatory true ;
                      }

                    }

                    case dst-range {
                      status obsolete {
                        ncd:revise-date 2017-07-20 ;
                      }

                      description 'Configure destination port in range type.' ;
                      leaf dst-range {
                        status obsolete {
                          ncd:revise-date 2017-07-20 ;
                        }

                        description 'Range operator.' ;
                        type empty ;

                        mandatory true ;
                      }

                      leaf dst-range-value {
                        status obsolete {
                          ncd:revise-date 2017-07-20 ;
                        }

                        description 'Destination port range.' ;
                        type acl-port-range ;

                        mandatory true ;
                      }

                    }

                  }

                  container destination-port {
                    description 'Specify the destination port.' ;
                    presence "Specify destination port" ;
                    choice destination-port {
                      description 'Specify the destination port.' ;
                      mandatory true ;
                      case dst-port-value {
                        description 'Specify the value of the destination port number.' ;
                        container dst-port-value {
                          description 'Specify the value of the destination port number.' ;
                          presence "Configure port number" ;
                          leaf dst-port-operator {
                            description 'Specify the operation type of the destination port number.' ;
                            type enumeration {
                              enum eq {
                                value 1 ;
                                description 'Equal to.' ;
                              }

                              enum ge {
                                value 2 ;
                                description 'Great than or equal to.' ;
                              }

                              enum le {
                                value 3 ;
                                description 'Less than or equal to.' ;
                              }

                            }

                            mandatory true ;
                          }

                          leaf dst-port-value {
                            description 'Specify the value of the destination port number.' ;
                            type uint16 {
                              range 0..65535 ;

                            }

                            mandatory true ;
                          }

                        }

                      }

                      case dst-port-range {
                        description 'Specify the range of the destination port number.' ;
                        container dst-port-range {
                          description 'Specify the range of the destination port number.' ;
                          presence "Configure port range" ;
                          leaf dst-port-operator {
                            description 'Specify the operation type of the destination port number.' ;
                            type enumeration {
                              enum range {
                                value 7 ;
                                description 'Range.' ;
                              }

                            }

                            mandatory true ;
                          }

                          leaf dst-port-range {
                            description 'Specify the range of the destination port number.' ;
                            type acl-port-range ;

                            mandatory true ;
                          }

                        }

                      }

                    }

                    ncd:revise-date 2017-07-20 ;
                  }

                  choice priority {
                    description 'Configure precedence or TOS or DSCP.' ;
                    case dscp {
                      description 'Specify the DSCP value.' ;
                      leaf dscp {
                        description 'Specify the DSCP value.' ;
                        type uint8 {
                          range 0..63 ;

                        }

                      }

                    }

                    case precedence {
                      description 'Specify the precedence value.' ;
                      leaf precedence {
                        description 'Specify the precedence value.' ;
                        type uint8 {
                          range 0..7 ;

                        }

                      }

                    }

                    case tos {
                      description 'Specify the TOS value.' ;
                      leaf tos {
                        description 'Specify the TOS value.' ;
                        type uint8 {
                          range 0..15 ;

                        }

                      }

                    }

                  }

                }

                leaf vrf {
                  description 'Specify the VRF instance name.
The referenced VRF must exist.' ;
                  type acl-vrf-name {
                    length 1..32 {
                      description 'VPN Routing/Forwarding instance name, support 1-32 characters.' ;
                    }

                  }

                  ncd:revise-date 2018-09-17 ;
                }

                leaf time-range {
                  description 'The name of the time range referenced by the ACL rule.
The referenced time range must exist.' ;
                  type string {
                    length 1..31 ;

                  }

                  ncd:revise-date 2021-04-02 ;
                }

                leaf log {
                  if-feature log-config ;

                  description 'Enable/Disable the function of counting matched packet data.' ;
                  type boolean ;

                  default false ;
                  ncd:revise-date 2022-01-20 ;
                }

              }

            }

            container rules-transit-inner {
              description 'Configure the IPv4 VXLAN ACL rules in transit-inner mode.
An IPv4 VXLAN ACL in transit-inner mode must be configured first.' ;
              list rule-transit-inner {
                description 'Configure an IPv4 VXLAN ACL rule in transit-inner mode.' ;
                key ruleid ;
                leaf ruleid {
                  description 'Specify the rule ID.' ;
                  type uint32 {
                    range 1..2147483644 ;

                  }

                }

                choice permit-deny {
                  description 'Specify the action as either permit or deny.' ;
                  mandatory true ;
                  case deny {
                    description 'Deny the packets that match the rule.' ;
                    leaf deny {
                      description 'Deny the packets that match the rule.' ;
                      type empty ;

                      mandatory true ;
                    }

                  }

                  case permit {
                    description 'Permit the packets that match the rule.' ;
                    leaf permit {
                      description 'Permit the packets that match the rule.' ;
                      type empty ;

                      mandatory true ;
                    }

                  }

                }

                container inner-layer {
                  description 'The inner-layer protocol of VXLAN.' ;
                  presence inner-layer ;
                  choice protocol-type {
                    description 'IPv4 protocol type.' ;
                    mandatory true ;
                    case tcp-udp {
                      description 'The protocol number is UDP or TCP.' ;
                      container tcp-udp {
                        description 'The protocol number is UDP or TCP.' ;
                        leaf tcp-udp {
                          description 'The protocol number is UDP or TCP.' ;
                          type enumeration {
                            enum tcp {
                              value 6 ;
                              description 'Transmission Control Protocol(6)' ;
                            }

                            enum udp {
                              value 17 ;
                              description 'User Datagram Protocol(17)' ;
                            }

                          }

                          mandatory true ;
                        }

                        choice src-addr {
                          description 'Specify source IP address.' ;
                          mandatory true ;
                          case addr-type {
                            description 'Source IP address.' ;
                            leaf src-address {
                              description 'Source IP address.' ;
                              type ncd:ipv4-address ;

                              mandatory true ;
                            }

                            leaf src-wildcard {
                              description 'Source IP address wildcard.' ;
                              type ncd:ipv4-address ;

                              mandatory true ;
                            }

                          }

                          case any-type {
                            description 'Any source IP address.' ;
                            leaf src-any-addr {
                              description 'Any source IP address.' ;
                              type empty ;

                              mandatory true ;
                            }

                          }

                        }

                        container source-port {
                          description 'Specify the source port.' ;
                          presence "Specify source port" ;
                          choice source-port {
                            description 'Specify the source port.' ;
                            mandatory true ;
                            case src-port-value {
                              description 'Specify the value of the source port number.' ;
                              container src-port-value {
                                description 'Specify the value of the source port number.' ;
                                presence "Configure port number" ;
                                leaf src-port-operator {
                                  description 'Specify the operation type of the source port number.' ;
                                  type enumeration {
                                    enum eq {
                                      value 1 ;
                                      description 'Equal to.' ;
                                    }

                                    enum ge {
                                      value 2 ;
                                      description 'Great than or equal to.' ;
                                    }

                                    enum le {
                                      value 3 ;
                                      description 'Less than or equal to.' ;
                                    }

                                  }

                                  mandatory true ;
                                }

                                leaf src-port-value {
                                  description 'Specify the value of the source port number.' ;
                                  type uint16 {
                                    range 0..65535 ;

                                  }

                                  mandatory true ;
                                }

                              }

                            }

                            case src-port-range {
                              description 'Specify the range of the source port number.' ;
                              container src-port-range {
                                description 'Specify the range of the source port number.' ;
                                presence "Configure port range" ;
                                leaf src-port-operator {
                                  description 'Specify the operation type of the source port number.' ;
                                  type enumeration {
                                    enum range {
                                      value 7 ;
                                      description 'Range.' ;
                                    }

                                  }

                                  mandatory true ;
                                }

                                leaf src-port-range {
                                  description 'Specify the range of the source port number.' ;
                                  type acl-port-range ;

                                  mandatory true ;
                                }

                              }

                            }

                          }

                        }

                        choice dst-addr {
                          description 'Specify destination IP address.' ;
                          mandatory true ;
                          case addr-type {
                            description 'Destination IP address.' ;
                            leaf dst-address {
                              description 'Destination IP address.' ;
                              type ncd:ipv4-address ;

                              mandatory true ;
                            }

                            leaf dst-wildcard {
                              description 'Destination IP address wildcard.' ;
                              type ncd:ipv4-address ;

                              mandatory true ;
                            }

                          }

                          case any-type {
                            description 'Any destination IP address.' ;
                            leaf dst-any-addr {
                              description 'Any destination IP address.' ;
                              type empty ;

                              mandatory true ;
                            }

                          }

                        }

                        container destination-port {
                          description 'Specify the destination port.' ;
                          presence "Specify destination port" ;
                          choice destination-port {
                            description 'Specify the destination port.' ;
                            mandatory true ;
                            case dst-port-value {
                              description 'Specify the value of the destination port number.' ;
                              container dst-port-value {
                                description 'Specify the value of the destination port number.' ;
                                presence "Configure port number" ;
                                leaf dst-port-operator {
                                  description 'Specify the operation type of the destination port number.' ;
                                  type enumeration {
                                    enum eq {
                                      value 1 ;
                                      description 'Equal to.' ;
                                    }

                                    enum ge {
                                      value 2 ;
                                      description 'Great than or equal to.' ;
                                    }

                                    enum le {
                                      value 3 ;
                                      description 'Less than or equal to.' ;
                                    }

                                  }

                                  mandatory true ;
                                }

                                leaf dst-port-value {
                                  description 'Specify the value of the destination port number.' ;
                                  type uint16 {
                                    range 0..65535 ;

                                  }

                                  mandatory true ;
                                }

                              }

                            }

                            case dst-port-range {
                              description 'Specify the range of the destination port number.' ;
                              container dst-port-range {
                                description 'Specify the range of the destination port number.' ;
                                presence "Configure port range" ;
                                leaf dst-port-operator {
                                  description 'Specify the operation type of the destination port number.' ;
                                  type enumeration {
                                    enum range {
                                      value 7 ;
                                      description 'Range.' ;
                                    }

                                  }

                                  mandatory true ;
                                }

                                leaf dst-port-range {
                                  description 'Specify the range of the destination port number.' ;
                                  type acl-port-range ;

                                  mandatory true ;
                                }

                              }

                            }

                          }

                        }

                        leaf rst {
                          type acl-tcp-flag ;

                          description 'Specify the RST flag.
When the value of tcp-udp is tcp, the node is valid.' ;
                          if-feature vxlan-acl-tcp-flag ;

                          ncd:revise-date 2024-06-01 ;
                        }

                        leaf ack {
                          type acl-tcp-flag ;

                          description 'Specify the ACK flag.
When the value of tcp-udp is tcp, the node is valid.' ;
                          if-feature vxlan-acl-tcp-flag ;

                          ncd:revise-date 2024-06-01 ;
                        }

                        leaf fin {
                          type acl-tcp-flag ;

                          description 'Specify the FIN flag.
When the value of tcp-udp is tcp, the node is valid.' ;
                          if-feature vxlan-acl-tcp-flag ;

                          ncd:revise-date 2024-06-01 ;
                        }

                        leaf syn {
                          type acl-tcp-flag ;

                          description 'Specify the SYN flag.
When the value of tcp-udp is tcp, the node is valid.' ;
                          if-feature vxlan-acl-tcp-flag ;

                          ncd:revise-date 2024-06-01 ;
                        }

                        leaf psh {
                          type acl-tcp-flag ;

                          description 'Specify the PSH flag.
When the value of tcp-udp is tcp, the node is valid.' ;
                          if-feature vxlan-acl-tcp-flag ;

                          ncd:revise-date 2024-06-01 ;
                        }

                        leaf urg {
                          type acl-tcp-flag ;

                          description 'Specify the URG flag.
When the value of tcp-udp is tcp, the node is valid.' ;
                          if-feature vxlan-acl-tcp-flag ;

                          ncd:revise-date 2024-06-01 ;
                        }

                      }

                    }

                    case ip {
                      description 'The protocol number is a value excluding TCP and UDP.' ;
                      container ipv4-protocol {
                        description 'The protocol number is a value excluding TCP and UDP.' ;
                        leaf protocol-type {
                          description 'Specify the IP protocol type excluding TCP and UDP.' ;
                          type uint16 {
                            range "0..5 | 7..16 | 18..255 | 65535" ;

                          }

                          mandatory true ;
                        }

                        choice src-addr {
                          description 'Specify source IP address.' ;
                          mandatory true ;
                          case addr-type {
                            description 'Source IP address.' ;
                            leaf src-address {
                              description 'Source IP address.' ;
                              type ncd:ipv4-address ;

                              mandatory true ;
                            }

                            leaf src-wildcard {
                              description 'Source IP address wildcard.' ;
                              type ncd:ipv4-address ;

                              mandatory true ;
                            }

                          }

                          case any-type {
                            description 'Any source IP address.' ;
                            leaf src-any-addr {
                              description 'Any source IP address.' ;
                              type empty ;

                              mandatory true ;
                            }

                          }

                        }

                        choice dst-addr {
                          description 'Specify destination IP address.' ;
                          mandatory true ;
                          case addr-type {
                            description 'Destination IP address.' ;
                            leaf dst-address {
                              description 'Destination IP address.' ;
                              type ncd:ipv4-address ;

                              mandatory true ;
                            }

                            leaf dst-wildcard {
                              description 'Destination IP address wildcard.' ;
                              type ncd:ipv4-address ;

                              mandatory true ;
                            }

                          }

                          case any-type {
                            description 'Any destination IP address.' ;
                            leaf dst-any-addr {
                              description 'Any destination IP address.' ;
                              type empty ;

                              mandatory true ;
                            }

                          }

                        }

                      }

                    }

                  }

                  choice priority {
                    description 'Configure precedence or TOS or DSCP.' ;
                    case dscp {
                      description 'Specify the DSCP value.' ;
                      leaf dscp {
                        description 'Specify the DSCP value.' ;
                        type uint8 {
                          range 0..63 ;

                        }

                      }

                    }

                    case precedence {
                      description 'Specify the precedence value.' ;
                      leaf precedence {
                        description 'Specify the precedence value.' ;
                        type uint8 {
                          range 0..7 ;

                        }

                      }

                    }

                    case tos {
                      description 'Specify the TOS value.' ;
                      leaf tos {
                        description 'Specify the TOS value.' ;
                        type uint8 {
                          range 0..15 ;

                        }

                      }

                    }

                  }

                  leaf ip-flags {
                    type string {
                      length 3 {
                        description 'The binary form value of IP flags, ranging from 000 to 011.' ;
                      }

                    }

                    if-feature ip-flags-config ;

                    description 'The binary value of the IP flags, ranging from 000 to 011.' ;
                    ncd:revise-date 2024-03-22 ;
                  }

                }

                container vni {
                  description 'VXLAN ID.' ;
                  presence vni ;
                  leaf vxlan-id {
                    description 'VXLAN ID.' ;
                    type uint32 {
                      range 1..16777215 ;

                    }

                    mandatory true ;
                  }

                }

                container sgt {
                  description 'Security group tag.' ;
                  presence sgt ;
                  leaf sgt-value {
                    description 'The security group tag value.' ;
                    type uint16 ;

                    mandatory true ;
                  }

                  ncd:revise-date 2019-08-14 ;
                }

                leaf vrf {
                  description 'Specify the VRF instance name.
The referenced VRF must exist.' ;
                  type acl-vrf-name {
                    length 1..32 {
                      description 'VPN Routing/Forwarding instance name, support 1-32 characters.' ;
                    }

                  }

                }

                leaf time-range {
                  description 'The name of the time range referenced by the ACL rule.
The referenced time range must exist.' ;
                  type string {
                    length 1..31 ;

                  }

                  ncd:revise-date 2021-04-02 ;
                }

                container l2-layer {
                  if-feature l2-layer ;

                  description 'L2 information.' ;
                  presence l2-layer ;
                  container link-prot {
                    description 'Specify the link protocol type.' ;
                    choice link-prot {
                      description 'Specify the link protocol type.' ;
                      case link-protocol {
                        description 'Specify the link protocol type.' ;
                        leaf link-protocol {
                          description 'Specify the link protocol type.' ;
                          type uint32 {
                            range 1536..65535 ;

                          }

                        }

                      }

                      case link-protocol-hex {
                        if-feature link-prot-hex-config ;

                        description 'Specify the link protocol in hexadecimal format.' ;
                        leaf link-protocol-hex {
                          description 'Specify the link protocol in hexadecimal format.' ;
                          type ncd:hex ;

                        }

                      }

                    }

                  }

                  container source-mac {
                    description 'Specify source MAC address.' ;
                    choice src-mac-addr {
                      description 'Specify source MAC address.' ;
                      mandatory true ;
                      case src-mac-addr {
                        description 'Source MAC address.' ;
                        leaf src-mac-address {
                          description 'Source MAC address.' ;
                          type ncd:mac-address ;

                          mandatory true ;
                        }

                        leaf src-mac-wildcard {
                          description 'Source MAC address wildcard.' ;
                          type ncd:mac-address ;

                          mandatory true ;
                        }

                      }

                      case src-mac-any {
                        description 'Any source MAC address.' ;
                        leaf src-mac-any {
                          description 'Any source MAC address.' ;
                          type empty ;

                          mandatory true ;
                        }

                      }

                    }

                  }

                  container destination-mac {
                    description 'Specify destination MAC address.' ;
                    choice dest-mac-addr {
                      description 'Specify destination MAC address.' ;
                      mandatory true ;
                      case dest-mac-addr {
                        description 'Destination MAC address.' ;
                        leaf dest-mac-address {
                          description 'Destination MAC address.' ;
                          type ncd:mac-address ;

                          mandatory true ;
                        }

                        leaf dest-mac-wildcard {
                          description 'Destination MAC address wildcard.' ;
                          type ncd:mac-address ;

                          mandatory true ;
                        }

                      }

                      case dest-mac-any {
                        description 'Any destination MAC address.' ;
                        leaf dest-mac-any {
                          description 'Any destination MAC address.' ;
                          type empty ;

                          mandatory true ;
                        }

                      }

                    }

                  }

                  leaf inner-cos {
                    if-feature link-cos-value ;

                    description 'Specify the inner-layer CoS value.' ;
                    type uint8 {
                      range 0..7 ;

                    }

                  }

                  leaf outer-cos {
                    if-feature link-cos-value ;

                    description 'Specify the outer-layer CoS value.' ;
                    type uint8 {
                      range 0..7 ;

                    }

                  }

                  leaf inner-vlan-range {
                    description 'Specify the range of the inner-layer VLAN.' ;
                    type acl-vlan-range ;

                  }

                  leaf outer-vlan-range {
                    description 'Specify the range of the outer-layer VLAN.' ;
                    type acl-vlan-range ;

                  }

                  ncd:revise-date 2021-10-26 ;
                }

                leaf log {
                  if-feature log-config ;

                  description 'Enable/Disable the function of counting matched packet data.' ;
                  type boolean ;

                  default false ;
                  ncd:revise-date 2022-01-20 ;
                }

              }

              ncd:revise-date 2018-09-17 ;
            }

            container rules-transit-outer {
              description 'Configure the IPv4 VXLAN ACL rules in transit-outer mode.
An IPv4 VXLAN ACL in transit-outer mode must be configured first.' ;
              list rule-transit-outer {
                description 'Configure an IPv4 VXLAN ACL rule in transit-outer mode.' ;
                key ruleid ;
                leaf ruleid {
                  description 'Specify the rule ID.' ;
                  type uint32 {
                    range 1..2147483644 ;

                  }

                }

                choice permit-deny {
                  description 'Specify the action as either permit or deny.' ;
                  mandatory true ;
                  case deny {
                    description 'Deny the packets that match the rule.' ;
                    leaf deny {
                      description 'Deny the packets that match the rule.' ;
                      type empty ;

                      mandatory true ;
                    }

                  }

                  case permit {
                    description 'Permit the packets that match the rule.' ;
                    leaf permit {
                      description 'Permit the packets that match the rule.' ;
                      type empty ;

                      mandatory true ;
                    }

                  }

                }

                container vni {
                  description 'VXLAN ID.' ;
                  presence vni ;
                  leaf vxlan-id {
                    description 'VXLAN ID.' ;
                    type uint32 {
                      range 1..16777215 ;

                    }

                    mandatory true ;
                  }

                }

                container sgt {
                  description 'Security group tag.' ;
                  presence sgt ;
                  leaf sgt-value {
                    description 'The security group tag value.' ;
                    type uint16 ;

                    mandatory true ;
                  }

                  ncd:revise-date 2019-08-14 ;
                }

                container outer-layer {
                  description 'The outer-layer protocol of VXLAN.' ;
                  leaf udp {
                    description 'The protocol number is UDP.' ;
                    type empty ;

                    mandatory true ;
                  }

                  choice src-addr {
                    description 'Specify source IP address.' ;
                    mandatory true ;
                    case addr-type {
                      description 'Source IP address.' ;
                      leaf src-address {
                        description 'Source IP address.' ;
                        type ncd:ipv4-address ;

                        mandatory true ;
                      }

                      leaf src-wildcard {
                        description 'Source IP address wildcard.' ;
                        type ncd:ipv4-address ;

                        mandatory true ;
                      }

                    }

                    case any-type {
                      description 'Any source IP address.' ;
                      leaf src-any-addr {
                        description 'Any source IP address.' ;
                        type empty ;

                        mandatory true ;
                      }

                    }

                  }

                  container source-port {
                    description 'Specify the source port.' ;
                    presence "Specify source port" ;
                    choice source-port {
                      description 'Specify the source port.' ;
                      mandatory true ;
                      case src-port-value {
                        description 'Specify the value of the source port number.' ;
                        container src-port-value {
                          description 'Specify the value of the source port number.' ;
                          presence "Configure port number" ;
                          leaf src-port-operator {
                            description 'Specify the operation type of the source port number.' ;
                            type enumeration {
                              enum eq {
                                value 1 ;
                                description 'Equal to.' ;
                              }

                              enum ge {
                                value 2 ;
                                description 'Great than or equal to.' ;
                              }

                              enum le {
                                value 3 ;
                                description 'Less than or equal to.' ;
                              }

                            }

                            mandatory true ;
                          }

                          leaf src-port-value {
                            description 'Specify the value of the source port number.' ;
                            type uint16 {
                              range 0..65535 ;

                            }

                            mandatory true ;
                          }

                        }

                      }

                      case src-port-range {
                        description 'Specify the range of the source port number.' ;
                        container src-port-range {
                          description 'Specify the range of the source port number.' ;
                          presence "Configure port range" ;
                          leaf src-port-operator {
                            description 'Specify the operation type of the source port number.' ;
                            type enumeration {
                              enum range {
                                value 7 ;
                                description 'Range.' ;
                              }

                            }

                            mandatory true ;
                          }

                          leaf src-port-range {
                            description 'Specify the range of the source port number.' ;
                            type acl-port-range ;

                            mandatory true ;
                          }

                        }

                      }

                    }

                  }

                  choice dst-addr {
                    description 'Specify destination IP address.' ;
                    mandatory true ;
                    case addr-type {
                      description 'Destination IP address.' ;
                      leaf dst-address {
                        description 'Destination IP address.' ;
                        type ncd:ipv4-address ;

                        mandatory true ;
                      }

                      leaf dst-wildcard {
                        description 'Destination IP address wildcard.' ;
                        type ncd:ipv4-address ;

                        mandatory true ;
                      }

                    }

                    case any-type {
                      description 'Any destination IP address.' ;
                      leaf dst-any-addr {
                        description 'Any destination IP address.' ;
                        type empty ;

                        mandatory true ;
                      }

                    }

                  }

                  container destination-port {
                    description 'Specify the destination port.' ;
                    presence "Specify destination port" ;
                    choice destination-port {
                      description 'Specify the destination port.' ;
                      mandatory true ;
                      case dst-port-value {
                        description 'Specify the value of the destination port number.' ;
                        container dst-port-value {
                          description 'Specify the value of the destination port number.' ;
                          presence "Configure port number" ;
                          leaf dst-port-operator {
                            description 'Specify the operation type of the destination port number.' ;
                            type enumeration {
                              enum eq {
                                value 1 ;
                                description 'Equal to.' ;
                              }

                              enum ge {
                                value 2 ;
                                description 'Great than or equal to.' ;
                              }

                              enum le {
                                value 3 ;
                                description 'Less than or equal to.' ;
                              }

                            }

                            mandatory true ;
                          }

                          leaf dst-port-value {
                            description 'Specify the value of the destination port number.' ;
                            type uint16 {
                              range 0..65535 ;

                            }

                            mandatory true ;
                          }

                        }

                      }

                      case dst-port-range {
                        description 'Specify the range of the destination port number.' ;
                        container dst-port-range {
                          description 'Specify the range of the destination port number.' ;
                          presence "Configure port range" ;
                          leaf dst-port-operator {
                            description 'Specify the operation type of the destination port number.' ;
                            type enumeration {
                              enum range {
                                value 7 ;
                                description 'Range.' ;
                              }

                            }

                            mandatory true ;
                          }

                          leaf dst-port-range {
                            description 'Specify the range of the destination port number.' ;
                            type acl-port-range ;

                            mandatory true ;
                          }

                        }

                      }

                    }

                  }

                  choice priority {
                    description 'Configure precedence or TOS or DSCP.' ;
                    case dscp {
                      description 'Specify the DSCP value.' ;
                      leaf dscp {
                        description 'Specify the DSCP value.' ;
                        type uint8 {
                          range 0..63 ;

                        }

                      }

                    }

                    case precedence {
                      description 'Specify the precedence value.' ;
                      leaf precedence {
                        description 'Specify the precedence value.' ;
                        type uint8 {
                          range 0..7 ;

                        }

                      }

                    }

                    case tos {
                      description 'Specify the TOS value.' ;
                      leaf tos {
                        description 'Specify the TOS value.' ;
                        type uint8 {
                          range 0..15 ;

                        }

                      }

                    }

                  }

                }

                leaf vrf {
                  description 'Specify the VRF instance name.
The referenced VRF must exist.' ;
                  type acl-vrf-name {
                    length 1..32 {
                      description 'VPN Routing/Forwarding instance name, support 1-32 characters.' ;
                    }

                  }

                }

                leaf time-range {
                  description 'The name of the time range referenced by the ACL rule.
The referenced time range must exist.' ;
                  type string {
                    length 1..31 ;

                  }

                  ncd:revise-date 2021-04-02 ;
                }

                leaf log {
                  if-feature log-config ;

                  type boolean ;

                  description 'Enable/Disable the function of counting matched packet data.' ;
                  default false ;
                  ncd:revise-date 2023-10-07 ;
                }

              }

              ncd:revise-date 2018-09-17 ;
            }

            container rules-vtep-inner {
              description 'Configure the IPv4 VXLAN ACL rules in VTEP-inner mode.
An IPv4 VXLAN ACL in VTEP-inner mode must be configured first.' ;
              list rule-vtep-inner {
                description 'Configure an IPv4 VXLAN ACL rule in VTEP-inner mode.' ;
                key ruleid ;
                leaf ruleid {
                  description 'Specify the rule ID.' ;
                  type uint32 {
                    range 1..2147483644 ;

                  }

                }

                choice permit-deny {
                  description 'Specify the action as either permit or deny.' ;
                  mandatory true ;
                  case deny {
                    description 'Deny the packets that match the rule.' ;
                    leaf deny {
                      description 'Deny the packets that match the rule.' ;
                      type empty ;

                      mandatory true ;
                    }

                  }

                  case permit {
                    description 'Permit the packets that match the rule.' ;
                    leaf permit {
                      description 'Permit the packets that match the rule.' ;
                      type empty ;

                      mandatory true ;
                    }

                  }

                }

                container inner-layer {
                  description 'The inner-layer protocol of VXLAN.' ;
                  presence inner-layer ;
                  choice protocol-type {
                    description 'IPv4 protocol type.' ;
                    mandatory true ;
                    case tcp-udp {
                      description 'The protocol number is UDP or TCP.' ;
                      container tcp-udp {
                        description 'The protocol number is UDP or TCP.' ;
                        leaf tcp-udp {
                          description 'The protocol number is UDP or TCP.' ;
                          type enumeration {
                            enum tcp {
                              value 6 ;
                              description 'Transmission Control Protocol(6)' ;
                            }

                            enum udp {
                              value 17 ;
                              description 'User Datagram Protocol(17)' ;
                            }

                          }

                          mandatory true ;
                        }

                        choice src-addr {
                          description 'Specify source IP address.' ;
                          mandatory true ;
                          case addr-type {
                            description 'Source IP address.' ;
                            leaf src-address {
                              description 'Source IP address.' ;
                              type ncd:ipv4-address ;

                              mandatory true ;
                            }

                            leaf src-wildcard {
                              description 'Source IP address wildcard.' ;
                              type ncd:ipv4-address ;

                              mandatory true ;
                            }

                          }

                          case any-type {
                            description 'Any source IP address.' ;
                            leaf src-any-addr {
                              description 'Any source IP address.' ;
                              type empty ;

                              mandatory true ;
                            }

                          }

                        }

                        container source-port {
                          description 'Specify the source port.' ;
                          presence "Specify source port" ;
                          choice source-port {
                            description 'Specify the source port.' ;
                            mandatory true ;
                            case src-port-value {
                              description 'Specify the value of the source port number.' ;
                              container src-port-value {
                                description 'Specify the value of the source port number.' ;
                                presence "Configure port number" ;
                                leaf src-port-operator {
                                  description 'Specify the operation type of the source port number.' ;
                                  type enumeration {
                                    enum eq {
                                      value 1 ;
                                      description 'Equal to.' ;
                                    }

                                    enum ge {
                                      value 2 ;
                                      description 'Great than or equal to.' ;
                                    }

                                    enum le {
                                      value 3 ;
                                      description 'Less than or equal to.' ;
                                    }

                                  }

                                  mandatory true ;
                                }

                                leaf src-port-value {
                                  description 'Specify the value of the source port number.' ;
                                  type uint16 {
                                    range 0..65535 ;

                                  }

                                  mandatory true ;
                                }

                              }

                            }

                            case src-port-range {
                              description 'Specify the range of the source port number.' ;
                              container src-port-range {
                                description 'Specify the range of the source port number.' ;
                                presence "Configure port range" ;
                                leaf src-port-operator {
                                  description 'Specify the operation type of the source port number.' ;
                                  type enumeration {
                                    enum range {
                                      value 7 ;
                                      description 'Range.' ;
                                    }

                                  }

                                  mandatory true ;
                                }

                                leaf src-port-range {
                                  description 'Specify the range of the source port number.' ;
                                  type acl-port-range ;

                                  mandatory true ;
                                }

                              }

                            }

                          }

                        }

                        choice dst-addr {
                          description 'Specify destination IP address.' ;
                          mandatory true ;
                          case addr-type {
                            description 'Destination IP address.' ;
                            leaf dst-address {
                              description 'Destination IP address.' ;
                              type ncd:ipv4-address ;

                              mandatory true ;
                            }

                            leaf dst-wildcard {
                              description 'Destination IP address wildcard.' ;
                              type ncd:ipv4-address ;

                              mandatory true ;
                            }

                          }

                          case any-type {
                            description 'Any destination IP address.' ;
                            leaf dst-any-addr {
                              description 'Any destination IP address.' ;
                              type empty ;

                              mandatory true ;
                            }

                          }

                        }

                        container destination-port {
                          description 'Specify the destination port.' ;
                          presence "Specify destination port" ;
                          choice destination-port {
                            description 'Specify the destination port.' ;
                            mandatory true ;
                            case dst-port-value {
                              description 'Specify the value of the destination port number.' ;
                              container dst-port-value {
                                description 'Specify the value of the destination port number.' ;
                                presence "Configure port number" ;
                                leaf dst-port-operator {
                                  description 'Specify the operation type of the destination port number.' ;
                                  type enumeration {
                                    enum eq {
                                      value 1 ;
                                      description 'Equal to.' ;
                                    }

                                    enum ge {
                                      value 2 ;
                                      description 'Great than or equal to.' ;
                                    }

                                    enum le {
                                      value 3 ;
                                      description 'Less than or equal to.' ;
                                    }

                                  }

                                  mandatory true ;
                                }

                                leaf dst-port-value {
                                  description 'Specify the value of the destination port number.' ;
                                  type uint16 {
                                    range 0..65535 ;

                                  }

                                  mandatory true ;
                                }

                              }

                            }

                            case dst-port-range {
                              description 'Specify the range of the destination port number.' ;
                              container dst-port-range {
                                description 'Specify the range of the destination port number.' ;
                                presence "Configure port range" ;
                                leaf dst-port-operator {
                                  description 'Specify the operation type of the destination port number.' ;
                                  type enumeration {
                                    enum range {
                                      value 7 ;
                                      description 'Range.' ;
                                    }

                                  }

                                  mandatory true ;
                                }

                                leaf dst-port-range {
                                  description 'Specify the range of the destination port number.' ;
                                  type acl-port-range ;

                                  mandatory true ;
                                }

                              }

                            }

                          }

                        }

                        leaf rst {
                          type acl-tcp-flag ;

                          if-feature vxlan-acl-tcp-flag ;

                          description 'Specify the RST flag.
When the value of tcp-udp is tcp, the node is valid.' ;
                          ncd:revise-date 2024-06-01 ;
                        }

                        leaf ack {
                          type acl-tcp-flag ;

                          if-feature vxlan-acl-tcp-flag ;

                          description 'Specify the ACK flag.
When the value of tcp-udp is tcp, the node is valid.' ;
                          ncd:revise-date 2024-06-01 ;
                        }

                        leaf fin {
                          type acl-tcp-flag ;

                          if-feature vxlan-acl-tcp-flag ;

                          description 'Specify the FIN flag.
When the value of tcp-udp is tcp, the node is valid.' ;
                          ncd:revise-date 2024-06-01 ;
                        }

                        leaf syn {
                          type acl-tcp-flag ;

                          if-feature vxlan-acl-tcp-flag ;

                          description 'Specify the SYN flag.
When the value of tcp-udp is tcp, the node is valid.' ;
                          ncd:revise-date 2024-06-01 ;
                        }

                        leaf psh {
                          type acl-tcp-flag ;

                          if-feature vxlan-acl-tcp-flag ;

                          description 'Specify the PSH flag.
When the value of tcp-udp is tcp, the node is valid.' ;
                          ncd:revise-date 2024-06-01 ;
                        }

                        leaf urg {
                          type acl-tcp-flag ;

                          if-feature vxlan-acl-tcp-flag ;

                          description 'Specify the URG flag.
When the value of tcp-udp is tcp, the node is valid.' ;
                          ncd:revise-date 2024-06-01 ;
                        }

                      }

                    }

                    case ip {
                      description 'The protocol number is a value excluding TCP and UDP.' ;
                      container ipv4-protocol {
                        description 'The protocol number is a value excluding TCP and UDP.' ;
                        leaf protocol-type {
                          description 'Specify the IP protocol type excluding TCP and UDP.' ;
                          type uint16 {
                            range "0..5 | 7..16 | 18..255 | 65535" ;

                          }

                          mandatory true ;
                        }

                        choice src-addr {
                          description 'Specify source IP address.' ;
                          mandatory true ;
                          case addr-type {
                            description 'Source IP address.' ;
                            leaf src-address {
                              description 'Source IP address.' ;
                              type ncd:ipv4-address ;

                              mandatory true ;
                            }

                            leaf src-wildcard {
                              description 'Source IP address wildcard.' ;
                              type ncd:ipv4-address ;

                              mandatory true ;
                            }

                          }

                          case any-type {
                            description 'Any source IP address.' ;
                            leaf src-any-addr {
                              description 'Any source IP address.' ;
                              type empty ;

                              mandatory true ;
                            }

                          }

                        }

                        choice dst-addr {
                          description 'Specify destination IP address.' ;
                          mandatory true ;
                          case addr-type {
                            description 'Destination IP address.' ;
                            leaf dst-address {
                              description 'Destination IP address.' ;
                              type ncd:ipv4-address ;

                              mandatory true ;
                            }

                            leaf dst-wildcard {
                              description 'Destination IP address wildcard.' ;
                              type ncd:ipv4-address ;

                              mandatory true ;
                            }

                          }

                          case any-type {
                            description 'Any destination address.' ;
                            leaf dst-any-addr {
                              description 'Any destination address.' ;
                              type empty ;

                              mandatory true ;
                            }

                          }

                        }

                      }

                    }

                  }

                  choice priority {
                    description 'Configure precedence or TOS or DSCP.' ;
                    case dscp {
                      description 'Specify the DSCP value.' ;
                      leaf dscp {
                        description 'Specify the DSCP value.' ;
                        type uint8 {
                          range 0..63 ;

                        }

                      }

                    }

                    case precedence {
                      description 'Specify the precedence value.' ;
                      leaf precedence {
                        description 'Specify the precedence value.' ;
                        type uint8 {
                          range 0..7 ;

                        }

                      }

                    }

                    case tos {
                      description 'Specify the TOS value.' ;
                      leaf tos {
                        description 'Specify the TOS value.' ;
                        type uint8 {
                          range 0..15 ;

                        }

                      }

                    }

                  }

                  leaf ip-flags {
                    type string {
                      length 3 {
                        description 'The binary form value of IP flags, ranging from 000 to 011.' ;
                      }

                    }

                    if-feature ip-flags-config ;

                    description 'The binary value of the IP flags, ranging from 000 to 011.' ;
                    ncd:revise-date 2024-03-22 ;
                  }

                }

                container vni {
                  description 'VXLAN ID.' ;
                  presence vni ;
                  leaf vxlan-id {
                    description 'VXLAN ID.' ;
                    type uint32 {
                      range 1..16777215 ;

                    }

                    mandatory true ;
                  }

                }

                container sgt {
                  description 'Security group tag.' ;
                  presence sgt ;
                  leaf sgt-value {
                    description 'The security group tag value.' ;
                    type uint16 ;

                    mandatory true ;
                  }

                  ncd:revise-date 2019-08-14 ;
                }

                leaf vrf {
                  description 'Specify the VRF instance name.
The referenced VRF must exist.' ;
                  type acl-vrf-name {
                    length 1..32 {
                      description 'VPN Routing/Forwarding instance name, support 1-32 characters.' ;
                    }

                  }

                }

                leaf time-range {
                  description 'The name of the time range referenced by the ACL rule.
The referenced time range must exist.' ;
                  type string {
                    length 1..31 ;

                  }

                  ncd:revise-date 2021-04-02 ;
                }

                container l2-layer {
                  if-feature l2-layer ;

                  description 'L2 information.' ;
                  presence l2-layer ;
                  container link-prot {
                    description 'Specify the link protocol type.' ;
                    choice link-prot {
                      description 'Specify the link protocol type.' ;
                      case link-protocol {
                        description 'Specify the link protocol type.' ;
                        leaf link-protocol {
                          description 'Specify the link protocol type.' ;
                          type uint32 {
                            range 1536..65535 ;

                          }

                        }

                      }

                      case link-protocol-hex {
                        if-feature link-prot-hex-config ;

                        description 'Specify the link protocol in hexadecimal format.' ;
                        leaf link-protocol-hex {
                          description 'Specify the link protocol in hexadecimal format.' ;
                          type ncd:hex ;

                        }

                      }

                    }

                  }

                  container source-mac {
                    description 'Specify source MAC address.' ;
                    choice src-mac-addr {
                      description 'Specify source MAC address.' ;
                      mandatory true ;
                      case src-mac-addr {
                        description 'Source MAC address.' ;
                        leaf src-mac-address {
                          description 'Source MAC address.' ;
                          type ncd:mac-address ;

                          mandatory true ;
                        }

                        leaf src-mac-wildcard {
                          description 'Source MAC address wildcard.' ;
                          type ncd:mac-address ;

                          mandatory true ;
                        }

                      }

                      case src-mac-any {
                        description 'Any source MAC address.' ;
                        leaf src-mac-any {
                          description 'Any source MAC address.' ;
                          type empty ;

                          mandatory true ;
                        }

                      }

                    }

                  }

                  container destination-mac {
                    description 'Specify destination MAC address.' ;
                    choice dest-mac-addr {
                      description 'Specify destination MAC address.' ;
                      mandatory true ;
                      case dest-mac-addr {
                        description 'Destination MAC address.' ;
                        leaf dest-mac-address {
                          description 'Destination MAC address.' ;
                          type ncd:mac-address ;

                          mandatory true ;
                        }

                        leaf dest-mac-wildcard {
                          description 'Destination MAC address wildcard.' ;
                          type ncd:mac-address ;

                          mandatory true ;
                        }

                      }

                      case dest-mac-any {
                        description 'Any destination MAC address.' ;
                        leaf dest-mac-any {
                          description 'Any destination MAC address.' ;
                          type empty ;

                          mandatory true ;
                        }

                      }

                    }

                  }

                  leaf inner-cos {
                    if-feature link-cos-value ;

                    description 'Specify the inner-layer CoS value.' ;
                    type uint8 {
                      range 0..7 ;

                    }

                  }

                  leaf outer-cos {
                    if-feature link-cos-value ;

                    description 'Specify the outer-layer CoS value.' ;
                    type uint8 {
                      range 0..7 ;

                    }

                  }

                  leaf inner-vlan-range {
                    description 'Specify the range of the inner-layer VLAN.' ;
                    type acl-vlan-range ;

                  }

                  leaf outer-vlan-range {
                    description 'Specify the range of the outer-layer VLAN.' ;
                    type acl-vlan-range ;

                  }

                  ncd:revise-date 2021-10-26 ;
                }

                leaf log {
                  if-feature log-config ;

                  description 'Enable/Disable the function of counting matched packet data.' ;
                  type boolean ;

                  default false ;
                  ncd:revise-date 2022-01-20 ;
                }

              }

              ncd:revise-date 2018-09-17 ;
            }

            container rules-vtep-outer {
              description 'Configure the IPv4 VXLAN ACL rules in VTEP-outer mode.
An IPv4 VXLAN ACL in VTEP-outer mode must be configured first.' ;
              list rule-vtep-outer {
                description 'Configure an IPv4 VXLAN ACL rule in VTEP-outer mode.' ;
                key ruleid ;
                leaf ruleid {
                  description 'Specify the rule ID.' ;
                  type uint32 {
                    range 1..2147483644 ;

                  }

                }

                choice permit-deny {
                  description 'Specify the action as either permit or deny.' ;
                  mandatory true ;
                  case deny {
                    description 'Deny the packets that match the rule.' ;
                    leaf deny {
                      description 'Deny the packets that match the rule.' ;
                      type empty ;

                      mandatory true ;
                    }

                  }

                  case permit {
                    description 'Permit the packets that match the rule.' ;
                    leaf permit {
                      description 'Permit the packets that match the rule.' ;
                      type empty ;

                      mandatory true ;
                    }

                  }

                }

                container vni {
                  description 'VXLAN ID.' ;
                  presence vni ;
                  leaf vxlan-id {
                    description 'VXLAN ID.' ;
                    type uint32 {
                      range 1..16777215 ;

                    }

                    mandatory true ;
                  }

                }

                container sgt {
                  description 'Security group tag.' ;
                  presence sgt ;
                  leaf sgt-value {
                    description 'The security group tag value.' ;
                    type uint16 ;

                    mandatory true ;
                  }

                  ncd:revise-date 2019-08-14 ;
                }

                container outer-layer {
                  description 'The outer-layer protocol of VXLAN.' ;
                  leaf udp {
                    description 'The protocol number is UDP.' ;
                    type empty ;

                    mandatory true ;
                  }

                  choice src-addr {
                    description 'Specify source IP address.' ;
                    mandatory true ;
                    case addr-type {
                      description 'Source IP address.' ;
                      leaf src-address {
                        description 'Source IP address.' ;
                        type ncd:ipv4-address ;

                        mandatory true ;
                      }

                      leaf src-wildcard {
                        description 'Source IP address wildcard.' ;
                        type ncd:ipv4-address ;

                        mandatory true ;
                      }

                    }

                    case any-type {
                      description 'Any source IP address.' ;
                      leaf src-any-addr {
                        description 'Any source IP address.' ;
                        type empty ;

                        mandatory true ;
                      }

                    }

                  }

                  container source-port {
                    description 'Specify the source port.' ;
                    presence "Specify source port" ;
                    choice source-port {
                      description 'Specify the source port.' ;
                      mandatory true ;
                      case src-port-value {
                        description 'Specify the value of the source port number.' ;
                        container src-port-value {
                          description 'Specify the value of the source port number.' ;
                          presence "Configure port number" ;
                          leaf src-port-operator {
                            description 'Specify the operation type of the source port number.' ;
                            type enumeration {
                              enum eq {
                                value 1 ;
                                description 'Equal to.' ;
                              }

                              enum ge {
                                value 2 ;
                                description 'Great than or equal to.' ;
                              }

                              enum le {
                                value 3 ;
                                description 'Less than or equal to.' ;
                              }

                            }

                            mandatory true ;
                          }

                          leaf src-port-value {
                            description 'Specify the value of the source port number.' ;
                            type uint16 {
                              range 0..65535 ;

                            }

                            mandatory true ;
                          }

                        }

                      }

                      case src-port-range {
                        description 'Specify the range of the source port number.' ;
                        container src-port-range {
                          description 'Specify the range of the source port number.' ;
                          presence "Configure port range" ;
                          leaf src-port-operator {
                            description 'Specify the operation type of the source port number.' ;
                            type enumeration {
                              enum range {
                                value 7 ;
                                description 'Range.' ;
                              }

                            }

                            mandatory true ;
                          }

                          leaf src-port-range {
                            description 'Specify the range of the source port number.' ;
                            type acl-port-range ;

                            mandatory true ;
                          }

                        }

                      }

                    }

                  }

                  choice dst-addr {
                    description 'Specify destination IP address.' ;
                    mandatory true ;
                    case addr-type {
                      description 'Destination IP address.' ;
                      leaf dst-address {
                        description 'Destination IP address.' ;
                        type ncd:ipv4-address ;

                        mandatory true ;
                      }

                      leaf dst-wildcard {
                        description 'Destination IP address wildcard.' ;
                        type ncd:ipv4-address ;

                        mandatory true ;
                      }

                    }

                    case any-type {
                      description 'Any destination IP address.' ;
                      leaf dst-any-addr {
                        description 'Any destination IP address.' ;
                        type empty ;

                        mandatory true ;
                      }

                    }

                  }

                  container destination-port {
                    description 'Specify the destination port.' ;
                    presence "Specify destination port" ;
                    choice destination-port {
                      description 'Specify the destination port.' ;
                      mandatory true ;
                      case dst-port-value {
                        description 'Specify the value of the destination port number.' ;
                        container dst-port-value {
                          description 'Specify the value of the destination port number.' ;
                          presence "Configure port number" ;
                          leaf dst-port-operator {
                            description 'Specify the operation type of the destination port number.' ;
                            type enumeration {
                              enum eq {
                                value 1 ;
                                description 'Equal to.' ;
                              }

                              enum ge {
                                value 2 ;
                                description 'Great than or equal to.' ;
                              }

                              enum le {
                                value 3 ;
                                description 'Less than or equal to.' ;
                              }

                            }

                            mandatory true ;
                          }

                          leaf dst-port-value {
                            description 'Specify the value of the destination port number.' ;
                            type uint16 {
                              range 0..65535 ;

                            }

                            mandatory true ;
                          }

                        }

                      }

                      case dst-port-range {
                        description 'Specify the range of the destination port number.' ;
                        container dst-port-range {
                          description 'Specify the range of the destination port number.' ;
                          presence "Configure port range" ;
                          leaf dst-port-operator {
                            description 'Specify the operation type of the destination port number.' ;
                            type enumeration {
                              enum range {
                                value 7 ;
                                description 'Range.' ;
                              }

                            }

                            mandatory true ;
                          }

                          leaf dst-port-range {
                            description 'Specify the range of the destination port number.' ;
                            type acl-port-range ;

                            mandatory true ;
                          }

                        }

                      }

                    }

                  }

                  choice priority {
                    description 'Configure precedence or TOS or DSCP.' ;
                    case dscp {
                      description 'Specify the DSCP value.' ;
                      leaf dscp {
                        description 'Specify the DSCP value.' ;
                        type uint8 {
                          range 0..63 ;

                        }

                      }

                    }

                    case precedence {
                      description 'Specify the precedence value.' ;
                      leaf precedence {
                        description 'Specify the precedence value.' ;
                        type uint8 {
                          range 0..7 ;

                        }

                      }

                    }

                    case tos {
                      description 'Specify the TOS value.' ;
                      leaf tos {
                        description 'Specify the TOS value.' ;
                        type uint8 {
                          range 0..15 ;

                        }

                      }

                    }

                  }

                }

                leaf vrf {
                  description 'Specify the VRF instance name.
The referenced VRF must exist.' ;
                  type acl-vrf-name {
                    length 1..32 {
                      description 'VPN Routing/Forwarding instance name, support 1-32 characters.' ;
                    }

                  }

                }

                leaf time-range {
                  description 'The name of the time range referenced by the ACL rule.
The referenced time range must exist.' ;
                  type string {
                    length 1..31 ;

                  }

                  ncd:revise-date 2021-04-02 ;
                }

                leaf log {
                  if-feature log-config ;

                  type boolean ;

                  description 'Enable/Disable the function of counting matched packet data.' ;
                  default false ;
                  ncd:revise-date 2023-10-07 ;
                }

              }

              ncd:revise-date 2018-09-17 ;
            }

          }

          ncd:revise-date 2016-03-04 ;
        }

        container user-defined-template-acls {
          if-feature udf-template-type ;

          description 'Configure the user-defined template ACL.' ;
          list user-defined-template-acl {
            if-feature udf-template-type ;

            description 'Configure the user-defined template ACL.' ;
            key acl-name ;
            leaf acl-name {
              description 'Specify the ACL name.' ;
              type acl-name-type ;

            }

            leaf template-name {
              description 'Specify the template name.' ;
              type acl-name-type ;

              mandatory true ;
            }

            container rules {
              description 'Configure user-defined template ACL rules.' ;
              list rule {
                description 'Configure a user-defined template ACL rule.' ;
                key ruleid ;
                leaf ruleid {
                  description 'Specify the rule ID.' ;
                  type uint32 {
                    range 1..2147483644 ;

                  }

                }

                choice permit-deny {
                  description 'Specify the action as either permit or deny.' ;
                  mandatory true ;
                  case deny {
                    description 'Deny the packets that match the rule.' ;
                    leaf deny {
                      description 'Deny the packets that match the rule.' ;
                      type empty ;

                    }

                  }

                  case permit {
                    description 'Permit the packets that match the rule.' ;
                    leaf permit {
                      description 'Permit the packets that match the rule.' ;
                      type empty ;

                      mandatory true ;
                    }

                  }

                }

                choice segment {
                  description 'Rule segments.' ;
                  mandatory true ;
                  case segment-any {
                    description 'Any rule segment.' ;
                    leaf any {
                      description 'Any rule segment.' ;
                      type empty ;

                    }

                  }

                  case segment-value {
                    description 'Configure the rule segment.' ;
                    container segment1 {
                      description 'Configure the first segment.' ;
                      presence segment1 ;
                      leaf rule-string {
                        description 'The first match field value.' ;
                        type string {
                          length 4..10 {
                            description 'User defined hexadecimal string,as follows:
0x00-0xffffffff.' ;
                          }

                        }

                        mandatory true ;
                      }

                      leaf rule-mask {
                        description 'The first match field mask.' ;
                        type string {
                          length 4..10 {
                            description 'User defined hexadecimal string mask,as follows:
0x00-0xffffffff.' ;
                          }

                        }

                        mandatory true ;
                      }

                    }

                    container segment2 {
                      description 'Configure the second segment.' ;
                      presence segment2 ;
                      leaf rule-string {
                        description 'The second match field value.' ;
                        type string {
                          length 4..10 {
                            description 'User defined hexadecimal string,as follows:
0x00-0xffffffff.' ;
                          }

                        }

                        mandatory true ;
                      }

                      leaf rule-mask {
                        description 'The second match field mask.' ;
                        type string {
                          length 4..10 {
                            description 'User defined hexadecimal string mask,as follows:
0x00-0xffffffff.' ;
                          }

                        }

                        mandatory true ;
                      }

                    }

                    container segment3 {
                      description 'Configure the third segment.' ;
                      presence segment3 ;
                      leaf rule-string {
                        description 'The third match field value.' ;
                        type string {
                          length 4..10 {
                            description 'User defined hexadecimal string,as follows:
0x00-0xffffffff.' ;
                          }

                        }

                        mandatory true ;
                      }

                      leaf rule-mask {
                        description 'The third match field mask.' ;
                        type string {
                          length 4..10 {
                            description 'User defined hexadecimal string mask,as follows:
0x00-0xffffffff.' ;
                          }

                        }

                        mandatory true ;
                      }

                    }

                    container segment4 {
                      description 'Configure the fourth segment.' ;
                      presence segment4 ;
                      leaf rule-string {
                        description 'The fourth match field value.' ;
                        type string {
                          length 4..10 {
                            description 'User defined hexadecimal string,as follows:
0x00-0xffffffff.' ;
                          }

                        }

                        mandatory true ;
                      }

                      leaf rule-mask {
                        description 'The fourth match field mask.' ;
                        type string {
                          length 4..10 {
                            description 'User defined hexadecimal string mask,as follows:
0x00-0xffffffff.' ;
                          }

                        }

                        mandatory true ;
                      }

                    }

                    container segment5 {
                      description 'Configure the fifth segment.' ;
                      presence segment5 ;
                      leaf rule-string {
                        description 'The fifth match field value.' ;
                        type string {
                          length 4..10 {
                            description 'User defined hexadecimal string,as follows:
0x00-0xffffffff.' ;
                          }

                        }

                        mandatory true ;
                      }

                      leaf rule-mask {
                        description 'The fifth match field mask.' ;
                        type string {
                          length 4..10 {
                            description 'User defined hexadecimal string mask,as follows:
0x00-0xffffffff.' ;
                          }

                        }

                        mandatory true ;
                      }

                    }

                    container segment6 {
                      description 'Configure the sixth segment.' ;
                      presence segment6 ;
                      leaf rule-string {
                        description 'The sixth match field value.' ;
                        type string {
                          length 4..10 {
                            description 'User defined hexadecimal string,as follows:
0x00-0xffffffff.' ;
                          }

                        }

                        mandatory true ;
                      }

                      leaf rule-mask {
                        description 'The sixth match field mask.' ;
                        type string {
                          length 4..10 {
                            description 'User defined hexadecimal string mask,as follows:
0x00-0xffffffff.' ;
                          }

                        }

                        mandatory true ;
                      }

                    }

                    container segment7 {
                      description 'Configure the seventh segment.' ;
                      presence segment7 ;
                      leaf rule-string {
                        description 'The seventh match field value.' ;
                        type string {
                          length 4..10 {
                            description 'User defined hexadecimal string,as follows:
0x00-0xffffffff.' ;
                          }

                        }

                        mandatory true ;
                      }

                      leaf rule-mask {
                        description 'The seventh match field mask.' ;
                        type string {
                          length 4..10 {
                            description 'User defined hexadecimal string mask,as follows:
0x00-0xffffffff.' ;
                          }

                        }

                        mandatory true ;
                      }

                    }

                    container segment8 {
                      description 'Configure the eighth segment.' ;
                      presence segment8 ;
                      leaf rule-string {
                        description 'The eighth match field value.' ;
                        type string {
                          length 4..10 {
                            description 'User defined hexadecimal string,as follows:
0x00-0xffffffff.' ;
                          }

                        }

                        mandatory true ;
                      }

                      leaf rule-mask {
                        description 'The eighth match field mask.' ;
                        type string {
                          length 4..10 {
                            description 'User defined hexadecimal string mask,as follows:
0x00-0xffffffff.' ;
                          }

                        }

                        mandatory true ;
                      }

                    }

                  }

                  ncd:revise-date 2017-06-13 ;
                }

                leaf log {
                  if-feature log-config ;

                  description 'Enable/Disable the function of counting matched packet data.' ;
                  type boolean ;

                  default false ;
                  ncd:revise-date 2022-01-27 ;
                }

              }

            }

          }

          ncd:revise-date 2017-05-08 ;
        }

        container ipv6-vxlan-access-lists {
          description 'Configure the IPv6 VXLAN ACL.' ;
          list ipv6-vxlan-access-list {
            description 'Configure the IPv6 VXLAN ACL.' ;
            key acl-name ;
            leaf acl-name {
              description 'Specify the ACL name.' ;
              type acl-name-type ;

            }

            leaf mode-type {
              description 'Mode type of the IPv6 VXLAN ACL.' ;
              type enumeration {
                enum transit-inner {
                  value 1 ;
                  description 'Transit node match VXLAN inner layer' ;
                }

                enum transit-outer {
                  value 2 ;
                  description 'Transit node match VXLAN outer layer' ;
                }

                enum vtep-inner {
                  value 3 ;
                  description 'VTEP node match VXLAN inner layer' ;
                }

                enum vtep-outer {
                  value 4 ;
                  description 'VTEP node match VXLAN outer layer' ;
                }

                enum outer-v4-transit-inner {
                  value 5 ;
                  description 'Transit node match VXLAN inner layer whose underlay is IPv4' ;
                }

                enum outer-v6-transit-inner {
                  value 6 ;
                  description 'Transit node match VXLAN inner layer whose underlay is IPv6' ;
                }

                enum outer-v4-vtep-inner {
                  value 7 ;
                  description 'VTEP node match VXLAN inner layer whose underlay is IPv4' ;
                }

                enum outer-v6-vtep-inner {
                  value 8 ;
                  description 'VTEP node match VXLAN inner layer whose underlay is IPv6' ;
                }

              }

              mandatory true ;
            }

            container rules-transit-inner {
              description 'Configure the IPv6 VXLAN ACL rules in transit-inner mode.
An IPv6 VXLAN ACL in transit-inner mode must be configured first.' ;
              list rule-transit-inner {
                description 'Configure an IPv6 VXLAN ACL rule in transit-inner mode.' ;
                key ruleid ;
                leaf ruleid {
                  description 'Specify the rule ID.' ;
                  type uint32 {
                    range 1..2147483644 ;

                  }

                }

                choice permit-deny {
                  description 'Specify the action as either permit or deny.' ;
                  mandatory true ;
                  case deny {
                    description 'Deny the packets that match the rule.' ;
                    leaf deny {
                      description 'Deny the packets that match the rule.' ;
                      type empty ;

                      mandatory true ;
                    }

                  }

                  case permit {
                    description 'Permit the packets that match the rule.' ;
                    leaf permit {
                      description 'Permit the packets that match the rule.' ;
                      type empty ;

                      mandatory true ;
                    }

                  }

                }

                container inner-layer {
                  description 'The inner-layer protocol of VXLAN.' ;
                  presence inner-layer ;
                  choice protocol-type {
                    description 'IPv6 protocol type.' ;
                    mandatory true ;
                    case tcp-udp {
                      description 'The protocol number is UDP or TCP.' ;
                      container tcp-udp {
                        description 'The protocol number is UDP or TCP.' ;
                        leaf tcp-udp {
                          description 'The protocol number is UDP or TCP.' ;
                          type enumeration {
                            enum tcp {
                              value 6 ;
                              description 'Transmission Control Protocol(6)' ;
                            }

                            enum udp {
                              value 17 ;
                              description 'User Datagram Protocol(17)' ;
                            }

                          }

                          mandatory true ;
                        }

                        choice src-addr {
                          description 'Specify source IPv6 address.' ;
                          mandatory true ;
                          case addr-type {
                            description 'Source IPv6 address.' ;
                            leaf src-address {
                              description 'Source IPv6 address.' ;
                              type ncd:ipv6-address ;

                              mandatory true ;
                            }

                            container src-wildcard {
                              description 'Source IPv6 address wildcard.' ;
                              choice wildcard-type {
                                description 'Source IPv6 address wildcard.' ;
                                mandatory true ;
                                case wildcard-len {
                                  description 'Source IPv6 address prefix length.' ;
                                  leaf src-wildcard-len {
                                    description 'Source IPv6 address prefix length.' ;
                                    type uint8 {
                                      range 0..128 ;

                                    }

                                    mandatory true ;
                                  }

                                }

                                case wildcard-bits {
                                  description 'Source IPv6 address wildcard.' ;
                                  leaf src-wildcard-bits {
                                    description 'Source IPv6 address wildcard.' ;
                                    type ncd:ipv6-address ;

                                    mandatory true ;
                                  }

                                }

                              }

                            }

                          }

                          case any-type {
                            description 'Any source IPv6 address.' ;
                            leaf src-any-addr {
                              description 'Any source IPv6 address.' ;
                              type empty ;

                              mandatory true ;
                            }

                          }

                        }

                        container source-port {
                          description 'Specify the source port.' ;
                          presence "Specify source port" ;
                          choice source-port {
                            description 'Specify the source port.' ;
                            mandatory true ;
                            case src-port-value {
                              description 'Specify the value of the source port number.' ;
                              container src-port-value {
                                description 'Specify the value of the source port number.' ;
                                presence "Configure port number" ;
                                leaf src-port-operator {
                                  description 'Specify the operation type of the source port number.' ;
                                  type enumeration {
                                    enum eq {
                                      value 1 ;
                                      description 'Equal to.' ;
                                    }

                                    enum ge {
                                      value 2 ;
                                      description 'Great than or equal to.' ;
                                    }

                                    enum le {
                                      value 3 ;
                                      description 'Less than or equal to.' ;
                                    }

                                  }

                                  mandatory true ;
                                }

                                leaf src-port-value {
                                  description 'Specify the value of the source port number.' ;
                                  type uint16 {
                                    range 0..65535 ;

                                  }

                                  mandatory true ;
                                }

                              }

                            }

                            case src-port-range {
                              description 'Specify the range of the source port number.' ;
                              container src-port-range {
                                description 'Specify the range of the source port number.' ;
                                presence "Configure port range" ;
                                leaf src-port-operator {
                                  description 'Specify the operation type of the source port number.' ;
                                  type enumeration {
                                    enum range {
                                      value 7 ;
                                      description 'Range.' ;
                                    }

                                  }

                                  mandatory true ;
                                }

                                leaf src-port-range {
                                  description 'Specify the range of the source port number.' ;
                                  type acl-port-range ;

                                  mandatory true ;
                                }

                              }

                            }

                          }

                        }

                        choice dst-addr {
                          description 'Specify destination IPv6 address.' ;
                          mandatory true ;
                          case addr-type {
                            description 'Destination IPv6 address.' ;
                            leaf dst-address {
                              description 'Destination IPv6 address.' ;
                              type ncd:ipv6-address ;

                              mandatory true ;
                            }

                            container dst-wildcard {
                              description 'Destination IPv6 address wildcard.' ;
                              choice wildcard-type {
                                description 'Destination IPv6 address wildcard.' ;
                                mandatory true ;
                                case wildcard-len {
                                  description 'Destination IPv6 address prefix length.' ;
                                  leaf dst-wildcard-len {
                                    description 'Destination IPv6 address prefix length.' ;
                                    type uint8 {
                                      range 0..128 ;

                                    }

                                    mandatory true ;
                                  }

                                }

                                case wildcard-bits {
                                  description 'Destination IPv6 address wildcard.' ;
                                  leaf dst-wildcard-bits {
                                    description 'Destination IPv6 address wildcard.' ;
                                    type ncd:ipv6-address ;

                                    mandatory true ;
                                  }

                                }

                              }

                            }

                          }

                          case any-type {
                            description 'Any destination IPv6 address.' ;
                            leaf dst-any-addr {
                              description 'Any destination IPv6 address.' ;
                              type empty ;

                              mandatory true ;
                            }

                          }

                        }

                        container destination-port {
                          description 'Specify the destination port.' ;
                          presence "Specify destination port" ;
                          choice destination-port {
                            description 'Specify the destination port.' ;
                            mandatory true ;
                            case dst-port-value {
                              description 'Specify the value of the destination port number.' ;
                              container dst-port-value {
                                description 'Specify the value of the destination port number.' ;
                                presence "Configure port number" ;
                                leaf dst-port-operator {
                                  description 'Specify the operation type of the destination port number.' ;
                                  type enumeration {
                                    enum eq {
                                      value 1 ;
                                      description 'Equal to.' ;
                                    }

                                    enum ge {
                                      value 2 ;
                                      description 'Great than or equal to.' ;
                                    }

                                    enum le {
                                      value 3 ;
                                      description 'Less than or equal to.' ;
                                    }

                                  }

                                  mandatory true ;
                                }

                                leaf dst-port-value {
                                  description 'Specify the value of the destination port number.' ;
                                  type uint16 {
                                    range 0..65535 ;

                                  }

                                  mandatory true ;
                                }

                              }

                            }

                            case dst-port-range {
                              description 'Specify the range of the destination port number.' ;
                              container dst-port-range {
                                description 'Specify the range of the destination port number.' ;
                                presence "Configure port range" ;
                                leaf dst-port-operator {
                                  description 'Specify the operation type of the destination port number.' ;
                                  type enumeration {
                                    enum range {
                                      value 7 ;
                                      description 'Range.' ;
                                    }

                                  }

                                  mandatory true ;
                                }

                                leaf dst-port-range {
                                  description 'Specify the range of the destination port number.' ;
                                  type acl-port-range ;

                                  mandatory true ;
                                }

                              }

                            }

                          }

                        }

                        leaf rst {
                          type acl-tcp-flag ;

                          if-feature vxlan-acl-tcp-flag ;

                          description 'Specify the RST flag.
When the value of tcp-udp is tcp, the node is valid.' ;
                          ncd:revise-date 2024-06-01 ;
                        }

                        leaf ack {
                          type acl-tcp-flag ;

                          if-feature vxlan-acl-tcp-flag ;

                          description 'Specify the ACK flag.
When the value of tcp-udp is tcp, the node is valid.' ;
                          ncd:revise-date 2024-06-01 ;
                        }

                        leaf fin {
                          type acl-tcp-flag ;

                          if-feature vxlan-acl-tcp-flag ;

                          description 'Specify the FIN flag.
When the value of tcp-udp is tcp, the node is valid.' ;
                          ncd:revise-date 2024-06-01 ;
                        }

                        leaf syn {
                          type acl-tcp-flag ;

                          if-feature vxlan-acl-tcp-flag ;

                          description 'Specify the SYN flag.
When the value of tcp-udp is tcp, the node is valid.' ;
                          ncd:revise-date 2024-06-01 ;
                        }

                        leaf psh {
                          type acl-tcp-flag ;

                          if-feature vxlan-acl-tcp-flag ;

                          description 'Specify the PSH flag.
When the value of tcp-udp is tcp, the node is valid.' ;
                          ncd:revise-date 2024-06-01 ;
                        }

                        leaf urg {
                          type acl-tcp-flag ;

                          if-feature vxlan-acl-tcp-flag ;

                          description 'Specify the URG flag.
When the value of tcp-udp is tcp, the node is valid.' ;
                          ncd:revise-date 2024-06-01 ;
                        }

                      }

                    }

                    case ip {
                      description 'The protocol number is a value excluding TCP and UDP.' ;
                      container ipv6-protocol {
                        description 'The protocol number is a value excluding TCP and UDP.' ;
                        leaf protocol-type {
                          description 'Specify the IPv6 protocol type excluding TCP and UDP.' ;
                          type uint16 {
                            range "0..5 | 7..16 | 18..255 | 65535" ;

                          }

                          mandatory true ;
                        }

                        choice src-addr {
                          description 'Specify source IPv6 address.' ;
                          mandatory true ;
                          case addr-type {
                            description 'Source IPv6 address.' ;
                            leaf src-address {
                              description 'Source IPv6 address.' ;
                              type ncd:ipv6-address ;

                              mandatory true ;
                            }

                            container src-wildcard {
                              description 'Source IPv6 address wildcard.' ;
                              choice wildcard-type {
                                description 'Source IPv6 address wildcard.' ;
                                mandatory true ;
                                case wildcard-len {
                                  description 'Source IPv6 address prefix length.' ;
                                  leaf src-wildcard-len {
                                    description 'Source IPv6 address prefix length.' ;
                                    type uint8 {
                                      range 0..128 ;

                                    }

                                    mandatory true ;
                                  }

                                }

                                case wildcard-bits {
                                  description 'Source IPv6 address wildcard.' ;
                                  leaf src-wildcard-bits {
                                    description 'Source IPv6 address wildcard.' ;
                                    type ncd:ipv6-address ;

                                    mandatory true ;
                                  }

                                }

                              }

                            }

                          }

                          case any-type {
                            description 'Any source IPv6 address.' ;
                            leaf src-any-addr {
                              description 'Any source IPv6 address.' ;
                              type empty ;

                              mandatory true ;
                            }

                          }

                        }

                        choice dst-addr {
                          description 'Specify destination IPv6 address.' ;
                          mandatory true ;
                          case addr-type {
                            description 'Destination IPv6 address.' ;
                            leaf dst-address {
                              description 'Destination IPv6 address.' ;
                              type ncd:ipv6-address ;

                              mandatory true ;
                            }

                            container dst-wildcard {
                              description 'Destination IPv6 address wildcard.' ;
                              choice wildcard-type {
                                description 'Destination IPv6 address wildcard.' ;
                                mandatory true ;
                                case wildcard-len {
                                  description 'Destination IPv6 address prefix length.' ;
                                  leaf dst-wildcard-len {
                                    description 'Destination IPv6 address prefix length.' ;
                                    type uint8 {
                                      range 0..128 ;

                                    }

                                    mandatory true ;
                                  }

                                }

                                case wildcard-bits {
                                  description 'Destination IPv6 address wildcard.' ;
                                  leaf dst-wildcard-bits {
                                    description 'Destination IPv6 address wildcard.' ;
                                    type ncd:ipv6-address ;

                                    mandatory true ;
                                  }

                                }

                              }

                            }

                          }

                          case any-type {
                            description 'Any destination IPv6 address.' ;
                            leaf dst-any-addr {
                              description 'Any destination IPv6 address.' ;
                              type empty ;

                              mandatory true ;
                            }

                          }

                        }

                      }

                    }

                  }

                  leaf dscp {
                    description 'Specify the DSCP value.' ;
                    type uint8 {
                      range 0..63 ;

                    }

                  }

                }

                container vni {
                  description 'VXLAN ID.' ;
                  presence vni ;
                  leaf vxlan-id {
                    description 'VXLAN ID.' ;
                    type uint32 {
                      range 1..16777215 ;

                    }

                    mandatory true ;
                  }

                }

                leaf vrf {
                  description 'Specify the VRF instance name.
The referenced VRF must exist.' ;
                  type acl-vrf-name {
                    length 1..32 {
                      description 'VPN Routing/Forwarding instance name, support 1-32 characters.' ;
                    }

                  }

                }

                leaf time-range {
                  description 'The name of the time range referenced by the ACL rule.
The referenced time range must exist.' ;
                  type string {
                    length 1..31 ;

                  }

                  ncd:revise-date 2021-04-02 ;
                }

                container l2-layer {
                  if-feature l2-layer ;

                  description 'L2 information.' ;
                  presence l2-layer ;
                  container link-prot {
                    description 'Specify the link protocol type.' ;
                    choice link-prot {
                      description 'Specify the link protocol type.' ;
                      case link-protocol {
                        description 'Specify the link protocol type.' ;
                        leaf link-protocol {
                          description 'Specify the link protocol type.' ;
                          type uint32 {
                            range 1536..65535 ;

                          }

                        }

                      }

                      case link-protocol-hex {
                        if-feature link-prot-hex-config ;

                        description 'Specify the link protocol in hexadecimal format.' ;
                        leaf link-protocol-hex {
                          description 'Specify the link protocol in hexadecimal format.' ;
                          type ncd:hex ;

                        }

                      }

                    }

                  }

                  container source-mac {
                    description 'Specify source MAC address.' ;
                    choice src-mac-addr {
                      description 'Specify source MAC address.' ;
                      mandatory true ;
                      case src-mac-addr {
                        description 'Source MAC address.' ;
                        leaf src-mac-address {
                          description 'Source MAC address.' ;
                          type ncd:mac-address ;

                          mandatory true ;
                        }

                        leaf src-mac-wildcard {
                          description 'Source MAC address wildcard.' ;
                          type ncd:mac-address ;

                          mandatory true ;
                        }

                      }

                      case src-mac-any {
                        description 'Any source MAC address.' ;
                        leaf src-mac-any {
                          description 'Any source MAC address.' ;
                          type empty ;

                          mandatory true ;
                        }

                      }

                    }

                  }

                  container destination-mac {
                    description 'Specify destination MAC address.' ;
                    choice dest-mac-addr {
                      description 'Specify destination MAC address.' ;
                      mandatory true ;
                      case dest-mac-addr {
                        description 'Destination MAC address.' ;
                        leaf dest-mac-address {
                          description 'Destination MAC address.' ;
                          type ncd:mac-address ;

                          mandatory true ;
                        }

                        leaf dest-mac-wildcard {
                          description 'Destination MAC address wildcard.' ;
                          type ncd:mac-address ;

                          mandatory true ;
                        }

                      }

                      case dest-mac-any {
                        description 'Any destination MAC address.' ;
                        leaf dest-mac-any {
                          description 'Any destination MAC address.' ;
                          type empty ;

                          mandatory true ;
                        }

                      }

                    }

                  }

                  leaf inner-cos {
                    if-feature link-cos-value ;

                    description 'Specify the inner-layer CoS value.' ;
                    type uint8 {
                      range 0..7 ;

                    }

                  }

                  leaf outer-cos {
                    if-feature link-cos-value ;

                    description 'Specify the outer-layer CoS value.' ;
                    type uint8 {
                      range 0..7 ;

                    }

                  }

                  leaf inner-vlan-range {
                    description 'Specify the range of the inner-layer VLAN.' ;
                    type acl-vlan-range ;

                  }

                  leaf outer-vlan-range {
                    description 'Specify the range of the outer-layer VLAN.' ;
                    type acl-vlan-range ;

                  }

                  ncd:revise-date 2021-10-26 ;
                }

                leaf log {
                  if-feature log-config ;

                  description 'Enable/Disable the function of counting matched packet data.' ;
                  type boolean ;

                  default false ;
                  ncd:revise-date 2022-01-20 ;
                }

              }

            }

            container rules-transit-outer {
              description 'Configure the IPv6 VXLAN ACL rules in transit-outer mode.
An IPv6 VXLAN ACL in transit-outer mode must be configured first.' ;
              list rule-transit-outer {
                description 'Configure the IPv6 VXLAN ACL rules in transit-outer mode.' ;
                key ruleid ;
                leaf ruleid {
                  description 'Specify the rule ID.' ;
                  type uint32 {
                    range 1..2147483644 ;

                  }

                }

                choice permit-deny {
                  description 'Specify the action as either permit or deny.' ;
                  mandatory true ;
                  case deny {
                    description 'Deny the packets that match the rule.' ;
                    leaf deny {
                      description 'Deny the packets that match the rule.' ;
                      type empty ;

                      mandatory true ;
                    }

                  }

                  case permit {
                    description 'Permit the packets that match the rule.' ;
                    leaf permit {
                      description 'Permit the packets that match the rule.' ;
                      type empty ;

                      mandatory true ;
                    }

                  }

                }

                container vni {
                  description 'VXLAN ID.' ;
                  presence vni ;
                  leaf vxlan-id {
                    description 'VXLAN ID.' ;
                    type uint32 {
                      range 1..16777215 ;

                    }

                    mandatory true ;
                  }

                }

                container outer-layer {
                  description 'The outer-layer protocol of VXLAN.' ;
                  leaf udp {
                    description 'The protocol number is UDP.' ;
                    type empty ;

                    mandatory true ;
                  }

                  choice src-addr {
                    description 'Specify source IPv6 address.' ;
                    mandatory true ;
                    case addr-type {
                      description 'Source IPv6 address.' ;
                      leaf src-address {
                        description 'Source IPv6 address.' ;
                        type ncd:ipv6-address ;

                        mandatory true ;
                      }

                      container src-wildcard {
                        description 'Source IPv6 address wildcard.' ;
                        choice wildcard-type {
                          description 'Source IPv6 address wildcard.' ;
                          mandatory true ;
                          case wildcard-len {
                            description 'Source IPv6 address prefix length.' ;
                            leaf src-wildcard-len {
                              description 'Source IPv6 address prefix length.' ;
                              type uint8 {
                                range 0..128 ;

                              }

                              mandatory true ;
                            }

                          }

                          case wildcard-bits {
                            description 'Source IPv6 address wildcard.' ;
                            leaf src-wildcard-bits {
                              description 'Source IPv6 address wildcard.' ;
                              type ncd:ipv6-address ;

                              mandatory true ;
                            }

                          }

                        }

                      }

                    }

                    case any-type {
                      description 'Any source IPv6 address.' ;
                      leaf src-any-addr {
                        description 'Any source IPv6 address.' ;
                        type empty ;

                        mandatory true ;
                      }

                    }

                  }

                  container source-port {
                    description 'Specify the source port.' ;
                    presence "Specify source port" ;
                    choice source-port {
                      description 'Specify the source port.' ;
                      mandatory true ;
                      case src-port-value {
                        description 'Specify the value of the source port number.' ;
                        container src-port-value {
                          description 'Specify the value of the source port number.' ;
                          presence "Configure port number" ;
                          leaf src-port-operator {
                            description 'Specify the operation type of the source port number.' ;
                            type enumeration {
                              enum eq {
                                value 1 ;
                                description 'Equal to.' ;
                              }

                              enum ge {
                                value 2 ;
                                description 'Great than or equal to.' ;
                              }

                              enum le {
                                value 3 ;
                                description 'Less than or equal to.' ;
                              }

                            }

                            mandatory true ;
                          }

                          leaf src-port-value {
                            description 'Specify the value of the source port number.' ;
                            type uint16 {
                              range 0..65535 ;

                            }

                            mandatory true ;
                          }

                        }

                      }

                      case src-port-range {
                        description 'Specify the range of the source port number.' ;
                        container src-port-range {
                          description 'Specify the range of the source port number.' ;
                          presence "Configure port range" ;
                          leaf src-port-operator {
                            description 'Specify the operation type of the source port number.' ;
                            type enumeration {
                              enum range {
                                value 7 ;
                                description 'Range.' ;
                              }

                            }

                            mandatory true ;
                          }

                          leaf src-port-range {
                            description 'Specify the range of the source port number.' ;
                            type acl-port-range ;

                            mandatory true ;
                          }

                        }

                      }

                    }

                  }

                  choice dst-addr {
                    description 'Specify destination IPv6 address.' ;
                    mandatory true ;
                    case addr-type {
                      description 'Destination IPv6 address.' ;
                      leaf dst-address {
                        description 'Destination IPv6 address.' ;
                        type ncd:ipv6-address ;

                        mandatory true ;
                      }

                      container dst-wildcard {
                        description 'Destination IPv6 address wildcard.' ;
                        choice wildcard-type {
                          description 'Destination IPv6 address wildcard.' ;
                          mandatory true ;
                          case wildcard-len {
                            description 'Destination IPv6 address prefix length.' ;
                            leaf dst-wildcard-len {
                              description 'Destination IPv6 address prefix length.' ;
                              type uint8 {
                                range 0..128 ;

                              }

                              mandatory true ;
                            }

                          }

                          case wildcard-bits {
                            description 'Destination IPv6 address wildcard.' ;
                            leaf dst-wildcard-bits {
                              description 'Destination IPv6 address wildcard.' ;
                              type ncd:ipv6-address ;

                              mandatory true ;
                            }

                          }

                        }

                      }

                    }

                    case any-type {
                      description 'Any destination IPv6 address.' ;
                      leaf dst-any-addr {
                        description 'Any destination IPv6 address.' ;
                        type empty ;

                        mandatory true ;
                      }

                    }

                  }

                  container destination-port {
                    description 'Specify the destination port.' ;
                    presence "Specify destination port" ;
                    choice destination-port {
                      description 'Specify the destination port.' ;
                      mandatory true ;
                      case dst-port-value {
                        description 'Specify the value of the destination port number.' ;
                        container dst-port-value {
                          description 'Specify the value of the destination port number.' ;
                          presence "Configure port number" ;
                          leaf dst-port-operator {
                            description 'Specify the operation type of the destination port number.' ;
                            type enumeration {
                              enum eq {
                                value 1 ;
                                description 'Equal to.' ;
                              }

                              enum ge {
                                value 2 ;
                                description 'Great than or equal to.' ;
                              }

                              enum le {
                                value 3 ;
                                description 'Less than or equal to.' ;
                              }

                            }

                            mandatory true ;
                          }

                          leaf dst-port-value {
                            description 'Specify the value of the destination port number.' ;
                            type uint16 {
                              range 0..65535 ;

                            }

                            mandatory true ;
                          }

                        }

                      }

                      case dst-port-range {
                        description 'Specify the range of the destination port number.' ;
                        container dst-port-range {
                          description 'Specify the range of the destination port number.' ;
                          presence "Configure port range" ;
                          leaf dst-port-operator {
                            description 'Specify the operation type of the destination port number.' ;
                            type enumeration {
                              enum range {
                                value 7 ;
                                description 'Range.' ;
                              }

                            }

                            mandatory true ;
                          }

                          leaf dst-port-range {
                            description 'Specify the range of the destination port number.' ;
                            type acl-port-range ;

                            mandatory true ;
                          }

                        }

                      }

                    }

                  }

                  leaf dscp {
                    description 'Specify the DSCP value.' ;
                    type uint8 {
                      range 0..63 ;

                    }

                  }

                }

                leaf vrf {
                  description 'Specify the VRF instance name.
The referenced VRF must exist.' ;
                  type acl-vrf-name {
                    length 1..32 {
                      description 'VPN Routing/Forwarding instance name, support 1-32 characters.' ;
                    }

                  }

                }

                leaf time-range {
                  description 'The name of the time range referenced by the ACL rule.
The referenced time range must exist.' ;
                  type string {
                    length 1..31 ;

                  }

                  ncd:revise-date 2021-04-02 ;
                }

                leaf log {
                  if-feature log-config ;

                  type boolean ;

                  description 'Enable/Disable the function of counting matched packet data.' ;
                  default false ;
                  ncd:revise-date 2023-10-07 ;
                }

              }

            }

            container rules-vtep-inner {
              description 'Configure the IPv6 VXLAN ACL rules in VTEP-inner mode.
An IPv6 VXLAN ACL in VTEP-inner mode must be configured first.' ;
              list rule-vtep-inner {
                description 'Configure an IPv6 VXLAN ACL rule in VTEP-inner mode.' ;
                key ruleid ;
                leaf ruleid {
                  description 'Specify the rule ID.' ;
                  type uint32 {
                    range 1..2147483644 ;

                  }

                }

                choice permit-deny {
                  description 'Specify the action as either permit or deny.' ;
                  mandatory true ;
                  case deny {
                    description 'Deny the packets that match the rule.' ;
                    leaf deny {
                      description 'Deny the packets that match the rule.' ;
                      type empty ;

                      mandatory true ;
                    }

                  }

                  case permit {
                    description 'Permit the packets that match the rule.' ;
                    leaf permit {
                      description 'Permit the packets that match the rule.' ;
                      type empty ;

                      mandatory true ;
                    }

                  }

                }

                container inner-layer {
                  description 'The inner-layer protocol of VXLAN.' ;
                  presence inner-layer ;
                  choice protocol-type {
                    description 'IPv6 protocol type.' ;
                    mandatory true ;
                    case tcp-udp {
                      description 'The protocol number is UDP or TCP.' ;
                      container tcp-udp {
                        description 'The protocol number is UDP or TCP.' ;
                        leaf tcp-udp {
                          description 'The protocol number is UDP or TCP.' ;
                          type enumeration {
                            enum tcp {
                              value 6 ;
                              description 'Transmission Control Protocol(6)' ;
                            }

                            enum udp {
                              value 17 ;
                              description 'User Datagram Protocol(17)' ;
                            }

                          }

                          mandatory true ;
                        }

                        choice src-addr {
                          description 'Specify source IPv6 address.' ;
                          mandatory true ;
                          case addr-type {
                            description 'Source IPv6 address.' ;
                            leaf src-address {
                              description 'Source IPv6 address.' ;
                              type ncd:ipv6-address ;

                              mandatory true ;
                            }

                            container src-wildcard {
                              description 'Source IPv6 address wildcard.' ;
                              choice wildcard-type {
                                description 'Source IPv6 address wildcard.' ;
                                mandatory true ;
                                case wildcard-len {
                                  description 'Source IPv6 address prefix length.' ;
                                  leaf src-wildcard-len {
                                    description 'Source IPv6 address prefix length.' ;
                                    type uint8 {
                                      range 0..128 ;

                                    }

                                    mandatory true ;
                                  }

                                }

                                case wildcard-bits {
                                  description 'Source IPv6 address wildcard.' ;
                                  leaf src-wildcard-bits {
                                    description 'Source IPv6 address wildcard.' ;
                                    type ncd:ipv6-address ;

                                    mandatory true ;
                                  }

                                }

                              }

                            }

                          }

                          case any-type {
                            description 'Any source IPv6 address.' ;
                            leaf src-any-addr {
                              description 'Any source IPv6 address.' ;
                              type empty ;

                              mandatory true ;
                            }

                          }

                        }

                        container source-port {
                          description 'Specify the source port.' ;
                          presence "Specify source port" ;
                          choice source-port {
                            description 'Specify the source port.' ;
                            mandatory true ;
                            case src-port-value {
                              description 'Specify the value of the source port number.' ;
                              container src-port-value {
                                description 'Specify the value of the source port number.' ;
                                presence "Configure port number" ;
                                leaf src-port-operator {
                                  description 'Specify the operation type of the source port number.' ;
                                  type enumeration {
                                    enum eq {
                                      value 1 ;
                                      description 'Equal to.' ;
                                    }

                                    enum ge {
                                      value 2 ;
                                      description 'Great than or equal to.' ;
                                    }

                                    enum le {
                                      value 3 ;
                                      description 'Less than or equal to.' ;
                                    }

                                  }

                                  mandatory true ;
                                }

                                leaf src-port-value {
                                  description 'Specify the value of the source port number.' ;
                                  type uint16 {
                                    range 0..65535 ;

                                  }

                                  mandatory true ;
                                }

                              }

                            }

                            case src-port-range {
                              description 'Specify the range of the source port number.' ;
                              container src-port-range {
                                description 'Specify the range of the source port number.' ;
                                presence "Configure port range" ;
                                leaf src-port-operator {
                                  description 'Specify the operation type of the source port number.' ;
                                  type enumeration {
                                    enum range {
                                      value 7 ;
                                      description 'Range.' ;
                                    }

                                  }

                                  mandatory true ;
                                }

                                leaf src-port-range {
                                  description 'Specify the range of the source port number.' ;
                                  type acl-port-range ;

                                  mandatory true ;
                                }

                              }

                            }

                          }

                        }

                        choice dst-addr {
                          description 'Specify destination IPv6 address.' ;
                          mandatory true ;
                          case addr-type {
                            description 'Destination IPv6 address.' ;
                            leaf dst-address {
                              description 'Destination IPv6 address.' ;
                              type ncd:ipv6-address ;

                              mandatory true ;
                            }

                            container dst-wildcard {
                              description 'Destination IPv6 address wildcard.' ;
                              choice wildcard-type {
                                description 'Destination IPv6 address wildcard.' ;
                                mandatory true ;
                                case wildcard-len {
                                  description 'Destination IPv6 address prefix length.' ;
                                  leaf dst-wildcard-len {
                                    description 'Destination IPv6 address prefix length.' ;
                                    type uint8 {
                                      range 0..128 ;

                                    }

                                    mandatory true ;
                                  }

                                }

                                case wildcard-bits {
                                  description 'Destination IPv6 address wildcard.' ;
                                  leaf dst-wildcard-bits {
                                    description 'Destination IPv6 address wildcard.' ;
                                    type ncd:ipv6-address ;

                                    mandatory true ;
                                  }

                                }

                              }

                            }

                          }

                          case any-type {
                            description 'Any destination IPv6 address.' ;
                            leaf dst-any-addr {
                              description 'Any destination IPv6 address.' ;
                              type empty ;

                              mandatory true ;
                            }

                          }

                        }

                        container destination-port {
                          description 'Specify the destination port.' ;
                          presence "Specify destination port" ;
                          choice destination-port {
                            description 'Specify the destination port.' ;
                            mandatory true ;
                            case dst-port-value {
                              description 'Specify the value of the destination port number.' ;
                              container dst-port-value {
                                description 'Specify the value of the destination port number.' ;
                                presence "Configure port number" ;
                                leaf dst-port-operator {
                                  description 'Specify the operation type of the destination port number.' ;
                                  type enumeration {
                                    enum eq {
                                      value 1 ;
                                      description 'Equal to.' ;
                                    }

                                    enum ge {
                                      value 2 ;
                                      description 'Great than or equal to.' ;
                                    }

                                    enum le {
                                      value 3 ;
                                      description 'Less than or equal to.' ;
                                    }

                                  }

                                  mandatory true ;
                                }

                                leaf dst-port-value {
                                  description 'Specify the value of the destination port number.' ;
                                  type uint16 {
                                    range 0..65535 ;

                                  }

                                  mandatory true ;
                                }

                              }

                            }

                            case dst-port-range {
                              description 'Specify the range of the destination port number.' ;
                              container dst-port-range {
                                description 'Specify the range of the destination port number.' ;
                                presence "Configure port range" ;
                                leaf dst-port-operator {
                                  description 'Specify the operation type of the destination port number.' ;
                                  type enumeration {
                                    enum range {
                                      value 7 ;
                                      description 'Range.' ;
                                    }

                                  }

                                  mandatory true ;
                                }

                                leaf dst-port-range {
                                  description 'Specify the range of the destination port number.' ;
                                  type acl-port-range ;

                                  mandatory true ;
                                }

                              }

                            }

                          }

                        }

                        leaf rst {
                          type acl-tcp-flag ;

                          if-feature vxlan-acl-tcp-flag ;

                          description 'Specify the RST flag.
When the value of tcp-udp is tcp, the node is valid.' ;
                          ncd:revise-date 2024-06-01 ;
                        }

                        leaf ack {
                          type acl-tcp-flag ;

                          if-feature vxlan-acl-tcp-flag ;

                          description 'Specify the ACK flag.
When the value of tcp-udp is tcp, the node is valid.' ;
                          ncd:revise-date 2024-06-01 ;
                        }

                        leaf fin {
                          type acl-tcp-flag ;

                          if-feature vxlan-acl-tcp-flag ;

                          description 'Specify the FIN flag.
When the value of tcp-udp is tcp, the node is valid.' ;
                          ncd:revise-date 2024-06-01 ;
                        }

                        leaf syn {
                          type acl-tcp-flag ;

                          if-feature vxlan-acl-tcp-flag ;

                          description 'Specify the SYN flag.
When the value of tcp-udp is tcp, the node is valid.' ;
                          ncd:revise-date 2024-06-01 ;
                        }

                        leaf psh {
                          type acl-tcp-flag ;

                          if-feature vxlan-acl-tcp-flag ;

                          description 'Specify the PSH flag.
When the value of tcp-udp is tcp, the node is valid.' ;
                          ncd:revise-date 2024-06-01 ;
                        }

                        leaf urg {
                          type acl-tcp-flag ;

                          if-feature vxlan-acl-tcp-flag ;

                          description 'Specify the URG flag.
When the value of tcp-udp is tcp, the node is valid.' ;
                          ncd:revise-date 2024-06-01 ;
                        }

                      }

                    }

                    case ip {
                      description 'The protocol number is a value excluding TCP and UDP.' ;
                      container ipv6-protocol {
                        description 'The protocol number is a value excluding TCP and UDP.' ;
                        leaf protocol-type {
                          description 'Specify the IPv6 protocol type excluding TCP and UDP.' ;
                          type uint16 {
                            range "0..5 | 7..16 | 18..255 | 65535" ;

                          }

                          mandatory true ;
                        }

                        choice src-addr {
                          description 'Specify source IPv6 address.' ;
                          mandatory true ;
                          case addr-type {
                            description 'Source IPv6 address.' ;
                            leaf src-address {
                              description 'Source IPv6 address.' ;
                              type ncd:ipv6-address ;

                              mandatory true ;
                            }

                            container src-wildcard {
                              description 'Source IPv6 address wildcard.' ;
                              choice wildcard-type {
                                description 'Source IPv6 address wildcard.' ;
                                mandatory true ;
                                case wildcard-len {
                                  description 'Source IPv6 address prefix length.' ;
                                  leaf src-wildcard-len {
                                    description 'Source IPv6 address prefix length.' ;
                                    type uint8 {
                                      range 0..128 ;

                                    }

                                    mandatory true ;
                                  }

                                }

                                case wildcard-bits {
                                  description 'Source IPv6 address wildcard.' ;
                                  leaf src-wildcard-bits {
                                    description 'Source IPv6 address wildcard.' ;
                                    type ncd:ipv6-address ;

                                    mandatory true ;
                                  }

                                }

                              }

                            }

                          }

                          case any-type {
                            description 'Any source IPv6 address.' ;
                            leaf src-any-addr {
                              description 'Any source IPv6 address.' ;
                              type empty ;

                              mandatory true ;
                            }

                          }

                        }

                        choice dst-addr {
                          description 'Specify destination IPv6 address.' ;
                          mandatory true ;
                          case addr-type {
                            description 'Destination IPv6 address.' ;
                            leaf dst-address {
                              description 'Destination IPv6 address.' ;
                              type ncd:ipv6-address ;

                              mandatory true ;
                            }

                            container dst-wildcard {
                              description 'Destination IPv6 address wildcard.' ;
                              choice wildcard-type {
                                description 'Destination IPv6 address wildcard.' ;
                                mandatory true ;
                                case wildcard-len {
                                  description 'Destination IPv6 address prefix length.' ;
                                  leaf dst-wildcard-len {
                                    description 'Destination IPv6 address prefix length.' ;
                                    type uint8 {
                                      range 0..128 ;

                                    }

                                    mandatory true ;
                                  }

                                }

                                case wildcard-bits {
                                  description 'Destination IPv6 address wildcard.' ;
                                  leaf dst-wildcard-bits {
                                    description 'Destination IPv6 address wildcard.' ;
                                    type ncd:ipv6-address ;

                                    mandatory true ;
                                  }

                                }

                              }

                            }

                          }

                          case any-type {
                            description 'Any destination IPv6 address.' ;
                            leaf dst-any-addr {
                              description 'Any destination IPv6 address.' ;
                              type empty ;

                              mandatory true ;
                            }

                          }

                        }

                      }

                    }

                  }

                  leaf dscp {
                    description 'Specify the DSCP value.' ;
                    type uint8 {
                      range 0..63 ;

                    }

                  }

                }

                container vni {
                  description 'VXLAN ID.' ;
                  presence vni ;
                  leaf vxlan-id {
                    description 'VXLAN ID.' ;
                    type uint32 {
                      range 1..16777215 ;

                    }

                    mandatory true ;
                  }

                }

                leaf vrf {
                  description 'Specify the VRF instance name.
The referenced VRF must exist.' ;
                  type acl-vrf-name {
                    length 1..32 {
                      description 'VPN Routing/Forwarding instance name, support 1-32 characters.' ;
                    }

                  }

                }

                leaf time-range {
                  description 'The name of the time range referenced by the ACL rule.
The referenced time range must exist.' ;
                  type string {
                    length 1..31 ;

                  }

                  ncd:revise-date 2021-04-02 ;
                }

                container l2-layer {
                  if-feature l2-layer ;

                  description 'L2 information.' ;
                  presence l2-layer ;
                  container link-prot {
                    description 'Specify the link protocol type.' ;
                    choice link-prot {
                      description 'Specify the link protocol type.' ;
                      case link-protocol {
                        description 'Specify the link protocol type.' ;
                        leaf link-protocol {
                          description 'Specify the link protocol type.' ;
                          type uint32 {
                            range 1536..65535 ;

                          }

                        }

                      }

                      case link-protocol-hex {
                        if-feature link-prot-hex-config ;

                        description 'Specify the link protocol in hexadecimal format.' ;
                        leaf link-protocol-hex {
                          description 'Specify the link protocol in hexadecimal format.' ;
                          type ncd:hex ;

                        }

                      }

                    }

                  }

                  container source-mac {
                    description 'Specify source MAC address.' ;
                    choice src-mac-addr {
                      description 'Specify source MAC address.' ;
                      mandatory true ;
                      case src-mac-addr {
                        description 'Source MAC address.' ;
                        leaf src-mac-address {
                          description 'Source MAC address.' ;
                          type ncd:mac-address ;

                          mandatory true ;
                        }

                        leaf src-mac-wildcard {
                          description 'Source MAC address wildcard.' ;
                          type ncd:mac-address ;

                          mandatory true ;
                        }

                      }

                      case src-mac-any {
                        description 'Any source MAC address.' ;
                        leaf src-mac-any {
                          description 'Any source MAC address.' ;
                          type empty ;

                          mandatory true ;
                        }

                      }

                    }

                  }

                  container destination-mac {
                    description 'Specify destination MAC address.' ;
                    choice dest-mac-addr {
                      description 'Specify destination MAC address.' ;
                      mandatory true ;
                      case dest-mac-addr {
                        description 'Destination MAC address.' ;
                        leaf dest-mac-address {
                          description 'Destination MAC address.' ;
                          type ncd:mac-address ;

                          mandatory true ;
                        }

                        leaf dest-mac-wildcard {
                          description 'Destination MAC address wildcard.' ;
                          type ncd:mac-address ;

                          mandatory true ;
                        }

                      }

                      case dest-mac-any {
                        description 'Any destination MAC address.' ;
                        leaf dest-mac-any {
                          description 'Any destination MAC address.' ;
                          type empty ;

                          mandatory true ;
                        }

                      }

                    }

                  }

                  leaf inner-cos {
                    if-feature link-cos-value ;

                    description 'Specify the inner-layer CoS value.' ;
                    type uint8 {
                      range 0..7 ;

                    }

                  }

                  leaf outer-cos {
                    if-feature link-cos-value ;

                    description 'Specify the outer-layer CoS value.' ;
                    type uint8 {
                      range 0..7 ;

                    }

                  }

                  leaf inner-vlan-range {
                    description 'Specify the range of the inner-layer VLAN.' ;
                    type acl-vlan-range ;

                  }

                  leaf outer-vlan-range {
                    description 'Specify the range of the outer-layer VLAN.' ;
                    type acl-vlan-range ;

                  }

                  ncd:revise-date 2021-10-26 ;
                }

                leaf log {
                  if-feature log-config ;

                  description 'Enable/Disable the function of counting matched packet data.' ;
                  type boolean ;

                  default false ;
                  ncd:revise-date 2022-01-20 ;
                }

              }

            }

            container rules-vtep-outer {
              description 'Configure the IPv6 VXLAN ACL rules in VTEP-outer mode.
An IPv6 VXLAN ACL in VTEP-outer mode must be configured first.' ;
              list rule-vtep-outer {
                description 'Configure an IPv6 VXLAN ACL rule in VTEP-outer mode.' ;
                key ruleid ;
                leaf ruleid {
                  description 'Specify the rule ID.' ;
                  type uint32 {
                    range 1..2147483644 ;

                  }

                }

                choice permit-deny {
                  description 'Specify the action as either permit or deny.' ;
                  mandatory true ;
                  case deny {
                    description 'Deny the packets that match the rule.' ;
                    leaf deny {
                      description 'Deny the packets that match the rule.' ;
                      type empty ;

                      mandatory true ;
                    }

                  }

                  case permit {
                    description 'Permit the packets that match the rule.' ;
                    leaf permit {
                      description 'Permit the packets that match the rule.' ;
                      type empty ;

                      mandatory true ;
                    }

                  }

                }

                container vni {
                  description 'VXLAN ID.' ;
                  presence vni ;
                  leaf vxlan-id {
                    description 'VXLAN ID.' ;
                    type uint32 {
                      range 1..16777215 ;

                    }

                    mandatory true ;
                  }

                }

                container outer-layer {
                  description 'The outer-layer protocol of VXLAN.' ;
                  leaf udp {
                    description 'The protocol number is UDP.' ;
                    type empty ;

                    mandatory true ;
                  }

                  choice src-addr {
                    description 'Specify source IPv6 address.' ;
                    mandatory true ;
                    case addr-type {
                      description 'Source IPv6 address.' ;
                      leaf src-address {
                        description 'Source IPv6 address.' ;
                        type ncd:ipv6-address ;

                        mandatory true ;
                      }

                      container src-wildcard {
                        description 'Source IPv6 address wildcard.' ;
                        choice wildcard-type {
                          description 'Source IPv6 address wildcard.' ;
                          mandatory true ;
                          case wildcard-len {
                            description 'Source IPv6 address prefix length.' ;
                            leaf src-wildcard-len {
                              description 'Source IPv6 address prefix length.' ;
                              type uint8 {
                                range 0..128 ;

                              }

                              mandatory true ;
                            }

                          }

                          case wildcard-bits {
                            description 'Source IPv6 address wildcard.' ;
                            leaf src-wildcard-bits {
                              description 'Source IPv6 address wildcard.' ;
                              type ncd:ipv6-address ;

                              mandatory true ;
                            }

                          }

                        }

                      }

                    }

                    case any-type {
                      description 'Any source IPv6 address.' ;
                      leaf src-any-addr {
                        description 'Any source IPv6 address.' ;
                        type empty ;

                        mandatory true ;
                      }

                    }

                  }

                  container source-port {
                    description 'Specify the source port.' ;
                    presence "Specify source port" ;
                    choice source-port {
                      description 'Specify the source port.' ;
                      mandatory true ;
                      case src-port-value {
                        description 'Specify the value of the source port number.' ;
                        container src-port-value {
                          description 'Specify the value of the source port number.' ;
                          presence "Configure port number" ;
                          leaf src-port-operator {
                            description 'Specify the operation type of the source port number.' ;
                            type enumeration {
                              enum eq {
                                value 1 ;
                                description 'Equal to.' ;
                              }

                              enum ge {
                                value 2 ;
                                description 'Great than or equal to.' ;
                              }

                              enum le {
                                value 3 ;
                                description 'Less than or equal to.' ;
                              }

                            }

                            mandatory true ;
                          }

                          leaf src-port-value {
                            description 'Specify the value of the source port number.' ;
                            type uint16 {
                              range 0..65535 ;

                            }

                            mandatory true ;
                          }

                        }

                      }

                      case src-port-range {
                        description 'Specify the range of the source port number.' ;
                        container src-port-range {
                          description 'Specify the range of the source port number.' ;
                          presence "Configure port range" ;
                          leaf src-port-operator {
                            description 'Specify the operation type of the source port number.' ;
                            type enumeration {
                              enum range {
                                value 7 ;
                                description 'Range.' ;
                              }

                            }

                            mandatory true ;
                          }

                          leaf src-port-range {
                            description 'Specify the range of the source port number.' ;
                            type acl-port-range ;

                            mandatory true ;
                          }

                        }

                      }

                    }

                  }

                  choice dst-addr {
                    description 'Specify destination IPv6 address.' ;
                    mandatory true ;
                    case addr-type {
                      description 'Destination IPv6 address.' ;
                      leaf dst-address {
                        description 'Destination IPv6 address.' ;
                        type ncd:ipv6-address ;

                        mandatory true ;
                      }

                      container dst-wildcard {
                        description 'Destination IPv6 address wildcard.' ;
                        choice wildcard-type {
                          description 'Destination IPv6 address wildcard.' ;
                          mandatory true ;
                          case wildcard-len {
                            description 'Destination IPv6 address prefix length.' ;
                            leaf dst-wildcard-len {
                              description 'Destination IPv6 address prefix length.' ;
                              type uint8 {
                                range 0..128 ;

                              }

                              mandatory true ;
                            }

                          }

                          case wildcard-bits {
                            description 'Destination IPv6 address wildcard.' ;
                            leaf dst-wildcard-bits {
                              description 'Destination IPv6 address wildcard.' ;
                              type ncd:ipv6-address ;

                              mandatory true ;
                            }

                          }

                        }

                      }

                    }

                    case any-type {
                      description 'Any destination IPv6 address.' ;
                      leaf dst-any-addr {
                        description 'Any destination IPv6 address.' ;
                        type empty ;

                        mandatory true ;
                      }

                    }

                  }

                  container destination-port {
                    description 'Specify the destination port.' ;
                    presence "Specify destination port" ;
                    choice destination-port {
                      description 'Specify the destination port.' ;
                      mandatory true ;
                      case dst-port-value {
                        description 'Specify the value of the destination port number.' ;
                        container dst-port-value {
                          description 'Specify the value of the destination port number.' ;
                          presence "Configure port number" ;
                          leaf dst-port-operator {
                            description 'Specify the operation type of the destination port number.' ;
                            type enumeration {
                              enum eq {
                                value 1 ;
                                description 'Equal to.' ;
                              }

                              enum ge {
                                value 2 ;
                                description 'Great than or equal to.' ;
                              }

                              enum le {
                                value 3 ;
                                description 'Less than or equal to.' ;
                              }

                            }

                            mandatory true ;
                          }

                          leaf dst-port-value {
                            description 'Specify the value of the destination port number.' ;
                            type uint16 {
                              range 0..65535 ;

                            }

                            mandatory true ;
                          }

                        }

                      }

                      case dst-port-range {
                        description 'Specify the range of the destination port number.' ;
                        container dst-port-range {
                          description 'Specify the range of the destination port number.' ;
                          presence "Configure port range" ;
                          leaf dst-port-operator {
                            description 'Specify the operation type of the destination port number.' ;
                            type enumeration {
                              enum range {
                                value 7 ;
                                description 'Range.' ;
                              }

                            }

                            mandatory true ;
                          }

                          leaf dst-port-range {
                            description 'Specify the range of the destination port number.' ;
                            type acl-port-range ;

                            mandatory true ;
                          }

                        }

                      }

                    }

                  }

                  leaf dscp {
                    description 'Specify the DSCP value.' ;
                    type uint8 {
                      range 0..63 ;

                    }

                  }

                }

                leaf vrf {
                  description 'Specify the VRF instance name.
The referenced VRF must exist.' ;
                  type acl-vrf-name {
                    length 1..32 {
                      description 'VPN Routing/Forwarding instance name, support 1-32 characters.' ;
                    }

                  }

                }

                leaf time-range {
                  description 'The name of the time range referenced by the ACL rule.
The referenced time range must exist.' ;
                  type string {
                    length 1..31 ;

                  }

                  ncd:revise-date 2021-04-02 ;
                }

                leaf log {
                  if-feature log-config ;

                  type boolean ;

                  description 'Enable/Disable the function of counting matched packet data.' ;
                  default false ;
                  ncd:revise-date 2023-10-07 ;
                }

              }

            }

          }

          ncd:revise-date 2020-03-18 ;
        }

      }

      container port-acl {
        description 'Configure ACL binding relationships, including bindings with interfaces, VLANs, global devices, etc.' ;
        container if-ipv4 {
          if-feature ipv4-feature ;

          description 'Bind an IPv4 ACL to the interface.' ;
          list egress {
            description 'Bind an IPv4 ACL in the outbound direction of the interface.' ;
            key if-name ;
            leaf if-name {
              description 'Specify the interface name.' ;
              type ncd:ifname ;

            }

            leaf acl-name {
              description 'Configure the ACL name.' ;
              type acl-name-type ;

              mandatory true ;
            }

            leaf port-acl-description {
              description 'Configure the description.' ;
              type ncd:string-with-blank {
                length 1..79 {
                  description 'Description of a port ACL, support 1-79 characters.' ;
                }

              }

              ncd:revise-date 2020-06-18 ;
            }

            leaf none-rule-default-action {
              if-feature none-rule-default-action ;

              description 'Configure the default rule action for the ACL that do not have configured rules or do not exist.' ;
              type enumeration {
                enum permit-any {
                  value 1 ;
                  description 'Configure default action is permit any in empty ACL.' ;
                }

                enum deny-any {
                  value 2 ;
                  description 'Configure default action is deny any in empty ACL.' ;
                }

              }

              ncd:revise-date 2021-11-23 ;
            }

          }

          list ingress {
            description 'Bind an IPv4 ACL in the inbound direction of the interface.' ;
            key if-name ;
            leaf if-name {
              description 'Specify the interface name.' ;
              type ncd:ifname ;

            }

            leaf acl-name {
              description 'Configure the ACL name.' ;
              type acl-name-type ;

              mandatory true ;
            }

            leaf port-acl-description {
              description 'Configure the description.' ;
              type ncd:string-with-blank {
                length 1..79 {
                  description 'Description of a port ACL, support 1-79 characters.' ;
                }

              }

              ncd:revise-date 2020-06-18 ;
            }

            leaf none-rule-default-action {
              if-feature none-rule-default-action ;

              description 'Configure the default rule action for the ACL that do not have configured rules or do not exist.' ;
              type enumeration {
                enum permit-any {
                  value 1 ;
                  description 'Configure default action is permit any in empty ACL.' ;
                }

                enum deny-any {
                  value 2 ;
                  description 'Configure default action is deny any in empty ACL.' ;
                }

              }

              ncd:revise-date 2021-11-23 ;
            }

          }

        }

        container vlan-ipv4 {
          if-feature ipv4-feature ;

          if-feature switchvlan-acl ;

          description 'Bind an IPv4 ACL to the VLAN.' ;
          list egress {
            description 'Bind an IPv4 ACL in the outbound direction of the VLAN.' ;
            key vlan-id ;
            leaf vlan-id {
              description 'Specify the VLAN ID.' ;
              type uint16 {
                range 1..4094 ;

              }

            }

            leaf acl-name {
              description 'Configure the ACL name.' ;
              type acl-name-type ;

              mandatory true ;
            }

            leaf port-acl-description {
              description 'Configure the description.' ;
              type ncd:string-with-blank {
                length 1..79 {
                  description 'Description of a port ACL, support 1-79 characters.' ;
                }

              }

              ncd:revise-date 2020-06-29 ;
            }

          }

          list ingress {
            description 'Bind an IPv4 ACL in the inbound direction of the VLAN.' ;
            key vlan-id ;
            leaf vlan-id {
              description 'Specify the VLAN ID.' ;
              type uint16 {
                range 1..4094 ;

              }

            }

            leaf acl-name {
              description 'Configure the ACL name.' ;
              type acl-name-type ;

              mandatory true ;
            }

            leaf port-acl-description {
              description 'Configure the description.' ;
              type ncd:string-with-blank {
                length 1..79 {
                  description 'Description of a port ACL, support 1-79 characters.' ;
                }

              }

              ncd:revise-date 2020-06-29 ;
            }

          }

        }

        container device-ipv4s {
          if-feature ipv4-feature ;

          if-feature statics-per-device ;

          description 'Bind an IPv4 ACL to the global device.' ;
          list device-ipv4 {
            description 'Bind an IPv4 ACL to the global device.' ;
            key direction ;
            leaf direction {
              description 'Specify the direction.' ;
              type acl-if-direction ;

            }

            leaf acl-name {
              description 'Configure the ACL name.' ;
              type acl-name-type ;

              mandatory true ;
            }

          }

          ncd:revise-date 2015-12-15 ;
        }

        container slot-ipv4s {
          if-feature ipv4-feature ;

          description 'Bind an IPv4 ACL to the slot.' ;
          list slot-ipv4 {
            description 'Bind an IPv4 ACL to the slot.' ;
            key 'slot-id direction' ;
            leaf slot-id {
              description 'Specify the slot id.' ;
              type uint8 {
                range 0..255 ;

              }

            }

            leaf direction {
              description 'Specify the direction.' ;
              type acl-if-direction ;

            }

            leaf acl-name {
              description 'Configure the ACL name.' ;
              type acl-name-type {
                length 1..31 {
                  description 'Name of an IPv4 access list.' ;
                }

              }

              mandatory true ;
            }

          }

          ncd:revise-date 2020-01-20 ;
        }

        container if-ipv4-mixed {
          if-feature ipv4-mixed-feature ;

          description 'Bind an IPv4 mixed ACL to the interface.' ;
          list egress {
            description 'Bind an IPv4 mixed ACL in the outbound direction of the interface.' ;
            key if-name ;
            leaf if-name {
              description 'Specify the interface name.' ;
              type ncd:ifname ;

            }

            leaf acl-name {
              description 'Configure the ACL name.' ;
              type acl-name-type ;

              mandatory true ;
            }

            leaf port-acl-description {
              description 'Configure the description.' ;
              type ncd:string-with-blank {
                length 1..79 {
                  description 'Description of a port ACL, support 1-79 characters.' ;
                }

              }

              ncd:revise-date 2020-06-18 ;
            }

          }

          list ingress {
            description 'Bind an IPv4 mixed ACL in the inbound direction of the interface.' ;
            key if-name ;
            leaf if-name {
              description 'Specify the interface name.' ;
              type ncd:ifname ;

            }

            leaf acl-name {
              description 'Configure the ACL name.' ;
              type acl-name-type ;

              mandatory true ;
            }

            leaf port-acl-description {
              description 'Configure the description.' ;
              type ncd:string-with-blank {
                length 1..79 {
                  description 'Description of a port ACL, support 1-79 characters.' ;
                }

              }

              ncd:revise-date 2020-06-18 ;
            }

          }

        }

        container vlan-ipv4-mixed {
          if-feature ipv4-mixed-feature ;

          if-feature switchvlan-acl ;

          description 'Bind an IPv4 mixed ACL to the VLAN.' ;
          list egress {
            description 'Bind an IPv4 mixed ACL in the outbound direction of the VLAN.' ;
            key vlan-id ;
            leaf vlan-id {
              description 'Specify the VLAN ID.' ;
              type uint16 {
                range 1..4094 ;

              }

            }

            leaf acl-name {
              description 'Configure the ACL name.' ;
              type acl-name-type ;

              mandatory true ;
            }

            leaf port-acl-description {
              description 'Configure the description.' ;
              type ncd:string-with-blank {
                length 1..79 {
                  description 'Description of a port ACL, support 1-79 characters.' ;
                }

              }

              ncd:revise-date 2020-06-29 ;
            }

          }

          list ingress {
            description 'Bind an IPv4 mixed ACL in the inbound direction of the VLAN.' ;
            key vlan-id ;
            leaf vlan-id {
              description 'Specify the VLAN ID.' ;
              type uint16 {
                range 1..4094 ;

              }

            }

            leaf acl-name {
              description 'Configure the ACL name.' ;
              type acl-name-type ;

              mandatory true ;
            }

            leaf port-acl-description {
              description 'Configure the description.' ;
              type ncd:string-with-blank {
                length 1..79 {
                  description 'Description of a port ACL, support 1-79 characters.' ;
                }

              }

              ncd:revise-date 2020-06-29 ;
            }

          }

        }

        container device-ipv4-mixeds {
          if-feature ipv4-mixed-feature ;

          if-feature statics-per-device ;

          description 'Bind an IPv4 mixed ACL to the global device.' ;
          list device-ipv4-mixed {
            description 'Bind an IPv4 mixed ACL to the global device.' ;
            key direction ;
            leaf direction {
              description 'Specify the direction.' ;
              type acl-if-direction ;

            }

            leaf acl-name {
              description 'Configure the ACL name.' ;
              type acl-name-type ;

              mandatory true ;
            }

          }

          ncd:revise-date 2015-12-15 ;
        }

        container if-ipv6 {
          if-feature ipv6-feature ;

          description 'Bind an IPv6 ACL to the interface.' ;
          list egress {
            description 'Bind an IPv6 ACL in the outbound direction of the interface.' ;
            key if-name ;
            leaf if-name {
              description 'Specify the interface name.' ;
              type ncd:ifname ;

            }

            leaf acl-name {
              description 'Configure the ACL name.' ;
              type acl-name-type ;

              mandatory true ;
            }

            leaf port-acl-description {
              description 'Configure the description.' ;
              type ncd:string-with-blank {
                length 1..79 {
                  description 'Description of a port ACL, support 1-79 characters.' ;
                }

              }

              ncd:revise-date 2020-06-18 ;
            }

            leaf none-rule-default-action {
              if-feature none-rule-default-action ;

              description 'Configure the default rule action for the ACL that do not have configured rules or do not exist.' ;
              type enumeration {
                enum permit-any {
                  value 1 ;
                  description 'Configure default action is permit any in empty ACL.' ;
                }

                enum deny-any {
                  value 2 ;
                  description 'Configure default action is deny any in empty ACL.' ;
                }

              }

              ncd:revise-date 2021-11-23 ;
            }

          }

          list ingress {
            description 'Bind an IPv6 ACL in the inbound direction of the interface.' ;
            key if-name ;
            leaf if-name {
              description 'Specify the interface name.' ;
              type ncd:ifname ;

            }

            leaf acl-name {
              description 'Configure the ACL name.' ;
              type acl-name-type ;

              mandatory true ;
            }

            leaf port-acl-description {
              description 'Configure the description.' ;
              type ncd:string-with-blank {
                length 1..79 {
                  description 'Description of a port ACL, support 1-79 characters.' ;
                }

              }

              ncd:revise-date 2020-06-18 ;
            }

            leaf none-rule-default-action {
              if-feature none-rule-default-action ;

              description 'Configure the default rule action for the ACL that do not have configured rules or do not exist.' ;
              type enumeration {
                enum permit-any {
                  value 1 ;
                  description 'Configure default action is permit any in empty ACL.' ;
                }

                enum deny-any {
                  value 2 ;
                  description 'Configure default action is deny any in empty ACL.' ;
                }

              }

              ncd:revise-date 2021-11-23 ;
            }

          }

        }

        container vlan-ipv6 {
          if-feature ipv6-feature ;

          if-feature switchvlan-acl ;

          description 'Bind an IPv6 ACL to the VLAN.' ;
          list egress {
            description 'Bind an IPv6 ACL in the outbound direction of the VLAN.' ;
            key vlan-id ;
            leaf vlan-id {
              description 'Specify the VLAN ID.' ;
              type uint16 {
                range 1..4094 ;

              }

            }

            leaf acl-name {
              description 'Configure the ACL name.' ;
              type acl-name-type ;

              mandatory true ;
            }

            leaf port-acl-description {
              description 'Configure the description.' ;
              type ncd:string-with-blank {
                length 1..79 {
                  description 'Description of a port ACL, support 1-79 characters.' ;
                }

              }

              ncd:revise-date 2020-06-29 ;
            }

          }

          list ingress {
            description 'Bind an IPv6 ACL in the inbound direction of the VLAN.' ;
            key vlan-id ;
            leaf vlan-id {
              description 'Specify the VLAN ID.' ;
              type uint16 {
                range 1..4094 ;

              }

            }

            leaf acl-name {
              description 'Configure the ACL name.' ;
              type acl-name-type ;

              mandatory true ;
            }

            leaf port-acl-description {
              description 'Configure the description.' ;
              type ncd:string-with-blank {
                length 1..79 {
                  description 'Description of a port ACL, support 1-79 characters.' ;
                }

              }

              ncd:revise-date 2020-06-29 ;
            }

          }

        }

        container device-ipv6s {
          if-feature ipv6-feature ;

          if-feature statics-per-device ;

          description 'Bind an IPv6 ACL to the global device.' ;
          list device-ipv6 {
            description 'Bind an IPv6 ACL to the global device.' ;
            key direction ;
            leaf direction {
              description 'Specify the direction.' ;
              type acl-if-direction ;

            }

            leaf acl-name {
              description 'Configure the ACL name.' ;
              type acl-name-type ;

              mandatory true ;
            }

          }

          ncd:revise-date 2015-12-15 ;
        }

        container slot-ipv6s {
          if-feature ipv6-feature ;

          description 'Bind an IPv6 ACL to the slot.' ;
          list slot-ipv6 {
            description 'Bind an IPv6 ACL to the slot.' ;
            key 'slot-id direction' ;
            leaf slot-id {
              description 'Specify the slot id.' ;
              type uint8 {
                range 0..255 ;

              }

            }

            leaf direction {
              description 'Specify the direction.' ;
              type acl-if-direction ;

            }

            leaf acl-name {
              description 'Configure the ACL name.' ;
              type acl-name-type {
                length 1..31 {
                  description 'Name of an IPv6 access list.' ;
                }

              }

              mandatory true ;
            }

          }

          ncd:revise-date 2020-01-20 ;
        }

        container if-ipv6-mixed {
          if-feature ipv6-mixed-feature ;

          description 'Bind an IPv6 mixed ACL to the interface.' ;
          list egress {
            description 'Bind an IPv6 mixed ACL in the outbound direction of the interface.' ;
            key if-name ;
            leaf if-name {
              description 'Specify the interface name.' ;
              type ncd:ifname ;

            }

            leaf acl-name {
              description 'Configure the ACL name.' ;
              type acl-name-type ;

              mandatory true ;
            }

            leaf port-acl-description {
              description 'Configure the description.' ;
              type ncd:string-with-blank {
                length 1..79 {
                  description 'Description of a port ACL, support 1-79 characters.' ;
                }

              }

              ncd:revise-date 2020-06-29 ;
            }

          }

          list ingress {
            description 'Bind an IPv6 mixed ACL in the inbound direction of the interface.' ;
            key if-name ;
            leaf if-name {
              description 'Specify the interface name.' ;
              type ncd:ifname ;

            }

            leaf acl-name {
              description 'Configure the ACL name.' ;
              type acl-name-type ;

              mandatory true ;
            }

            leaf port-acl-description {
              description 'Configure the description.' ;
              type ncd:string-with-blank {
                length 1..79 {
                  description 'Description of a port ACL, support 1-79 characters.' ;
                }

              }

              ncd:revise-date 2020-06-29 ;
            }

          }

        }

        container vlan-ipv6-mixed {
          if-feature ipv6-mixed-feature ;

          if-feature switchvlan-acl ;

          description 'Bind an IPv6 mixed ACL to the VLAN.' ;
          list egress {
            description 'Bind an IPv6 mixed ACL in the outbound direction of the VLAN.' ;
            key vlan-id ;
            leaf vlan-id {
              description 'Specify the VLAN ID.' ;
              type uint16 {
                range 1..4094 ;

              }

            }

            leaf acl-name {
              description 'Configure the ACL name.' ;
              type acl-name-type ;

              mandatory true ;
            }

            leaf port-acl-description {
              description 'Configure the description.' ;
              type ncd:string-with-blank {
                length 1..79 {
                  description 'Description of a port ACL, support 1-79 characters.' ;
                }

              }

              ncd:revise-date 2020-06-29 ;
            }

          }

          list ingress {
            description 'Bind an IPv6 mixed ACL in the inbound direction of the VLAN.' ;
            key vlan-id ;
            leaf vlan-id {
              description 'Specify the VLAN ID.' ;
              type uint16 {
                range 1..4094 ;

              }

            }

            leaf acl-name {
              description 'Configure the ACL name.' ;
              type acl-name-type ;

              mandatory true ;
            }

            leaf port-acl-description {
              description 'Configure the description.' ;
              type ncd:string-with-blank {
                length 1..79 {
                  description 'Description of a port ACL, support 1-79 characters.' ;
                }

              }

              ncd:revise-date 2020-06-29 ;
            }

          }

        }

        container device-ipv6-mixeds {
          if-feature ipv6-mixed-feature ;

          if-feature statics-per-device ;

          description 'Bind an IPv6 mixed ACL to the global device.' ;
          list device-ipv6-mixed {
            description 'Bind an IPv6 mixed ACL to the global device.' ;
            key direction ;
            leaf direction {
              description 'Specify the direction.' ;
              type acl-if-direction ;

            }

            leaf acl-name {
              description 'Configure the ACL name.' ;
              type acl-name-type ;

              mandatory true ;
            }

          }

          ncd:revise-date 2015-12-15 ;
        }

        container if-link {
          if-feature link-feature ;

          description 'Bind a link ACL to the interface.' ;
          list egress {
            description 'Bind a link ACL in the outbound direction of the interface.' ;
            key if-name ;
            leaf if-name {
              description 'Specify the interface name.' ;
              type ncd:ifname ;

            }

            leaf acl-name {
              description 'Configure the ACL name.' ;
              type acl-name-type ;

              mandatory true ;
            }

            leaf none-rule-default-action {
              if-feature none-rule-default-action ;

              description 'Configure the default rule action for the ACL that do not have configured rules or do not exist.' ;
              type enumeration {
                enum permit-any {
                  value 1 ;
                  description 'Configure default action is permit any in empty ACL.' ;
                }

                enum deny-any {
                  value 2 ;
                  description 'Configure default action is deny any in empty ACL.' ;
                }

              }

              ncd:revise-date 2021-11-23 ;
            }

          }

          list ingress {
            description 'Bind a link ACL in the inbound direction of the interface.' ;
            key if-name ;
            leaf if-name {
              description 'Specify the interface name.' ;
              type ncd:ifname ;

            }

            leaf acl-name {
              description 'Configure the ACL name.' ;
              type acl-name-type ;

              mandatory true ;
            }

            leaf none-rule-default-action {
              if-feature none-rule-default-action ;

              description 'Configure the default rule action for the ACL that do not have configured rules or do not exist.' ;
              type enumeration {
                enum permit-any {
                  value 1 ;
                  description 'Configure default action is permit any in empty ACL.' ;
                }

                enum deny-any {
                  value 2 ;
                  description 'Configure default action is deny any in empty ACL.' ;
                }

              }

              ncd:revise-date 2021-11-23 ;
            }

          }

        }

        container vlan-link {
          if-feature link-feature ;

          if-feature switchvlan-acl ;

          description 'Bind a link ACL to the VLAN.' ;
          list egress {
            description 'Bind a link ACL in the outbound direction of the VLAN.' ;
            key vlan-id ;
            leaf vlan-id {
              description 'Specify the VLAN ID.' ;
              type uint16 {
                range 1..4094 ;

              }

            }

            leaf acl-name {
              description 'Configure the ACL name.' ;
              type acl-name-type ;

              mandatory true ;
            }

          }

          list ingress {
            description 'Bind a link ACL in the inbound direction of the VLAN.' ;
            key vlan-id ;
            leaf vlan-id {
              description 'Specify the VLAN ID.' ;
              type uint16 {
                range 1..4094 ;

              }

            }

            leaf acl-name {
              description 'Configure the ACL name.' ;
              type acl-name-type ;

              mandatory true ;
            }

          }

        }

        container device-links {
          if-feature link-feature ;

          if-feature statics-per-device ;

          description 'Bind a link ACL to the global device.' ;
          list device-link {
            description 'Bind a link ACL to the global device.' ;
            key direction ;
            leaf direction {
              description 'Specify the direction.' ;
              type acl-if-direction ;

            }

            leaf acl-name {
              description 'Configure the ACL name.' ;
              type acl-name-type ;

              mandatory true ;
            }

          }

          ncd:revise-date 2015-12-15 ;
        }

        container device-user-defineds {
          if-feature statics-per-device ;

          if-feature user-defined-feature ;

          description 'Bind a user-defined ACL to the global device.' ;
          list device-user-defined {
            description 'Bind a user-defined ACL to the global device.' ;
            key direction ;
            leaf direction {
              description 'Specify the direction.' ;
              type acl-if-direction ;

            }

            leaf acl-name {
              description 'Configure the ACL name.' ;
              type acl-name-type ;

              mandatory true ;
            }

          }

          ncd:revise-date 2015-12-15 ;
        }

        container if-ipv4-vxlan {
          if-feature ipv4-vxlan-feature ;

          description 'Bind an IPv4 VXLAN ACL to the interface.' ;
          container egresses {
            description 'Bind an IPv4 VXLAN ACL in the outbound direction of the interface.' ;
            list egress {
              description 'Bind an IPv4 VXLAN ACL in the outbound direction of the interface.' ;
              key if-name ;
              leaf if-name {
                description 'Specify the interface name.' ;
                type ncd:ifname ;

              }

              leaf acl-name {
                description 'Configure the ACL name.' ;
                type acl-name-type ;

                mandatory true ;
              }

            }

          }

          container ingresses {
            description 'Bind an IPv4 VXLAN ACL in the inbound direction of the interface.' ;
            list ingress {
              description 'Bind an IPv4 VXLAN ACL in the inbound direction of the interface.' ;
              key if-name ;
              leaf if-name {
                description 'Specify the interface name.' ;
                type ncd:ifname ;

              }

              leaf acl-name {
                description 'Configure the ACL name.' ;
                type acl-name-type ;

                mandatory true ;
              }

            }

          }

          ncd:revise-date 2016-03-04 ;
        }

        container vlan-ipv4-vxlan {
          if-feature switchvlan-acl ;

          if-feature ipv4-vxlan-feature ;

          description 'Bind an IPv4 VXLAN ACL to the VLAN.' ;
          container egresses {
            description 'Bind an IPv4 VXLAN ACL in the outbound direction of the VLAN.' ;
            list egress {
              description 'Bind an IPv4 VXLAN ACL in the outbound direction of the VLAN.' ;
              key vlan-id ;
              leaf vlan-id {
                description 'Specify the VLAN ID.' ;
                type uint16 {
                  range 1..4094 ;

                }

              }

              leaf acl-name {
                description 'Configure the ACL name.' ;
                type acl-name-type ;

                mandatory true ;
              }

            }

          }

          container ingresses {
            description 'Bind an IPv4 VXLAN ACL in the inbound direction of the VLAN.' ;
            list ingress {
              description 'Bind an IPv4 VXLAN ACL in the inbound direction of the VLAN.' ;
              key vlan-id ;
              leaf vlan-id {
                description 'Specify the VLAN ID.' ;
                type uint16 {
                  range 1..4094 ;

                }

              }

              leaf acl-name {
                description 'Configure the ACL name.' ;
                type acl-name-type ;

                mandatory true ;
              }

            }

          }

          ncd:revise-date 2016-03-04 ;
        }

        container device-ipv4-vxlans {
          if-feature statics-per-device ;

          if-feature ipv4-vxlan-feature ;

          description 'Bind an IPv4 VXLAN ACL to the global device.' ;
          list device-ipv4-vxlan {
            description 'Bind an IPv4 VXLAN ACL to the global device.' ;
            key direction ;
            leaf direction {
              description 'Specify the direction.' ;
              type acl-if-direction ;

            }

            leaf acl-name {
              description 'Configure the ACL name.' ;
              type acl-name-type ;

              mandatory true ;
            }

          }

          ncd:revise-date 2016-03-04 ;
        }

        container if-udf-template {
          if-feature udf-template-type ;

          description 'Bind a user-defined template ACL to the interface.' ;
          container egresses {
            description 'Bind a user-defined template ACL in the outbound direction of the interface.' ;
            list egress {
              description 'Bind a user-defined template ACL in the outbound direction of the interface.' ;
              key if-name ;
              leaf if-name {
                description 'Specify the interface name.' ;
                type ncd:ifname ;

              }

              leaf acl-name {
                description 'Configure the ACL name.' ;
                type acl-name-type ;

                mandatory true ;
              }

            }

          }

          container ingresses {
            description 'Bind a user-defined template ACL in the inbound direction of the interface.' ;
            list ingress {
              description 'Bind a user-defined template ACL in the inbound direction of the interface.' ;
              key if-name ;
              leaf if-name {
                description 'Specify the interface name.' ;
                type ncd:ifname ;

              }

              leaf acl-name {
                description 'Configure the ACL name.' ;
                type acl-name-type ;

                mandatory true ;
              }

            }

          }

          ncd:revise-date 2017-05-08 ;
        }

        container if-ipv6-vxlan {
          description 'Bind an IPv6 VXLAN ACL to the interface.' ;
          container egresses {
            description 'Bind an IPv6 VXLAN ACL in the outbound direction of the interface.' ;
            list egress {
              description 'Bind an IPv6 VXLAN ACL in the outbound direction of the interface.' ;
              key if-name ;
              leaf if-name {
                description 'Specify the interface name.' ;
                type ncd:ifname ;

              }

              leaf acl-name {
                description 'Configure the ACL name.' ;
                type acl-name-type ;

                mandatory true ;
              }

            }

          }

          container ingresses {
            description 'Bind an IPv6 VXLAN ACL in the inbound direction of the interface.' ;
            list ingress {
              description 'Bind an IPv6 VXLAN ACL in the inbound direction of the interface.' ;
              key if-name ;
              leaf if-name {
                description 'Specify the interface name.' ;
                type ncd:ifname ;

              }

              leaf acl-name {
                description 'Configure the ACL name.' ;
                type acl-name-type ;

                mandatory true ;
              }

            }

          }

          ncd:revise-date 2020-03-18 ;
        }

        container vlan-ipv6-vxlan {
          description 'Bind an IPv6 VXLAN ACL to the VLAN.' ;
          container egresses {
            description 'Bind an IPv6 VXLAN ACL in the outbound direction of the VLAN.' ;
            list egress {
              description 'Bind an IPv6 VXLAN ACL in the outbound direction of the VLAN.' ;
              key vlan-id ;
              leaf vlan-id {
                description 'Specify the VLAN ID.' ;
                type uint16 {
                  range 1..4094 ;

                }

              }

              leaf acl-name {
                description 'Configure the ACL name.' ;
                type acl-name-type ;

                mandatory true ;
              }

            }

          }

          container ingresses {
            description 'Bind an IPv6 VXLAN ACL in the inbound direction of the VLAN.' ;
            list ingress {
              description 'Bind an IPv6 VXLAN ACL in the inbound direction of the VLAN.' ;
              key vlan-id ;
              leaf vlan-id {
                description 'Specify the VLAN ID.' ;
                type uint16 {
                  range 1..4094 ;

                }

              }

              leaf acl-name {
                description 'Configure the ACL name.' ;
                type acl-name-type ;

                mandatory true ;
              }

            }

          }

          ncd:revise-date 2020-03-18 ;
        }

        container device-ipv6-vxlans {
          description 'Bind an IPv6 VXLAN ACL to the global device.' ;
          list device-ipv6-vxlan {
            description 'Bind an IPv6 VXLAN ACL to the global device.' ;
            key direction ;
            leaf direction {
              description 'Specify the direction.' ;
              type acl-if-direction ;

            }

            leaf acl-name {
              description 'Configure the ACL name.' ;
              type acl-name-type ;

              mandatory true ;
            }

          }

          ncd:revise-date 2020-03-18 ;
        }

      }

      container vni-acl {
        description 'Configure the binding of VXLAN instances to a VXLAN type ACL.' ;
        container vni-ipv4-vxlans {
          if-feature ipv4-vxlan-feature ;

          description 'Bind an IPv4 VXLAN ACL to the VXLAN instance.' ;
          list vni-ipv4-vxlan {
            description 'Bind an IPv4 VXLAN ACL to the VXLAN instance.' ;
            key 'vxlan-id direction' ;
            leaf vxlan-id {
              description 'Specify the VXLAN instance ID.' ;
              type uint32 {
                range 1..16777215 {
                  description 'VXLAN ID.' ;
                }

              }

            }

            leaf direction {
              description 'Specify the VXLAN instance direction.' ;
              type acl-if-direction ;

            }

            leaf acl-name {
              description 'Configure the IPv4 VXLAN ACL name.' ;
              type acl-name-type {
                length 1..31 {
                  description 'Name of an IPv4 VXLAN access list.' ;
                }

              }

              mandatory true ;
            }

          }

        }

        ncd:revise-date 2016-03-04 ;
      }

      container statistics-switch {
        if-feature acl-statistics ;

        description 'Configure ACL statistics switches.' ;
        presence "Configure ACL log statistics switch" ;
        container ipv4-log-switchs {
          if-feature ipv4-feature ;

          description 'Configure the IPv4 type interface granularity statistics switch.' ;
          list ipv4-log-switch {
            description 'Configure the IPv4 type interface granularity statistics switch.' ;
            key 'if-name if-direction' ;
            leaf if-name {
              description 'Specify the interface name.' ;
              type ncd:ifname ;

            }

            leaf if-direction {
              description 'Specify the interface direction.' ;
              type acl-if-direction ;

            }

            choice switch-option {
              description 'Configure the statistics switch.' ;
              mandatory true ;
              case off {
                description 'Turn off the statistics.' ;
                leaf off {
                  description 'Turn off the statistics.' ;
                  type empty ;

                  mandatory true ;
                }

              }

              case on {
                description 'Turn on the statistics.' ;
                leaf on {
                  description 'Turn on the statistics.' ;
                  type empty ;

                  mandatory true ;
                }

                leaf action {
                  description 'Specify the action of the rule to be counted.' ;
                  type enumeration {
                    enum permit {
                      value 1 ;
                      description 'Enable permit ACL log.' ;
                    }

                    enum deny {
                      value 2 ;
                      description 'Enable deny ACL log.' ;
                    }

                    enum all {
                      value 3 ;
                      description 'Enable all ACL log.' ;
                    }

                  }

                  mandatory true ;
                }

              }

            }

          }

        }

        container ipv6-log-switchs {
          if-feature ipv6-feature ;

          description 'Configure the IPv6 type interface granularity statistics switch.' ;
          list ipv6-log-switch {
            description 'Configure the IPv6 type interface granularity statistics switch.' ;
            key 'if-name if-direction' ;
            leaf if-name {
              description 'Specify the interface name.' ;
              type ncd:ifname ;

            }

            leaf if-direction {
              description 'Specify the interface direction.' ;
              type acl-if-direction ;

            }

            choice switch-option {
              description 'Configure the statistics switch.' ;
              mandatory true ;
              case off {
                description 'Turn off the statistics.' ;
                leaf off {
                  description 'Turn off the statistics.' ;
                  type empty ;

                  mandatory true ;
                }

              }

              case on {
                description 'Turn on the statistics.' ;
                leaf on {
                  description 'Turn on the statistics.' ;
                  type empty ;

                  mandatory true ;
                }

                leaf action {
                  description 'Specify the action of the rule to be counted.' ;
                  type enumeration {
                    enum permit {
                      value 1 ;
                      description 'Enable permit ACL log.' ;
                    }

                    enum deny {
                      value 2 ;
                      description 'Enable deny ACL log.' ;
                    }

                    enum all {
                      value 3 ;
                      description 'Enable all ACL log.' ;
                    }

                  }

                  mandatory true ;
                }

              }

            }

          }

        }

        container link-log-switchs {
          if-feature link-log-config ;

          description 'Configure the link type interface granularity statistics switch.' ;
          list link-log-switch {
            description 'Configure the link type interface granularity statistics switch.' ;
            key 'if-name if-direction' ;
            leaf if-name {
              description 'Specify the interface name.' ;
              type ncd:ifname ;

            }

            leaf if-direction {
              description 'Specify the interface direction.' ;
              type acl-if-direction ;

            }

            choice switch-option {
              description 'Configure the statistics switch.' ;
              mandatory true ;
              case off {
                description 'Turn off the statistics.' ;
                leaf off {
                  description 'Turn off the statistics.' ;
                  type empty ;

                  mandatory true ;
                }

              }

              case on {
                description 'Turn on the statistics.' ;
                leaf on {
                  description 'Turn on the statistics.' ;
                  type empty ;

                  mandatory true ;
                }

                leaf action {
                  description 'Specify the action of the rule to be counted.' ;
                  type enumeration {
                    enum permit {
                      value 1 ;
                      description 'Enable permit ACL log.' ;
                    }

                    enum deny {
                      value 2 ;
                      description 'Enable deny ACL log.' ;
                    }

                    enum all {
                      value 3 ;
                      description 'Enable all ACL log.' ;
                    }

                  }

                  mandatory true ;
                }

              }

            }

          }

          ncd:revise-date 2019-10-08 ;
        }

        container ipv4-mixed-log-switchs {
          if-feature ipv4-mixed-log-config ;

          description 'Configure the IPv4 mixed type interface granularity statistics switch.' ;
          list ipv4-mixed-log-switch {
            description 'Configure the IPv4 mixed type interface granularity statistics switch.' ;
            key 'if-name if-direction' ;
            leaf if-name {
              description 'Specify the interface name.' ;
              type ncd:ifname ;

            }

            leaf if-direction {
              description 'Specify the interface direction.' ;
              type acl-if-direction ;

            }

            choice switch-option {
              description 'Configure the statistics switch.' ;
              mandatory true ;
              case off {
                description 'Turn off the statistics.' ;
                leaf off {
                  description 'Turn off the statistics.' ;
                  type empty ;

                  mandatory true ;
                }

              }

              case on {
                description 'Turn on the statistics.' ;
                leaf on {
                  description 'Turn on the statistics.' ;
                  type empty ;

                  mandatory true ;
                }

                leaf action {
                  description 'Specify the action of the rule to be counted.' ;
                  type enumeration {
                    enum permit {
                      value 1 ;
                      description 'Enable permit ACL log.' ;
                    }

                    enum deny {
                      value 2 ;
                      description 'Enable deny ACL log.' ;
                    }

                    enum all {
                      value 3 ;
                      description 'Enable all ACL log.' ;
                    }

                  }

                  mandatory true ;
                }

              }

            }

          }

          ncd:revise-date 2019-10-08 ;
        }

        container ipv6-mixed-log-switchs {
          if-feature ipv6-mixed-log-config ;

          description 'Configure the IPv6 mixed type interface granularity statistics switch.' ;
          list ipv6-mixed-log-switch {
            description 'Configure the IPv6 mixed type interface granularity statistics switch.' ;
            key 'if-name if-direction' ;
            leaf if-name {
              description 'Specify the interface name.' ;
              type ncd:ifname ;

            }

            leaf if-direction {
              description 'Specify the interface direction.' ;
              type acl-if-direction ;

            }

            choice switch-option {
              description 'Configure the statistics switch.' ;
              mandatory true ;
              case off {
                description 'Turn off the statistics.' ;
                leaf off {
                  description 'Turn off the statistics.' ;
                  type empty ;

                  mandatory true ;
                }

              }

              case on {
                description 'Turn on the statistics.' ;
                leaf on {
                  description 'Turn on the statistics.' ;
                  type empty ;

                  mandatory true ;
                }

                leaf action {
                  description 'Specify the action of the rule to be counted.' ;
                  type enumeration {
                    enum permit {
                      value 1 ;
                      description 'Enable permit ACL log.' ;
                    }

                    enum deny {
                      value 2 ;
                      description 'Enable deny ACL log.' ;
                    }

                    enum all {
                      value 3 ;
                      description 'Enable all ACL log.' ;
                    }

                  }

                  mandatory true ;
                }

              }

            }

          }

          ncd:revise-date 2021-06-03 ;
        }

        container ipv4-log-switchs-by-acl {
          description 'Configure the IPv4 type ACL granularity statistics switch.' ;
          list ipv4-log-switch-by-acl {
            description 'Configure the IPv4 type ACL granularity statistics switch.' ;
            key 'acl-name if-direction' ;
            leaf acl-name {
              description 'Specify the ACL name.' ;
              type acl-name-type ;

            }

            leaf if-direction {
              description 'Specify the direction.' ;
              type acl-if-direction ;

            }

            leaf switch-action {
              description 'Specify the action of the rule to be counted.' ;
              type enumeration {
                enum permit {
                  value 1 ;
                  description 'Enable permit ACL log.' ;
                }

                enum deny {
                  value 2 ;
                  description 'Enable deny ACL log.' ;
                }

                enum all {
                  value 3 ;
                  description 'Enable all ACL log.' ;
                }

              }

              mandatory true ;
            }

          }

          ncd:revise-date 2021-10-20 ;
        }

        container ipv6-log-switchs-by-acl {
          description 'Configure the IPv6 type ACL granularity statistics switch.' ;
          list ipv6-log-switch-by-acl {
            description 'Configure the IPv6 type ACL granularity statistics switch.' ;
            key 'acl-name if-direction' ;
            leaf acl-name {
              description 'Specify the ACL name.' ;
              type acl-name-type ;

            }

            leaf if-direction {
              description 'Specify the direction.' ;
              type acl-if-direction ;

            }

            leaf switch-action {
              description 'Specify the action of the rule to be counted.' ;
              type enumeration {
                enum permit {
                  value 1 ;
                  description 'Enable permit ACL log.' ;
                }

                enum deny {
                  value 2 ;
                  description 'Enable deny ACL log.' ;
                }

                enum all {
                  value 3 ;
                  description 'Enable all ACL log.' ;
                }

              }

              mandatory true ;
            }

          }

          ncd:revise-date 2021-10-20 ;
        }

        container link-log-switchs-by-acl {
          description 'Configure the link type ACL granularity statistics switch.' ;
          list link-log-switch-by-acl {
            description 'Configure the link type ACL granularity statistics switch.' ;
            key 'acl-name if-direction' ;
            leaf acl-name {
              description 'Specify the ACL name.' ;
              type acl-name-type ;

            }

            leaf if-direction {
              description 'Specify the direction.' ;
              type acl-if-direction ;

            }

            leaf switch-action {
              description 'Specify the action of the rule to be counted.' ;
              type enumeration {
                enum permit {
                  value 1 ;
                  description 'Enable permit ACL log.' ;
                }

                enum deny {
                  value 2 ;
                  description 'Enable deny ACL log.' ;
                }

                enum all {
                  value 3 ;
                  description 'Enable all ACL log.' ;
                }

              }

              mandatory true ;
            }

          }

          ncd:revise-date 2021-10-20 ;
        }

        container ipv4-mixed-log-switchs-by-acl {
          description 'Configure the IPv4 mixed type ACL granularity statistics switch.' ;
          list ipv4-mixed-log-switch-by-acl {
            description 'Configure the IPv4 mixed type ACL granularity statistics switch.' ;
            key 'acl-name if-direction' ;
            leaf acl-name {
              description 'Specify the ACL name.' ;
              type acl-name-type ;

            }

            leaf if-direction {
              description 'Specify the direction.' ;
              type acl-if-direction ;

            }

            leaf switch-action {
              description 'Specify the action of the rule to be counted.' ;
              type enumeration {
                enum permit {
                  value 1 ;
                  description 'Enable permit ACL log.' ;
                }

                enum deny {
                  value 2 ;
                  description 'Enable deny ACL log.' ;
                }

                enum all {
                  value 3 ;
                  description 'Enable all ACL log.' ;
                }

              }

              mandatory true ;
            }

          }

          ncd:revise-date 2021-10-20 ;
        }

        container ipv6-mixed-log-switchs-by-acl {
          description 'Configure the IPv6 mixed type ACL granularity statistics switch.' ;
          list ipv6-mixed-log-switch-by-acl {
            description 'Configure the IPv6 mixed type ACL granularity statistics switch.' ;
            key 'acl-name if-direction' ;
            leaf acl-name {
              description 'Specify the ACL name.' ;
              type acl-name-type ;

            }

            leaf if-direction {
              description 'Specify the direction.' ;
              type acl-if-direction ;

            }

            leaf switch-action {
              description 'Specify the action of the rule to be counted.' ;
              type enumeration {
                enum permit {
                  value 1 ;
                  description 'Enable permit ACL log.' ;
                }

                enum deny {
                  value 2 ;
                  description 'Enable deny ACL log.' ;
                }

                enum all {
                  value 3 ;
                  description 'Enable all ACL log.' ;
                }

              }

              mandatory true ;
            }

          }

          ncd:revise-date 2021-10-20 ;
        }

        container ipv4-vxlan-log-switches-by-acl {
          description 'Configure the IPv4 VXLAN type ACL granularity statistics switch.' ;
          list ipv4-vxlan-log-switch-by-acl {
            description 'Configure the IPv4 VXLAN type ACL granularity statistics switch.' ;
            key 'acl-name if-direction' ;
            leaf acl-name {
              description 'Specify the ACL name.' ;
              type acl-name-type ;

            }

            leaf if-direction {
              description 'Specify the direction.' ;
              type acl-if-direction ;

            }

            leaf switch-action {
              description 'Specify the action of the rule to be counted.' ;
              type enumeration {
                enum permit {
                  value 1 ;
                  description 'Enable permit ACL log.' ;
                }

                enum deny {
                  value 2 ;
                  description 'Enable deny ACL log.' ;
                }

                enum all {
                  value 3 ;
                  description 'Enable all ACL log.' ;
                }

              }

              mandatory true ;
            }

          }

          ncd:revise-date 2022-01-20 ;
        }

        container ipv6-vxlan-log-switches-by-acl {
          description 'Configure the IPv6 VXLAN type ACL granularity statistics switch.' ;
          list ipv6-vxlan-log-switch-by-acl {
            description 'Configure the IPv6 VXLAN type ACL granularity statistics switch.' ;
            key 'acl-name if-direction' ;
            leaf acl-name {
              description 'Specify the ACL name.' ;
              type acl-name-type ;

            }

            leaf if-direction {
              description 'Specify the direction.' ;
              type acl-if-direction ;

            }

            leaf switch-action {
              description 'Specify the action of the rule to be counted.' ;
              type enumeration {
                enum permit {
                  value 1 ;
                  description 'Enable permit ACL log.' ;
                }

                enum deny {
                  value 2 ;
                  description 'Enable deny ACL log.' ;
                }

                enum all {
                  value 3 ;
                  description 'Enable all ACL log.' ;
                }

              }

              mandatory true ;
            }

          }

          ncd:revise-date 2022-01-20 ;
        }

        container user-defined-template-log-switchs {
          if-feature udf-template-type ;

          description 'Configure the user-defined template type interface granularity statistics switch.' ;
          list user-defined-template-log-switch {
            description 'Configure the user-defined template type interface granularity statistics switch.' ;
            key 'if-name if-direction' ;
            leaf if-name {
              description 'Specify the interface name.' ;
              type ncd:ifname ;

            }

            leaf if-direction {
              description 'Specify the interface direction.' ;
              type acl-if-direction ;

            }

            leaf action {
              description 'Specify the action of the rule to be counted.' ;
              type enumeration {
                enum permit {
                  value 1 ;
                  description 'Enable permit ACL log.' ;
                }

                enum deny {
                  value 2 ;
                  description 'Enable deny ACL log.' ;
                }

                enum all {
                  value 3 ;
                  description 'Enable all ACL log.' ;
                }

              }

              mandatory true ;
            }

          }

          ncd:revise-date 2022-01-27 ;
        }

        ncd:revise-date 2015-06-08 ;
      }

      container interface-applications {
        list interface-application {
          leaf if-name {
            type ncd:ifname {
              length 1..31 {
                description 'Name of the attaching interface, support 1-31 characters' ;
              }

            }

            description 'Specify the interface name.' ;
          }

          leaf mode-type {
            type acl-if-application-mode-type ;

            description 'Specify the mode type.' ;
          }

          description 'Configure the interface-related applications.' ;
          key 'if-name mode-type' ;
          if-feature acl-if-application {
            ncd:revise-date 2024-01-16 ;
          }

        }

        description 'Configure the interface-related applications.' ;
        ncd:revise-date 2024-01-16 ;
      }

    }

  }

  container operation {
    config false ;
    description 'Operation model.' ;
    container acl {
      description 'Operation related to ACL.' ;
      container ipv4-log-clears {
        if-feature ipv4-feature ;

        if-feature acl-statistics ;

        description 'Clear the IPv4 type interface granularity statistical data.' ;
        choice clear-type {
          description 'Methods for clearing statistical data.' ;
          case specify-if {
            description 'Specify the interface and direction to clear statistical data.' ;
            list ipv4-log-clear {
              description 'Specify the interface and direction to clear statistical data.' ;
              key 'if-name if-direction' ;
              leaf if-name {
                description 'Specify the interface name.' ;
                type ncd:ifname ;

              }

              leaf if-direction {
                description 'Specify the interface direction.' ;
                type acl-if-direction ;

              }

            }

          }

          case all-if {
            description 'Clear statistical data for all interfaces.' ;
            leaf ipv4-log-clear-all {
              description 'Clear IPv4 ACL statistical data for all interfaces.' ;
              type empty ;

              mandatory true ;
            }

            ncd:revise-date 2021-11-02 ;
          }

        }

      }

      container ipv6-log-clears {
        if-feature ipv6-feature ;

        if-feature acl-statistics ;

        description 'Clear the IPv6 type interface granularity statistical data.' ;
        choice clear-type {
          description 'Methods for clearing statistical data.' ;
          case specify-if {
            description 'Specify the interface and direction to clear statistical data.' ;
            list ipv6-log-clear {
              description 'Specify the interface and direction to clear statistical data.' ;
              key 'if-name if-direction' ;
              leaf if-name {
                description 'Specify the interface name.' ;
                type ncd:ifname ;

              }

              leaf if-direction {
                description 'Specify the interface direction.' ;
                type acl-if-direction ;

              }

            }

          }

          case all-if {
            description 'Clear statistical data for all interfaces.' ;
            leaf ipv6-log-clear-all {
              description 'Clear IPv6 ACL statistical data for all interfaces.' ;
              type empty ;

              mandatory true ;
            }

            ncd:revise-date 2021-11-02 ;
          }

        }

      }

      container link-log-clears {
        if-feature link-feature ;

        if-feature acl-statistics ;

        description 'Clear the link type interface granularity statistical data.' ;
        choice clear-type {
          description 'Methods for clearing statistical data.' ;
          case specify-if {
            description 'Specify the interface and direction to clear statistical data.' ;
            list link-log-clear {
              description 'Specify the interface and direction to clear statistical data.' ;
              key 'if-name if-direction' ;
              leaf if-name {
                description 'Specify the interface name.' ;
                type ncd:ifname ;

              }

              leaf if-direction {
                description 'Specify the interface direction.' ;
                type acl-if-direction ;

              }

            }

          }

          case all-if {
            description 'Clear statistical data for all interfaces.' ;
            leaf link-log-clear-all {
              description 'Clear link ACL statistical data for all interfaces.' ;
              type empty ;

              mandatory true ;
            }

            ncd:revise-date 2021-11-02 ;
          }

        }

      }

      container ipv4-mixed-log-clears {
        if-feature ipv4-mixed-log-config ;

        description 'Clear the IPv4 mixed type interface granularity statistical data.' ;
        choice clear-type {
          description 'Methods for clearing statistical data.' ;
          case specify-if {
            description 'Specify the interface and direction to clear statistical data.' ;
            list ipv4-mixed-log-clear {
              description 'Specify the interface and direction to clear statistical data.' ;
              key 'if-name if-direction' ;
              leaf if-name {
                description 'Specify the interface name.' ;
                type ncd:ifname ;

              }

              leaf if-direction {
                description 'Specify the interface direction.' ;
                type acl-if-direction ;

              }

            }

          }

          case all-if {
            description 'Clear statistical data for all interfaces.' ;
            leaf ipv4-mixed-log-clear-all {
              description 'Clear IPv4 mixed ACL statistical data for all interfaces.' ;
              type empty ;

              mandatory true ;
            }

            ncd:revise-date 2021-11-02 ;
          }

        }

        ncd:revise-date 2019-10-08 ;
      }

      container ipv6-mixed-log-clears {
        if-feature ipv6-mixed-log-config ;

        description 'Clear the IPv6 mixed type interface granularity statistical data.' ;
        list ipv6-mixed-log-clear {
          description 'Specify the interface and direction to clear statistical data.' ;
          key 'if-name if-direction' ;
          leaf if-name {
            description 'Specify the interface name.' ;
            type ncd:ifname ;

          }

          leaf if-direction {
            description 'Specify the interface direction.' ;
            type acl-if-direction ;

          }

        }

        ncd:revise-date 2021-06-03 ;
      }

      container ipv4-log-clears-by-acl {
        description 'Clear the IPv4 type ACL granularity statistical data.' ;
        list ipv4-log-clear-by-acl {
          description 'Specify the ACL and direction to clear statistical data.' ;
          key 'acl-name if-direction' ;
          leaf acl-name {
            description 'Specify the ACL name.' ;
            type acl-name-type ;

          }

          leaf if-direction {
            description 'Specify the direction.' ;
            type acl-if-direction ;

          }

        }

        ncd:revise-date 2021-10-20 ;
      }

      container ipv6-log-clears-by-acl {
        description 'Clear the IPv6 type ACL granularity statistical data.' ;
        list ipv6-log-clear-by-acl {
          description 'Specify the ACL and direction to clear statistical data.' ;
          key 'acl-name if-direction' ;
          leaf acl-name {
            description 'Specify the ACL name.' ;
            type acl-name-type ;

          }

          leaf if-direction {
            description 'Specify the direction.' ;
            type acl-if-direction ;

          }

        }

        ncd:revise-date 2021-10-20 ;
      }

      container link-log-clears-by-acl {
        description 'Clear the link type ACL granularity statistical data.' ;
        list link-log-clear-by-acl {
          description 'Specify the ACL and direction to clear statistical data.' ;
          key 'acl-name if-direction' ;
          leaf acl-name {
            description 'Specify the ACL name.' ;
            type acl-name-type ;

          }

          leaf if-direction {
            description 'Specify the direction.' ;
            type acl-if-direction ;

          }

        }

        ncd:revise-date 2021-10-20 ;
      }

      container ipv4-mixed-log-clears-by-acl {
        description 'Clear the IPv4 mixed type ACL granularity statistical data.' ;
        list ipv4-mixed-log-clear-by-acl {
          description 'Specify the ACL and direction to clear statistical data.' ;
          key 'acl-name if-direction' ;
          leaf acl-name {
            description 'Specify the ACL name.' ;
            type acl-name-type ;

          }

          leaf if-direction {
            description 'Specify the direction.' ;
            type acl-if-direction ;

          }

        }

        ncd:revise-date 2021-10-20 ;
      }

      container ipv6-mixed-log-clears-by-acl {
        description 'Clear the IPv6 mixed type ACL granularity statistical data.' ;
        list ipv6-mixed-log-clear-by-acl {
          description 'Specify the ACL and direction to clear statistical data.' ;
          key 'acl-name if-direction' ;
          leaf acl-name {
            description 'Specify the ACL name.' ;
            type acl-name-type ;

          }

          leaf if-direction {
            description 'Specify the direction.' ;
            type acl-if-direction ;

          }

        }

        ncd:revise-date 2021-10-20 ;
      }

      container ipv4-vxlan-log-clears-by-acl {
        description 'Clear the IPv4 VXLAN type ACL granularity statistical data.' ;
        list ipv4-vxlan-log-clear-by-acl {
          description 'Specify the ACL and direction to clear statistical data.' ;
          key 'acl-name if-direction' ;
          leaf acl-name {
            description 'Specify the ACL name.' ;
            type acl-name-type ;

          }

          leaf if-direction {
            description 'Specify the direction.' ;
            type acl-if-direction ;

          }

        }

        ncd:revise-date 2022-01-20 ;
      }

      container ipv6-vxlan-log-clears-by-acl {
        description 'Clear the IPv6 VXLAN type ACL granularity statistical data.' ;
        list ipv6-vxlan-log-clear-by-acl {
          description 'Specify the ACL and direction to clear statistical data.' ;
          key 'acl-name if-direction' ;
          leaf acl-name {
            description 'Specify the ACL name.' ;
            type acl-name-type ;

          }

          leaf if-direction {
            description 'Specify the direction.' ;
            type acl-if-direction ;

          }

        }

        ncd:revise-date 2022-01-20 ;
      }

      container user-defined-template-log-clears {
        if-feature udf-template-type ;

        if-feature acl-statistics ;

        description 'Clear the user-defined template type interface granularity statistical data.' ;
        list user-defined-template-log-clear {
          description 'Specify the interface and direction to clear statistical data.' ;
          key 'if-name if-direction' ;
          leaf if-name {
            description 'Specify the interface name.' ;
            type ncd:ifname ;

          }

          leaf if-direction {
            description 'Specify the interface direction.' ;
            type acl-if-direction ;

          }

        }

        ncd:revise-date 2022-01-27 ;
      }

    }

    ncd:revise-date 2015-06-08 ;
  }

  container state {
    config false ;
    description 'State model.' ;
    container acl {
      description 'State about ACL.' ;
      container acl-v4-statistics {
        if-feature ipv4-feature ;

        if-feature acl-statistics ;

        description 'Query the IPv4 type interface granularity statistical data.' ;
        list acl-v4-statistic {
          description 'Query the IPv4 type interface granularity statistical data.' ;
          key 'if-name if-direction acl-ruleid' ;
          leaf if-name {
            description 'Specify the interface name.' ;
            type ncd:ifname ;

          }

          leaf if-direction {
            description 'Specify the interface direction.' ;
            type acl-if-direction ;

          }

          leaf acl-ruleid {
            description 'Specify the rule ID.' ;
            type uint32 {
              range 1..2147483644 {
                description 'ID of this rule.' ;
              }

            }

          }

          leaf acl-name {
            description 'ACL Name.' ;
            type acl-name-type ;

          }

          leaf stats-bytes {
            description 'The number of bytes in the packets that match the rule.' ;
            type uint64 ;

            units byte ;
          }

          leaf stats-packets {
            description 'The number of packets that match the rule.' ;
            type uint64 ;

          }

          leaf stats-rate {
            description 'The instantaneous rate of packets that match the rule.' ;
            type uint64 ;

            units bps ;
          }

          ncd:select "if-name if-direction" ;
          ncd:select "if-name if-direction acl-ruleid" ;
        }

      }

      container acl-v6-statistics {
        if-feature ipv6-feature ;

        if-feature acl-statistics ;

        description 'Query the IPv6 type interface granularity statistical data.' ;
        list acl-v6-statistic {
          description 'Query the IPv6 type interface granularity statistical data.' ;
          key 'if-name if-direction acl-ruleid' ;
          leaf if-name {
            description 'Specify the interface name.' ;
            type ncd:ifname ;

          }

          leaf if-direction {
            description 'Specify the interface direction.' ;
            type acl-if-direction ;

          }

          leaf acl-ruleid {
            description 'Specify the rule ID.' ;
            type uint32 {
              range 1..2147483644 {
                description 'ID of this rule.' ;
              }

            }

          }

          leaf acl-name {
            description 'ACL Name.' ;
            type acl-name-type ;

          }

          leaf stats-bytes {
            description 'The number of bytes in the packets that match the rule.' ;
            type uint64 ;

            units byte ;
          }

          leaf stats-packets {
            description 'The number of packets that match the rule.' ;
            type uint64 ;

          }

          leaf stats-rate {
            description 'The instantaneous rate of packets that match the rule.' ;
            type uint64 ;

            units bps ;
          }

          ncd:select "if-name if-direction" ;
          ncd:select "if-name if-direction acl-ruleid" ;
        }

      }

      container acl-link-statistics {
        if-feature link-log-config ;

        description 'Query the link type interface granularity statistical data.' ;
        list acl-link-statistic {
          description 'Query the link type interface granularity statistical data.' ;
          key 'if-name if-direction acl-ruleid' ;
          leaf if-name {
            description 'Specify the interface name.' ;
            type ncd:ifname ;

          }

          leaf if-direction {
            description 'Specify the interface direction.' ;
            type acl-if-direction ;

          }

          leaf acl-ruleid {
            description 'Specify the rule ID.' ;
            type uint32 {
              range 1..2147483644 {
                description 'ID of this rule.' ;
              }

            }

          }

          leaf acl-name {
            description 'ACL Name.' ;
            type acl-name-type ;

          }

          leaf stats-bytes {
            description 'The number of bytes in the packets that match the rule.' ;
            type uint64 ;

            units byte ;
          }

          leaf stats-packets {
            description 'The number of packets that match the rule.' ;
            type uint64 ;

          }

          leaf stats-rate {
            description 'The instantaneous rate of packets that match the rule.' ;
            type uint64 ;

            units bps ;
          }

          ncd:select "if-name if-direction" ;
          ncd:select "if-name if-direction acl-ruleid" ;
        }

        ncd:revise-date 2019-10-08 ;
      }

      container acl-v4-mixed-statistics {
        if-feature ipv4-mixed-log-config ;

        description 'Query the IPv4 mixed type interface granularity statistical data.' ;
        list acl-v4-mixed-statistic {
          description 'Query the IPv4 mixed type interface granularity statistical data.' ;
          key 'if-name if-direction acl-ruleid' ;
          leaf if-name {
            description 'Specify the interface name.' ;
            type ncd:ifname ;

          }

          leaf if-direction {
            description 'Specify the interface direction.' ;
            type acl-if-direction ;

          }

          leaf acl-ruleid {
            description 'Specify the rule ID.' ;
            type uint32 {
              range 1..2147483644 {
                description 'ID of this rule.' ;
              }

            }

          }

          leaf acl-name {
            description 'ACL Name.' ;
            type acl-name-type ;

          }

          leaf stats-bytes {
            description 'The number of bytes in the packets that match the rule.' ;
            type uint64 ;

            units byte ;
          }

          leaf stats-packets {
            description 'The number of packets that match the rule.' ;
            type uint64 ;

          }

          leaf stats-rate {
            description 'The instantaneous rate of packets that match the rule.' ;
            type uint64 ;

            units bps ;
          }

          ncd:select "if-name if-direction" ;
          ncd:select "if-name if-direction acl-ruleid" ;
        }

        ncd:revise-date 2019-10-08 ;
      }

      container acl-v6-mixed-statistics {
        if-feature ipv6-mixed-log-config ;

        description 'Query the IPv6 mixed type interface granularity statistical data.' ;
        list acl-v6-mixed-statistic {
          description 'Query the IPv6 mixed type interface granularity statistical data.' ;
          key 'if-name if-direction acl-ruleid' ;
          leaf if-name {
            description 'Specify the interface name.' ;
            type ncd:ifname ;

          }

          leaf if-direction {
            description 'Specify the interface direction.' ;
            type acl-if-direction ;

          }

          leaf acl-ruleid {
            description 'Specify the rule ID.' ;
            type uint32 {
              range 1..2147483644 {
                description 'ID of this rule.' ;
              }

            }

          }

          leaf acl-name {
            description 'ACL Name.' ;
            type acl-name-type ;

          }

          leaf stats-bytes {
            description 'The number of bytes in the packets that match the rule.' ;
            type uint64 ;

            units byte ;
          }

          leaf stats-packets {
            description 'The number of packets that match the rule.' ;
            type uint64 ;

          }

          leaf stats-rate {
            description 'The instantaneous rate of packets that match the rule.' ;
            type uint64 ;

            units bps ;
          }

          ncd:select "if-name if-direction" ;
          ncd:select "if-name if-direction acl-ruleid" ;
        }

        ncd:revise-date 2021-06-03 ;
      }

      container acl-v4-statistics-by-acl {
        description 'Query the IPv4 type ACL granularity statistical data.' ;
        list acl-v4-statistic-by-acl {
          description 'Query the IPv4 type ACL granularity statistical data.' ;
          key 'acl-name if-direction acl-ruleid' ;
          leaf acl-name {
            description 'Specify the ACL name.' ;
            type acl-name-type ;

          }

          leaf if-direction {
            description 'Specify the direction.' ;
            type acl-if-direction ;

          }

          leaf acl-ruleid {
            description 'Specify the rule ID.' ;
            type uint32 {
              range 1..2147483644 {
                description 'ID of this rule.' ;
              }

            }

          }

          leaf stats-bytes {
            description 'The number of bytes in the packets that match the rule.' ;
            type uint64 ;

            units byte ;
          }

          leaf stats-packets {
            description 'The number of packets that match the rule.' ;
            type uint64 ;

          }

          leaf stats-rate {
            description 'The instantaneous rate of packets that match the rule.' ;
            type uint64 ;

            units bps ;
          }

          ncd:select "acl-name if-direction" ;
          ncd:select "acl-name if-direction acl-ruleid" ;
        }

        ncd:revise-date 2021-10-20 ;
      }

      container acl-v6-statistics-by-acl {
        description 'Query the IPv6 type ACL granularity statistical data.' ;
        list acl-v6-statistic-by-acl {
          description 'Query the IPv6 type ACL granularity statistical data.' ;
          key 'acl-name if-direction acl-ruleid' ;
          leaf acl-name {
            description 'Specify the ACL name.' ;
            type acl-name-type ;

          }

          leaf if-direction {
            description 'Specify the direction.' ;
            type acl-if-direction ;

          }

          leaf acl-ruleid {
            description 'Specify the rule ID.' ;
            type uint32 {
              range 1..2147483644 {
                description 'ID of this rule.' ;
              }

            }

          }

          leaf stats-bytes {
            description 'The number of bytes in the packets that match the rule.' ;
            type uint64 ;

            units byte ;
          }

          leaf stats-packets {
            description 'The number of packets that match the rule.' ;
            type uint64 ;

          }

          leaf stats-rate {
            description 'The instantaneous rate of packets that match the rule.' ;
            type uint64 ;

            units bps ;
          }

          ncd:select "acl-name if-direction" ;
          ncd:select "acl-name if-direction acl-ruleid" ;
        }

        ncd:revise-date 2021-10-20 ;
      }

      container acl-link-statistics-by-acl {
        description 'Query the link type ACL granularity statistical data.' ;
        list acl-link-statistic-by-acl {
          description 'Query the link type ACL granularity statistical data.' ;
          key 'acl-name if-direction acl-ruleid' ;
          leaf acl-name {
            description 'Specify the ACL name.' ;
            type acl-name-type ;

          }

          leaf if-direction {
            description 'Specify the direction.' ;
            type acl-if-direction ;

          }

          leaf acl-ruleid {
            description 'Specify the rule ID.' ;
            type uint32 {
              range 1..2147483644 {
                description 'ID of this rule.' ;
              }

            }

          }

          leaf stats-bytes {
            description 'The number of bytes in the packets that match the rule.' ;
            type uint64 ;

            units byte ;
          }

          leaf stats-packets {
            description 'The number of packets that match the rule.' ;
            type uint64 ;

          }

          leaf stats-rate {
            description 'The instantaneous rate of packets that match the rule.' ;
            type uint64 ;

            units bps ;
          }

          ncd:select "acl-name if-direction" ;
          ncd:select "acl-name if-direction acl-ruleid" ;
        }

        ncd:revise-date 2021-10-20 ;
      }

      container acl-v4-mixed-statistics-by-acl {
        description 'Query the IPv4 mixed type ACL granularity statistical data.' ;
        list acl-v4-mixed-statistic-by-acl {
          description 'Query the IPv4 mixed type ACL granularity statistical data.' ;
          key 'acl-name if-direction acl-ruleid' ;
          leaf acl-name {
            description 'Specify the ACL name.' ;
            type acl-name-type ;

          }

          leaf if-direction {
            description 'Specify the direction.' ;
            type acl-if-direction ;

          }

          leaf acl-ruleid {
            description 'Specify the rule ID.' ;
            type uint32 {
              range 1..2147483644 {
                description 'ID of this rule.' ;
              }

            }

          }

          leaf stats-bytes {
            description 'The number of bytes in the packets that match the rule.' ;
            type uint64 ;

            units byte ;
          }

          leaf stats-packets {
            description 'The number of packets that match the rule.' ;
            type uint64 ;

          }

          leaf stats-rate {
            description 'The instantaneous rate of packets that match the rule.' ;
            type uint64 ;

            units bps ;
          }

          ncd:select "acl-name if-direction" ;
          ncd:select "acl-name if-direction acl-ruleid" ;
        }

        ncd:revise-date 2021-10-20 ;
      }

      container acl-v6-mixed-statistics-by-acl {
        description 'Query the IPv6 mixed type ACL granularity statistical data.' ;
        list acl-v6-mixed-statistic-by-acl {
          description 'Query the IPv6 mixed type ACL granularity statistical data.' ;
          key 'acl-name if-direction acl-ruleid' ;
          leaf acl-name {
            description 'Specify the ACL name.' ;
            type acl-name-type ;

          }

          leaf if-direction {
            description 'Specify the direction.' ;
            type acl-if-direction ;

          }

          leaf acl-ruleid {
            description 'Specify the rule ID.' ;
            type uint32 {
              range 1..2147483644 {
                description 'ID of this rule.' ;
              }

            }

          }

          leaf stats-bytes {
            description 'The number of bytes in the packets that match the rule.' ;
            type uint64 ;

            units byte ;
          }

          leaf stats-packets {
            description 'The number of packets that match the rule.' ;
            type uint64 ;

          }

          leaf stats-rate {
            description 'The instantaneous rate of packets that match the rule.' ;
            type uint64 ;

            units bps ;
          }

          ncd:select "acl-name if-direction" ;
          ncd:select "acl-name if-direction acl-ruleid" ;
        }

        ncd:revise-date 2021-10-20 ;
      }

      container acl-v4-vxlan-statistics-by-acl {
        description 'Query the IPv4 VXLAN type ACL granularity statistical data.' ;
        list acl-v4-vxlan-statistics-by-acl {
          description 'Query the IPv4 VXLAN type ACL granularity statistical data.' ;
          key 'acl-name if-direction acl-ruleid' ;
          leaf acl-name {
            description 'Specify the ACL name.' ;
            type acl-name-type ;

          }

          leaf if-direction {
            description 'Specify the direction.' ;
            type acl-if-direction ;

          }

          leaf acl-ruleid {
            description 'Specify the rule ID.' ;
            type uint32 {
              range 1..2147483644 {
                description 'ID of this rule.' ;
              }

            }

          }

          leaf stats-bytes {
            description 'The number of bytes in the packets that match the rule.' ;
            type uint64 ;

            units byte ;
          }

          leaf stats-packets {
            description 'The number of packets that match the rule.' ;
            type uint64 ;

          }

          leaf stats-rate {
            description 'The instantaneous rate of packets that match the rule.' ;
            type uint64 ;

            units bps ;
          }

          ncd:select "acl-name if-direction" ;
          ncd:select "acl-name if-direction acl-ruleid" ;
        }

        ncd:revise-date 2022-01-20 ;
      }

      container acl-v6-vxlan-statistics-by-acl {
        description 'Query the IPv6 VXLAN type ACL granularity statistical data.' ;
        list acl-v6-vxlan-statistics-by-acl {
          description 'Query the IPv6 VXLAN type ACL granularity statistical data.' ;
          key 'acl-name if-direction acl-ruleid' ;
          leaf acl-name {
            description 'Specify the ACL name.' ;
            type acl-name-type ;

          }

          leaf if-direction {
            description 'Specify the direction.' ;
            type acl-if-direction ;

          }

          leaf acl-ruleid {
            description 'Specify the rule ID.' ;
            type uint32 {
              range 1..2147483644 {
                description 'ID of this rule.' ;
              }

            }

          }

          leaf stats-bytes {
            description 'The number of bytes in the packets that match the rule.' ;
            type uint64 ;

            units byte ;
          }

          leaf stats-packets {
            description 'The number of packets that match the rule.' ;
            type uint64 ;

          }

          leaf stats-rate {
            description 'The instantaneous rate of packets that match the rule.' ;
            type uint64 ;

            units bps ;
          }

          ncd:select "acl-name if-direction" ;
          ncd:select "acl-name if-direction acl-ruleid" ;
        }

        ncd:revise-date 2022-01-20 ;
      }

    }

    ncd:revise-date 2015-06-08 ;
  }

}
