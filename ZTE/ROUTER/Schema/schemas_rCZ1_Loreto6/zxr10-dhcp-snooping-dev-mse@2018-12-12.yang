module zxr10-dhcp-snooping-dev-mse {
  namespace 'http://www.zte.com.cn/zxr10/netconf/schema/rosng/dhcp-snooping-dev'
          + '-mse'
            ;
  prefix dhcp-snooping-dev-mse ;
  import zxr10-dhcp-snooping {
    prefix dhcps ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  revision 2018-12-12 {
    description Create. ;
  }
  deviation '/dhcps:configuration/dhcps:dhcp-snooping/dhcps:global/dhcps:inform'
          + 'ation/dhcps:format'
            {
    description 'The format of option82.'
                ;
    deviate replace {
      default china-tel ;
      type enumeration {
        enum china-tel {
          value 1 ;
          description 'China telecom' ;
        }
        enum dsl-forum {
          value 2 ;
          description 'DSL forum'
                      ;
        }
        enum telenor {
          value 3 ;
          description Telenor ;
        }
      }
    }
  }
}
