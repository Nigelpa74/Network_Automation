module zxr10-ipv6-pim-dev-upn {
  namespace 'http://www.zte.com.cn/zxr10/netconf/schema/rosng/ipv6-pim-dev-upn' ;
  prefix ipv6-pim-dev-upn ;
  import zxr10-ipv6-pim {
    prefix pim6 ;
  }
  organization 'ZTE Corporation' ;
  contact "ZTE Corporation  
\n"
        + "   Nanjing Institute of ZTE Corporation 
\n"
        + "   No.68 Zijinghua Rd. Yuhuatai District, Nanjing, China 
\n"
        + '   Tel: +86-25-52870000'
          ;
  revision 2015-04-02 {
    description 'Delete the revision date of the import.' ;
  }
  revision 2014-02-25 {
    description 'Initial version' ;
  }
  deviation "/pim6:configuration/pim6:ipv6-router-pim/pim6:vrf-pim6s/pim6:vrf-p"
          + "im6/pim6:bidir-pim"
            {
    description 'The bidir-pim is only for version of swith' ;
    deviate not-supported ;
  }
  deviation "/pim6:configuration/pim6:ipv6-router-pim/pim6:vrf-pim6s/pim6:vrf-p"
          + "im6/pim6:crps/pim6:crp/pim6:bidir-pim"
            {
    description 'The option of bidir-pim is only for version of swith' ;
    deviate not-supported ;
  }
  deviation "/pim6:configuration/pim6:ipv6-router-pim/pim6:vrf-pim6s/pim6:vrf-p"
          + "im6/pim6:srps/pim6:srp/pim6:bidir-pim"
            {
    description 'The option of bidir-pim is only for version of swith' ;
    deviate not-supported ;
  }
  deviation "/pim6:configuration/pim6:ipv6-router-pim/pim6:pim6/pim6:global/pim"
          + "6:bidir-pim"
            {
    description 'The bidir-pim is only for version of swith' ;
    deviate not-supported ;
  }
  deviation "/pim6:configuration/pim6:ipv6-router-pim/pim6:pim6/pim6:crps/pim6:"
          + "crp/pim6:bidir-pim"
            {
    description 'The option of bidir-pim is only for version of swith' ;
    deviate not-supported ;
  }
  deviation "/pim6:configuration/pim6:ipv6-router-pim/pim6:pim6/pim6:srps/pim6:"
          + "srp/pim6:bidir-pim"
            {
    description 'The option of bidir-pim is only for version of swith' ;
    deviate not-supported ;
  }
}
