module zxr10-mr-dev-upn {
  namespace "http://www.zte.com.cn/zxr10/netconf/schema/rosng/multicast-router" ;
  prefix router-multicast ;
  import zxr10-multicast {
    prefix mr ;
  }

  organization "ZTE Corporation" ;
  contact "ZTE Corporation  
     Nanjing Institute of ZTE Corporation 
     No.68 Zijinghua Rd. Yuhuatai District, Nanjing, China 
     Tel: +86-25-52870000" ;
  description 'The netconf module of describing multicast router.' ;
  revision 2023-06-08 {
    description 'Because the project label is released, the command restrictions are released.' ;
  }

  revision 2015-04-02 {
    description 'Delete the revision date of the import.' ;
  }

  revision 2014-02-13 {
    description 'Initial version' ;
  }

}
